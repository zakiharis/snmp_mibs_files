--------------------------------------------------------------------------------
--
-- System Manager SNMP MIB (SmSnmp.MIB)
--
-- All Rights Reserved, Copyright (C) 1998,2000, Hitachi.Ltd.
--
-- Version 03-00-00-00  DATE 2000.03.21
--
--------------------------------------------------------------------------------

SystemManager-MIB DEFINITIONS ::= BEGIN

  IMPORTS
    enterprises, Counter, Gauge
      FROM RFC1155-SMI
    OBJECT-TYPE
      FROM RFC-1212
    DisplayString
      FROM RFC-1213;

--------------------------------------------------------------------------------

  hitachi         OBJECT IDENTIFIER  ::= { enterprises   116 }

--------------------------------------------------------------------------------

  systemExMib         OBJECT IDENTIFIER  ::= { hitachi             5 }
  systemManagerMibs   OBJECT IDENTIFIER  ::= { systemExMib        21 }
  information         OBJECT IDENTIFIER  ::= { systemManagerMibs   1 }

--------------------------------------------------------------------------------
-- System Manager
-- information
--------------------------------------------------------------------------------

  hitachiSM-SAGroupsDefinition OBJECT IDENTIFIER  ::= { information     1 }

--------------------------------------------------------------------------------
  componentid OBJECT-TYPE
    SYNTAX  Componentid
    ACCESS  not-accessible
    STATUS  mandatory
DESCRIPTION ""
  ::= { hitachiSM-SAGroupsDefinition 1 }

  Componentid ::= SEQUENCE
  {
    manufacturer  DisplayString,
    product       DisplayString,
    version       DisplayString,
    serialNumber  DisplayString,
    installation  DisplayString,
    verify        INTEGER
  }

  manufacturer OBJECT-TYPE
    SYNTAX  DisplayString (SIZE (1..64))
    ACCESS  read-only
    STATUS  mandatory
    DESCRIPTION
      "Manufacturer of this system. It is expressed in the form of string
       (ASCII Code)."
  ::= { componentid 1 }

  product OBJECT-TYPE
    SYNTAX  DisplayString (SIZE (1..64))
    ACCESS  read-only
    STATUS  mandatory
    DESCRIPTION
      "Product name for this system. It is expressed in the form of string
       (ASCII Code)."
  ::= { componentid 2 }

  version OBJECT-TYPE
    SYNTAX  DisplayString (SIZE (1..64))
    ACCESS  read-only
    STATUS  mandatory
    DESCRIPTION
      "Version number of this system. It is expressed in the form of string
       (ASCII Code)."
  ::= { componentid 3 }

  serialNumber OBJECT-TYPE
    SYNTAX  DisplayString (SIZE (1..64))
    ACCESS  read-only
    STATUS  mandatory
    DESCRIPTION
      "Serial number for this system. It is expressed in the form of string
       (ASCII Code)."
  ::= { componentid 4 }

  installation OBJECT-TYPE
    SYNTAX  DisplayString (SIZE (1..25))
    ACCESS  read-only
    STATUS  mandatory
    DESCRIPTION
      "The time and date when this component was installed. It is expressed in
       the form of string(ASCII Code)."
  ::= { componentid 5 }

  verify OBJECT-TYPE
    SYNTAX  INTEGER
    ACCESS  read-only
    STATUS  mandatory
    DESCRIPTION
      "A code that provides a level of verification that the component is still
       installed and working. It is indicated by a integer value as follows 
       (hexadecimal).
         0x00 = An error occurred; check status code.
         0x01 = This component does not exist.
         0x02 = Verification is not supported.
         0x03 = Reserved.
         0x04 = This component exists, but the functionality is untested.
         0x05 = This component exists, but the functionality is unknown.
         0x06 = This component exists, and is not functioning correctly.
         0x07 = This component exists, and is functioning correctly."
  ::= { componentid 6 }


--------------------------------------------------------------------------------
  operatingSystem OBJECT IDENTIFIER ::= { hitachiSM-SAGroupsDefinition 3 }

  operatingSystemTable OBJECT-TYPE
    SYNTAX  SEQUENCE OF OperatingSystem
    ACCESS  not-accessible
    STATUS  mandatory
DESCRIPTION ""
  ::= { operatingSystem 1 }

  operatingSystemEntry OBJECT-TYPE
    SYNTAX  OperatingSystem
    ACCESS  not-accessible
    STATUS  mandatory
DESCRIPTION ""
    INDEX   { operatingSystemIndex }
  ::= { operatingSystemTable 1 }

  OperatingSystem ::= SEQUENCE
  {
    operatingSystemIndex                  INTEGER,
    operatingSystemName                   DisplayString,
    operatingSystemVersion                DisplayString,
    primaryOperatingSystem                INTEGER,
    operatingSystemBootDeviceStorageType  INTEGER,
    operatingSystemBootDeviceIndex        INTEGER,
    operatingSystemBootPartitionIndex     INTEGER,
    operatingSystemDescription            DisplayString
  }

  operatingSystemIndex OBJECT-TYPE
    SYNTAX  INTEGER
    ACCESS  read-only
    STATUS  mandatory
    DESCRIPTION
      "The index into the operating system table."
  ::= { operatingSystemEntry 1 }

  operatingSystemName OBJECT-TYPE
    SYNTAX  DisplayString (SIZE (1..64))
    ACCESS  read-only
    STATUS  mandatory
    DESCRIPTION
      "The name of this operating system. It is expressed in the form of string
       (ASCII Code)."
  ::= { operatingSystemEntry 2 }

  operatingSystemVersion OBJECT-TYPE
    SYNTAX  DisplayString (SIZE (1..64))
    ACCESS  read-only
    STATUS  mandatory
    DESCRIPTION
      "The version number of this operating system. It is expressed in the form
       of string(ASCII Code)."
  ::= { operatingSystemEntry 3 }

  primaryOperatingSystem OBJECT-TYPE
    SYNTAX  INTEGER
    ACCESS  read-only
    STATUS  mandatory
    DESCRIPTION
      "If true, this is the primary operating system. It is indicated by a
       integer value as follows (hexadecimal).
         0x00 = False
         0x01 = True"
  ::= { operatingSystemEntry 4 }

  operatingSystemBootDeviceStorageType OBJECT-TYPE
    SYNTAX  INTEGER
    ACCESS  read-only
    STATUS  mandatory
    DESCRIPTION
      "An index into the Disks Table to indicate the device from which this
       operating system was booted. To fully access the Disks Table, this index
       must be combined with the attribute Boot Device Index. It is indicated by
       a integer value as follows (hexadecimal).
         0x01 = Other
         0x02 = Unknown
         0x03 = Hard Disk
         0x04 = Floppy Disk
         0x05 = Optical ROM
         0x06 = Optical WORM
         0x07 = Optical RW
         0x08 = Compact Disk
         0x09 = Flash Disk
         0x0A = Bernoulli
         0x0B = Optical Floppy Disk"
  ::= { operatingSystemEntry 5 }

  operatingSystemBootDeviceIndex OBJECT-TYPE
    SYNTAX  INTEGER
    ACCESS  read-only
    STATUS  mandatory
    DESCRIPTION
      "An index into the Disks Table."
  ::= { operatingSystemEntry 6 }

  operatingSystemBootPartitionIndex OBJECT-TYPE
    SYNTAX  INTEGER
    ACCESS  read-only
    STATUS  mandatory
    DESCRIPTION
      "An index into the Partition table indicating the partition from which
       this operating system booted."
  ::= { operatingSystemEntry 7 }

  operatingSystemDescription OBJECT-TYPE
    SYNTAX  DisplayString (SIZE (1..128))
    ACCESS  read-only
    STATUS  mandatory
    DESCRIPTION
      "A description of this operating system. It is expressed in the form of
       string(ASCII Code)."
  ::= { operatingSystemEntry 8 }


--------------------------------------------------------------------------------
  systemBios OBJECT IDENTIFIER ::= { hitachiSM-SAGroupsDefinition 4 }

  systemBiosTable OBJECT-TYPE
    SYNTAX  SEQUENCE OF SystemBios
    ACCESS  not-accessible
    STATUS  mandatory
DESCRIPTION ""
  ::= { systemBios 1 }

  systemBiosEntry OBJECT-TYPE
    SYNTAX  SystemBios
    ACCESS  not-accessible
    STATUS  mandatory
DESCRIPTION ""
    INDEX   { biosIndex }
  ::= { systemBiosTable 1 }

  SystemBios ::= SEQUENCE
  {
    biosIndex             INTEGER,
    biosManufacturer      DisplayString,
    biosVersion           DisplayString,
    biosRomSize           INTEGER,
    biosStartingAddress   OCTET STRING,
    biosEndingAddress     OCTET STRING,
    biosLoaderVersion     DisplayString,
    biosReleaseDate       DisplayString,
    primaryBios           INTEGER
  }

  biosIndex OBJECT-TYPE
    SYNTAX  INTEGER
    ACCESS  read-only
    STATUS  mandatory
    DESCRIPTION
      "The index into the system BIOS table."
  ::= { systemBiosEntry 1 }

  biosManufacturer OBJECT-TYPE
    SYNTAX  DisplayString (SIZE (1..64))
    ACCESS  read-only
    STATUS  mandatory
    DESCRIPTION
      "The name of the company that wrote this System BIOS. It is expressed in
       the form of string(ASCII Code)."
  ::= { systemBiosEntry 2 }

  biosVersion OBJECT-TYPE
    SYNTAX  DisplayString (SIZE (1..64))
    ACCESS  read-only
    STATUS  mandatory
    DESCRIPTION
      "The version number or version string of this BIOS. It is expressed in the
       form of string(ASCII Code)."
  ::= { systemBiosEntry 3 }

  biosRomSize OBJECT-TYPE
    SYNTAX  INTEGER
    ACCESS  read-only
    STATUS  mandatory
    DESCRIPTION
      "The physical size of this BIOS ROM device in kilobytes."
  ::= { systemBiosEntry 4 }

  biosStartingAddress OBJECT-TYPE
    SYNTAX  OCTET STRING (SIZE(1..8))
    ACCESS  read-only
    STATUS  mandatory
    DESCRIPTION
      "The starting physical address for the memory which the BIOS occupies. It
       is indicated by a 8bytes value laid out as big endian (byte 0 is the most
       significant, byte 7 is the least significant)."
  ::= { systemBiosEntry 5 }

  biosEndingAddress OBJECT-TYPE
    SYNTAX  OCTET STRING (SIZE(1..8))
    ACCESS  read-only
    STATUS  mandatory
    DESCRIPTION
      "The ending physical address for the memory which the BIOS occupies. It is
       indicated by a 8bytes value laid out as big endian (byte 0 is the most
       significant, byte 7 is the least significant)."
  ::= { systemBiosEntry 6 }

  biosLoaderVersion OBJECT-TYPE
    SYNTAX  DisplayString (SIZE (1..64))
    ACCESS  read-only
    STATUS  mandatory
    DESCRIPTION
      "The BIOS flash loader version number or string. It is expressed in the
       form of string(ASCII Code)."
  ::= { systemBiosEntry 7 }

  biosReleaseDate OBJECT-TYPE
    SYNTAX  DisplayString (SIZE (1..25))
    ACCESS  read-only
    STATUS  mandatory
    DESCRIPTION
      "The BIOS release date. It is expressed in the form of string
       (ASCII Code)."
  ::= { systemBiosEntry 8 }

  primaryBios OBJECT-TYPE
    SYNTAX  INTEGER
    ACCESS  read-only
    STATUS  mandatory
    DESCRIPTION
      "If true, this is the primary System BIOS. It is indicated by a integer
       value as follows (hexadecimal).
         0x00 = False
         0x01 = True"
  ::= { systemBiosEntry 9 }


--------------------------------------------------------------------------------
  processor OBJECT IDENTIFIER ::= { hitachiSM-SAGroupsDefinition 6 }

  processorTable OBJECT-TYPE
    SYNTAX  SEQUENCE OF Processor
    ACCESS  not-accessible
    STATUS  mandatory
DESCRIPTION ""
  ::= { processor 1 }

  processorEntry OBJECT-TYPE
    SYNTAX  Processor
    ACCESS  not-accessible
    STATUS  mandatory
DESCRIPTION ""
    INDEX   { processorIndex }
  ::= { processorTable 1 }

  Processor ::= SEQUENCE
  {
    processorIndex                INTEGER,
    processorType                 INTEGER,
    processorFamily               INTEGER,
    processorVersionInformation   DisplayString,
    maximumSpeed                  INTEGER,
    currentSpeed                  INTEGER,
    processorUpgrade              INTEGER,
    fruGroupIndex                 INTEGER,
    operationalGroupIndex         INTEGER,
    level1CacheIndex              INTEGER,
    level2CacheIndex              INTEGER,
    level3CacheIndex              INTEGER
  }

  processorIndex OBJECT-TYPE
    SYNTAX  INTEGER
    ACCESS  read-only
    STATUS  mandatory
    DESCRIPTION
      "An index into the processor table."
  ::= { processorEntry 1 }

  processorType OBJECT-TYPE
    SYNTAX  INTEGER
    ACCESS  read-only
    STATUS  mandatory
    DESCRIPTION
      "The type of processor currently in the system. It is indicated by a
       integer value as follows (hexadecimal).
         0x01 = Other
         0x02 = Unknown
         0x03 = Central Processor
         0x04 = Math Processor
         0x05 = DSP Processor
         0x06 = Video Processor"
  ::= { processorEntry 2 }

  processorFamily OBJECT-TYPE
    SYNTAX  INTEGER
    ACCESS  read-only
    STATUS  mandatory
    DESCRIPTION
      "The family of processors to which this processor belongs. It is indicated
       by a integer value as follows (hexadecimal).
         0x01 = Other
         0x02 = Unknown
         0x03 = 8086
         0x04 = 80286
         0x05 = 80386
         0x06 = 80486
         0x07 = 8087
         0x08 = 80287
         0x09 = 80387
         0x0A = 80487
         0x0B = Pentium Family
         0x0C = Pentium Pro
         0x12 = M1 Family
         0x19 = K5 Family
         0x20 = Power PC Family
         0x21 = Power PC 601
         0x22 = Power PC 603
         0x23 = Power PC 603+
         0x24 = Power PC 604
         0x30 = Alpha Family
         0x40 = MIPS Family
         0x50 = SPARC Family
         0x60 = 68040
         0x61 = 68xxx Family
         0x62 = 68000
         0x63 = 68010
         0x64 = 68020
         0x65 = 68030
         0x70 = Hobbit Family
         0x80 = Weitek
         0x90 = PA-RISC Family
         0xA0 = V30 Family"
  ::= { processorEntry 3 }

  processorVersionInformation OBJECT-TYPE
    SYNTAX  DisplayString (SIZE (1..80))
    ACCESS  read-only
    STATUS  mandatory
    DESCRIPTION
      "The version number or string for this processor. It is expressed in the
       form of string(ASCII Code)."
  ::= { processorEntry 4 }

  maximumSpeed OBJECT-TYPE
    SYNTAX  INTEGER
    ACCESS  read-only
    STATUS  mandatory
    DESCRIPTION
      "The maximum speed (in MHz) of this processor."
  ::= { processorEntry 5 }

  currentSpeed OBJECT-TYPE
    SYNTAX  INTEGER
    ACCESS  read-only
    STATUS  mandatory
    DESCRIPTION
      "The current speed (in MHz) of this processor."
  ::= { processorEntry 6 }

  processorUpgrade OBJECT-TYPE
    SYNTAX  INTEGER
    ACCESS  read-only
    STATUS  mandatory
    DESCRIPTION
      "The method by which this processor can be upgraded, if upgrades are
       supported. It is indicated by a integer value as follows (hexadecimal).
         0x01 = Other
         0x02 = Unknown
         0x03 = Daughter Board
         0x04 = ZIF Socket
         0x05 = Replacement/Piggy Back
         0x06 = None
         0x07 = LIF Socket"
  ::= { processorEntry 7 }

  fruGroupIndex OBJECT-TYPE
    SYNTAX  INTEGER
    ACCESS  read-only
    STATUS  mandatory
    DESCRIPTION
      "If this is a Field Replaceable Unit or if it is part of another FRU, this
       provides an index into the FRU table; 'value = -1' indicates that the
       group is not a FRU."
  ::= { processorEntry 8 }

  operationalGroupIndex OBJECT-TYPE
    SYNTAX  INTEGER
    ACCESS  read-only
    STATUS  mandatory
    DESCRIPTION
      "The index into the Operational State Table for this device if
       applicable."
  ::= { processorEntry 9 }

  level1CacheIndex OBJECT-TYPE
    SYNTAX  INTEGER
    ACCESS  read-only
    STATUS  mandatory
    DESCRIPTION
      "An index into the System Cache table that identifies the entry that
       describes the L1 cache for this processor. If more than one processor
       points to the same cache entry this means they share that cache."
  ::= { processorEntry 10 }

  level2CacheIndex OBJECT-TYPE
    SYNTAX  INTEGER
    ACCESS  read-only
    STATUS  mandatory
    DESCRIPTION
      "An index into the System Cache table that identifies the entry that
       describes the L2 cache for this processor If more than one processor
       points to the same cache entry this means they share that cache."
  ::= { processorEntry 11 }

  level3CacheIndex OBJECT-TYPE
    SYNTAX  INTEGER
    ACCESS  read-only
    STATUS  mandatory
    DESCRIPTION
      "An index into the System Cache table that identifies the entry that
       describes the L3 cache for this processor. If more than one processor
       points to the same cache entry this means they share that cache."
  ::= { processorEntry 12 }


--------------------------------------------------------------------------------
  motherboard OBJECT-TYPE
    SYNTAX  Motherboard
    ACCESS  not-accessible
    STATUS  mandatory
DESCRIPTION ""
  ::= { hitachiSM-SAGroupsDefinition 7 }

  Motherboard ::= SEQUENCE
  {
    numberOfExpansionSlots  INTEGER,
    fruGroupIndex           INTEGER,
    operationalGroupIndex   INTEGER
  }

  numberOfExpansionSlots OBJECT-TYPE
    SYNTAX  INTEGER
    ACCESS  read-only
    STATUS  mandatory
    DESCRIPTION
      "The total number of expansion slots which physically exist on the
       motherboard whether occupied or not (see System Slots group)."
  ::= { motherboard 1 }

  fruGroupIndex OBJECT-TYPE
    SYNTAX  INTEGER
    ACCESS  read-only
    STATUS  mandatory
    DESCRIPTION
      "If this is a Field Replaceable Unit or if it is part of another FRU, this
       provides an index into the FRU table; 'value = -1' indicates that the
       group is not a FRU."
  ::= { motherboard 2 }

  operationalGroupIndex OBJECT-TYPE
    SYNTAX  INTEGER
    ACCESS  read-only
    STATUS  mandatory
    DESCRIPTION
      "The index into the Operational State Table for this device if
       applicable."
  ::= { motherboard 3 }


--------------------------------------------------------------------------------
  systemCache OBJECT IDENTIFIER ::= { hitachiSM-SAGroupsDefinition 10 }

  systemCacheTable OBJECT-TYPE
    SYNTAX  SEQUENCE OF SystemCache
    ACCESS  not-accessible
    STATUS  mandatory
DESCRIPTION ""
  ::= { systemCache 1 }

  systemCacheEntry OBJECT-TYPE
    SYNTAX  SystemCache
    ACCESS  not-accessible
    STATUS  mandatory
DESCRIPTION ""
    INDEX   { systemCacheIndex }
  ::= { systemCacheTable 1 }

  SystemCache ::= SEQUENCE
  {
    systemCacheIndex            INTEGER,
    systemCacheLevel            INTEGER,
    systemCacheSpeed            INTEGER,
    systemCacheSize             INTEGER,
    systemCacheWritePolicy      INTEGER,
    systemCacheErrorCorrection  INTEGER,
    fruGroupIndex               INTEGER,
    operationalGroupIndex       INTEGER,
    systemCacheType             INTEGER
  }

  systemCacheIndex OBJECT-TYPE
    SYNTAX  INTEGER
    ACCESS  read-only
    STATUS  mandatory
    DESCRIPTION
      "An index into the System Cache table."
  ::= { systemCacheEntry 1 }

  systemCacheLevel OBJECT-TYPE
    SYNTAX  INTEGER
    ACCESS  read-only
    STATUS  mandatory
    DESCRIPTION
      "Is this the primary System Cache, or a subsidiary cache? It is indicated
       by a integer value as follows (hexadecimal).
         0x01 = Other
         0x02 = Unknown
         0x03 = Primary
         0x04 = Secondary
         0x05 = Tertiary"
  ::= { systemCacheEntry 2 }

  systemCacheSpeed OBJECT-TYPE
    SYNTAX  INTEGER
    ACCESS  read-only
    STATUS  mandatory
    DESCRIPTION
      "The speed of this System Cache module in nanoseconds."
  ::= { systemCacheEntry 3 }

  systemCacheSize OBJECT-TYPE
    SYNTAX  INTEGER
    ACCESS  read-only
    STATUS  mandatory
    DESCRIPTION
      "The size of this System Cache module in kilobytes."
  ::= { systemCacheEntry 4 }

  systemCacheWritePolicy OBJECT-TYPE
    SYNTAX  INTEGER
    ACCESS  read-only
    STATUS  mandatory
    DESCRIPTION
      "Is this a write-back or a write-through cache? It is indicated by a
       integer value as follows (hexadecimal).
         0x01 = Other
         0x02 = Unknown
         0x03 = Write Back
         0x04 = Write Through"
  ::= { systemCacheEntry 5 }

  systemCacheErrorCorrection OBJECT-TYPE
    SYNTAX  INTEGER
    ACCESS  read-only
    STATUS  mandatory
    DESCRIPTION
      "The error correction scheme supported by this cache component. It is
       indicated by a integer value as follows (hexadecimal).
         0x01 = Other
         0x02 = Unknown
         0x03 = None
         0x04 = Parity
         0x05 = Single Bit ECC
         0x06 = MultiBit ECC"
  ::= { systemCacheEntry 6 }

  fruGroupIndex OBJECT-TYPE
    SYNTAX  INTEGER
    ACCESS  read-only
    STATUS  mandatory
    DESCRIPTION
      "If this is a Field Replaceable Unit or if it is part of another FRU, this
       provides an index into the FRU table; 'value = -1' indicates that the
       group is not a FRU."
  ::= { systemCacheEntry 7 }

  operationalGroupIndex OBJECT-TYPE
    SYNTAX  INTEGER
    ACCESS  read-only
    STATUS  mandatory
    DESCRIPTION
      "The index into the Operational State Table for this device."
  ::= { systemCacheEntry 8 }

  systemCacheType OBJECT-TYPE
    SYNTAX  INTEGER
    ACCESS  read-only
    STATUS  mandatory
    DESCRIPTION
      "This defines the system cache type. It is indicated by a integer value as
       follows (hexadecimal).
         0x01 = Other
         0x02 = Unknown
         0x03 = Instruction
         0x04 = Data
         0x05 = Unified"
  ::= { systemCacheEntry 9 }


--------------------------------------------------------------------------------
  powerSupply OBJECT IDENTIFIER ::= { hitachiSM-SAGroupsDefinition 17 }

  powerSupplyTable OBJECT-TYPE
    SYNTAX  SEQUENCE OF PowerSupply
    ACCESS  not-accessible
    STATUS  mandatory
DESCRIPTION ""
  ::= { powerSupply 1 }

  powerSupplyEntry OBJECT-TYPE
    SYNTAX  PowerSupply
    ACCESS  not-accessible
    STATUS  mandatory
DESCRIPTION ""
    INDEX   { powerSupplyIndex }
  ::= { powerSupplyTable 1 }

  PowerSupply ::= SEQUENCE
  {
    powerSupplyIndex                    INTEGER,
    fruGroupIndex                       INTEGER,
    operationalGroupIndex               INTEGER,
    powerUnitIndex                      INTEGER,
    powerSupplyType                     INTEGER,
    inputVoltageCapabilityDescription   DisplayString,
    range1InputVoltageLow               INTEGER,
    range1InputVoltageHigh              INTEGER,
    range1VoltageProbeIndex             INTEGER,
    range1ElectricalCurrentProbeIndex   INTEGER,
    range2InputVoltageLow               INTEGER,
    range2InputVoltageHigh              INTEGER,
    range2VoltageProbeIndex             INTEGER,
    range2CurrentProbeIndex             INTEGER,
    activeInputVoltageRange             INTEGER,
    inputVoltageRangeSwitching          INTEGER,
    range1InputFrequencyLow             INTEGER,
    range1InputFrequencyHigh            INTEGER,
    range2InputFrequencyLow             INTEGER,
    range2InputFrequencyHigh            INTEGER,
    totalOutputPower                    INTEGER
  }

  powerSupplyIndex OBJECT-TYPE
    SYNTAX  INTEGER
    ACCESS  read-only
    STATUS  mandatory
    DESCRIPTION
      "The index number of the current power supply."
  ::= { powerSupplyEntry 1 }

  fruGroupIndex OBJECT-TYPE
    SYNTAX  INTEGER
    ACCESS  read-only
    STATUS  mandatory
    DESCRIPTION
      "If this is a Field Replaceable Unit or if it is part of another FRU, this
       provides an index into the FRU table; 'value = -1' indicates that the
       group is not a FRU."
  ::= { powerSupplyEntry 2 }

  operationalGroupIndex OBJECT-TYPE
    SYNTAX  INTEGER
    ACCESS  read-only
    STATUS  mandatory
    DESCRIPTION
      "The index into the Operational State table for this device."
  ::= { powerSupplyEntry 3 }

  powerUnitIndex OBJECT-TYPE
    SYNTAX  INTEGER
    ACCESS  read-only
    STATUS  mandatory
    DESCRIPTION
      "This is the ID of the Power Unit (logical power supply) to which this
       Power Supply belongs. This value matches up with the Power Unit Table
       Index attribute defined in the Power Unit Globe Table."
  ::= { powerSupplyEntry 4 }

  powerSupplyType OBJECT-TYPE
    SYNTAX  INTEGER
    ACCESS  read-only
    STATUS  mandatory
    DESCRIPTION
      "This attribute describes the type of Power Supply, e.g. Linear,
       Switching, Battery, etc. It is indicated by a integer value as follows 
       (hexadecimal).
         0x01 = Other
         0x02 = Unknown
         0x03 = Linear
         0x04 = Switching
         0x05 = Battery
         0x06 = UPS
         0x07 = Converter
         0x08 = Regulator"
  ::= { powerSupplyEntry 5 }

  inputVoltageCapabilityDescription OBJECT-TYPE
    SYNTAX  DisplayString (SIZE (1..80))
    ACCESS  read-only
    STATUS  mandatory
    DESCRIPTION
      "An expanded description of the Input Voltage Capability for this Power
       Supply. It is expressed in the form of string(ASCII Code)."
  ::= { powerSupplyEntry 6 }

  range1InputVoltageLow OBJECT-TYPE
    SYNTAX  INTEGER
    ACCESS  read-only
    STATUS  mandatory
    DESCRIPTION
      "The low voltage of Input Voltage Range 1 for this Power Supply, in
       millivolts. A value of 0x80000000 denotes 'unknown'."
  ::= { powerSupplyEntry 7 }

  range1InputVoltageHigh OBJECT-TYPE
    SYNTAX  INTEGER
    ACCESS  read-only
    STATUS  mandatory
    DESCRIPTION
      "The high voltage of Input Voltage Range 1 for this Power Supply, in
       millivolts. A value of 0x80000000 denotes 'unknown'."
  ::= { powerSupplyEntry 8 }

  range1VoltageProbeIndex OBJECT-TYPE
    SYNTAX  INTEGER
    ACCESS  read-only
    STATUS  mandatory
    DESCRIPTION
      "Index into the Voltage Probe table identifying the voltage probe
       monitoring this input range. 0 indicates no probe provided."
  ::= { powerSupplyEntry 9 }

  range1ElectricalCurrentProbeIndex OBJECT-TYPE
    SYNTAX  INTEGER
    ACCESS  read-only
    STATUS  mandatory
    DESCRIPTION
      "Index into the Elelctrical Current Probe table identifying the Electrical
       current probe monitoring this input range. 0 indicates no probe
       provided."
  ::= { powerSupplyEntry 10 }

  range2InputVoltageLow OBJECT-TYPE
    SYNTAX  INTEGER
    ACCESS  read-only
    STATUS  mandatory
    DESCRIPTION
      "The low voltage of Input Voltage Range 2 for this Power Supply, in
       millivolts. A value of 0x80000000 denotes 'unknown'."
  ::= { powerSupplyEntry 11 }

  range2InputVoltageHigh OBJECT-TYPE
    SYNTAX  INTEGER
    ACCESS  read-only
    STATUS  mandatory
    DESCRIPTION
      "The high voltage of Input Voltage Range 2 for this Power Supply, in
       millivolts. A value of 0x80000000 denotes 'unknown'."
  ::= { powerSupplyEntry 12 }

  range2VoltageProbeIndex OBJECT-TYPE
    SYNTAX  INTEGER
    ACCESS  read-only
    STATUS  mandatory
    DESCRIPTION
      "Index into the Voltage Probe table identifying the voltage probe
       monitoring this input range. 0 indicates no probe provided."
  ::= { powerSupplyEntry 13 }

  range2CurrentProbeIndex OBJECT-TYPE
    SYNTAX  INTEGER
    ACCESS  read-only
    STATUS  mandatory
    DESCRIPTION
      "Index into the Current Probe table identifying the current probe
       monitoring this input range. 0 indicates no probe provided."
  ::= { powerSupplyEntry 14 }

  activeInputVoltageRange OBJECT-TYPE
    SYNTAX  INTEGER
    ACCESS  read-only
    STATUS  mandatory
    DESCRIPTION
      "The value of this attribute indicates which input voltage range of this
       Power Supply is currently active. It is indicated by a integer value as
       follows (hexadecimal).
         0x01 = Other
         0x02 = Unknown
         0x03 = Range 1
         0x04 = Range 2
         0x05 = Both"
  ::= { powerSupplyEntry 15 }

  inputVoltageRangeSwitching OBJECT-TYPE
    SYNTAX  INTEGER
    ACCESS  read-only
    STATUS  mandatory
    DESCRIPTION
      "This attribute describes the kind of input voltage range switching that
       is implemented in this power supply. It is indicated by a integer value
       as follows (hexadecimal).
         0x01 = Other
         0x02 = Unknown
         0x03 = Manual
         0x04 = Autoswitch
         0x05 = Wide Range
         0x06 = Not Applicable"
  ::= { powerSupplyEntry 16 }

  range1InputFrequencyLow OBJECT-TYPE
    SYNTAX  INTEGER
    ACCESS  read-only
    STATUS  mandatory
    DESCRIPTION
      "The frequency at the low end of this power supply's Input Frequency Range
       1. A value of zero implies DC. A value of 0x80000000 denotes 'unknown'."
  ::= { powerSupplyEntry 17 }

  range1InputFrequencyHigh OBJECT-TYPE
    SYNTAX  INTEGER
    ACCESS  read-only
    STATUS  mandatory
    DESCRIPTION
      "The frequency at the high end of this power supply's Input Frequency
       Range 1. A value of zero implies DC. A value of 0x80000000 denotes
       'unknown'."
  ::= { powerSupplyEntry 18 }

  range2InputFrequencyLow OBJECT-TYPE
    SYNTAX  INTEGER
    ACCESS  read-only
    STATUS  mandatory
    DESCRIPTION
      "The frequency at the low end of this power supply's Input Frequency Range
       2. A value of zero implies DC. A value of 0x80000000 denotes 'unknown'."
  ::= { powerSupplyEntry 19 }

  range2InputFrequencyHigh OBJECT-TYPE
    SYNTAX  INTEGER
    ACCESS  read-only
    STATUS  mandatory
    DESCRIPTION
      "The frequency at the high end of this power supply's Input Frequency
       Range 2. A value of zero implies DC. A value of 0x80000000 denotes
       'unknown'."
  ::= { powerSupplyEntry 20 }

  totalOutputPower OBJECT-TYPE
    SYNTAX  INTEGER
    ACCESS  read-only
    STATUS  mandatory
    DESCRIPTION
      "This attribute value represents the total output power of this power
       supply in milliWatts. 0x80000000 denotes 'unknown'."
  ::= { powerSupplyEntry 21 }


--------------------------------------------------------------------------------
  coolingDevice OBJECT IDENTIFIER ::= { hitachiSM-SAGroupsDefinition 18 }

  coolingDeviceTable OBJECT-TYPE
    SYNTAX  SEQUENCE OF CoolingDevice
    ACCESS  not-accessible
    STATUS  mandatory
DESCRIPTION ""
  ::= { coolingDevice 1 }

  coolingDeviceEntry OBJECT-TYPE
    SYNTAX  CoolingDevice
    ACCESS  not-accessible
    STATUS  mandatory
DESCRIPTION ""
    INDEX   { coolingDeviceTableIndex }
  ::= { coolingDeviceTable 1 }

  CoolingDevice ::= SEQUENCE
  {
    coolingDeviceTableIndex   INTEGER,
    fruGroupIndex             INTEGER,
    operationalGroupIndex     INTEGER,
    coolingUnitIndex          INTEGER,
    coolingDeviceType         INTEGER,
    temperatureProbeIndex     INTEGER
  }

  coolingDeviceTableIndex OBJECT-TYPE
    SYNTAX  INTEGER
    ACCESS  read-only
    STATUS  mandatory
    DESCRIPTION
      "An index into the cooling device table."
  ::= { coolingDeviceEntry 1 }

  fruGroupIndex OBJECT-TYPE
    SYNTAX  INTEGER
    ACCESS  read-only
    STATUS  mandatory
    DESCRIPTION
      "If this is a Field Replaceable Unit or if it is part of another FRU, this
       provides an index into the FRU table; 'value = -1' indicates that the
       group is not a FRU."
  ::= { coolingDeviceEntry 2 }

  operationalGroupIndex OBJECT-TYPE
    SYNTAX  INTEGER
    ACCESS  read-only
    STATUS  mandatory
    DESCRIPTION
      "The index into the Operational State table for this device."
  ::= { coolingDeviceEntry 3 }

  coolingUnitIndex OBJECT-TYPE
    SYNTAX  INTEGER
    ACCESS  read-only
    STATUS  mandatory
    DESCRIPTION
      "This is the ID of the Cooling Unit (logical cooling device) of which this
       Cooling Device is a part. This value matches up with the Cooling Unit
       Table Index attribute defined in the Cooling Unit Globe Table."
  ::= { coolingDeviceEntry 4 }

  coolingDeviceType OBJECT-TYPE
    SYNTAX  INTEGER
    ACCESS  read-only
    STATUS  mandatory
    DESCRIPTION
      "The type of Cooling Device that this is e.g. Fan, Heat Pipe, etc. It is
       indicated by a integer value as follows (hexadecimal).
         0x01 = Other
         0x02 = Unknown
         0x03 = Fan
         0x04 = Centrifugal Blower
         0x05 = Chip Fan
         0x06 = Cabinet Fan
         0x07 = Power Supply Fan
         0x08 = Heat Pipe
         0x09 = Integrated Refrigeration
         0x20 = Active Cooling
         0x21 = Passive Cooling"
  ::= { coolingDeviceEntry 5 }

  temperatureProbeIndex OBJECT-TYPE
    SYNTAX  INTEGER
    ACCESS  read-only
    STATUS  mandatory
    DESCRIPTION
      "Index into the Temperature Probe table identifying the temperature probe
       monitoring this cooling device. 0 indicates no probe provided."
  ::= { coolingDeviceEntry 6 }


--------------------------------------------------------------------------------
  disks OBJECT IDENTIFIER ::= { hitachiSM-SAGroupsDefinition 23 }

  disksTable OBJECT-TYPE
    SYNTAX  SEQUENCE OF Disks
    ACCESS  not-accessible
    STATUS  mandatory
DESCRIPTION ""
  ::= { disks 1 }

  disksEntry OBJECT-TYPE
    SYNTAX  Disks
    ACCESS  not-accessible
    STATUS  mandatory
DESCRIPTION ""
    INDEX   { storageType,
              diskIndex    }
  ::= { disksTable 1 }

  Disks ::= SEQUENCE
  {
    storageType                               INTEGER,
    diskIndex                                 INTEGER,
    storageInterfaceType                      INTEGER,
    interfaceDescription                      DisplayString,
    mediaLoaded                               INTEGER,
    removableDrive                            INTEGER,
    removableMedia                            INTEGER,
    deviceId                                  INTEGER,
    logicalUnitNumber                         INTEGER,
    numberOfPhysicalCylinders                 INTEGER,
    numberOfPhysicalSectorsPerTrack           INTEGER,
    numberOfPhysicalHeads                     INTEGER,
    physicalCylinderForWritePrecompensation   INTEGER,
    physicalCylinderForLandingZone            INTEGER,
    sectorSize                                INTEGER,
    totalPhysicalSize                         INTEGER,
    numberOfCurrentBadBlocksOrSectors         INTEGER,
    partitions                                INTEGER,
    physicalLocation                          INTEGER,
    fruGroupIndex                             INTEGER,
    operationalGroupIndex                     INTEGER,
    securitySettings                          INTEGER
  }

  storageType OBJECT-TYPE
    SYNTAX  INTEGER
    ACCESS  read-only
    STATUS  mandatory
    DESCRIPTION
      "The type of this mass storage device. It is indicated by a integer value
       as follows (hexadecimal).
         0x01 = Other
         0x02 = Unknown
         0x03 = Hard Disk
         0x04 = Floppy Disk
         0x05 = Optical ROM
         0x06 = Optical WORM
         0x07 = Optical RW
         0x08 = Compact Disk
         0x09 = Flash Disk
         0x0A = Bernoulli
         0x0B = Optical Floppy Disk"
  ::= { disksEntry 1 }

  diskIndex OBJECT-TYPE
    SYNTAX  INTEGER
    ACCESS  read-only
    STATUS  mandatory
    DESCRIPTION
      "An index into the disk table."
  ::= { disksEntry 2 }

  storageInterfaceType OBJECT-TYPE
    SYNTAX  INTEGER
    ACCESS  read-only
    STATUS  mandatory
    DESCRIPTION
      "The interface used by this mass storage device. It is indicated by a
       integer value as follows (hexadecimal).
         0x01 = Other
         0x02 = Unknown
         0x03 = SCSI
         0x04 = ESDI
         0x05 = IDE
         0x06 = CMD
         0x07 = IPI
         0x08 = ST506
         0x09 = DSSI
         0x0A = Parallel Port
         0x0B = HIPPI
         0x0C = QIC2
         0x0D = Floppy Disk Interface
         0x0E = PCMCIA
         0x0F = Enhanced ATA/IDE"
  ::= { disksEntry 3 }

  interfaceDescription OBJECT-TYPE
    SYNTAX  DisplayString (SIZE (1..64))
    ACCESS  read-only
    STATUS  mandatory
    DESCRIPTION
      "A longer description of the mass storage interface. For example, SCSI2
       fast wide. It is expressed in the form of string(ASCII Code)."
  ::= { disksEntry 4 }

  mediaLoaded OBJECT-TYPE
    SYNTAX  INTEGER
    ACCESS  read-only
    STATUS  mandatory
    DESCRIPTION
      "If true, the media is loaded. It is indicated by a integer value as
       follows (hexadecimal).
         0x00 = False
         0x01 = True"
  ::= { disksEntry 5 }

  removableDrive OBJECT-TYPE
    SYNTAX  INTEGER
    ACCESS  read-only
    STATUS  mandatory
    DESCRIPTION
      "If true, this drive is removable. It is indicated by a integer value as
       follows (hexadecimal).
         0x00 = False
         0x01 = True"
  ::= { disksEntry 6 }

  removableMedia OBJECT-TYPE
    SYNTAX  INTEGER
    ACCESS  read-only
    STATUS  mandatory
    DESCRIPTION
      "If true, the media in this drive is removable. It is indicated by a
       integer value as follows (hexadecimal).
         0x00 = False
         0x01 = True"
  ::= { disksEntry 7 }

  deviceId OBJECT-TYPE
    SYNTAX  INTEGER
    ACCESS  read-only
    STATUS  mandatory
    DESCRIPTION
      "The SCSI address of this device."
  ::= { disksEntry 8 }

  logicalUnitNumber OBJECT-TYPE
    SYNTAX  INTEGER
    ACCESS  read-only
    STATUS  mandatory
    DESCRIPTION
      "The logical unit number of this SCSI device."
  ::= { disksEntry 9 }

  numberOfPhysicalCylinders OBJECT-TYPE
    SYNTAX  INTEGER
    ACCESS  read-only
    STATUS  mandatory
    DESCRIPTION
      "The number of reported physical cylinders on this device."
  ::= { disksEntry 10 }

  numberOfPhysicalSectorsPerTrack OBJECT-TYPE
    SYNTAX  INTEGER
    ACCESS  read-only
    STATUS  mandatory
    DESCRIPTION
      "The number of reported physical sectors per track for this device."
  ::= { disksEntry 11 }

  numberOfPhysicalHeads OBJECT-TYPE
    SYNTAX  INTEGER
    ACCESS  read-only
    STATUS  mandatory
    DESCRIPTION
      "The number of reported physical heads for this device."
  ::= { disksEntry 12 }

  physicalCylinderForWritePrecompensation OBJECT-TYPE
    SYNTAX  INTEGER
    ACCESS  read-only
    STATUS  mandatory
    DESCRIPTION
      "Specifies the physical cylinder used for write precompensation on this
       device."
  ::= { disksEntry 13 }

  physicalCylinderForLandingZone OBJECT-TYPE
    SYNTAX  INTEGER
    ACCESS  read-only
    STATUS  mandatory
    DESCRIPTION
      "The physical landing zone cylinder of this device."
  ::= { disksEntry 14 }

  sectorSize OBJECT-TYPE
    SYNTAX  INTEGER
    ACCESS  read-only
    STATUS  mandatory
    DESCRIPTION
      "The size in bytes of the physical disk sector or logical block as
       reported by the disk."
  ::= { disksEntry 15 }

  totalPhysicalSize OBJECT-TYPE
    SYNTAX  INTEGER
    ACCESS  read-only
    STATUS  mandatory
    DESCRIPTION
      "The total size in kilobytes (1024 bytes) of this device that is available
       to users."
  ::= { disksEntry 16 }

  numberOfCurrentBadBlocksOrSectors OBJECT-TYPE
    SYNTAX  INTEGER
    ACCESS  read-only
    STATUS  mandatory
    DESCRIPTION
      "The number of current bad blocks or sectors to include total of both
       factory assigned and grown defects."
  ::= { disksEntry 17 }

  partitions OBJECT-TYPE
    SYNTAX  INTEGER
    ACCESS  read-only
    STATUS  mandatory
    DESCRIPTION
      "The number of partitions on this storage unit."
  ::= { disksEntry 18 }

  physicalLocation OBJECT-TYPE
    SYNTAX  INTEGER
    ACCESS  read-only
    STATUS  mandatory
    DESCRIPTION
      "The physical location of this disk drive assembly relative to the system
       enclosure. It is indicated by a integer value as follows (hexadecimal).
         0x01 = Other
         0x02 = Unknown
         0x03 = Internal
         0x04 = External"
  ::= { disksEntry 19 }

  fruGroupIndex OBJECT-TYPE
    SYNTAX  INTEGER
    ACCESS  read-only
    STATUS  mandatory
    DESCRIPTION
      "If this is a Field Replaceable Unit or if it is part of another FRU, this
       provides an index into the FRU table; 'value = -1' indicates that the
       group is not a FRU."
  ::= { disksEntry 20 }

  operationalGroupIndex OBJECT-TYPE
    SYNTAX  INTEGER
    ACCESS  read-only
    STATUS  mandatory
    DESCRIPTION
      "The index into the Operational State table for this device."
  ::= { disksEntry 21 }

  securitySettings OBJECT-TYPE
    SYNTAX  INTEGER
    ACCESS  read-only
    STATUS  mandatory
    DESCRIPTION
      "Enum describing the current hardware security settings on this device. It
       is indicated by a integer value as follows (hexadecimal).
         0x01 = Other
         0x02 = Unknown
         0x03 = None
         0x04 = Read-Only
         0x05 = Lockout Enabled
         0x06 = Boot-Bypass
         0x07 = Boot-Bypass & Read-Only"
  ::= { disksEntry 22 }


--------------------------------------------------------------------------------
  diskController OBJECT IDENTIFIER ::= { hitachiSM-SAGroupsDefinition 26 }

  diskControllerTable OBJECT-TYPE
    SYNTAX  SEQUENCE OF DiskController
    ACCESS  not-accessible
    STATUS  mandatory
DESCRIPTION ""
  ::= { diskController 1 }

  diskControllerEntry OBJECT-TYPE
    SYNTAX  DiskController
    ACCESS  not-accessible
    STATUS  mandatory
DESCRIPTION ""
    INDEX   { diskControllerIndex }
  ::= { diskControllerTable 1 }

  DiskController ::= SEQUENCE
  {
    diskControllerIndex               INTEGER,
    fruGroupIndex                     INTEGER,
    operationalGroupIndex             INTEGER,
    systemSlotIndex                   INTEGER,
    diskControllerIdentification      DisplayString,
    controllerSoftwareRevisionLevel   DisplayString,
    controllerChannelCount            INTEGER,
    controllerMaximumDevices          INTEGER
  }

  diskControllerIndex OBJECT-TYPE
    SYNTAX  INTEGER
    ACCESS  read-only
    STATUS  mandatory
    DESCRIPTION
      "Index value used by the system to identify the disk controller."
  ::= { diskControllerEntry 1 }

  fruGroupIndex OBJECT-TYPE
    SYNTAX  INTEGER
    ACCESS  read-only
    STATUS  mandatory
    DESCRIPTION
      "If this is a Field Replaceable Unit or if it is part of another FRU, this
       provides an index into the FRU table; 'value = -1' indicates that the
       group is not a FRU."
  ::= { diskControllerEntry 2 }

  operationalGroupIndex OBJECT-TYPE
    SYNTAX  INTEGER
    ACCESS  read-only
    STATUS  mandatory
    DESCRIPTION
      "The index into the Operational State table for this device."
  ::= { diskControllerEntry 3 }

  systemSlotIndex OBJECT-TYPE
    SYNTAX  INTEGER
    ACCESS  read-only
    STATUS  mandatory
    DESCRIPTION
      "Index value in System Slot table of disk Controller. 0 = no slot."
  ::= { diskControllerEntry 4 }

  diskControllerIdentification OBJECT-TYPE
    SYNTAX  DisplayString (SIZE (1..80))
    ACCESS  read-only
    STATUS  mandatory
    DESCRIPTION
      "Name, brand and hardware revision level of the disk controller. It is
       expressed in the form of string(ASCII Code)."
  ::= { diskControllerEntry 5 }

  controllerSoftwareRevisionLevel OBJECT-TYPE
    SYNTAX  DisplayString (SIZE (1..16))
    ACCESS  read-only
    STATUS  mandatory
    DESCRIPTION
      "Level and version of the software associated with this controller. It is
       expressed in the form of string(ASCII Code)."
  ::= { diskControllerEntry 6 }

  controllerChannelCount OBJECT-TYPE
    SYNTAX  INTEGER
    ACCESS  read-only
    STATUS  mandatory
    DESCRIPTION
      "The number of channels supported by this controller. 0x80000000 =
       Unknown."
  ::= { diskControllerEntry 7 }

  controllerMaximumDevices OBJECT-TYPE
    SYNTAX  INTEGER
    ACCESS  read-only
    STATUS  mandatory
    DESCRIPTION
      "The maximum number of devices for all channels which can be controlled by
       this disk controller. 0x80000000 = Unknown."
  ::= { diskControllerEntry 8 }


--------------------------------------------------------------------------------
  logicalDrives OBJECT IDENTIFIER ::= { hitachiSM-SAGroupsDefinition 27 }

  logicalDrivesTable OBJECT-TYPE
    SYNTAX  SEQUENCE OF LogicalDrives
    ACCESS  not-accessible
    STATUS  mandatory
DESCRIPTION ""
  ::= { logicalDrives 1 }

  logicalDrivesEntry OBJECT-TYPE
    SYNTAX  LogicalDrives
    ACCESS  not-accessible
    STATUS  mandatory
DESCRIPTION ""
    INDEX   { logicalDriveIndex }
  ::= { logicalDrivesTable 1 }

  LogicalDrives ::= SEQUENCE
  {
    logicalDriveIndex     INTEGER,
    logicalDriveName      DisplayString,
    logicalDriveType      INTEGER,
    logicalDriveSize      INTEGER,
    freeLogicalDriveSize  INTEGER,
    logicalDrivePath      DisplayString
  }

  logicalDriveIndex OBJECT-TYPE
    SYNTAX  INTEGER
    ACCESS  read-only
    STATUS  mandatory
    DESCRIPTION
      "An index into the Logical Drive table."
  ::= { logicalDrivesEntry 1 }

  logicalDriveName OBJECT-TYPE
    SYNTAX  DisplayString (SIZE (1..64))
    ACCESS  read-only
    STATUS  mandatory
    DESCRIPTION
      "Name used by the system to identify this logical drive. For DOS, this
       could be the logical drive letter (A, B, C...). It is expressed in the
       form of string(ASCII Code)."
  ::= { logicalDrivesEntry 2 }

  logicalDriveType OBJECT-TYPE
    SYNTAX  INTEGER
    ACCESS  read-only
    STATUS  mandatory
    DESCRIPTION
      "This defines the logical drive type. It is indicated by a integer value
       as follows (hexadecimal).
         0x01 = Other
         0x02 = Unknown
         0x03 = Fixed Drive
         0x04 = Removable Drive
         0x05 = Remote Drive
         0x06 = CDROM
         0x07 = Floppy Drive
         0x08 = RAM Drive
         0x09 = Drive Array"
  ::= { logicalDrivesEntry 3 }

  logicalDriveSize OBJECT-TYPE
    SYNTAX  INTEGER
    ACCESS  read-only
    STATUS  mandatory
    DESCRIPTION
      "The size of this logical drive in kilobytes."
  ::= { logicalDrivesEntry 4 }

  freeLogicalDriveSize OBJECT-TYPE
    SYNTAX  INTEGER
    ACCESS  read-only
    STATUS  mandatory
    DESCRIPTION
      "The remaining space on this logical drive in kilobytes."
  ::= { logicalDrivesEntry 5 }

  logicalDrivePath OBJECT-TYPE
    SYNTAX  DisplayString (SIZE (1..512))
    ACCESS  read-only
    STATUS  mandatory
    DESCRIPTION
      "The path used to access this logical drive (for remote drives). It is
       expressed in the form of string(ASCII Code)."
  ::= { logicalDrivesEntry 6 }


--------------------------------------------------------------------------------
  keyboard OBJECT-TYPE
    SYNTAX  Keyboard
    ACCESS  not-accessible
    STATUS  mandatory
DESCRIPTION ""
  ::= { hitachiSM-SAGroupsDefinition 29 }

  Keyboard ::= SEQUENCE
  {
    keyboardLayout          DisplayString,
    keyboardType            DisplayString,
    keyboardConnectorType   INTEGER,
    fruGroupIndex           INTEGER,
    operationalGroupIndex   INTEGER,
    securitySettings        INTEGER
  }

  keyboardLayout OBJECT-TYPE
    SYNTAX  DisplayString (SIZE (1..80))
    ACCESS  read-only
    STATUS  mandatory
    DESCRIPTION
      "A description of the layout of this keyboard. It is expressed in the form
       of string(ASCII Code)."
  ::= { keyboard 1 }

  keyboardType OBJECT-TYPE
    SYNTAX  DisplayString (SIZE (1..80))
    ACCESS  read-only
    STATUS  mandatory
    DESCRIPTION
      "The type description of this keyboard. It is expressed in the form of
       string(ASCII Code)."
  ::= { keyboard 2 }

  keyboardConnectorType OBJECT-TYPE
    SYNTAX  INTEGER
    ACCESS  read-only
    STATUS  mandatory
    DESCRIPTION
      "The type of keyboard connector used by this keyboard. It is indicated by
       a integer value as follows (hexadecimal).
         0x01 = Other
         0x02 = Unknown
         0x03 = Mini-Din
         0x04 = Micro-Din
         0x05 = PS/2
         0x06 = Infrared
         0x07 = HP-HIL
         0x08 = DB-9
         0x09 = Access Bus
         0xA0 = PC-98"
  ::= { keyboard 3 }

  fruGroupIndex OBJECT-TYPE
    SYNTAX  INTEGER
    ACCESS  read-only
    STATUS  mandatory
    DESCRIPTION
      "If this is a Field Replaceable Unit or if it is part of another FRU, this
       provides an index into the FRU table; 'value = -1' indicates that the
       group is not a FRU."
  ::= { keyboard 4 }

  operationalGroupIndex OBJECT-TYPE
    SYNTAX  INTEGER
    ACCESS  read-only
    STATUS  mandatory
    DESCRIPTION
      "The index into the Operational State table for this device."
  ::= { keyboard 5 }

  securitySettings OBJECT-TYPE
    SYNTAX  INTEGER
    ACCESS  read-only
    STATUS  mandatory
    DESCRIPTION
      "Enum describing the current hardware security settings on this device. It
       is indicated by a integer value as follows (hexadecimal).
         0x01 = Other
         0x02 = Unknown
         0x03 = None
         0x04 = External Interface Locked Out
         0x05 = External Interface Enabled"
  ::= { keyboard 6 }


--------------------------------------------------------------------------------
  fieldReplaceableUnit OBJECT IDENTIFIER ::= { hitachiSM-SAGroupsDefinition 30 }

  fieldReplaceableUnitTable OBJECT-TYPE
    SYNTAX  SEQUENCE OF FieldReplaceableUnit
    ACCESS  not-accessible
    STATUS  mandatory
DESCRIPTION ""
  ::= { fieldReplaceableUnit 1 }

  fieldReplaceableUnitEntry OBJECT-TYPE
    SYNTAX  FieldReplaceableUnit
    ACCESS  not-accessible
    STATUS  mandatory
DESCRIPTION ""
    INDEX   { fruIndex }
  ::= { fieldReplaceableUnitTable 1 }

  FieldReplaceableUnit ::= SEQUENCE
  {
    fruIndex                            INTEGER,
    deviceGroupIndex                    INTEGER,
    description                         DisplayString,
    manufacturer                        DisplayString,
    model                               DisplayString,
    partNumber                          DisplayString,
    fruSerialNumber                     DisplayString,
    revisionLevel                       DisplayString,
    warrantyStartDate                   DisplayString,
    warrantyDuration                    INTEGER,
    supportPhoneNumber                  DisplayString,
    fruInternetUniformResourceLocator   DisplayString
  }

  fruIndex OBJECT-TYPE
    SYNTAX  INTEGER
    ACCESS  read-only
    STATUS  mandatory
    DESCRIPTION
      "The index into the Field Replaceable Unit table."
  ::= { fieldReplaceableUnitEntry 1 }

  deviceGroupIndex OBJECT-TYPE
    SYNTAX  INTEGER
    ACCESS  read-only
    STATUS  mandatory
    DESCRIPTION
      "The group ID of the group referencing this Field Replaceable Unit
       instance."
  ::= { fieldReplaceableUnitEntry 2 }

  description OBJECT-TYPE
    SYNTAX  DisplayString (SIZE (1..255))
    ACCESS  read-only
    STATUS  mandatory
    DESCRIPTION
      "A clear description of this Field Replaceable Unit. It is expressed in
       the form of string(ASCII Code)."
  ::= { fieldReplaceableUnitEntry 3 }

  manufacturer OBJECT-TYPE
    SYNTAX  DisplayString (SIZE (1..80))
    ACCESS  read-only
    STATUS  mandatory
    DESCRIPTION
      "The name of the company manufacturing or providing this Field Replaceable
       Unit. It is expressed in the form of string(ASCII Code)."
  ::= { fieldReplaceableUnitEntry 4 }

  model OBJECT-TYPE
    SYNTAX  DisplayString (SIZE (1..64))
    ACCESS  read-only
    STATUS  mandatory
    DESCRIPTION
      "The manufacturer's model number for this Field Replaceable Unit. It is
       expressed in the form of string(ASCII Code)."
  ::= { fieldReplaceableUnitEntry 5 }

  partNumber OBJECT-TYPE
    SYNTAX  DisplayString (SIZE (1..64))
    ACCESS  read-only
    STATUS  mandatory
    DESCRIPTION
      "A part number by which a replacement part can be ordered for this Field
       Replaceable Unit. It is expressed in the form of string(ASCII Code)."
  ::= { fieldReplaceableUnitEntry 6 }

  fruSerialNumber OBJECT-TYPE
    SYNTAX  DisplayString (SIZE (1..64))
    ACCESS  read-only
    STATUS  mandatory
    DESCRIPTION
      "The manufacturer's serial number for this Field Replaceable Unit. It is
       expressed in the form of string(ASCII Code)."
  ::= { fieldReplaceableUnitEntry 7 }

  revisionLevel OBJECT-TYPE
    SYNTAX  DisplayString (SIZE (1..64))
    ACCESS  read-only
    STATUS  mandatory
    DESCRIPTION
      "The revision level of this Field Replaceable Unit. It is expressed in the
       form of string(ASCII Code)."
  ::= { fieldReplaceableUnitEntry 8 }

  warrantyStartDate OBJECT-TYPE
    SYNTAX  DisplayString (SIZE (1..25))
    ACCESS  read-only
    STATUS  mandatory
    DESCRIPTION
      "The start date of the service warranty for this Field Replaceable Unit.
       It is expressed in the form of string(ASCII Code)."
  ::= { fieldReplaceableUnitEntry 9 }

  warrantyDuration OBJECT-TYPE
    SYNTAX  INTEGER
    ACCESS  read-only
    STATUS  mandatory
    DESCRIPTION
      "The total duration of this Field Replaceable Unit warranty in months."
  ::= { fieldReplaceableUnitEntry 10 }

  supportPhoneNumber OBJECT-TYPE
    SYNTAX  DisplayString (SIZE (1..64))
    ACCESS  read-only
    STATUS  mandatory
    DESCRIPTION
      "The phone number(s) for support for this Field Replaceable Unit. It is
       expressed in the form of string(ASCII Code)."
  ::= { fieldReplaceableUnitEntry 11 }

  fruInternetUniformResourceLocator OBJECT-TYPE
    SYNTAX  DisplayString (SIZE (1..256))
    ACCESS  read-only
    STATUS  mandatory
    DESCRIPTION
      "The Internet Uniform Resource Locator string that can be used through a
       World Wide Web browser to obtain further information about this FRU. It
       is expressed in the form of string(ASCII Code)."
  ::= { fieldReplaceableUnitEntry 12 }


--------------------------------------------------------------------------------
  operationalState OBJECT IDENTIFIER ::= { hitachiSM-SAGroupsDefinition 31 }

  operationalStateTable OBJECT-TYPE
    SYNTAX  SEQUENCE OF OperationalState
    ACCESS  not-accessible
    STATUS  mandatory
DESCRIPTION ""
  ::= { operationalState 1 }

  operationalStateEntry OBJECT-TYPE
    SYNTAX  OperationalState
    ACCESS  not-accessible
    STATUS  mandatory
DESCRIPTION ""
    INDEX   { operationalStateInstanceIndex }
  ::= { operationalStateTable 1 }

  OperationalState ::= SEQUENCE
  {
    operationalStateInstanceIndex   INTEGER,
    deviceGroupIndex                INTEGER,
    operationalStatus               INTEGER,
    usageState                      INTEGER,
    availabilityStatus              INTEGER,
    administrativeState             INTEGER,
    fatalErrorCount                 Counter,
    majorErrorCount                 Counter,
    warningErrorCount               Counter,
    currentErrorStatus              INTEGER
  }

  operationalStateInstanceIndex OBJECT-TYPE
    SYNTAX  INTEGER
    ACCESS  read-only
    STATUS  mandatory
    DESCRIPTION
      "The Index into the Operational State table."
  ::= { operationalStateEntry 1 }

  deviceGroupIndex OBJECT-TYPE
    SYNTAX  INTEGER
    ACCESS  read-only
    STATUS  mandatory
    DESCRIPTION
      "The group ID of the group referencing this instance."
  ::= { operationalStateEntry 2 }

  operationalStatus OBJECT-TYPE
    SYNTAX  INTEGER
    ACCESS  read-only
    STATUS  mandatory
    DESCRIPTION
      "The operational status of the Device Group instance. It is indicated by a
       integer value as follows (hexadecimal).
         0x01 = Other
         0x02 = Unknown
         0x03 = Enabled
         0x04 = Disabled
         0x05 = Not Applicable"
  ::= { operationalStateEntry 3 }

  usageState OBJECT-TYPE
    SYNTAX  INTEGER
    ACCESS  read-only
    STATUS  mandatory
    DESCRIPTION
      "The usage state of the Device Group instance. It is indicated by a
       integer value as follows (hexadecimal).
         0x01 = Other
         0x02 = Unknown
         0x03 = Idle
         0x04 = Active
         0x05 = Busy
         0x06 = Not Applicable"
  ::= { operationalStateEntry 4 }

  availabilityStatus OBJECT-TYPE
    SYNTAX  INTEGER
    ACCESS  read-only
    STATUS  mandatory
    DESCRIPTION
      "The availability status of the Device Group instance. It is indicated by
       a integer value as follows (hexadecimal).
         0x01 = Other
         0x02 = Unknown
         0x03 = Running
         0x04 = Warning
         0x05 = In Test
         0x06 = Not Applicable
         0x07 = Power Off
         0x08 = Off Line
         0x09 = Off Duty
         0x0A = Degraded
         0x0B = Not Installed
         0x0C = Install Error
         0x0D = Power Save"
  ::= { operationalStateEntry 5 }

  administrativeState OBJECT-TYPE
    SYNTAX  INTEGER
    ACCESS  read-only
    STATUS  mandatory
    DESCRIPTION
      "The administrative state of the Device Group instance. It is indicated by
       a integer value as follows (hexadecimal).
         0x01 = Other
         0x02 = Unknown
         0x03 = Locked
         0x04 = Unlocked
         0x05 = Not Applicable
         0x06 = Shutting Down"
  ::= { operationalStateEntry 6 }

  fatalErrorCount OBJECT-TYPE
    SYNTAX  Counter
    ACCESS  read-only
    STATUS  mandatory
    DESCRIPTION
      "The accumulated Fatal or Non-recoverable error count for this Device
       Group instance."
  ::= { operationalStateEntry 7 }

  majorErrorCount OBJECT-TYPE
    SYNTAX  Counter
    ACCESS  read-only
    STATUS  mandatory
    DESCRIPTION
      "The accumulated Major or Critical error count for this Device Group
       instance."
  ::= { operationalStateEntry 8 }

  warningErrorCount OBJECT-TYPE
    SYNTAX  Counter
    ACCESS  read-only
    STATUS  mandatory
    DESCRIPTION
      "The accumulated Warning or Non-Critical error count for this Device Group
       instance."
  ::= { operationalStateEntry 9 }

  currentErrorStatus OBJECT-TYPE
    SYNTAX  INTEGER
    ACCESS  read-only
    STATUS  mandatory
    DESCRIPTION
      "This attribute presents the current error status for this Device Group
       instance. The most critical error status in effect should be presented.
       I.e. if a part of the Device Group instance is 'Critical', while other
       status is 'Non-critical' then the status 'Critical' should be reported.
       It is indicated by a integer value as follows (hexadecimal).
         0x01 = Other
         0x02 = Unknown
         0x03 = OK
         0x04 = Non-critical
         0x05 = Critical
         0x06 = Non-recoverable"
  ::= { operationalStateEntry 10 }


--------------------------------------------------------------------------------
  physicalMemoryArray OBJECT IDENTIFIER ::= { hitachiSM-SAGroupsDefinition 34 }

  physicalMemoryArrayTable OBJECT-TYPE
    SYNTAX  SEQUENCE OF PhysicalMemoryArray
    ACCESS  not-accessible
    STATUS  mandatory
DESCRIPTION ""
  ::= { physicalMemoryArray 1 }

  physicalMemoryArrayEntry OBJECT-TYPE
    SYNTAX  PhysicalMemoryArray
    ACCESS  not-accessible
    STATUS  mandatory
DESCRIPTION ""
    INDEX   { memoryArrayTableIndex }
  ::= { physicalMemoryArrayTable 1 }

  PhysicalMemoryArray ::= SEQUENCE
  {
    memoryArrayTableIndex             INTEGER,
    memoryArrayLocation               INTEGER,
    memoryArrayUse                    INTEGER,
    maximumMemoryCapacity             INTEGER,
    numberOfMemoryDeviceSockets       INTEGER,
    numberOfMemoryDeviceSocketsUsed   INTEGER,
    memoryErrorCorrection             INTEGER,
    arrayErrorType                    INTEGER,
    lastErrorUpdate                   INTEGER,
    errorOperation                    INTEGER,
    errorDataSize                     INTEGER,
    errorData                         OCTET STRING,
    vendorSyndrome                    OCTET STRING,
    errorAddress                      OCTET STRING,
    errorResolution                   INTEGER,
    fruGroupIndex                     INTEGER,
    operationalGroupIndex             INTEGER
  }

  memoryArrayTableIndex OBJECT-TYPE
    SYNTAX  INTEGER
    ACCESS  read-only
    STATUS  mandatory
    DESCRIPTION
      "A unique number that identifies this row."
  ::= { physicalMemoryArrayEntry 1 }

  memoryArrayLocation OBJECT-TYPE
    SYNTAX  INTEGER
    ACCESS  read-only
    STATUS  mandatory
    DESCRIPTION
      "The physical location of the Memory Array, whether on the system board or
       an add-on board. It is indicated by a integer value as follows 
       (hexadecimal).
         0x01 = Other
         0x02 = Unknown
         0x03 = System board or motherboard
         0x04 = ISA add-on card
         0x05 = EISA add-on card
         0x06 = PCI add-on card
         0x07 = MCA add-on card
         0x08 = PCMCIA add-on card
         0x09 = Proprietary add-on card
         0x10 = NuBus
         0xA0 = PC-98/C20 add-on card
         0xA1 = PC-98/C24 add-on card
         0xA2 = PC-98/E add-on card
         0xA3 = PC-98/Local bus add-on card
         0xA4 = PC-98/Card slot add-on card"
  ::= { physicalMemoryArrayEntry 2 }

  memoryArrayUse OBJECT-TYPE
    SYNTAX  INTEGER
    ACCESS  read-only
    STATUS  mandatory
    DESCRIPTION
      "What this Memory Array is used for. It is indicated by a integer value as
       follows (hexadecimal).
         0x01 = Other
         0x02 = Unknown
         0x03 = System memory
         0x04 = Video memory
         0x05 = Flash memory
         0x06 = Non Volatile RAM
         0x07 = Cache Memory"
  ::= { physicalMemoryArrayEntry 3 }

  maximumMemoryCapacity OBJECT-TYPE
    SYNTAX  INTEGER
    ACCESS  read-only
    STATUS  mandatory
    DESCRIPTION
      "The maximum memory capacity, in kilobytes, on this array. 0x80000000
       denotes 'unknown'."
  ::= { physicalMemoryArrayEntry 4 }

  numberOfMemoryDeviceSockets OBJECT-TYPE
    SYNTAX  INTEGER
    ACCESS  read-only
    STATUS  mandatory
    DESCRIPTION
      "The number of SIMM slots or sockets available for Memory Devices in this
       array. 0x80000000 denotes 'unknown'."
  ::= { physicalMemoryArrayEntry 5 }

  numberOfMemoryDeviceSocketsUsed OBJECT-TYPE
    SYNTAX  INTEGER
    ACCESS  read-only
    STATUS  mandatory
    DESCRIPTION
      "The number of SIMM slots or sockets in use for Memory Devices in this
       array. 0x80000000 denotes 'unknown'."
  ::= { physicalMemoryArrayEntry 6 }

  memoryErrorCorrection OBJECT-TYPE
    SYNTAX  INTEGER
    ACCESS  read-only
    STATUS  mandatory
    DESCRIPTION
      "The main hardware error correction or detection method supported by this
       Memory Array. It is indicated by a integer value as follows 
       (hexadecimal).
         0x01 = Other
         0x02 = Unknown
         0x03 = None
         0x04 = Parity
         0x05 = Single Bit ECC
         0x06 = MultiBit ECC
         0x07 = CRC"
  ::= { physicalMemoryArrayEntry 7 }

  arrayErrorType OBJECT-TYPE
    SYNTAX  INTEGER
    ACCESS  read-only
    STATUS  mandatory
    DESCRIPTION
      "The type of error that is associated with the current status reported in
       Operational State for this Memory Array. It is indicated by a integer
       value as follows (hexadecimal).
         0x01 = Other
         0x02 = Unknown
         0x03 = OK
         0x04 = Bad read
         0x05 = Parity error
         0x06 = Single-bit error
         0x07 = Double-bit error
         0x08 = Multi-bit error
         0x09 = Nibble error
         0x0A = Checksum error
         0x0B = CRC error
         0x0C = Corrected Single-bit error
         0x0D = Corrected error
         0x0E = Uncorrectable error"
  ::= { physicalMemoryArrayEntry 8 }

  lastErrorUpdate OBJECT-TYPE
    SYNTAX  INTEGER
    ACCESS  read-only
    STATUS  mandatory
    DESCRIPTION
      "System state during which last error status was collected. It is
       indicated by a integer value as follows (hexadecimal).
         0x01 = Other
         0x02 = Unknown
         0x03 = No update since last instrumentation start.
         0x04 = Updated from information obtained prior to instrumentation start.
         0x05 = Updated during instrumentation run-time."
  ::= { physicalMemoryArrayEntry 9 }

  errorOperation OBJECT-TYPE
    SYNTAX  INTEGER
    ACCESS  read-only
    STATUS  mandatory
    DESCRIPTION
      "The memory access operation that caused the current error. It is
       indicated by a integer value as follows (hexadecimal).
         0x01 = Other
         0x02 = Unknown
         0x03 = Read
         0x04 = Write
         0x05 = Partial write"
  ::= { physicalMemoryArrayEntry 10 }

  errorDataSize OBJECT-TYPE
    SYNTAX  INTEGER
    ACCESS  read-only
    STATUS  mandatory
    DESCRIPTION
      "The size of the data transfer that caused the error, in bits. Zero
       indicates no error, 0x80000000 denotes 'unknown'."
  ::= { physicalMemoryArrayEntry 11 }

  errorData OBJECT-TYPE
    SYNTAX  OCTET STRING (SIZE(1..64))
    ACCESS  read-only
    STATUS  mandatory
    DESCRIPTION
      "Data captured during the erroneous Memory Array access. The data occupy
       the first n bytes of the octetstring required to hold 'Error Data Size'
       bits of the data. Data are stored least-significant byte first."
  ::= { physicalMemoryArrayEntry 12 }

  vendorSyndrome OBJECT-TYPE
    SYNTAX  OCTET STRING (SIZE(1..64))
    ACCESS  read-only
    STATUS  mandatory
    DESCRIPTION
      "Vendor-specific syndrome or CRC data associated with the erroneous
       access."
  ::= { physicalMemoryArrayEntry 13 }

  errorAddress OBJECT-TYPE
    SYNTAX  OCTET STRING (SIZE(1..8))
    ACCESS  read-only
    STATUS  mandatory
    DESCRIPTION
      "Physical address of the error based on the addressing of the bus that the
       Memory Array is connected to. 0x8000 0000 0000 0000 denotes 'unknown'. It
       is indicated by a 8bytes value laid out as big endian (byte 0 is the most
       significant, byte 7 is the least significant)."
  ::= { physicalMemoryArrayEntry 14 }

  errorResolution OBJECT-TYPE
    SYNTAX  INTEGER
    ACCESS  read-only
    STATUS  mandatory
    DESCRIPTION
      "Range in bytes that the error can be determined to be within, when an
       Error Address is given. 0x80000000 denotes 'unknown'."
  ::= { physicalMemoryArrayEntry 15 }

  fruGroupIndex OBJECT-TYPE
    SYNTAX  INTEGER
    ACCESS  read-only
    STATUS  mandatory
    DESCRIPTION
      "If this is a Field Replaceable Unit or if it is part of another FRU, this
       provides an index into the FRU table; 'value = -1' indicates that the
       group is not a FRU."
  ::= { physicalMemoryArrayEntry 16 }

  operationalGroupIndex OBJECT-TYPE
    SYNTAX  INTEGER
    ACCESS  read-only
    STATUS  mandatory
    DESCRIPTION
      "The index into the Operational State Table for this Memory Array. The
       Operational State row is used to hold the overall error count and error
       status for this array."
  ::= { physicalMemoryArrayEntry 17 }


--------------------------------------------------------------------------------
  memoryDevice OBJECT IDENTIFIER ::= { hitachiSM-SAGroupsDefinition 36 }

  memoryDeviceTable OBJECT-TYPE
    SYNTAX  SEQUENCE OF MemoryDevice
    ACCESS  not-accessible
    STATUS  mandatory
DESCRIPTION ""
  ::= { memoryDevice 1 }

  memoryDeviceEntry OBJECT-TYPE
    SYNTAX  MemoryDevice
    ACCESS  not-accessible
    STATUS  mandatory
DESCRIPTION ""
    INDEX   { memoryDeviceTableIndex }
  ::= { memoryDeviceTable 1 }

  MemoryDevice ::= SEQUENCE
  {
    memoryDeviceTableIndex  INTEGER,
    memoryArrayIndex        INTEGER,
    deviceLocator           DisplayString,
    bankLocator             DisplayString,
    memorydDviceSize        INTEGER,
    formFactor              INTEGER,
    totalWidth              INTEGER,
    dataWidth               INTEGER,
    memoryType              INTEGER,
    typeDetail              INTEGER,
    deviceSet               INTEGER,
    deviceErrorType         INTEGER,
    errorGranularity        INTEGER,
    lastErrorUpdate         INTEGER,
    errorOperation          INTEGER,
    errorDataSize           INTEGER,
    errorData               OCTET STRING,
    vendorSyndrome          OCTET STRING,
    deviceErrorAddress      INTEGER,
    arrayErrorAddress       INTEGER,
    errorResolution         INTEGER,
    fruGroupIndex           INTEGER,
    operationalGroupIndex   INTEGER
  }

  memoryDeviceTableIndex OBJECT-TYPE
    SYNTAX  INTEGER
    ACCESS  read-only
    STATUS  mandatory
    DESCRIPTION
      "A unique number that identifies this row."
  ::= { memoryDeviceEntry 1 }

  memoryArrayIndex OBJECT-TYPE
    SYNTAX  INTEGER
    ACCESS  read-only
    STATUS  mandatory
    DESCRIPTION
      "The ID of the Memory Array that this Memory Device is a part of."
  ::= { memoryDeviceEntry 2 }

  deviceLocator OBJECT-TYPE
    SYNTAX  DisplayString (SIZE (1..64))
    ACCESS  read-only
    STATUS  mandatory
    DESCRIPTION
      "A string identifying the physically labeled socket or board position
       where the memory device is located. Eg. 'SIMM 3' or 'IC12'. It is
       expressed in the form of string(ASCII Code)."
  ::= { memoryDeviceEntry 3 }

  bankLocator OBJECT-TYPE
    SYNTAX  DisplayString (SIZE (1..64))
    ACCESS  read-only
    STATUS  mandatory
    DESCRIPTION
      "A string identifying the physically labeled bank where the memory device
       is located. Eg. 'Bank 0' or 'A'. It is expressed in the form of string
       (ASCII Code)."
  ::= { memoryDeviceEntry 4 }

  memorydDviceSize OBJECT-TYPE
    SYNTAX  INTEGER
    ACCESS  read-only
    STATUS  mandatory
    DESCRIPTION
      "Size of this memory device, in bytes."
  ::= { memoryDeviceEntry 5 }

  formFactor OBJECT-TYPE
    SYNTAX  INTEGER
    ACCESS  read-only
    STATUS  mandatory
    DESCRIPTION
      "Implementation form factor for this memory device. It is indicated by a
       integer value as follows (hexadecimal).
         0x01 = Other
         0x02 = Unknown
         0x03 = SIMM
         0x04 = SIP
         0x05 = Chip
         0x06 = DIP
         0x07 = ZIP
         0x08 = Proprietary Card
         0x09 = DIMM
         0x0A = TSOP
         0x0B = Row of chips"
  ::= { memoryDeviceEntry 6 }

  totalWidth OBJECT-TYPE
    SYNTAX  INTEGER
    ACCESS  read-only
    STATUS  mandatory
    DESCRIPTION
      "Total width of this memory device, including check or error correction
       bits, in bits. If there are no error correction bits, the value in this
       attribute should match that specified in Data Width. 0x80000000 denotes
       'unknown'."
  ::= { memoryDeviceEntry 7 }

  dataWidth OBJECT-TYPE
    SYNTAX  INTEGER
    ACCESS  read-only
    STATUS  mandatory
    DESCRIPTION
      "Data width of this memory device, in bits. A data width of 0 and a Total
       Width of 8 would indicate that the device is solely being used to provide
       eight error correction bits. 0x80000000 denotes 'unknown'."
  ::= { memoryDeviceEntry 8 }

  memoryType OBJECT-TYPE
    SYNTAX  INTEGER
    ACCESS  read-only
    STATUS  mandatory
    DESCRIPTION
      "Type of memory used in this memory device. It is indicated by a integer
       value as follows (hexadecimal).
         0x01 = Other
         0x02 = Unknown
         0x03 = DRAM
         0x04 = EDRAM
         0x05 = VRAM
         0x06 = SRAM
         0x07 = RAM
         0x08 = ROM
         0x09 = FLASH
         0x0A = EEPROM
         0x0B = FEPROM
         0x0C = EPROM"
  ::= { memoryDeviceEntry 9 }

  typeDetail OBJECT-TYPE
    SYNTAX  INTEGER
    ACCESS  read-only
    STATUS  mandatory
    DESCRIPTION
      "Additional detail on the device type. It is indicated by a integer value
       as follows (hexadecimal).
         0x01 = Other
         0x02 = Unknown
         0x03 = fast paged
         0x04 = static column
         0x05 = pseudo-static
         0x06 = RAMBUS
         0x07 = Synchronous
         0x08 = CMOS
         0x09 = EDO
         0x0A = Window DRAM
         0x0B = Cache DRAM
         0x0C = Non-volatile"
  ::= { memoryDeviceEntry 10 }

  deviceSet OBJECT-TYPE
    SYNTAX  INTEGER
    ACCESS  read-only
    STATUS  mandatory
    DESCRIPTION
      "This attribute is used to identify when the Memory Device is one of a set
       of Memory Devices that must be populated with all devices of the same
       type and size, and which set the device belongs to. For example, when one
       SIMM belongs to a set of four. 0 indicates the Memory Device isn't part
       of a set. 0x80000000 denotes 'unknown'."
  ::= { memoryDeviceEntry 11 }

  deviceErrorType OBJECT-TYPE
    SYNTAX  INTEGER
    ACCESS  read-only
    STATUS  mandatory
    DESCRIPTION
      "The type of error that is associated with the current status reported in
       Operational State for this Memory Device. It is indicated by a integer
       value as follows (hexadecimal).
         0x01 = Other
         0x02 = Unknown
         0x03 = OK
         0x04 = Bad read
         0x05 = Parity error
         0x06 = Single-bit error
         0x07 = Double-bit error
         0x08 = Multi-bit error
         0x09 = Nibble error
         0x0A = Checksum error
         0x0B = CRC error
         0x0C = Corrected Single-bit error
         0x0D = Corrected error
         0x0E = Uncorrectable error"
  ::= { memoryDeviceEntry 12 }

  errorGranularity OBJECT-TYPE
    SYNTAX  INTEGER
    ACCESS  read-only
    STATUS  mandatory
    DESCRIPTION
      "Specifies whether the current error's location can be resolved to the
       partition or device level. It is indicated by a integer value as follows 
       (hexadecimal).
         0x01 = Other
         0x02 = Unknown
         0x03 = Device level
         0x04 = Memory Partition level"
  ::= { memoryDeviceEntry 13 }

  lastErrorUpdate OBJECT-TYPE
    SYNTAX  INTEGER
    ACCESS  read-only
    STATUS  mandatory
    DESCRIPTION
      "System state during which the last error update was collected. It is
       indicated by a integer value as follows (hexadecimal).
         0x01 = Other
         0x02 = Unknown
         0x03 = No update since last instrumentation start.
         0x04 = Updated from information obtained prior to instrumentation start.
         0x05 = Updated during instrumentation run-time."
  ::= { memoryDeviceEntry 14 }

  errorOperation OBJECT-TYPE
    SYNTAX  INTEGER
    ACCESS  read-only
    STATUS  mandatory
    DESCRIPTION
      "The memory access operation that caused the current error. It is
       indicated by a integer value as follows (hexadecimal).
         0x01 = Other
         0x02 = Unknown
         0x03 = Read
         0x04 = Write
         0x05 = Partial write"
  ::= { memoryDeviceEntry 15 }

  errorDataSize OBJECT-TYPE
    SYNTAX  INTEGER
    ACCESS  read-only
    STATUS  mandatory
    DESCRIPTION
      "The size of the data transfer that caused the error,in bits. Zero
       indicates no error, 0x80000000 denotes 'unknown'."
  ::= { memoryDeviceEntry 16 }

  errorData OBJECT-TYPE
    SYNTAX  OCTET STRING (SIZE(1..64))
    ACCESS  read-only
    STATUS  mandatory
    DESCRIPTION
      "Data captured during the erroneous Memory Array access. The data occupies
       the first n bytes of the octetstring required to hold 'Error Data Size'
       bits of the data. Data is stored least-significant byte first."
  ::= { memoryDeviceEntry 17 }

  vendorSyndrome OBJECT-TYPE
    SYNTAX  OCTET STRING (SIZE(1..64))
    ACCESS  read-only
    STATUS  mandatory
    DESCRIPTION
      "Vendor-specific syndrome or CRC data associated withthe erroneous
       access."
  ::= { memoryDeviceEntry 18 }

  deviceErrorAddress OBJECT-TYPE
    SYNTAX  INTEGER
    ACCESS  read-only
    STATUS  mandatory
    DESCRIPTION
      "Physical address of the error relative to the start of the device, in
       bytes. 0x80000000 denotes 'unknown'."
  ::= { memoryDeviceEntry 19 }

  arrayErrorAddress OBJECT-TYPE
    SYNTAX  INTEGER
    ACCESS  read-only
    STATUS  mandatory
    DESCRIPTION
      "Physical address of the kilobyte where the error is located, relative to
       the bus for the Memory Array. 0x80000000 denotes 'unknown'."
  ::= { memoryDeviceEntry 20 }

  errorResolution OBJECT-TYPE
    SYNTAX  INTEGER
    ACCESS  read-only
    STATUS  mandatory
    DESCRIPTION
      "Range in bytes that the error can be determined to be within, when an
       Error Address is given. 0x80000000 denotes 'unknown'."
  ::= { memoryDeviceEntry 21 }

  fruGroupIndex OBJECT-TYPE
    SYNTAX  INTEGER
    ACCESS  read-only
    STATUS  mandatory
    DESCRIPTION
      "If this is a Field Replaceable Unit or if it is partof another FRU, this
       provides an index into the FRU table; 'value = -1' indicates that the
       group is not a FRU."
  ::= { memoryDeviceEntry 22 }

  operationalGroupIndex OBJECT-TYPE
    SYNTAX  INTEGER
    ACCESS  read-only
    STATUS  mandatory
    DESCRIPTION
      "The index into the Operational State Table for this device."
  ::= { memoryDeviceEntry 23 }


--------------------------------------------------------------------------------
  systemResources2 OBJECT IDENTIFIER ::= { hitachiSM-SAGroupsDefinition 38 }

  systemResources2Table OBJECT-TYPE
    SYNTAX  SEQUENCE OF SystemResources2
    ACCESS  not-accessible
    STATUS  mandatory
DESCRIPTION ""
  ::= { systemResources2 1 }

  systemResources2Entry OBJECT-TYPE
    SYNTAX  SystemResources2
    ACCESS  not-accessible
    STATUS  mandatory
DESCRIPTION ""
    INDEX   { systemResourcesIndex }
  ::= { systemResources2Table 1 }

  SystemResources2 ::= SEQUENCE
  {
    systemResourcesIndex  INTEGER,
    resourceUser          INTEGER,
    resourceSet           INTEGER,
    resourceAssignment    INTEGER,
    resourceType          INTEGER,
    resourceNumber        INTEGER,
    resourceInfoId        INTEGER,
    startAddress          OCTET STRING,
    endAddress            OCTET STRING,
    resourceSize          INTEGER,
    baseAlignment         INTEGER,
    shareable             INTEGER,
    shared                INTEGER
  }

  systemResourcesIndex OBJECT-TYPE
    SYNTAX  INTEGER
    ACCESS  read-only
    STATUS  mandatory
    DESCRIPTION
      "A number that uniquely identifies the rows in this table."
  ::= { systemResources2Entry 1 }

  resourceUser OBJECT-TYPE
    SYNTAX  INTEGER
    ACCESS  read-only
    STATUS  mandatory
    DESCRIPTION
      "A unique number for each different 'resource user' that has resources
       specified in this table."
  ::= { systemResources2Entry 2 }

  resourceSet OBJECT-TYPE
    SYNTAX  INTEGER
    ACCESS  read-only
    STATUS  mandatory
    DESCRIPTION
      "A number used as the ID of a set of Memory, I/O, DMA and/or INT resources
       for the resource user."
  ::= { systemResources2Entry 3 }

  resourceAssignment OBJECT-TYPE
    SYNTAX  INTEGER
    ACCESS  read-only
    STATUS  mandatory
    DESCRIPTION
      "Describes the state of the assignment of this set of resources. (Note:
       This value must be the same for all resources within a given set.) It is
       indicated by a integer value as follows (hexadecimal).
         0x01 = Other
         0x02 = Unknown
         0x03 = Allocated
         0x04 = Assignable
         0x05 = Temporary Assignment"
  ::= { systemResources2Entry 4 }

  resourceType OBJECT-TYPE
    SYNTAX  INTEGER
    ACCESS  read-only
    STATUS  mandatory
    DESCRIPTION
      "The type of resource described by this row. It is indicated by a integer
       value as follows (hexadecimal).
         0x01 = Other
         0x02 = Unknown
         0x03 = Memory
         0x04 = I/O
         0x05 = IRQ
         0x06 = DMA"
  ::= { systemResources2Entry 5 }

  resourceNumber OBJECT-TYPE
    SYNTAX  INTEGER
    ACCESS  read-only
    STATUS  mandatory
    DESCRIPTION
      "DMA or IRQ number - 0 for Memory and I/O ranges. This is the interrupt or
       DMA number relative to the bus that the interrupt is sourced from."
  ::= { systemResources2Entry 6 }

  resourceInfoId OBJECT-TYPE
    SYNTAX  INTEGER
    ACCESS  read-only
    STATUS  mandatory
    DESCRIPTION
      "ID of the row in the 'Info' table for this type of system resource. E.g.
       if this Resource Type is 'I/O' then this would be an index into the
       'System Resource I/O Info' table."
  ::= { systemResources2Entry 7 }

  startAddress OBJECT-TYPE
    SYNTAX  OCTET STRING (SIZE(1..8))
    ACCESS  read-only
    STATUS  mandatory
    DESCRIPTION
      "Starting physical address for this memory range, or the minimum base
       address if this attribute is being used to describe a programmable range.
       0 for IRQ and DMA resources. It is indicated by a 8bytes value laid out
       as big endian (byte 0 is the most significant, byte 7 is the least
       significant)."
  ::= { systemResources2Entry 8 }

  endAddress OBJECT-TYPE
    SYNTAX  OCTET STRING (SIZE(1..8))
    ACCESS  read-only
    STATUS  mandatory
    DESCRIPTION
      "Ending physical address (address of last byte) for this memory range, or
       the maximum configurable base address if this attribute is being used to
       describe a programmable range. 0 for IRQ and DMA resources. It is
       indicated by a 8bytes value laid out as big endian (byte 0 is the most
       significant, byte 7 is the least significant)."
  ::= { systemResources2Entry 9 }

  resourceSize OBJECT-TYPE
    SYNTAX  INTEGER
    ACCESS  read-only
    STATUS  mandatory
    DESCRIPTION
      "Number of consecutive bytes that a memory or I/O resource consumes. 0 for
       IRQ and DMA resources."
  ::= { systemResources2Entry 10 }

  baseAlignment OBJECT-TYPE
    SYNTAX  INTEGER
    ACCESS  read-only
    STATUS  mandatory
    DESCRIPTION
      "Alignment of Start Address, in bytes. Indicates the granularity of the
       increments in which a programmable range can be set."
  ::= { systemResources2Entry 11 }

  shareable OBJECT-TYPE
    SYNTAX  INTEGER
    ACCESS  read-only
    STATUS  mandatory
    DESCRIPTION
      "Indicates whether the resource is shareable. It is indicated by a integer
       value as follows (hexadecimal).
         0x00 = False
         0x01 = True
         0x02 = Unknown"
  ::= { systemResources2Entry 12 }

  shared OBJECT-TYPE
    SYNTAX  INTEGER
    ACCESS  read-only
    STATUS  mandatory
    DESCRIPTION
      "Indicates whether this resource, or a portion of this resource, is shared
       with another device. It is indicated by a integer value as follows 
       (hexadecimal).
         0x00 = False
         0x01 = True
         0x02 = Unknown"
  ::= { systemResources2Entry 13 }


--------------------------------------------------------------------------------
  upsBattery OBJECT-TYPE
    SYNTAX  UpsBattery
    ACCESS  not-accessible
    STATUS  mandatory
DESCRIPTION ""
  ::= { hitachiSM-SAGroupsDefinition 53 }

  UpsBattery ::= SEQUENCE
  {
    batteryStatus               INTEGER,
    secondsOnBattery            Counter,
    estimatedMinutesRemaining   INTEGER,
    estimatedChargeRemaining    Gauge,
    batteryVoltage              Gauge,
    batteryCurrent              Gauge,
    temperatureProbeIndex       INTEGER,
    fruGroupIndex               INTEGER,
    operationalGroupIndex       INTEGER
  }

  batteryStatus OBJECT-TYPE
    SYNTAX  INTEGER
    ACCESS  read-only
    STATUS  mandatory
    DESCRIPTION
      "The indication of the capacity remaining in the UPS system's batteries. A
       value of 'battery normal' indicates that the remaining estimated minutes
       of run-time is greater than the UPS's configured 'low battery time' 
       (typically two minutes). A value of 'battery low' indicates that the
       remaining estimated minutes of battery run-time is less than or equal to
       the UPS's configured 'low battery time'. A value of 'battery depleted'
       indicates that the UPS will be unable to sustain the present load when
       and if the utility power is lost (including the possibility that the
       utility power is currently absent and the UPS is unable to sustain the
       output). It is indicated by a integer value as follows (hexadecimal).
         0x01 = Unknown
         0x02 = Battery Normal
         0x03 = Battery Low
         0x04 = Battery Depleted"
  ::= { upsBattery 1 }

  secondsOnBattery OBJECT-TYPE
    SYNTAX  Counter
    ACCESS  read-only
    STATUS  mandatory
    DESCRIPTION
      "If the UPS is on battery power, the elapsed time in seconds since the UPS
       last switched to battery power, or the time since the UPS component
       software was last restarted, whichever is less. Zero shall be returned if
       the UPS is not on battery power."
  ::= { upsBattery 2 }

  estimatedMinutesRemaining OBJECT-TYPE
    SYNTAX  INTEGER
    ACCESS  read-only
    STATUS  mandatory
    DESCRIPTION
      "An estimate in minutes of the time to battery charge depletion under the
       present load conditions if the utility power is off and remains off, or
       if it were to be lost and remain off."
  ::= { upsBattery 3 }

  estimatedChargeRemaining OBJECT-TYPE
    SYNTAX  Gauge
    ACCESS  read-only
    STATUS  mandatory
    DESCRIPTION
      "An estimate of the time to battery charge depletion under the present
       load conditions if the utility power is off and remains off, or if it
       were to be lost and remain off. The value represents a percent of full
       charge."
  ::= { upsBattery 4 }

  batteryVoltage OBJECT-TYPE
    SYNTAX  Gauge
    ACCESS  read-only
    STATUS  mandatory
    DESCRIPTION
      "The magnitude of the present battery voltage in 0.1 volts DC."
  ::= { upsBattery 5 }

  batteryCurrent OBJECT-TYPE
    SYNTAX  Gauge
    ACCESS  read-only
    STATUS  mandatory
    DESCRIPTION
      "The present battery current in 0.1 Amps DC."
  ::= { upsBattery 6 }

  temperatureProbeIndex OBJECT-TYPE
    SYNTAX  INTEGER
    ACCESS  read-only
    STATUS  mandatory
    DESCRIPTION
      "Index into the Temperature Probe table. This probe indicates the ambient
       temperature at or near the UPS battery casing. Zero implies no probe is
       present."
  ::= { upsBattery 7 }

  fruGroupIndex OBJECT-TYPE
    SYNTAX  INTEGER
    ACCESS  read-only
    STATUS  mandatory
    DESCRIPTION
      "If this is a Field Replaceable Unit or it is part of another FRU, this
       provides an index into the FRU table; 'value = -1' indicates that the
       group is not a FRU."
  ::= { upsBattery 8 }

  operationalGroupIndex OBJECT-TYPE
    SYNTAX  INTEGER
    ACCESS  read-only
    STATUS  mandatory
    DESCRIPTION
      "The index into the Operational State table for this device."
  ::= { upsBattery 9 }


--------------------------------------------------------------------------------
  voltageProbe OBJECT IDENTIFIER ::= { hitachiSM-SAGroupsDefinition 54 }

  voltageProbeTable OBJECT-TYPE
    SYNTAX  SEQUENCE OF VoltageProbe
    ACCESS  not-accessible
    STATUS  mandatory
DESCRIPTION ""
  ::= { voltageProbe 1 }

  voltageProbeEntry OBJECT-TYPE
    SYNTAX  VoltageProbe
    ACCESS  not-accessible
    STATUS  mandatory
DESCRIPTION ""
    INDEX   { voltageProbeIndex }
  ::= { voltageProbeTable 1 }

  VoltageProbe ::= SEQUENCE
  {
    voltageProbeIndex                           INTEGER,
    voltageProbeLocation                        INTEGER,
    voltageProbeDescription                     DisplayString,
    voltageStatus                               INTEGER,
    voltageProbeVoltageLevel                    INTEGER,
    monitoredVoltageNominalLevel                INTEGER,
    monitoredVoltageNormalMaximum               INTEGER,
    monitoredVoltageNormalMinimum               INTEGER,
    voltageProbeMaximum                         INTEGER,
    voltageProbeMinimum                         INTEGER,
    voltageLevelLowerThreshold-Non-Critical     INTEGER,
    voltageLevelUpperThreshold-Non-Critical     INTEGER,
    voltageLevelLowerThreshold-Critical         INTEGER,
    voltageLevelUpperThreshold-Critical         INTEGER,
    voltageLevelLowerThreshold-Non-Recoverable  INTEGER,
    voltageLevelUpperThreshold-Non-Recoverable  INTEGER,
    voltageProbeResolution                      INTEGER,
    voltageProbeTolerance                       INTEGER,
    voltageProbeAccuracy                        INTEGER,
    fruGroupIndex                               INTEGER,
    operationalGroupIndex                       INTEGER
  }

  voltageProbeIndex OBJECT-TYPE
    SYNTAX  INTEGER
    ACCESS  read-only
    STATUS  mandatory
    DESCRIPTION
      "Index into this voltage probe table."
  ::= { voltageProbeEntry 1 }

  voltageProbeLocation OBJECT-TYPE
    SYNTAX  INTEGER
    ACCESS  read-only
    STATUS  mandatory
    DESCRIPTION
      "Identifies the physical location of the voltage probe. It is indicated by
       a integer value as follows (hexadecimal).
         0x01 = Other
         0x02 = Unknown
         0x03 = Processor
         0x04 = Disk
         0x05 = Peripheral Bay
         0x06 = System Management Module
         0x07 = Motherboard
         0x08 = Memory Module
         0x09 = Processor Module
         0x0A = Power Unit
         0x0B = Add-in Card"
  ::= { voltageProbeEntry 2 }

  voltageProbeDescription OBJECT-TYPE
    SYNTAX  DisplayString (SIZE (1..64))
    ACCESS  read-only
    STATUS  mandatory
    DESCRIPTION
      "Additional descriptive information about the voltage probe or probe's
       location. It is expressed in the form of string(ASCII Code)."
  ::= { voltageProbeEntry 3 }

  voltageStatus OBJECT-TYPE
    SYNTAX  INTEGER
    ACCESS  read-only
    STATUS  mandatory
    DESCRIPTION
      "Defines the status of the voltage monitored by this voltage probe. It is
       indicated by a integer value as follows (hexadecimal).
         0x01 = Other
         0x02 = Unknown
         0x03 = OK
         0x04 = Non-critical
         0x05 = Critical
         0x06 = Non-recoverable"
  ::= { voltageProbeEntry 4 }

  voltageProbeVoltageLevel OBJECT-TYPE
    SYNTAX  INTEGER
    ACCESS  read-only
    STATUS  mandatory
    DESCRIPTION
      "The current voltage level of this voltage probe in millivolts. 0x8000000
       denotes 'unknown'."
  ::= { voltageProbeEntry 5 }

  monitoredVoltageNominalLevel OBJECT-TYPE
    SYNTAX  INTEGER
    ACCESS  read-only
    STATUS  mandatory
    DESCRIPTION
      "The nominal voltage level of the voltage monitored by this probe in
       millivolts. 0x80000000 denotes 'unknown'."
  ::= { voltageProbeEntry 6 }

  monitoredVoltageNormalMaximum OBJECT-TYPE
    SYNTAX  INTEGER
    ACCESS  read-only
    STATUS  mandatory
    DESCRIPTION
      "The normal maximum voltage level of the voltage monitored by this probe
       in millivolts. 0x80000000 denotes 'unknown'."
  ::= { voltageProbeEntry 7 }

  monitoredVoltageNormalMinimum OBJECT-TYPE
    SYNTAX  INTEGER
    ACCESS  read-only
    STATUS  mandatory
    DESCRIPTION
      "The normal minimum voltage level of the voltage monitored by this probe
       in millivolts. 0x80000000 denotes 'unknown'."
  ::= { voltageProbeEntry 8 }

  voltageProbeMaximum OBJECT-TYPE
    SYNTAX  INTEGER
    ACCESS  read-only
    STATUS  mandatory
    DESCRIPTION
      "The maximum voltage level specified to be readable by this probe in
       millivolts. 0x80000000 denotes 'unknown'."
  ::= { voltageProbeEntry 9 }

  voltageProbeMinimum OBJECT-TYPE
    SYNTAX  INTEGER
    ACCESS  read-only
    STATUS  mandatory
    DESCRIPTION
      "The minimum voltage level specified to be readable by this probe in
       millivolts. 0x80000000 denotes 'unknown'."
  ::= { voltageProbeEntry 10 }

  voltageLevelLowerThreshold-Non-Critical OBJECT-TYPE
    SYNTAX  INTEGER
    ACCESS  read-only
    STATUS  mandatory
    DESCRIPTION
      "The lower non-critical threshold for the voltage level set by the user,
       in millivolts. 0x80000000 denotes 'unknown'."
  ::= { voltageProbeEntry 11 }

  voltageLevelUpperThreshold-Non-Critical OBJECT-TYPE
    SYNTAX  INTEGER
    ACCESS  read-only
    STATUS  mandatory
    DESCRIPTION
      "The upper non-critical threshold for the voltage probe, in millivolts.
       0x80000000 denotes 'unknown'."
  ::= { voltageProbeEntry 12 }

  voltageLevelLowerThreshold-Critical OBJECT-TYPE
    SYNTAX  INTEGER
    ACCESS  read-only
    STATUS  mandatory
    DESCRIPTION
      "The lower critical threshold for the voltage probe, in millivolts.
       0x80000000 denotes 'unknown'."
  ::= { voltageProbeEntry 13 }

  voltageLevelUpperThreshold-Critical OBJECT-TYPE
    SYNTAX  INTEGER
    ACCESS  read-only
    STATUS  mandatory
    DESCRIPTION
      "The upper critical threshold for the voltage probe, in millivolts.
       0x80000000 denotes 'unknown'."
  ::= { voltageProbeEntry 14 }

  voltageLevelLowerThreshold-Non-Recoverable OBJECT-TYPE
    SYNTAX  INTEGER
    ACCESS  read-only
    STATUS  mandatory
    DESCRIPTION
      "The lower non-recoverable threshold for the voltage probe, in millivolts.
       0x80000000 denotes 'unknown'."
  ::= { voltageProbeEntry 15 }

  voltageLevelUpperThreshold-Non-Recoverable OBJECT-TYPE
    SYNTAX  INTEGER
    ACCESS  read-only
    STATUS  mandatory
    DESCRIPTION
      "The upper non-recoverable threshold for the voltage probe, in millivolts.
       0x80000000 denotes 'unknown'."
  ::= { voltageProbeEntry 16 }

  voltageProbeResolution OBJECT-TYPE
    SYNTAX  INTEGER
    ACCESS  read-only
    STATUS  mandatory
    DESCRIPTION
      "The resolution for the reading from this voltage probe, in tenths of
       millivolts. '0x80000000 denotes 'unknown'."
  ::= { voltageProbeEntry 17 }

  voltageProbeTolerance OBJECT-TYPE
    SYNTAX  INTEGER
    ACCESS  read-only
    STATUS  mandatory
    DESCRIPTION
      "The tolerance for the reading from this voltage probe, in plus/minus
       millivolts. 0x80000000 denotes 'unknown'."
  ::= { voltageProbeEntry 18 }

  voltageProbeAccuracy OBJECT-TYPE
    SYNTAX  INTEGER
    ACCESS  read-only
    STATUS  mandatory
    DESCRIPTION
      "The accuracy for the reading from this voltage probe, in plus/minus
       hundredths of a percent. 0x80000000 denotes 'unknown'."
  ::= { voltageProbeEntry 19 }

  fruGroupIndex OBJECT-TYPE
    SYNTAX  INTEGER
    ACCESS  read-only
    STATUS  mandatory
    DESCRIPTION
      "Index into the FRU table."
  ::= { voltageProbeEntry 20 }

  operationalGroupIndex OBJECT-TYPE
    SYNTAX  INTEGER
    ACCESS  read-only
    STATUS  mandatory
    DESCRIPTION
      "Index into the Operational State table."
  ::= { voltageProbeEntry 21 }


--------------------------------------------------------------------------------
  temperatureProbe OBJECT IDENTIFIER ::= { hitachiSM-SAGroupsDefinition 55 }

  temperatureProbeTable OBJECT-TYPE
    SYNTAX  SEQUENCE OF TemperatureProb
    ACCESS  not-accessible
    STATUS  mandatory
DESCRIPTION ""
  ::= { temperatureProbe 1 }

  temperatureProbeEntry OBJECT-TYPE
    SYNTAX  TemperatureProb
    ACCESS  not-accessible
    STATUS  mandatory
DESCRIPTION ""
    INDEX   { temperatureProbeTableIndex }
  ::= { temperatureProbeTable 1 }

  TemperatureProb ::= SEQUENCE
  {
    temperatureProbeTableIndex                        INTEGER,
    temperatureProbeLocation                          INTEGER,
    temperatureProbeDescription                       DisplayString,
    temperatureStatus                                 INTEGER,
    temperatureProbeTemperatureReading                INTEGER,
    monitoredTemperatureNominalReading                INTEGER,
    monitoredTemperatureNormalMaximum                 INTEGER,
    monitoredTemperatureNormalMinimum                 INTEGER,
    temperatureProbeMaximum                           INTEGER,
    temperatureProbeMinimum                           INTEGER,
    temperatureReadingLowerThreshold-Non-Critical     INTEGER,
    temperatureReadingUpperThreshold-Non-Critical     INTEGER,
    temperatureReadingLowerThreshold-Critical         INTEGER,
    temperatureReadingUpperThreshold-Critical         INTEGER,
    temperatureReadingLowerThreshold-Non-Recoverable  INTEGER,
    temperatureReadingUpperThreshold-Non-Recoverable  INTEGER,
    temperatureProbeResolution                        INTEGER,
    temperatureProbeTolerance                         INTEGER,
    temperatureProbeAccuracy                          INTEGER,
    fruGroupIndex                                     INTEGER,
    operationalGroupIndex                             INTEGER
  }

  temperatureProbeTableIndex OBJECT-TYPE
    SYNTAX  INTEGER
    ACCESS  read-only
    STATUS  mandatory
    DESCRIPTION
      "Index into this temperature probe table."
  ::= { temperatureProbeEntry 1 }

  temperatureProbeLocation OBJECT-TYPE
    SYNTAX  INTEGER
    ACCESS  read-only
    STATUS  mandatory
    DESCRIPTION
      "Identifies the physical location of the temperature probe. It is
       indicated by a integer value as follows (hexadecimal).
         0x01 = Other
         0x02 = Unknown
         0x03 = Processor
         0x04 = Disk
         0x05 = Peripheral Bay
         0x06 = SMB Master
         0x07 = Motherboard
         0x08 = Memory Module
         0x09 = Processor Module
         0x0A = Power Unit
         0x0B = Add-in Card"
  ::= { temperatureProbeEntry 2 }

  temperatureProbeDescription OBJECT-TYPE
    SYNTAX  DisplayString (SIZE (1..64))
    ACCESS  read-only
    STATUS  mandatory
    DESCRIPTION
      "Additional descriptive information about the temperature probe or probe's
       location. It is expressed in the form of string(ASCII Code)."
  ::= { temperatureProbeEntry 3 }

  temperatureStatus OBJECT-TYPE
    SYNTAX  INTEGER
    ACCESS  read-only
    STATUS  mandatory
    DESCRIPTION
      "Defines the status of the temperature monitored by this temperature
       probe. It is indicated by a integer value as follows (hexadecimal).
         0x01 = Other
         0x02 = Unknown
         0x03 = OK
         0x04 = Non-critical
         0x05 = Critical
         0x06 = Non-recoverable"
  ::= { temperatureProbeEntry 4 }

  temperatureProbeTemperatureReading OBJECT-TYPE
    SYNTAX  INTEGER
    ACCESS  read-only
    STATUS  mandatory
    DESCRIPTION
      "The present temperature reading of this temperature probe in 1/10th
       degrees C. 0x8000000 denotes 'unknown'."
  ::= { temperatureProbeEntry 5 }

  monitoredTemperatureNominalReading OBJECT-TYPE
    SYNTAX  INTEGER
    ACCESS  read-only
    STATUS  mandatory
    DESCRIPTION
      "The nominal temperature reading of the temperature monitored by this
       probe in 1/10th degrees C. 0x80000000 denotes 'unknown'."
  ::= { temperatureProbeEntry 6 }

  monitoredTemperatureNormalMaximum OBJECT-TYPE
    SYNTAX  INTEGER
    ACCESS  read-only
    STATUS  mandatory
    DESCRIPTION
      "The normal maximum temperature reading of the temperature monitored by
       this probe in 1/10th degrees C. 0x80000000 denotes 'unknown'."
  ::= { temperatureProbeEntry 7 }

  monitoredTemperatureNormalMinimum OBJECT-TYPE
    SYNTAX  INTEGER
    ACCESS  read-only
    STATUS  mandatory
    DESCRIPTION
      "The normal minimum temperature reading of the temperature monitored by
       this probe in 1/10th degrees C. 0x80000000 denotes 'unknown'."
  ::= { temperatureProbeEntry 8 }

  temperatureProbeMaximum OBJECT-TYPE
    SYNTAX  INTEGER
    ACCESS  read-only
    STATUS  mandatory
    DESCRIPTION
      "The maximum temperature reading specified to be readable by this probe in
       1/10th degrees C. 0x80000000 denotes 'unknown'."
  ::= { temperatureProbeEntry 9 }

  temperatureProbeMinimum OBJECT-TYPE
    SYNTAX  INTEGER
    ACCESS  read-only
    STATUS  mandatory
    DESCRIPTION
      "The minimum temperature reading specified to be readable by this probe in
       1/10th degrees C. 0x80000000 denotes 'unknown'."
  ::= { temperatureProbeEntry 10 }

  temperatureReadingLowerThreshold-Non-Critical OBJECT-TYPE
    SYNTAX  INTEGER
    ACCESS  read-only
    STATUS  mandatory
    DESCRIPTION
      "The lower non-critical threshold for the temperature reading set by the
       user, in 1/10th degrees C. 0x80000000 denotes 'unknown'."
  ::= { temperatureProbeEntry 11 }

  temperatureReadingUpperThreshold-Non-Critical OBJECT-TYPE
    SYNTAX  INTEGER
    ACCESS  read-only
    STATUS  mandatory
    DESCRIPTION
      "The upper non-critical threshold for the temperature probe, in 1/10th
       degrees C. 0x80000000 denotes 'unknown'."
  ::= { temperatureProbeEntry 12 }

  temperatureReadingLowerThreshold-Critical OBJECT-TYPE
    SYNTAX  INTEGER
    ACCESS  read-only
    STATUS  mandatory
    DESCRIPTION
      "The lower critical threshold for the temperature probe, in 1/10 degrees
       C. 0x80000000 denotes 'unknown'."
  ::= { temperatureProbeEntry 13 }

  temperatureReadingUpperThreshold-Critical OBJECT-TYPE
    SYNTAX  INTEGER
    ACCESS  read-only
    STATUS  mandatory
    DESCRIPTION
      "The upper critical threshold for the temperature probe, in /10th degrees
       C. 0x80000000 denotes 'unknown'."
  ::= { temperatureProbeEntry 14 }

  temperatureReadingLowerThreshold-Non-Recoverable OBJECT-TYPE
    SYNTAX  INTEGER
    ACCESS  read-only
    STATUS  mandatory
    DESCRIPTION
      "The lower non-recoverable threshold for the temperature probe, in 1/10th
       degrees C. 0x80000000 denotes 'unknown'."
  ::= { temperatureProbeEntry 15 }

  temperatureReadingUpperThreshold-Non-Recoverable OBJECT-TYPE
    SYNTAX  INTEGER
    ACCESS  read-only
    STATUS  mandatory
    DESCRIPTION
      "The upper non-recoverable threshold for the temperature probe, in 1/10th
       degrees C. 0x80000000 denotes 'unknown'."
  ::= { temperatureProbeEntry 16 }

  temperatureProbeResolution OBJECT-TYPE
    SYNTAX  INTEGER
    ACCESS  read-only
    STATUS  mandatory
    DESCRIPTION
      "The resolution for the reading from this temperature probe, in tenths of
       1/10th degrees C. '0x80000000 denotes 'unknown'."
  ::= { temperatureProbeEntry 17 }

  temperatureProbeTolerance OBJECT-TYPE
    SYNTAX  INTEGER
    ACCESS  read-only
    STATUS  mandatory
    DESCRIPTION
      "The tolerance for the reading from this temperature probe, in plus/minus
       1/10 degrees C. 0x80000000 denotes 'unknown'."
  ::= { temperatureProbeEntry 18 }

  temperatureProbeAccuracy OBJECT-TYPE
    SYNTAX  INTEGER
    ACCESS  read-only
    STATUS  mandatory
    DESCRIPTION
      "The accuracy for the reading from this temperature probe, in plus/minus
       hundredths of a percent. 0x80000000 denotes 'unknown' or 'unsupported'."
  ::= { temperatureProbeEntry 19 }

  fruGroupIndex OBJECT-TYPE
    SYNTAX  INTEGER
    ACCESS  read-only
    STATUS  mandatory
    DESCRIPTION
      "Index into the FRU table. A value of -1 indicates that this device is not
       an FRU."
  ::= { temperatureProbeEntry 20 }

  operationalGroupIndex OBJECT-TYPE
    SYNTAX  INTEGER
    ACCESS  read-only
    STATUS  mandatory
    DESCRIPTION
      "Index into the Operational State table."
  ::= { temperatureProbeEntry 21 }


--------------------------------------------------------------------------------
  memoryInfo OBJECT-TYPE
    SYNTAX  MemoryInfo
    ACCESS  not-accessible
    STATUS  mandatory
DESCRIPTION ""
  ::= { hitachiSM-SAGroupsDefinition 202 }

  MemoryInfo ::= SEQUENCE
  {
    totalPhysicalMemorySize   INTEGER,
    totalPageFileSize         INTEGER,
    eccErrorCount             Counter,
    eccSbcAddress             OCTET STRING,
    eccUncAddress             OCTET STRING
  }

  totalPhysicalMemorySize OBJECT-TYPE
    SYNTAX  INTEGER
    ACCESS  read-only
    STATUS  mandatory
    DESCRIPTION
      "The total size of the physical memory in bytes."
  ::= { memoryInfo 1 }

  totalPageFileSize OBJECT-TYPE
    SYNTAX  INTEGER
    ACCESS  read-only
    STATUS  mandatory
    DESCRIPTION
      "The total Page File Size of the physical memory in bytes."
  ::= { memoryInfo 2 }

  eccErrorCount OBJECT-TYPE
    SYNTAX  Counter
    ACCESS  read-only
    STATUS  mandatory
    DESCRIPTION
      "Ecc Error Count."
  ::= { memoryInfo 3 }

  eccSbcAddress OBJECT-TYPE
    SYNTAX  OCTET STRING (SIZE(1..8))
    ACCESS  read-only
    STATUS  mandatory
    DESCRIPTION
      "Ecc Sbc Address. It is indicated by a 8bytes value laid out as big endian
       (byte 0 is the most significant, byte 7 is the least significant)."
  ::= { memoryInfo 4 }

  eccUncAddress OBJECT-TYPE
    SYNTAX  OCTET STRING (SIZE(1..8))
    ACCESS  read-only
    STATUS  mandatory
    DESCRIPTION
      "Ecc Unc Address. It is indicated by a 8bytes value laid out as big endian
       (byte 0 is the most significant, byte 7 is the least significant)."
  ::= { memoryInfo 5 }


--------------------------------------------------------------------------------
  driveInfo OBJECT IDENTIFIER ::= { hitachiSM-SAGroupsDefinition 203 }

  driveInfoTable OBJECT-TYPE
    SYNTAX  SEQUENCE OF DriveInfo
    ACCESS  not-accessible
    STATUS  mandatory
DESCRIPTION ""
  ::= { driveInfo 1 }

  driveInfoEntry OBJECT-TYPE
    SYNTAX  DriveInfo
    ACCESS  not-accessible
    STATUS  mandatory
DESCRIPTION ""
    INDEX   { logicalDriveIndex }
  ::= { driveInfoTable 1 }

  DriveInfo ::= SEQUENCE
  {
    logicalDriveIndex   INTEGER,
    partitionType       DisplayString,
    fdType              DisplayString
  }

  logicalDriveIndex OBJECT-TYPE
    SYNTAX  INTEGER
    ACCESS  read-only
    STATUS  mandatory
    DESCRIPTION
      "An index into the Logical Drive table."
  ::= { driveInfoEntry 1 }

  partitionType OBJECT-TYPE
    SYNTAX  DisplayString (SIZE (1..8))
    ACCESS  read-only
    STATUS  mandatory
    DESCRIPTION
      "Partition Type. It is expressed in the form of string(ASCII Code)."
  ::= { driveInfoEntry 2 }

  fdType OBJECT-TYPE
    SYNTAX  DisplayString (SIZE (1..64))
    ACCESS  read-only
    STATUS  mandatory
    DESCRIPTION
      "Detail floppy disk type. It is expressed in the form of string
       (ASCII Code)."
  ::= { driveInfoEntry 3 }


--------------------------------------------------------------------------------
  cpuSlotsInfo OBJECT IDENTIFIER ::= { hitachiSM-SAGroupsDefinition 204 }

  cpuSlotsInfoTable OBJECT-TYPE
    SYNTAX  SEQUENCE OF CpuSlotsInfo
    ACCESS  not-accessible
    STATUS  mandatory
DESCRIPTION ""
  ::= { cpuSlotsInfo 1 }

  cpuSlotsInfoEntry OBJECT-TYPE
    SYNTAX  CpuSlotsInfo
    ACCESS  not-accessible
    STATUS  mandatory
DESCRIPTION ""
    INDEX   { processorIndex }
  ::= { cpuSlotsInfoTable 1 }

  CpuSlotsInfo ::= SEQUENCE
  {
    processorIndex      INTEGER,
    cpuExistence        INTEGER,
    coprocessorName     DisplayString,
    coolingDeviceIndex  INTEGER,
    slotExistence       INTEGER
  }

  processorIndex OBJECT-TYPE
    SYNTAX  INTEGER
    ACCESS  read-only
    STATUS  mandatory
    DESCRIPTION
      "An index into the processor table."
  ::= { cpuSlotsInfoEntry 1 }

  cpuExistence OBJECT-TYPE
    SYNTAX  INTEGER
    ACCESS  read-only
    STATUS  mandatory
    DESCRIPTION
      "Wearing state of CPU. It is indicated by a integer value as follows 
       (hexadecimal).
         0x00 = Unknown
         0x01 = Wearing
         0x02 = Non Wearing"
  ::= { cpuSlotsInfoEntry 2 }

  coprocessorName OBJECT-TYPE
    SYNTAX  DisplayString (SIZE (1..32))
    ACCESS  read-only
    STATUS  mandatory
    DESCRIPTION
      "Coprocessor Name. It is expressed in the form of string(ASCII Code)."
  ::= { cpuSlotsInfoEntry 3 }

  coolingDeviceIndex OBJECT-TYPE
    SYNTAX  INTEGER
    ACCESS  read-only
    STATUS  mandatory
    DESCRIPTION
      "Cooling Device Index."
  ::= { cpuSlotsInfoEntry 4 }

  slotExistence OBJECT-TYPE
    SYNTAX  INTEGER
    ACCESS  read-only
    STATUS  mandatory
    DESCRIPTION
      "Slot Existence. It is indicated by a integer value as follows 
       (hexadecimal).
         0x00 = Unknown
         0x01 = TRUE
         0x02 = FALSE"
  ::= { cpuSlotsInfoEntry 5 }


--------------------------------------------------------------------------------
  rasDriverInfo OBJECT-TYPE
    SYNTAX  RasDriverInfo
    ACCESS  not-accessible
    STATUS  mandatory
DESCRIPTION ""
  ::= { hitachiSM-SAGroupsDefinition 205 }

  RasDriverInfo ::= SEQUENCE
  {
    rasDriverVersion  DisplayString
  }

  rasDriverVersion OBJECT-TYPE
    SYNTAX  DisplayString (SIZE (1..11))
    ACCESS  read-only
    STATUS  mandatory
    DESCRIPTION
      "RAS Driver Version. It is expressed in the form of string(ASCII Code)."
  ::= { rasDriverInfo 1 }


--------------------------------------------------------------------------------
  additionalUpsInfo OBJECT-TYPE
    SYNTAX  AdditionalUpsInfo
    ACCESS  not-accessible
    STATUS  mandatory
DESCRIPTION ""
  ::= { hitachiSM-SAGroupsDefinition 206 }

  AdditionalUpsInfo ::= SEQUENCE
  {
    batteryChargingStatus   INTEGER
  }

  batteryChargingStatus OBJECT-TYPE
    SYNTAX  INTEGER
    ACCESS  read-only
    STATUS  mandatory
    DESCRIPTION
      "Battery Charging Status. It is indicated by a integer value as follows 
       (hexadecimal).
         0x00 = Unknown
         0x01 = Charging
         0x02 = Non Charging"
  ::= { additionalUpsInfo 1 }


--------------------------------------------------------------------------------
  powerUnitInfo OBJECT IDENTIFIER ::= { hitachiSM-SAGroupsDefinition 207 }

  powerUnitInfoTable OBJECT-TYPE
    SYNTAX  SEQUENCE OF PowerUnitInfo
    ACCESS  not-accessible
    STATUS  mandatory
DESCRIPTION ""
  ::= { powerUnitInfo 1 }

  powerUnitInfoEntry OBJECT-TYPE
    SYNTAX  PowerUnitInfo
    ACCESS  not-accessible
    STATUS  mandatory
DESCRIPTION ""
    INDEX   { powerSupplyIndex }
  ::= { powerUnitInfoTable 1 }

  PowerUnitInfo ::= SEQUENCE
  {
    powerSupplyIndex  INTEGER,
    unitExistence     INTEGER
  }

  powerSupplyIndex OBJECT-TYPE
    SYNTAX  INTEGER
    ACCESS  read-only
    STATUS  mandatory
    DESCRIPTION
      "The index number of the current power supply."
  ::= { powerUnitInfoEntry 1 }

  unitExistence OBJECT-TYPE
    SYNTAX  INTEGER
    ACCESS  read-only
    STATUS  mandatory
    DESCRIPTION
      "Unit Existence. It is indicated by a integer value as follows 
       (hexadecimal).
         0x00 = Unknown
         0x01 = Wearing
         0x02 = Non Wearing"
  ::= { powerUnitInfoEntry 2 }


--------------------------------------------------------------------------------
  pciSlotsInfo OBJECT-TYPE
    SYNTAX  PciSlotsInfo
    ACCESS  not-accessible
    STATUS  mandatory
DESCRIPTION ""
  ::= { hitachiSM-SAGroupsDefinition 208 }

  PciSlotsInfo ::= SEQUENCE
  {
    primaryPciDeviceNumber    INTEGER,
    primaryPciStatus          INTEGER,
    secondlyPciDeviceNumber   INTEGER,
    secondlyPciStatus         INTEGER
  }

  primaryPciDeviceNumber OBJECT-TYPE
    SYNTAX  INTEGER
    ACCESS  read-only
    STATUS  mandatory
    DESCRIPTION
      "Primary PCI Device Number."
  ::= { pciSlotsInfo 1 }

  primaryPciStatus OBJECT-TYPE
    SYNTAX  INTEGER
    ACCESS  read-only
    STATUS  mandatory
    DESCRIPTION
      "Primary PCI Status. It is indicated by a integer value as follows 
       (hexadecimal).
         0x00 = Unknown
         0x01 = Normality
         0x02 = Parity Error
         0x03 = System Error"
  ::= { pciSlotsInfo 2 }

  secondlyPciDeviceNumber OBJECT-TYPE
    SYNTAX  INTEGER
    ACCESS  read-only
    STATUS  mandatory
    DESCRIPTION
      "Secondly PCI Device Number."
  ::= { pciSlotsInfo 3 }

  secondlyPciStatus OBJECT-TYPE
    SYNTAX  INTEGER
    ACCESS  read-only
    STATUS  mandatory
    DESCRIPTION
      "Secondly PCI Status. It is indicated by a integer value as follows 
       (hexadecimal).
         0x00 = Unknown
         0x01 = Normality
         0x02 = Parity Error
         0x03 = System Error"
  ::= { pciSlotsInfo 4 }


--------------------------------------------------------------------------------
  pciDevicesInfo OBJECT IDENTIFIER ::= { hitachiSM-SAGroupsDefinition 209 }

  pciDevicesInfoTable OBJECT-TYPE
    SYNTAX  SEQUENCE OF PciDevicesInfo
    ACCESS  not-accessible
    STATUS  mandatory
DESCRIPTION ""
  ::= { pciDevicesInfo 1 }

  pciDevicesInfoEntry OBJECT-TYPE
    SYNTAX  PciDevicesInfo
    ACCESS  not-accessible
    STATUS  mandatory
DESCRIPTION ""
    INDEX   { deviceIndex }
  ::= { pciDevicesInfoTable 1 }

  PciDevicesInfo ::= SEQUENCE
  {
    deviceIndex     INTEGER,
    slotExistence   INTEGER,
    slotJointBoard  INTEGER,
    slotStatus      INTEGER,
    deviceId        INTEGER,
    vendorId        INTEGER,
    fuseStatus      INTEGER,
    deviceName      INTEGER,
    vendorName      INTEGER
  }

  deviceIndex OBJECT-TYPE
    SYNTAX  INTEGER
    ACCESS  read-only
    STATUS  mandatory
    DESCRIPTION
      "Device Index."
  ::= { pciDevicesInfoEntry 1 }

  slotExistence OBJECT-TYPE
    SYNTAX  INTEGER
    ACCESS  read-only
    STATUS  mandatory
    DESCRIPTION
      "Slot Existence. It is indicated by a integer value as follows 
       (hexadecimal).
         0x00 = Unknown
         0x01 = TRUE
         0x02 = FALSE"
  ::= { pciDevicesInfoEntry 2 }

  slotJointBoard OBJECT-TYPE
    SYNTAX  INTEGER
    ACCESS  read-only
    STATUS  mandatory
    DESCRIPTION
      "Slot Joint Board. It is indicated by a integer value as follows 
       (hexadecimal).
         0x00 = Unknown
         0x01 = Connection
         0x02 = Non Connection"
  ::= { pciDevicesInfoEntry 3 }

  slotStatus OBJECT-TYPE
    SYNTAX  INTEGER
    ACCESS  read-only
    STATUS  mandatory
    DESCRIPTION
      "Status ID. It is indicated by a integer value as follows (hexadecimal).
         0x00 = Unknown
         0x01 = Normality
         0x02 = Parity Error
         0x03 = System Error"
  ::= { pciDevicesInfoEntry 4 }

  deviceId OBJECT-TYPE
    SYNTAX  INTEGER
    ACCESS  read-only
    STATUS  mandatory
    DESCRIPTION
      "Device ID."
  ::= { pciDevicesInfoEntry 5 }

  vendorId OBJECT-TYPE
    SYNTAX  INTEGER
    ACCESS  read-only
    STATUS  mandatory
    DESCRIPTION
      "Vendor ID."
  ::= { pciDevicesInfoEntry 6 }

  fuseStatus OBJECT-TYPE
    SYNTAX  INTEGER
    ACCESS  read-only
    STATUS  mandatory
    DESCRIPTION
      "Fuse Status. It is indicated by a integer value as follows (hexadecimal).
         0x00 = Unknown
         0x01 = TRUE
         0x02 = FALSE"
  ::= { pciDevicesInfoEntry 7 }

  deviceName OBJECT-TYPE
    SYNTAX  INTEGER
    ACCESS  read-only
    STATUS  mandatory
    DESCRIPTION
      "PCI Device Name. It is indicated by a integer value as follows 
       (hexadecimal).
         0x00 = Unknown
         0x01 = Graphic Board Standard
         0x02 = Graphic Board PC-CV7100
         0x03 = SCSI Board PC-CS7200
         0x04 = SCSI Board PC-CS7220
         0x05 = SCSI Board PC-CS7231
         0x06 = SCSI Board PC-CS7232
         0x07 = LAN Board PC-CN7200
         0x08 = LAN Board PC-CN7220
         0x09 = LAN Board PC-CN7310
         0x0A = LAN Board PC-CN7320
         0x0B = LAN Board PC-CN7420
         0x0C = Disk Array Controller Board PC-CA7100
         0x0D = Disk Array Controller Board PC-CA7112
         0x0E = Mirrored Server Link Kit PC-EM7310
         0x0F = SVP Board PC-CM7100/PC-CM7100A
         0x10 = SCSI Board PC-CS7241
         0x11 = Multi Communication Box PC-CR7800"
  ::= { pciDevicesInfoEntry 8 }

  vendorName OBJECT-TYPE
    SYNTAX  INTEGER
    ACCESS  read-only
    STATUS  mandatory
    DESCRIPTION
      "PCI Vendor Name. It is indicated by a integer value as follows 
       (hexadecimal).
         0x00 = Unknown
         0x01 = Cirrus
         0x02 = S3
         0x03 = Symbios
         0x04 = AMD
         0x05 = 3COM
         0x06 = DEC
         0x07 = Adaptec
         0x08 = Mylex
         0x09 = Intel
         0x0A = Hitachi
         0x0B = Digi"
  ::= { pciDevicesInfoEntry 9 }


--------------------------------------------------------------------------------
  eisaDevicesInfo OBJECT IDENTIFIER ::= { hitachiSM-SAGroupsDefinition 210 }

  eisaDevicesInfoTable OBJECT-TYPE
    SYNTAX  SEQUENCE OF EisaDevicesInfo
    ACCESS  not-accessible
    STATUS  mandatory
DESCRIPTION ""
  ::= { eisaDevicesInfo 1 }

  eisaDevicesInfoEntry OBJECT-TYPE
    SYNTAX  EisaDevicesInfo
    ACCESS  not-accessible
    STATUS  mandatory
DESCRIPTION ""
    INDEX   { deviceIndex }
  ::= { eisaDevicesInfoTable 1 }

  EisaDevicesInfo ::= SEQUENCE
  {
    deviceIndex     INTEGER,
    slotExistence   INTEGER,
    slotJointBoard  INTEGER,
    slotStatus      INTEGER,
    compressedId    INTEGER,
    deviceName      INTEGER,
    vendorName      INTEGER
  }

  deviceIndex OBJECT-TYPE
    SYNTAX  INTEGER
    ACCESS  read-only
    STATUS  mandatory
    DESCRIPTION
      "Device Index."
  ::= { eisaDevicesInfoEntry 1 }

  slotExistence OBJECT-TYPE
    SYNTAX  INTEGER
    ACCESS  read-only
    STATUS  mandatory
    DESCRIPTION
      "Slot Existence. It is indicated by a integer value as follows 
       (hexadecimal).
         0x00 = Unknown
         0x01 = TRUE
         0x02 = FALSE"
  ::= { eisaDevicesInfoEntry 2 }

  slotJointBoard OBJECT-TYPE
    SYNTAX  INTEGER
    ACCESS  read-only
    STATUS  mandatory
    DESCRIPTION
      "Slot Joint Board. It is indicated by a integer value as follows 
       (hexadecimal).
         0x00 = Unknown
         0x01 = Connection
         0x02 = Non Connection"
  ::= { eisaDevicesInfoEntry 3 }

  slotStatus OBJECT-TYPE
    SYNTAX  INTEGER
    ACCESS  read-only
    STATUS  mandatory
    DESCRIPTION
      "Slot Status. It is indicated by a integer value as follows (hexadecimal).
         0x00 = Unknown
         0x01 = TRUE
         0x02 = FALSE"
  ::= { eisaDevicesInfoEntry 4 }

  compressedId OBJECT-TYPE
    SYNTAX  INTEGER
    ACCESS  read-only
    STATUS  mandatory
    DESCRIPTION
      "Compressd ID."
  ::= { eisaDevicesInfoEntry 5 }

  deviceName OBJECT-TYPE
    SYNTAX  INTEGER
    ACCESS  read-only
    STATUS  mandatory
    DESCRIPTION
      "EISA Device Name. It is indicated by a integer value as follows 
       (hexadecimal).
         0x00 = Unknown
         0x01 = LAN Board PC-CN2200A
         0x02 = LAN Board PC-CN2200B
         0x03 = LAN Board PC-CN2200C
         0x04 = LAN Board PC-CN5200
         0x05 = ISDN Board PC-CI2200
         0x06 = ISDN Board Set PC-SHT4840-IS
         0x07 = Communication Board PC-CH2100
         0x08 = Multi Communication Box PC-CR5800
         0x09 = RS-232C/Parallel Board PC-CZ1100
         0x0A = SCSI Board PC-CS5600
         0x0B = Disk Array Board
         0x0C = Character recognition Board PC-EP1200
         0x0D = SVP Board PC-CM5100/PC-CM5100A/PC-CM5100B"
  ::= { eisaDevicesInfoEntry 6 }

  vendorName OBJECT-TYPE
    SYNTAX  INTEGER
    ACCESS  read-only
    STATUS  mandatory
    DESCRIPTION
      "EISA Vendor Name. It is indicated by a integer value as follows 
       (hexadecimal).
         0x00 = Unknown
         0x01 = Novel
         0x02 = Unknown (ISA Board)
         0x03 = Adaptec
         0x04 = Hitachi
         0x05 = Mylex
         0x06 = Digi"
  ::= { eisaDevicesInfoEntry 7 }


--------------------------------------------------------------------------------
  bodyFanInfo OBJECT IDENTIFIER ::= { hitachiSM-SAGroupsDefinition 211 }

  bodyFanInfoTable OBJECT-TYPE
    SYNTAX  SEQUENCE OF BodyFanInfo
    ACCESS  not-accessible
    STATUS  mandatory
DESCRIPTION ""
  ::= { bodyFanInfo 1 }

  bodyFanInfoEntry OBJECT-TYPE
    SYNTAX  BodyFanInfo
    ACCESS  not-accessible
    STATUS  mandatory
DESCRIPTION ""
    INDEX   { bodyFanIndex }
  ::= { bodyFanInfoTable 1 }

  BodyFanInfo ::= SEQUENCE
  {
    bodyFanIndex        INTEGER,
    coolingDeviceIndex  INTEGER,
    bodyFanExistence    INTEGER
  }

  bodyFanIndex OBJECT-TYPE
    SYNTAX  INTEGER
    ACCESS  read-only
    STATUS  mandatory
    DESCRIPTION
      "Body Fan Index."
  ::= { bodyFanInfoEntry 1 }

  coolingDeviceIndex OBJECT-TYPE
    SYNTAX  INTEGER
    ACCESS  read-only
    STATUS  mandatory
    DESCRIPTION
      "Cooling Device Index."
  ::= { bodyFanInfoEntry 2 }

  bodyFanExistence OBJECT-TYPE
    SYNTAX  INTEGER
    ACCESS  read-only
    STATUS  mandatory
    DESCRIPTION
      "Wearing state of Body Fan. It is indicated by a integer value as follows 
       (hexadecimal).
         0x00 = Unknown
         0x01 = Wearing
         0x02 = Non Wearing"
  ::= { bodyFanInfoEntry 3 }


--------------------------------------------------------------------------------
  memorySlotInfo OBJECT IDENTIFIER ::= { hitachiSM-SAGroupsDefinition 212 }

  memorySlotInfoTable OBJECT-TYPE
    SYNTAX  SEQUENCE OF MemorySlotInfo
    ACCESS  not-accessible
    STATUS  mandatory
DESCRIPTION ""
  ::= { memorySlotInfo 1 }

  memorySlotInfoEntry OBJECT-TYPE
    SYNTAX  MemorySlotInfo
    ACCESS  not-accessible
    STATUS  mandatory
DESCRIPTION ""
    INDEX   { memoryDeviceTableIndex }
  ::= { memorySlotInfoTable 1 }

  MemorySlotInfo ::= SEQUENCE
  {
    memoryDeviceTableIndex  INTEGER,
    slotStatus              INTEGER,
    memoryArrayTableIndex   INTEGER
  }

  memoryDeviceTableIndex OBJECT-TYPE
    SYNTAX  INTEGER
    ACCESS  read-only
    STATUS  mandatory
    DESCRIPTION
      "A unique number that identifies this row."
  ::= { memorySlotInfoEntry 1 }

  slotStatus OBJECT-TYPE
    SYNTAX  INTEGER
    ACCESS  read-only
    STATUS  mandatory
    DESCRIPTION
      "Slot Status. It is indicated by a integer value as follows (hexadecimal).
         0x00 = Unknown
         0x01 = TRUE
         0x02 = Non Slot
         0x03 = Non Connection
         0x04 = Disable
         0x05 = ECC Error
         0x06 = Change"
  ::= { memorySlotInfoEntry 2 }

  memoryArrayTableIndex OBJECT-TYPE
    SYNTAX  INTEGER
    ACCESS  read-only
    STATUS  mandatory
    DESCRIPTION
      "Memory Array Table Index."
  ::= { memorySlotInfoEntry 3 }


--------------------------------------------------------------------------------
  scsiPortInfo OBJECT IDENTIFIER ::= { hitachiSM-SAGroupsDefinition 213 }

  scsiPortInfoTable OBJECT-TYPE
    SYNTAX  SEQUENCE OF ScsiPortInfo
    ACCESS  not-accessible
    STATUS  mandatory
DESCRIPTION ""
  ::= { scsiPortInfo 1 }

  scsiPortInfoEntry OBJECT-TYPE
    SYNTAX  ScsiPortInfo
    ACCESS  not-accessible
    STATUS  mandatory
DESCRIPTION ""
    INDEX   { scsiPortIndex }
  ::= { scsiPortInfoTable 1 }

  ScsiPortInfo ::= SEQUENCE
  {
    scsiPortIndex         INTEGER,
    diskControllerIndex   INTEGER,
    driverName            DisplayString
  }

  scsiPortIndex OBJECT-TYPE
    SYNTAX  INTEGER
    ACCESS  read-only
    STATUS  mandatory
    DESCRIPTION
      "SCSI Port Index."
  ::= { scsiPortInfoEntry 1 }

  diskControllerIndex OBJECT-TYPE
    SYNTAX  INTEGER
    ACCESS  read-only
    STATUS  mandatory
    DESCRIPTION
      "Index value used by the system to identify the disk controller."
  ::= { scsiPortInfoEntry 2 }

  driverName OBJECT-TYPE
    SYNTAX  DisplayString (SIZE (1..16))
    ACCESS  read-only
    STATUS  mandatory
    DESCRIPTION
      "Driver Name. It is expressed in the form of string(ASCII Code)."
  ::= { scsiPortInfoEntry 3 }


--------------------------------------------------------------------------------
  scsiBusInfo OBJECT IDENTIFIER ::= { hitachiSM-SAGroupsDefinition 214 }

  scsiBusInfoTable OBJECT-TYPE
    SYNTAX  SEQUENCE OF ScsiBusInfo
    ACCESS  not-accessible
    STATUS  mandatory
DESCRIPTION ""
  ::= { scsiBusInfo 1 }

  scsiBusInfoEntry OBJECT-TYPE
    SYNTAX  ScsiBusInfo
    ACCESS  not-accessible
    STATUS  mandatory
DESCRIPTION ""
    INDEX   { scsiBusIndex }
  ::= { scsiBusInfoTable 1 }

  ScsiBusInfo ::= SEQUENCE
  {
    scsiBusIndex    INTEGER,
    scsiPortIndex   INTEGER
  }

  scsiBusIndex OBJECT-TYPE
    SYNTAX  INTEGER
    ACCESS  read-only
    STATUS  mandatory
    DESCRIPTION
      "SCSI Bus Index."
  ::= { scsiBusInfoEntry 1 }

  scsiPortIndex OBJECT-TYPE
    SYNTAX  INTEGER
    ACCESS  read-only
    STATUS  mandatory
    DESCRIPTION
      "SCSI Port Index."
  ::= { scsiBusInfoEntry 2 }


--------------------------------------------------------------------------------
  scsiDevicesInfo OBJECT IDENTIFIER ::= { hitachiSM-SAGroupsDefinition 215 }

  scsiDevicesInfoTable OBJECT-TYPE
    SYNTAX  SEQUENCE OF ScsiDevicesInfo
    ACCESS  not-accessible
    STATUS  mandatory
DESCRIPTION ""
  ::= { scsiDevicesInfo 1 }

  scsiDevicesInfoEntry OBJECT-TYPE
    SYNTAX  ScsiDevicesInfo
    ACCESS  not-accessible
    STATUS  mandatory
DESCRIPTION ""
    INDEX   { scsiDeviceIndex }
  ::= { scsiDevicesInfoTable 1 }

  ScsiDevicesInfo ::= SEQUENCE
  {
    scsiDeviceIndex           INTEGER,
    scsiPortIndex             INTEGER,
    scsiBusIndex              INTEGER,
    diskIndex                 INTEGER,
    totalUsedTime             Counter,
    totalReadCount            Counter,
    totalWriteCount           Counter,
    totalReadErrors           Counter,
    totalWriteErrors          Counter,
    totalRecoverdReadErrors   Counter,
    totalRecoverdWriteErrors  Counter,
    totalSectorReassignCount  Counter,
    totalBusResetCount        Counter,
    totalBusParityErrors      Counter,
    totalBusPhaseErrors       Counter,
    totalSelectionTimeouts    Counter,
    totalMediumErrors         Counter,
    totalHardErrors           Counter,
    totalResetCount           Counter,
    scsiDeviceType            INTEGER
  }

  scsiDeviceIndex OBJECT-TYPE
    SYNTAX  INTEGER
    ACCESS  read-only
    STATUS  mandatory
    DESCRIPTION
      "SCSI Device Index."
  ::= { scsiDevicesInfoEntry 1 }

  scsiPortIndex OBJECT-TYPE
    SYNTAX  INTEGER
    ACCESS  read-only
    STATUS  mandatory
    DESCRIPTION
      "SCSI Port Index."
  ::= { scsiDevicesInfoEntry 2 }

  scsiBusIndex OBJECT-TYPE
    SYNTAX  INTEGER
    ACCESS  read-only
    STATUS  mandatory
    DESCRIPTION
      "SCSI Bus Index."
  ::= { scsiDevicesInfoEntry 3 }

  diskIndex OBJECT-TYPE
    SYNTAX  INTEGER
    ACCESS  read-only
    STATUS  mandatory
    DESCRIPTION
      "An index into the disk table."
  ::= { scsiDevicesInfoEntry 4 }

  totalUsedTime OBJECT-TYPE
    SYNTAX  Counter
    ACCESS  read-only
    STATUS  mandatory
    DESCRIPTION
      "Total Used Time."
  ::= { scsiDevicesInfoEntry 5 }

  totalReadCount OBJECT-TYPE
    SYNTAX  Counter
    ACCESS  read-only
    STATUS  mandatory
    DESCRIPTION
      "Total Read Count."
  ::= { scsiDevicesInfoEntry 6 }

  totalWriteCount OBJECT-TYPE
    SYNTAX  Counter
    ACCESS  read-only
    STATUS  mandatory
    DESCRIPTION
      "Total Write Count."
  ::= { scsiDevicesInfoEntry 7 }

  totalReadErrors OBJECT-TYPE
    SYNTAX  Counter
    ACCESS  read-only
    STATUS  mandatory
    DESCRIPTION
      "Total Read Errors."
  ::= { scsiDevicesInfoEntry 8 }

  totalWriteErrors OBJECT-TYPE
    SYNTAX  Counter
    ACCESS  read-only
    STATUS  mandatory
    DESCRIPTION
      "Total Write Errors."
  ::= { scsiDevicesInfoEntry 9 }

  totalRecoverdReadErrors OBJECT-TYPE
    SYNTAX  Counter
    ACCESS  read-only
    STATUS  mandatory
    DESCRIPTION
      "Total Recoverd Read Errors."
  ::= { scsiDevicesInfoEntry 10 }

  totalRecoverdWriteErrors OBJECT-TYPE
    SYNTAX  Counter
    ACCESS  read-only
    STATUS  mandatory
    DESCRIPTION
      "Total Recoverd Write Errors."
  ::= { scsiDevicesInfoEntry 11 }

  totalSectorReassignCount OBJECT-TYPE
    SYNTAX  Counter
    ACCESS  read-only
    STATUS  mandatory
    DESCRIPTION
      "Total Sector Reassign Count."
  ::= { scsiDevicesInfoEntry 12 }

  totalBusResetCount OBJECT-TYPE
    SYNTAX  Counter
    ACCESS  read-only
    STATUS  mandatory
    DESCRIPTION
      "Total Bus Reset Count."
  ::= { scsiDevicesInfoEntry 13 }

  totalBusParityErrors OBJECT-TYPE
    SYNTAX  Counter
    ACCESS  read-only
    STATUS  mandatory
    DESCRIPTION
      "Total Bus Parity Errors."
  ::= { scsiDevicesInfoEntry 14 }

  totalBusPhaseErrors OBJECT-TYPE
    SYNTAX  Counter
    ACCESS  read-only
    STATUS  mandatory
    DESCRIPTION
      "Total Bus Phase Errors."
  ::= { scsiDevicesInfoEntry 15 }

  totalSelectionTimeouts OBJECT-TYPE
    SYNTAX  Counter
    ACCESS  read-only
    STATUS  mandatory
    DESCRIPTION
      "Total Selection Timeouts."
  ::= { scsiDevicesInfoEntry 16 }

  totalMediumErrors OBJECT-TYPE
    SYNTAX  Counter
    ACCESS  read-only
    STATUS  mandatory
    DESCRIPTION
      "Total Medium Errors."
  ::= { scsiDevicesInfoEntry 17 }

  totalHardErrors OBJECT-TYPE
    SYNTAX  Counter
    ACCESS  read-only
    STATUS  mandatory
    DESCRIPTION
      "Total Hard Errors."
  ::= { scsiDevicesInfoEntry 18 }

  totalResetCount OBJECT-TYPE
    SYNTAX  Counter
    ACCESS  read-only
    STATUS  mandatory
    DESCRIPTION
      "Total Reset Count."
  ::= { scsiDevicesInfoEntry 19 }

  scsiDeviceType OBJECT-TYPE
    SYNTAX  INTEGER
    ACCESS  read-only
    STATUS  mandatory
    DESCRIPTION
      "SCSI Device Type. It is indicated by a integer value as follows 
       (hexadecimal).
         0x00 = Unknown
         0x01 = DIRECT ACCESS DEVICE
         0x02 = SEQUENTIAL ACCESS DEVICE
         0x03 = PRINTER DEVICE
         0x04 = PROCESSOR DEVICE
         0x05 = WRITE ONCE READ MULTIPLE DEVICE
         0x06 = READ ONLY DIRECT ACCESS DEVICE
         0x07 = SCANNER DEVICE
         0x08 = OPTICAL DEVICE
         0x09 = MEDIUM CHANGER
         0x0A = COMMUNICATION DEVICE
         0x0B = DISK ARRAY"
  ::= { scsiDevicesInfoEntry 20 }


--------------------------------------------------------------------------------
  resourceInfo OBJECT IDENTIFIER ::= { hitachiSM-SAGroupsDefinition 218 }

  resourceInfoTable OBJECT-TYPE
    SYNTAX  SEQUENCE OF ResourceInfo
    ACCESS  not-accessible
    STATUS  mandatory
DESCRIPTION ""
  ::= { resourceInfo 1 }

  resourceInfoEntry OBJECT-TYPE
    SYNTAX  ResourceInfo
    ACCESS  not-accessible
    STATUS  mandatory
DESCRIPTION ""
    INDEX   { systemResourcesIndex }
  ::= { resourceInfoTable 1 }

  ResourceInfo ::= SEQUENCE
  {
    systemResourcesIndex  INTEGER,
    userName              DisplayString
  }

  systemResourcesIndex OBJECT-TYPE
    SYNTAX  INTEGER
    ACCESS  read-only
    STATUS  mandatory
    DESCRIPTION
      "A number that uniquely identifies the rows in this table."
  ::= { resourceInfoEntry 1 }

  userName OBJECT-TYPE
    SYNTAX  DisplayString (SIZE (1..260))
    ACCESS  read-only
    STATUS  mandatory
    DESCRIPTION
      "User Name. It is expressed in the form of string(ASCII Code)."
  ::= { resourceInfoEntry 2 }


--------------------------------------------------------------------------------
  propertyInfo OBJECT-TYPE
    SYNTAX  PropertyInfo
    ACCESS  not-accessible
    STATUS  mandatory
DESCRIPTION ""
  ::= { hitachiSM-SAGroupsDefinition 219 }

  PropertyInfo ::= SEQUENCE
  {
    productName   DisplayString,
    makerName     DisplayString,
    serialNumber  DisplayString
  }

  productName OBJECT-TYPE
    SYNTAX  DisplayString (SIZE (1..32))
    ACCESS  read-only
    STATUS  mandatory
    DESCRIPTION
      "Product Name. It is expressed in the form of string(ASCII Code)."
  ::= { propertyInfo 1 }

  makerName OBJECT-TYPE
    SYNTAX  DisplayString (SIZE (1..32))
    ACCESS  read-only
    STATUS  mandatory
    DESCRIPTION
      "Maker Name. It is expressed in the form of string(ASCII Code)."
  ::= { propertyInfo 2 }

  serialNumber OBJECT-TYPE
    SYNTAX  DisplayString (SIZE (1..16))
    ACCESS  read-only
    STATUS  mandatory
    DESCRIPTION
      "Serial Number. It is expressed in the form of string(ASCII Code)."
  ::= { propertyInfo 3 }


--------------------------------------------------------------------------------
  bodyTempInfo OBJECT-TYPE
    SYNTAX  BodyTempInfo
    ACCESS  not-accessible
    STATUS  mandatory
DESCRIPTION ""
  ::= { hitachiSM-SAGroupsDefinition 220 }

  BodyTempInfo ::= SEQUENCE
  {
    temperatureProbeTableIndex  INTEGER
  }

  temperatureProbeTableIndex OBJECT-TYPE
    SYNTAX  INTEGER
    ACCESS  read-only
    STATUS  mandatory
    DESCRIPTION
      "Temperature Probe Table Index."
  ::= { bodyTempInfo 1 }


--------------------------------------------------------------------------------
  powerFanInfo OBJECT IDENTIFIER ::= { hitachiSM-SAGroupsDefinition 221 }

  powerFanInfoTable OBJECT-TYPE
    SYNTAX  SEQUENCE OF PowerFanInfo
    ACCESS  not-accessible
    STATUS  mandatory
DESCRIPTION ""
  ::= { powerFanInfo 1 }

  powerFanInfoEntry OBJECT-TYPE
    SYNTAX  PowerFanInfo
    ACCESS  not-accessible
    STATUS  mandatory
DESCRIPTION ""
    INDEX   { powerFanIndex }
  ::= { powerFanInfoTable 1 }

  PowerFanInfo ::= SEQUENCE
  {
    powerFanIndex       INTEGER,
    coolingDeviceIndex  INTEGER
  }

  powerFanIndex OBJECT-TYPE
    SYNTAX  INTEGER
    ACCESS  read-only
    STATUS  mandatory
    DESCRIPTION
      "Power Fan Index."
  ::= { powerFanInfoEntry 1 }

  coolingDeviceIndex OBJECT-TYPE
    SYNTAX  INTEGER
    ACCESS  read-only
    STATUS  mandatory
    DESCRIPTION
      "Cooling Device Index."
  ::= { powerFanInfoEntry 2 }


--------------------------------------------------------------------------------
  biosPostInfo OBJECT IDENTIFIER ::= { hitachiSM-SAGroupsDefinition 222 }

  biosPostInfoTable OBJECT-TYPE
    SYNTAX  SEQUENCE OF BiosPostInfo
    ACCESS  not-accessible
    STATUS  mandatory
DESCRIPTION ""
  ::= { biosPostInfo 1 }

  biosPostInfoEntry OBJECT-TYPE
    SYNTAX  BiosPostInfo
    ACCESS  not-accessible
    STATUS  mandatory
DESCRIPTION ""
    INDEX   { biosPostLogIndex }
  ::= { biosPostInfoTable 1 }

  BiosPostInfo ::= SEQUENCE
  {
    biosPostLogIndex  INTEGER,
    errorCode         INTEGER,
    occerredTime      DisplayString,
    errorMessage      DisplayString,
    additionalData    INTEGER
  }

  biosPostLogIndex OBJECT-TYPE
    SYNTAX  INTEGER
    ACCESS  read-only
    STATUS  mandatory
    DESCRIPTION
      "BIOS Post Log Index."
  ::= { biosPostInfoEntry 1 }

  errorCode OBJECT-TYPE
    SYNTAX  INTEGER
    ACCESS  read-only
    STATUS  mandatory
    DESCRIPTION
      "Error Code."
  ::= { biosPostInfoEntry 2 }

  occerredTime OBJECT-TYPE
    SYNTAX  DisplayString (SIZE (1..25))
    ACCESS  read-only
    STATUS  mandatory
    DESCRIPTION
      "Occerred Time. It is expressed in the form of string(ASCII Code)."
  ::= { biosPostInfoEntry 3 }

  errorMessage OBJECT-TYPE
    SYNTAX  DisplayString (SIZE (1..128))
    ACCESS  read-only
    STATUS  mandatory
    DESCRIPTION
      "Error Message. It is expressed in the form of string(ASCII Code)."
  ::= { biosPostInfoEntry 4 }

  additionalData OBJECT-TYPE
    SYNTAX  INTEGER
    ACCESS  read-only
    STATUS  mandatory
    DESCRIPTION
      "Additional Data."
  ::= { biosPostInfoEntry 5 }


--------------------------------------------------------------------------------
-- System Manager
-- trap information
--------------------------------------------------------------------------------

  trap                OBJECT IDENTIFIER  ::= { systemManagerMibs   2 }

--------------------------------------------------------------------------------
  general OBJECT-TYPE
    SYNTAX  GeneralEntry
    ACCESS  not-accessible
    STATUS  mandatory
DESCRIPTION ""
  ::= { trap 1 }

  GeneralEntry ::= SEQUENCE
  {
    generalTrapEventComponent           DisplayString,
    generalTrapEventType                INTEGER,
    generalTrapEventSeverity            INTEGER,
    generalTrapEventSystem              INTEGER,
    generalTrapEventSubsystem           INTEGER,
    generalTrapEventClass               DisplayString,
    generalTrapEventInstance            DisplayString,
    generalTrapEventGenerationTime      DisplayString,
    generalTrapEventMessage             DisplayString,
    generalTrapEventSolution            DisplayString,
    generalTrapEventVenderSpecificData  OCTET STRING
  }

  generalTrapEventComponent OBJECT-TYPE
    SYNTAX  DisplayString (SIZE (1..256))
    ACCESS  read-only
    STATUS  mandatory
    DESCRIPTION
      "The component of the event has occurred. It is expressed in the form of
       string(ASCII Code)."
  ::= { general 1 }

  generalTrapEventType OBJECT-TYPE
    SYNTAX  INTEGER
    ACCESS  read-only
    STATUS  mandatory
    DESCRIPTION
      "The type of event that has occurred. If you want to confirm the meaning of
       values, please see the component's specification."
  ::= { general 2 }

  generalTrapEventSeverity OBJECT-TYPE
    SYNTAX  INTEGER
    ACCESS  read-only
    STATUS  mandatory
    DESCRIPTION
      "The severity of this event. It is indicated by a integer value as follows
       (hexadecimal).
         0x001 = Monitor
         0x002 = Information
         0x004 = OK
         0x008 = Non-Critical
         0x010 = Critical
         0x020 = Non-Recoverable"
  ::= { general 3 }

  generalTrapEventSystem OBJECT-TYPE
    SYNTAX  INTEGER
    ACCESS  read-only
    STATUS  mandatory
    DESCRIPTION
      "The major functional aspect of the product causing the fault.
       If you want to confirm the meaning of values, please see the
       component's specification."
  ::= { general 4 }

  generalTrapEventSubsystem OBJECT-TYPE
    SYNTAX  INTEGER
    ACCESS  read-only
    STATUS  mandatory
    DESCRIPTION
      "The minor functional aspect of the product causing the fault.
      If you want to confirm the meaning of values, please see the
      component's specification."
  ::= { general 5 }

  generalTrapEventClass OBJECT-TYPE
    SYNTAX  DisplayString (SIZE (1..256))
    ACCESS  read-only
    STATUS  mandatory
    DESCRIPTION
      "The name of the group that is associated with the event."
  ::= { general 6 }

  generalTrapEventInstance OBJECT-TYPE
    SYNTAX  DisplayString (SIZE (1..256))
    ACCESS  read-only
    STATUS  mandatory
    DESCRIPTION
      "A list of DMI's integer indexes that identify the instance of the
       associated group that actually generated the event. The list of
       integer indexs are represented in the value of this attribute as a string
       containing a comma-separetaed list of integers."
  ::= { general 7 }

  generalTrapEventGenerationTime OBJECT-TYPE
    SYNTAX  DisplayString (SIZE (1..26))
    ACCESS  read-only
    STATUS  mandatory
    DESCRIPTION
      "The time when the event has occurred. It is expressed in the form of
       string(ASCII Code)."
  ::= { general 8 }

  generalTrapEventMessage OBJECT-TYPE
    SYNTAX  DisplayString (SIZE (1..256))
    ACCESS  read-only
    STATUS  mandatory
    DESCRIPTION
      "Auxiliary infomation related to the event."
  ::= { general 9 }

  generalTrapEventSolution OBJECT-TYPE
    SYNTAX  INTEGER
    ACCESS  read-only
    STATUS  mandatory
    DESCRIPTION
      "A solution to the problem that caused the event. If you want to confirm
       the meaning of values, please see the component's specification."
  ::= { general 10 }

  generalTrapEventVenderSpecificData OBJECT-TYPE
    SYNTAX  OCTET STRING (SIZE (1..256))
    ACCESS  read-only
    STATUS  mandatory
    DESCRIPTION
      "Auxiliary information related to the event."
  ::= { general 11 }

--------------------------------------------------------------------------------
  driver OBJECT-TYPE
    SYNTAX  DriverEntry
    ACCESS  not-accessible
    STATUS  mandatory
DESCRIPTION ""
  ::= { trap 2 }

  DriverEntry ::= SEQUENCE
  {
    driverTrapEventID               INTEGER,
    driverTrapEventType             INTEGER,
    driverTrapEventSeverity         INTEGER,
    driverTrapEventSystem           INTEGER,
    driverTrapEventSubsystem        INTEGER,
    driverTrapEventClass            DisplayString,
    driverTrapEventInstance         DisplayString,
    driverTrapEventGenerationTime   DisplayString,
    driverTrapEventMessage          DisplayString
  }

  driverTrapEventID OBJECT-TYPE
    SYNTAX  INTEGER
    ACCESS  read-only
    STATUS  mandatory
    DESCRIPTION
      "The id of event that has occurred."
  ::= { driver 1 }

  driverTrapEventType OBJECT-TYPE
    SYNTAX  INTEGER
    ACCESS  read-only
    STATUS  mandatory
    DESCRIPTION
      "The type of event that has occurred. It is indicated by a integer value
       as follows (hexadecimal).
         0x001 = Dummy"
  ::= { driver 2 }

  driverTrapEventSeverity OBJECT-TYPE
    SYNTAX  INTEGER
    ACCESS  read-only
    STATUS  mandatory
    DESCRIPTION
      "The severity of this event. It is indicated by a integer value as follows
       (hexadecimal).
         0x001 = Monitor
         0x002 = Information
         0x004 = OK
         0x008 = Non-Critical
         0x010 = Critical
         0x020 = Non-Recoverable"
  ::= { driver 3 }

  driverTrapEventSystem OBJECT-TYPE
    SYNTAX  INTEGER
    ACCESS  read-only
    STATUS  mandatory
    DESCRIPTION
      "The major functional aspect of the product causing the fault. It is
       indicated by a integer value as follows (hexadecimal).
         0x000 = Driver
         0x001 = CI
         0x002 = SVP
         0x003 = OS
         0x004 = Body/Power
         0x005 = UPS
         0x006 = SystemBoard
         0x007 = Extended Slot
         0x008 = SCSI
         0x009 = Disk Array
         0x00A = BIOS POST
         0x00B = Cluster
         0x00C = Network"
  ::= { driver 4 }

  driverTrapEventSubsystem OBJECT-TYPE
    SYNTAX  INTEGER
    ACCESS  read-only
    STATUS  mandatory
    DESCRIPTION
      "The minor functional aspect of the product causing the fault.
       This information is useless now(reserved)."
  ::= { driver 5 }

  driverTrapEventClass OBJECT-TYPE
    SYNTAX  DisplayString (SIZE (1..256))
    ACCESS  read-only
    STATUS  mandatory
    DESCRIPTION
      "The name of the group that is associated with the event. It is
       expressed in the form of string(ASCII Code)."
  ::= { driver 6 }

  driverTrapEventInstance OBJECT-TYPE
    SYNTAX  DisplayString (SIZE (1..256))
    ACCESS  read-only
    STATUS  mandatory
    DESCRIPTION
      "A list of DMI's integer indexs that identify the instance of the
       associated group that actually generated the event. The list of
       integer indexs are represented in the value of this attribute as a string
       containing a comma-separetaed list of integers. It is expressed in the
       form of string(ASCII Code)."
  ::= { driver 7 }

  driverTrapEventGenerationTime OBJECT-TYPE
    SYNTAX  DisplayString (SIZE (1..26))
    ACCESS  read-only
    STATUS  mandatory
    DESCRIPTION
      "The time when the event has occurred. It is expressed in the form of
       string(ASCII Code)."
  ::= { driver 8 }

  driverTrapEventMessage OBJECT-TYPE
    SYNTAX  DisplayString (SIZE (1..256))
    ACCESS  read-only
    STATUS  mandatory
    DESCRIPTION
      "Auxiliary infomation related to the event. It is expressed in the form of
       string(in Japanese, Sift JIS Code)."
  ::= { driver 9 }

--------------------------------------------------------------------------------
  ci OBJECT-TYPE
    SYNTAX  CiEntry
    ACCESS  not-accessible
    STATUS  mandatory
DESCRIPTION ""
  ::= { trap 3 }

  CiEntry ::= SEQUENCE
  {
    ciTrapEventID               INTEGER,
    ciTrapEventType             INTEGER,
    ciTrapEventSeverity         INTEGER,
    ciTrapEventSystem           INTEGER,
    ciTrapEventSubsystem        INTEGER,
    ciTrapEventClass            DisplayString,
    ciTrapEventInstance         DisplayString,
    ciTrapEventGenerationTime   DisplayString,
    ciTrapEventMessage          DisplayString
  }

  ciTrapEventID OBJECT-TYPE
    SYNTAX  INTEGER
    ACCESS  read-only
    STATUS  mandatory
    DESCRIPTION
      "The id of event that has occurred."
  ::= { ci 1 }

  ciTrapEventType OBJECT-TYPE
    SYNTAX  INTEGER
    ACCESS  read-only
    STATUS  mandatory
    DESCRIPTION
      "The type of event that has occurred. It is indicated by a integer value
       as follows (hexadecimal).
         0x001 = Dummy"
  ::= { ci 2 }

  ciTrapEventSeverity OBJECT-TYPE
    SYNTAX  INTEGER
    ACCESS  read-only
    STATUS  mandatory
    DESCRIPTION
      "The severity of this event. It is indicated by a integer value as follows
       (hexadecimal).
         0x001 = Monitor
         0x002 = Information
         0x004 = OK
         0x008 = Non-Critical
         0x010 = Critical
         0x020 = Non-Recoverable"
  ::= { ci 3 }

  ciTrapEventSystem OBJECT-TYPE
    SYNTAX  INTEGER
    ACCESS  read-only
    STATUS  mandatory
    DESCRIPTION
      "The major functional aspect of the product causing the fault. It is
       indicated by a integer value as follows (hexadecimal).
         0x000 = Driver
         0x001 = CI
         0x002 = SVP
         0x003 = OS
         0x004 = Body/Power
         0x005 = UPS
         0x006 = SystemBoard
         0x007 = Extended Slot
         0x008 = SCSI
         0x009 = Disk Array
         0x00A = BIOS POST
         0x00B = Cluster
         0x00C = Network"
  ::= { ci 4 }

  ciTrapEventSubsystem OBJECT-TYPE
    SYNTAX  INTEGER
    ACCESS  read-only
    STATUS  mandatory
    DESCRIPTION
      "The minor functional aspect of the product causing the fault.
       This information is useless now(reserved)."
  ::= { ci 5 }

  ciTrapEventClass OBJECT-TYPE
    SYNTAX  DisplayString (SIZE (1..256))
    ACCESS  read-only
    STATUS  mandatory
    DESCRIPTION
      "The name of the group that is associated with the event. It is
       expressed in the form of string(ASCII Code)."
  ::= { ci 6 }

  ciTrapEventInstance OBJECT-TYPE
    SYNTAX  DisplayString (SIZE (1..256))
    ACCESS  read-only
    STATUS  mandatory
    DESCRIPTION
      "A list of DMI's integer indexs that identify the instance of the
       associated group that actually generated the event. The list of
       integer indexs are represented in the value of this attribute as a string
       containing a comma-separetaed list of integers. It is expressed in the
       form of string(ASCII Code)."
  ::= { ci 7 }

  ciTrapEventGenerationTime OBJECT-TYPE
    SYNTAX  DisplayString (SIZE (1..26))
    ACCESS  read-only
    STATUS  mandatory
    DESCRIPTION
      "The time when the event has occurred. It is expressed in the form of
       string(ASCII Code)."
  ::= { ci 8 }

  ciTrapEventMessage OBJECT-TYPE
    SYNTAX  DisplayString (SIZE (1..256))
    ACCESS  read-only
    STATUS  mandatory
    DESCRIPTION
      "Auxiliary infomation related to the event. It is expressed in the form of
       string(in Japanese, Sift JIS Code)."
  ::= { ci 9 }

--------------------------------------------------------------------------------
  svp OBJECT-TYPE
    SYNTAX  SvpEntry
    ACCESS  not-accessible
    STATUS  mandatory
DESCRIPTION ""
  ::= { trap 4 }

  SvpEntry ::= SEQUENCE
  {
    svpTrapEventID               INTEGER,
    svpTrapEventType             INTEGER,
    svpTrapEventSeverity         INTEGER,
    svpTrapEventSystem           INTEGER,
    svpTrapEventSubsystem        INTEGER,
    svpTrapEventClass            DisplayString,
    svpTrapEventInstance         DisplayString,
    svpTrapEventGenerationTime   DisplayString,
    svpTrapEventMessage          DisplayString
  }

  svpTrapEventID OBJECT-TYPE
    SYNTAX  INTEGER
    ACCESS  read-only
    STATUS  mandatory
    DESCRIPTION
      "The id of event that has occurred."
  ::= { svp 1 }

  svpTrapEventType OBJECT-TYPE
    SYNTAX  INTEGER
    ACCESS  read-only
    STATUS  mandatory
    DESCRIPTION
      "The type of event that has occurred. It is indicated by a integer value
       as follows (hexadecimal).
         0x001 = Dummy"
  ::= { svp 2 }

  svpTrapEventSeverity OBJECT-TYPE
    SYNTAX  INTEGER
    ACCESS  read-only
    STATUS  mandatory
    DESCRIPTION
      "The severity of this event. It is indicated by a integer value as follows
       (hexadecimal).
         0x001 = Monitor
         0x002 = Information
         0x004 = OK
         0x008 = Non-Critical
         0x010 = Critical
         0x020 = Non-Recoverable"
  ::= { svp 3 }

  svpTrapEventSystem OBJECT-TYPE
    SYNTAX  INTEGER
    ACCESS  read-only
    STATUS  mandatory
    DESCRIPTION
      "The major functional aspect of the product causing the fault. It is
       indicated by a integer value as follows (hexadecimal).
         0x000 = Driver
         0x001 = CI
         0x002 = SVP
         0x003 = OS
         0x004 = Body/Power
         0x005 = UPS
         0x006 = SystemBoard
         0x007 = Extended Slot
         0x008 = SCSI
         0x009 = Disk Array
         0x00A = BIOS POST
         0x00B = Cluster
         0x00C = Network"
  ::= { svp 4 }

  svpTrapEventSubsystem OBJECT-TYPE
    SYNTAX  INTEGER
    ACCESS  read-only
    STATUS  mandatory
    DESCRIPTION
      "The minor functional aspect of the product causing the fault.
       This information is useless now(reserved)."
  ::= { svp 5 }

  svpTrapEventClass OBJECT-TYPE
    SYNTAX  DisplayString (SIZE (1..256))
    ACCESS  read-only
    STATUS  mandatory
    DESCRIPTION
      "The name of the group that is associated with the event. It is
       expressed in the form of string(ASCII Code)."
  ::= { svp 6 }

  svpTrapEventInstance OBJECT-TYPE
    SYNTAX  DisplayString (SIZE (1..256))
    ACCESS  read-only
    STATUS  mandatory
    DESCRIPTION
      "A list of DMI's integer indexs that identify the instance of the
       associated group that actually generated the event. The list of
       integer indexs are represented in the value of this attribute as a string
       containing a comma-separetaed list of integers. It is expressed in the
       form of string(ASCII Code)."
  ::= { svp 7 }

  svpTrapEventGenerationTime OBJECT-TYPE
    SYNTAX  DisplayString (SIZE (1..26))
    ACCESS  read-only
    STATUS  mandatory
    DESCRIPTION
      "The time when the event has occurred. It is expressed in the form of
       string(ASCII Code)."
  ::= { svp 8 }

  svpTrapEventMessage OBJECT-TYPE
    SYNTAX  DisplayString (SIZE (1..256))
    ACCESS  read-only
    STATUS  mandatory
    DESCRIPTION
      "Auxiliary infomation related to the event. It is expressed in the form of
       string(in Japanese, Sift JIS Code)."
  ::= { svp 9 }

--------------------------------------------------------------------------------
  os OBJECT-TYPE
    SYNTAX  OsEntry
    ACCESS  not-accessible
    STATUS  mandatory
DESCRIPTION ""
  ::= { trap 5 }

  OsEntry ::= SEQUENCE
  {
    osTrapEventID               INTEGER,
    osTrapEventType             INTEGER,
    osTrapEventSeverity         INTEGER,
    osTrapEventSystem           INTEGER,
    osTrapEventSubsystem        INTEGER,
    osTrapEventClass            DisplayString,
    osTrapEventInstance         DisplayString,
    osTrapEventGenerationTime   DisplayString,
    osTrapEventMessage          DisplayString
  }

  osTrapEventID OBJECT-TYPE
    SYNTAX  INTEGER
    ACCESS  read-only
    STATUS  mandatory
    DESCRIPTION
      "The id of event that has occurred."
  ::= { os 1 }

  osTrapEventType OBJECT-TYPE
    SYNTAX  INTEGER
    ACCESS  read-only
    STATUS  mandatory
    DESCRIPTION
      "The type of event that has occurred. It is indicated by a integer value
       as follows (hexadecimal).
         0x001 = Dummy"
  ::= { os 2 }

  osTrapEventSeverity OBJECT-TYPE
    SYNTAX  INTEGER
    ACCESS  read-only
    STATUS  mandatory
    DESCRIPTION
      "The severity of this event. It is indicated by a integer value as follows
       (hexadecimal).
         0x001 = Monitor
         0x002 = Information
         0x004 = OK
         0x008 = Non-Critical
         0x010 = Critical
         0x020 = Non-Recoverable"
  ::= { os 3 }

  osTrapEventSystem OBJECT-TYPE
    SYNTAX  INTEGER
    ACCESS  read-only
    STATUS  mandatory
    DESCRIPTION
      "The major functional aspect of the product causing the fault. It is
       indicated by a integer value as follows (hexadecimal).
         0x000 = Driver
         0x001 = CI
         0x002 = SVP
         0x003 = OS
         0x004 = Body/Power
         0x005 = UPS
         0x006 = SystemBoard
         0x007 = Extended Slot
         0x008 = SCSI
         0x009 = Disk Array
         0x00A = BIOS POST
         0x00B = Cluster
         0x00C = Network"
  ::= { os 4 }

  osTrapEventSubsystem OBJECT-TYPE
    SYNTAX  INTEGER
    ACCESS  read-only
    STATUS  mandatory
    DESCRIPTION
      "The minor functional aspect of the product causing the fault.
       This information is useless now(reserved)."
  ::= { os 5 }

  osTrapEventClass OBJECT-TYPE
    SYNTAX  DisplayString (SIZE (1..256))
    ACCESS  read-only
    STATUS  mandatory
    DESCRIPTION
      "The name of the group that is associated with the event. It is
       expressed in the form of string(ASCII Code)."
  ::= { os 6 }

  osTrapEventInstance OBJECT-TYPE
    SYNTAX  DisplayString (SIZE (1..256))
    ACCESS  read-only
    STATUS  mandatory
    DESCRIPTION
      "A list of DMI's integer indexs that identify the instance of the
       associated group that actually generated the event. The list of
       integer indexs are represented in the value of this attribute as a string
       containing a comma-separetaed list of integers. It is expressed in the
       form of string(ASCII Code)."
  ::= { os 7 }

  osTrapEventGenerationTime OBJECT-TYPE
    SYNTAX  DisplayString (SIZE (1..26))
    ACCESS  read-only
    STATUS  mandatory
    DESCRIPTION
      "The time when the event has occurred. It is expressed in the form of
       string(ASCII Code)."
  ::= { os 8 }

  osTrapEventMessage OBJECT-TYPE
    SYNTAX  DisplayString (SIZE (1..256))
    ACCESS  read-only
    STATUS  mandatory
    DESCRIPTION
      "Auxiliary infomation related to the event. It is expressed in the form of
       string(in Japanese, Sift JIS Code)."
  ::= { os 9 }

--------------------------------------------------------------------------------
  body OBJECT-TYPE
    SYNTAX  BodyEntry
    ACCESS  not-accessible
    STATUS  mandatory
DESCRIPTION ""
  ::= { trap 6 }

  BodyEntry ::= SEQUENCE
  {
    bodyTrapEventID               INTEGER,
    bodyTrapEventType             INTEGER,
    bodyTrapEventSeverity         INTEGER,
    bodyTrapEventSystem           INTEGER,
    bodyTrapEventSubsystem        INTEGER,
    bodyTrapEventClass            DisplayString,
    bodyTrapEventInstance         DisplayString,
    bodyTrapEventGenerationTime   DisplayString,
    bodyTrapEventMessage          DisplayString
  }

  bodyTrapEventID OBJECT-TYPE
    SYNTAX  INTEGER
    ACCESS  read-only
    STATUS  mandatory
    DESCRIPTION
      "The id of event that has occurred."
  ::= { body 1 }

  bodyTrapEventType OBJECT-TYPE
    SYNTAX  INTEGER
    ACCESS  read-only
    STATUS  mandatory
    DESCRIPTION
      "The type of event that has occurred. It is indicated by a integer value
       as follows (hexadecimal).
         0x001 = Dummy"
  ::= { body 2 }

  bodyTrapEventSeverity OBJECT-TYPE
    SYNTAX  INTEGER
    ACCESS  read-only
    STATUS  mandatory
    DESCRIPTION
      "The severity of this event. It is indicated by a integer value as follows
       (hexadecimal).
         0x001 = Monitor
         0x002 = Information
         0x004 = OK
         0x008 = Non-Critical
         0x010 = Critical
         0x020 = Non-Recoverable"
  ::= { body 3 }

  bodyTrapEventSystem OBJECT-TYPE
    SYNTAX  INTEGER
    ACCESS  read-only
    STATUS  mandatory
    DESCRIPTION
      "The major functional aspect of the product causing the fault. It is
       indicated by a integer value as follows (hexadecimal).
         0x000 = Driver
         0x001 = CI
         0x002 = SVP
         0x003 = OS
         0x004 = Body/Power
         0x005 = UPS
         0x006 = SystemBoard
         0x007 = Extended Slot
         0x008 = SCSI
         0x009 = Disk Array
         0x00A = BIOS POST
         0x00B = Cluster
         0x00C = Network"
  ::= { body 4 }

  bodyTrapEventSubsystem OBJECT-TYPE
    SYNTAX  INTEGER
    ACCESS  read-only
    STATUS  mandatory
    DESCRIPTION
      "The minor functional aspect of the product causing the fault.
       This information is useless now(reserved)."
  ::= { body 5 }

  bodyTrapEventClass OBJECT-TYPE
    SYNTAX  DisplayString (SIZE (1..256))
    ACCESS  read-only
    STATUS  mandatory
    DESCRIPTION
      "The name of the group that is associated with the event. It is
       expressed in the form of string(ASCII Code)."
  ::= { body 6 }

  bodyTrapEventInstance OBJECT-TYPE
    SYNTAX  DisplayString (SIZE (1..256))
    ACCESS  read-only
    STATUS  mandatory
    DESCRIPTION
      "A list of DMI's integer indexs that identify the instance of the
       associated group that actually generated the event. The list of
       integer indexs are represented in the value of this attribute as a string
       containing a comma-separetaed list of integers. It is expressed in the
       form of string(ASCII Code)."
  ::= { body 7 }

  bodyTrapEventGenerationTime OBJECT-TYPE
    SYNTAX  DisplayString (SIZE (1..26))
    ACCESS  read-only
    STATUS  mandatory
    DESCRIPTION
      "The time when the event has occurred. It is expressed in the form of
       string(ASCII Code)."
  ::= { body 8 }

  bodyTrapEventMessage OBJECT-TYPE
    SYNTAX  DisplayString (SIZE (1..256))
    ACCESS  read-only
    STATUS  mandatory
    DESCRIPTION
      "Auxiliary infomation related to the event. It is expressed in the form of
       string(in Japanese, Sift JIS Code)."
  ::= { body 9 }

--------------------------------------------------------------------------------
  powerUps OBJECT-TYPE
    SYNTAX  PowerUpsEntry
    ACCESS  not-accessible
    STATUS  mandatory
DESCRIPTION ""
  ::= { trap 7 }

  PowerUpsEntry ::= SEQUENCE
  {
    powerUpsTrapEventID               INTEGER,
    powerUpsTrapEventType             INTEGER,
    powerUpsTrapEventSeverity         INTEGER,
    powerUpsTrapEventSystem           INTEGER,
    powerUpsTrapEventSubsystem        INTEGER,
    powerUpsTrapEventClass            DisplayString,
    powerUpsTrapEventInstance         DisplayString,
    powerUpsTrapEventGenerationTime   DisplayString,
    powerUpsTrapEventMessage          DisplayString
  }

  powerUpsTrapEventID OBJECT-TYPE
    SYNTAX  INTEGER
    ACCESS  read-only
    STATUS  mandatory
    DESCRIPTION
      "The id of event that has occurred."
  ::= { powerUps 1 }

  powerUpsTrapEventType OBJECT-TYPE
    SYNTAX  INTEGER
    ACCESS  read-only
    STATUS  mandatory
    DESCRIPTION
      "The type of event that has occurred. It is indicated by a integer value
       as follows (hexadecimal).
         0x001 = Dummy"
  ::= { powerUps 2 }

  powerUpsTrapEventSeverity OBJECT-TYPE
    SYNTAX  INTEGER
    ACCESS  read-only
    STATUS  mandatory
    DESCRIPTION
      "The severity of this event. It is indicated by a integer value as follows
       (hexadecimal).
         0x001 = Monitor
         0x002 = Information
         0x004 = OK
         0x008 = Non-Critical
         0x010 = Critical
         0x020 = Non-Recoverable"
  ::= { powerUps 3 }

  powerUpsTrapEventSystem OBJECT-TYPE
    SYNTAX  INTEGER
    ACCESS  read-only
    STATUS  mandatory
    DESCRIPTION
      "The major functional aspect of the product causing the fault. It is
       indicated by a integer value as follows (hexadecimal).
         0x000 = Driver
         0x001 = CI
         0x002 = SVP
         0x003 = OS
         0x004 = Body/Power
         0x005 = UPS
         0x006 = SystemBoard
         0x007 = Extended Slot
         0x008 = SCSI
         0x009 = Disk Array
         0x00A = BIOS POST
         0x00B = Cluster
         0x00C = Network"
  ::= { powerUps 4 }

  powerUpsTrapEventSubsystem OBJECT-TYPE
    SYNTAX  INTEGER
    ACCESS  read-only
    STATUS  mandatory
    DESCRIPTION
      "The minor functional aspect of the product causing the fault.
       This information is useless now(reserved)."
  ::= { powerUps 5 }

  powerUpsTrapEventClass OBJECT-TYPE
    SYNTAX  DisplayString (SIZE (1..256))
    ACCESS  read-only
    STATUS  mandatory
    DESCRIPTION
      "The name of the group that is associated with the event. It is
       expressed in the form of string(ASCII Code)."
  ::= { powerUps 6 }

  powerUpsTrapEventInstance OBJECT-TYPE
    SYNTAX  DisplayString (SIZE (1..256))
    ACCESS  read-only
    STATUS  mandatory
    DESCRIPTION
      "A list of DMI's integer indexs that identify the instance of the
       associated group that actually generated the event. The list of
       integer indexs are represented in the value of this attribute as a string
       containing a comma-separetaed list of integers. It is expressed in the
       form of string(ASCII Code)."
  ::= { powerUps 7 }

  powerUpsTrapEventGenerationTime OBJECT-TYPE
    SYNTAX  DisplayString (SIZE (1..26))
    ACCESS  read-only
    STATUS  mandatory
    DESCRIPTION
      "The time when the event has occurred. It is expressed in the form of
       string(ASCII Code)."
  ::= { powerUps 8 }

  powerUpsTrapEventMessage OBJECT-TYPE
    SYNTAX  DisplayString (SIZE (1..256))
    ACCESS  read-only
    STATUS  mandatory
    DESCRIPTION
      "Auxiliary infomation related to the event. It is expressed in the form of
       string(in Japanese, Sift JIS Code)."
  ::= { powerUps 9 }

--------------------------------------------------------------------------------
  systemBoard OBJECT-TYPE
    SYNTAX  SystemBoardEntry
    ACCESS  not-accessible
    STATUS  mandatory
DESCRIPTION ""
  ::= { trap 8 }

  SystemBoardEntry ::= SEQUENCE
  {
    systenBoardTrapEventID               INTEGER,
    systenBoardTrapEventType             INTEGER,
    systenBoardTrapEventSeverity         INTEGER,
    systenBoardTrapEventSystem           INTEGER,
    systenBoardTrapEventSubsystem        INTEGER,
    systenBoardTrapEventClass            DisplayString,
    systenBoardTrapEventInstance         DisplayString,
    systenBoardTrapEventGenerationTime   DisplayString,
    systenBoardTrapEventMessage          DisplayString
  }

  systenBoardTrapEventID OBJECT-TYPE
    SYNTAX  INTEGER
    ACCESS  read-only
    STATUS  mandatory
    DESCRIPTION
      "The id of event that has occurred."
  ::= { systemBoard 1 }

  systenBoardTrapEventType OBJECT-TYPE
    SYNTAX  INTEGER
    ACCESS  read-only
    STATUS  mandatory
    DESCRIPTION
      "The type of event that has occurred. It is indicated by a integer value
       as follows (hexadecimal).
         0x001 = Dummy"
  ::= { systemBoard 2 }

  systenBoardTrapEventSeverity OBJECT-TYPE
    SYNTAX  INTEGER
    ACCESS  read-only
    STATUS  mandatory
    DESCRIPTION
      "The severity of this event. It is indicated by a integer value as follows
       (hexadecimal).
         0x001 = Monitor
         0x002 = Information
         0x004 = OK
         0x008 = Non-Critical
         0x010 = Critical
         0x020 = Non-Recoverable"
  ::= { systemBoard 3 }

  systenBoardTrapEventSystem OBJECT-TYPE
    SYNTAX  INTEGER
    ACCESS  read-only
    STATUS  mandatory
    DESCRIPTION
      "The major functional aspect of the product causing the fault. It is
       indicated by a integer value as follows (hexadecimal).
         0x000 = Driver
         0x001 = CI
         0x002 = SVP
         0x003 = OS
         0x004 = Body/Power
         0x005 = UPS
         0x006 = SystemBoard
         0x007 = Extended Slot
         0x008 = SCSI
         0x009 = Disk Array
         0x00A = BIOS POST
         0x00B = Cluster
         0x00C = Network"
  ::= { systemBoard 4 }

  systenBoardTrapEventSubsystem OBJECT-TYPE
    SYNTAX  INTEGER
    ACCESS  read-only
    STATUS  mandatory
    DESCRIPTION
      "The minor functional aspect of the product causing the fault.
       This information is useless now(reserved)."
  ::= { systemBoard 5 }

  systenBoardTrapEventClass OBJECT-TYPE
    SYNTAX  DisplayString (SIZE (1..256))
    ACCESS  read-only
    STATUS  mandatory
    DESCRIPTION
      "The name of the group that is associated with the event. It is
       expressed in the form of string(ASCII Code)."
  ::= { systemBoard 6 }

  systenBoardTrapEventInstance OBJECT-TYPE
    SYNTAX  DisplayString (SIZE (1..256))
    ACCESS  read-only
    STATUS  mandatory
    DESCRIPTION
      "A list of DMI's integer indexs that identify the instance of the
       associated group that actually generated the event. The list of
       integer indexs are represented in the value of this attribute as a string
       containing a comma-separetaed list of integers. It is expressed in the
       form of string(ASCII Code)."
  ::= { systemBoard 7 }

  systenBoardTrapEventGenerationTime OBJECT-TYPE
    SYNTAX  DisplayString (SIZE (1..26))
    ACCESS  read-only
    STATUS  mandatory
    DESCRIPTION
      "The time when the event has occurred. It is expressed in the form of
       string(ASCII Code)."
  ::= { systemBoard 8 }

  systenBoardTrapEventMessage OBJECT-TYPE
    SYNTAX  DisplayString (SIZE (1..256))
    ACCESS  read-only
    STATUS  mandatory
    DESCRIPTION
      "Auxiliary infomation related to the event. It is expressed in the form of
       string(in Japanese, Sift JIS Code)."
  ::= { systemBoard 9 }

--------------------------------------------------------------------------------
  extendedSlot OBJECT-TYPE
    SYNTAX  ExtendedSlotEntry
    ACCESS  not-accessible
    STATUS  mandatory
DESCRIPTION ""
  ::= { trap 9 }

  ExtendedSlotEntry ::= SEQUENCE
  {
    extendedSlotTrapEventID               INTEGER,
    extendedSlotTrapEventType             INTEGER,
    extendedSlotTrapEventSeverity         INTEGER,
    extendedSlotTrapEventSystem           INTEGER,
    extendedSlotTrapEventSubsystem        INTEGER,
    extendedSlotTrapEventClass            DisplayString,
    extendedSlotTrapEventInstance         DisplayString,
    extendedSlotTrapEventGenerationTime   DisplayString,
    extendedSlotTrapEventMessage          DisplayString
  }

  extendedSlotTrapEventID OBJECT-TYPE
    SYNTAX  INTEGER
    ACCESS  read-only
    STATUS  mandatory
    DESCRIPTION
      "The id of event that has occurred."
  ::= { extendedSlot 1 }

  extendedSlotTrapEventType OBJECT-TYPE
    SYNTAX  INTEGER
    ACCESS  read-only
    STATUS  mandatory
    DESCRIPTION
      "The type of event that has occurred. It is indicated by a integer value
       as follows (hexadecimal).
         0x001 = Dummy"
  ::= { extendedSlot 2 }

  extendedSlotTrapEventSeverity OBJECT-TYPE
    SYNTAX  INTEGER
    ACCESS  read-only
    STATUS  mandatory
    DESCRIPTION
      "The severity of this event. It is indicated by a integer value as follows
       (hexadecimal).
         0x001 = Monitor
         0x002 = Information
         0x004 = OK
         0x008 = Non-Critical
         0x010 = Critical
         0x020 = Non-Recoverable"
  ::= { extendedSlot 3 }

  extendedSlotTrapEventSystem OBJECT-TYPE
    SYNTAX  INTEGER
    ACCESS  read-only
    STATUS  mandatory
    DESCRIPTION
      "The major functional aspect of the product causing the fault. It is
       indicated by a integer value as follows (hexadecimal).
         0x000 = Driver
         0x001 = CI
         0x002 = SVP
         0x003 = OS
         0x004 = Body/Power
         0x005 = UPS
         0x006 = SystemBoard
         0x007 = Extended Slot
         0x008 = SCSI
         0x009 = Disk Array
         0x00A = BIOS POST
         0x00B = Cluster
         0x00C = Network"
  ::= { extendedSlot 4 }

  extendedSlotTrapEventSubsystem OBJECT-TYPE
    SYNTAX  INTEGER
    ACCESS  read-only
    STATUS  mandatory
    DESCRIPTION
      "The minor functional aspect of the product causing the fault.
       This information is useless now(reserved)."
  ::= { extendedSlot 5 }

  extendedSlotTrapEventClass OBJECT-TYPE
    SYNTAX  DisplayString (SIZE (1..256))
    ACCESS  read-only
    STATUS  mandatory
    DESCRIPTION
      "The name of the group that is associated with the event. It is
       expressed in the form of string(ASCII Code)."
  ::= { extendedSlot 6 }

  extendedSlotTrapEventInstance OBJECT-TYPE
    SYNTAX  DisplayString (SIZE (1..256))
    ACCESS  read-only
    STATUS  mandatory
    DESCRIPTION
      "A list of DMI's integer indexs that identify the instance of the
       associated group that actually generated the event. The list of
       integer indexs are represented in the value of this attribute as a string
       containing a comma-separetaed list of integers. It is expressed in the
       form of string(ASCII Code)."
  ::= { extendedSlot 7 }

  extendedSlotTrapEventGenerationTime OBJECT-TYPE
    SYNTAX  DisplayString (SIZE (1..26))
    ACCESS  read-only
    STATUS  mandatory
    DESCRIPTION
      "The time when the event has occurred. It is expressed in the form of
       string(ASCII Code)."
  ::= { extendedSlot 8 }

  extendedSlotTrapEventMessage OBJECT-TYPE
    SYNTAX  DisplayString (SIZE (1..256))
    ACCESS  read-only
    STATUS  mandatory
    DESCRIPTION
      "Auxiliary infomation related to the event. It is expressed in the form of
       string(in Japanese, Sift JIS Code)."
  ::= { extendedSlot 9 }

--------------------------------------------------------------------------------
  scsi OBJECT-TYPE
    SYNTAX  ScsiEntry
    ACCESS  not-accessible
    STATUS  mandatory
DESCRIPTION ""
  ::= { trap 10 }

  ScsiEntry ::= SEQUENCE
  {
    scsiTrapEventID               INTEGER,
    scsiTrapEventType             INTEGER,
    scsiTrapEventSeverity         INTEGER,
    scsiTrapEventSystem           INTEGER,
    scsiTrapEventSubsystem        INTEGER,
    scsiTrapEventClass            DisplayString,
    scsiTrapEventInstance         DisplayString,
    scsiTrapEventGenerationTime   DisplayString,
    scsiTrapEventMessage          DisplayString
  }

  scsiTrapEventID OBJECT-TYPE
    SYNTAX  INTEGER
    ACCESS  read-only
    STATUS  mandatory
    DESCRIPTION
      "The id of event that has occurred."
  ::= { scsi 1 }

  scsiTrapEventType OBJECT-TYPE
    SYNTAX  INTEGER
    ACCESS  read-only
    STATUS  mandatory
    DESCRIPTION
      "The type of event that has occurred. It is indicated by a integer value
       as follows (hexadecimal).
         0x001 = Dummy"
  ::= { scsi 2 }

  scsiTrapEventSeverity OBJECT-TYPE
    SYNTAX  INTEGER
    ACCESS  read-only
    STATUS  mandatory
    DESCRIPTION
      "The severity of this event. It is indicated by a integer value as follows
       (hexadecimal).
         0x001 = Monitor
         0x002 = Information
         0x004 = OK
         0x008 = Non-Critical
         0x010 = Critical
         0x020 = Non-Recoverable"
  ::= { scsi 3 }

  scsiTrapEventSystem OBJECT-TYPE
    SYNTAX  INTEGER
    ACCESS  read-only
    STATUS  mandatory
    DESCRIPTION
      "The major functional aspect of the product causing the fault. It is
       indicated by a integer value as follows (hexadecimal).
         0x000 = Driver
         0x001 = CI
         0x002 = SVP
         0x003 = OS
         0x004 = Body/Power
         0x005 = UPS
         0x006 = SystemBoard
         0x007 = Extended Slot
         0x008 = SCSI
         0x009 = Disk Array
         0x00A = BIOS POST
         0x00B = Cluster
         0x00C = Network"
  ::= { scsi 4 }

  scsiTrapEventSubsystem OBJECT-TYPE
    SYNTAX  INTEGER
    ACCESS  read-only
    STATUS  mandatory
    DESCRIPTION
      "The minor functional aspect of the product causing the fault.
       This information is useless now(reserved)."
  ::= { scsi 5 }

  scsiTrapEventClass OBJECT-TYPE
    SYNTAX  DisplayString (SIZE (1..256))
    ACCESS  read-only
    STATUS  mandatory
    DESCRIPTION
      "The name of the group that is associated with the event. It is
       expressed in the form of string(ASCII Code)."
  ::= { scsi 6 }

  scsiTrapEventInstance OBJECT-TYPE
    SYNTAX  DisplayString (SIZE (1..256))
    ACCESS  read-only
    STATUS  mandatory
    DESCRIPTION
      "A list of DMI's integer indexs that identify the instance of the
       associated group that actually generated the event. The list of
       integer indexs are represented in the value of this attribute as a string
       containing a comma-separetaed list of integers. It is expressed in the
       form of string(ASCII Code)."
  ::= { scsi 7 }

  scsiTrapEventGenerationTime OBJECT-TYPE
    SYNTAX  DisplayString (SIZE (1..26))
    ACCESS  read-only
    STATUS  mandatory
    DESCRIPTION
      "The time when the event has occurred. It is expressed in the form of
       string(ASCII Code)."
  ::= { scsi 8 }

  scsiTrapEventMessage OBJECT-TYPE
    SYNTAX  DisplayString (SIZE (1..256))
    ACCESS  read-only
    STATUS  mandatory
    DESCRIPTION
      "Auxiliary infomation related to the event. It is expressed in the form of
       string(in Japanese, Sift JIS Code)."
  ::= { scsi 9 }

--------------------------------------------------------------------------------
  diskArray OBJECT-TYPE
    SYNTAX  DiskArrayEntry
    ACCESS  not-accessible
    STATUS  mandatory
DESCRIPTION ""
  ::= { trap 11 }

  DiskArrayEntry ::= SEQUENCE
  {
    diskArrayTrapEventID               INTEGER,
    diskArrayTrapEventType             INTEGER,
    diskArrayTrapEventSeverity         INTEGER,
    diskArrayTrapEventSystem           INTEGER,
    diskArrayTrapEventSubsystem        INTEGER,
    diskArrayTrapEventClass            DisplayString,
    diskArrayTrapEventInstance         DisplayString,
    diskArrayTrapEventGenerationTime   DisplayString,
    diskArrayTrapEventMessage          DisplayString
  }

  diskArrayTrapEventID OBJECT-TYPE
    SYNTAX  INTEGER
    ACCESS  read-only
    STATUS  mandatory
    DESCRIPTION
      "The id of event that has occurred."
  ::= { diskArray 1 }

  diskArrayTrapEventType OBJECT-TYPE
    SYNTAX  INTEGER
    ACCESS  read-only
    STATUS  mandatory
    DESCRIPTION
      "The type of event that has occurred. It is indicated by a integer value
       as follows (hexadecimal).
         0x001 = Dummy"
  ::= { diskArray 2 }

  diskArrayTrapEventSeverity OBJECT-TYPE
    SYNTAX  INTEGER
    ACCESS  read-only
    STATUS  mandatory
    DESCRIPTION
      "The severity of this event. It is indicated by a integer value as follows
       (hexadecimal).
         0x001 = Monitor
         0x002 = Information
         0x004 = OK
         0x008 = Non-Critical
         0x010 = Critical
         0x020 = Non-Recoverable"
  ::= { diskArray 3 }

  diskArrayTrapEventSystem OBJECT-TYPE
    SYNTAX  INTEGER
    ACCESS  read-only
    STATUS  mandatory
    DESCRIPTION
      "The major functional aspect of the product causing the fault. It is
       indicated by a integer value as follows (hexadecimal).
         0x000 = Driver
         0x001 = CI
         0x002 = SVP
         0x003 = OS
         0x004 = Body/Power
         0x005 = UPS
         0x006 = SystemBoard
         0x007 = Extended Slot
         0x008 = SCSI
         0x009 = Disk Array
         0x00A = BIOS POST
         0x00B = Cluster
         0x00C = Network"
  ::= { diskArray 4 }

  diskArrayTrapEventSubsystem OBJECT-TYPE
    SYNTAX  INTEGER
    ACCESS  read-only
    STATUS  mandatory
    DESCRIPTION
      "The minor functional aspect of the product causing the fault.
       This information is useless now(reserved)."
  ::= { diskArray 5 }

  diskArrayTrapEventClass OBJECT-TYPE
    SYNTAX  DisplayString (SIZE (1..256))
    ACCESS  read-only
    STATUS  mandatory
    DESCRIPTION
      "The name of the group that is associated with the event. It is
       expressed in the form of string(ASCII Code)."
  ::= { diskArray 6 }

  diskArrayTrapEventInstance OBJECT-TYPE
    SYNTAX  DisplayString (SIZE (1..256))
    ACCESS  read-only
    STATUS  mandatory
    DESCRIPTION
      "A list of DMI's integer indexs that identify the instance of the
       associated group that actually generated the event. The list of
       integer indexs are represented in the value of this attribute as a string
       containing a comma-separetaed list of integers. It is expressed in the
       form of string(ASCII Code)."
  ::= { diskArray 7 }

  diskArrayTrapEventGenerationTime OBJECT-TYPE
    SYNTAX  DisplayString (SIZE (1..26))
    ACCESS  read-only
    STATUS  mandatory
    DESCRIPTION
      "The time when the event has occurred. It is expressed in the form of
       string(ASCII Code)."
  ::= { diskArray 8 }

  diskArrayTrapEventMessage OBJECT-TYPE
    SYNTAX  DisplayString (SIZE (1..256))
    ACCESS  read-only
    STATUS  mandatory
    DESCRIPTION
      "Auxiliary infomation related to the event. It is expressed in the form of
       string(in Japanese, Sift JIS Code)."
  ::= { diskArray 9 }

--------------------------------------------------------------------------------
  biosPost OBJECT-TYPE
    SYNTAX  BiosPostEntry
    ACCESS  not-accessible
    STATUS  mandatory
DESCRIPTION ""
  ::= { trap 12 }

  BiosPostEntry ::= SEQUENCE
  {
    biosPostTrapEventID               INTEGER,
    biosPostTrapEventType             INTEGER,
    biosPostTrapEventSeverity         INTEGER,
    biosPostTrapEventSystem           INTEGER,
    biosPostTrapEventSubsystem        INTEGER,
    biosPostTrapEventClass            DisplayString,
    biosPostTrapEventInstance         DisplayString,
    biosPostTrapEventGenerationTime   DisplayString,
    biosPostTrapEventMessage          DisplayString
  }

  biosPostTrapEventID OBJECT-TYPE
    SYNTAX  INTEGER
    ACCESS  read-only
    STATUS  mandatory
    DESCRIPTION
      "The id of event that has occurred."
  ::= { biosPost 1 }

  biosPostTrapEventType OBJECT-TYPE
    SYNTAX  INTEGER
    ACCESS  read-only
    STATUS  mandatory
    DESCRIPTION
      "The type of event that has occurred. It is indicated by a integer value
       as follows (hexadecimal).
         0x001 = Dummy"
  ::= { biosPost 2 }

  biosPostTrapEventSeverity OBJECT-TYPE
    SYNTAX  INTEGER
    ACCESS  read-only
    STATUS  mandatory
    DESCRIPTION
      "The severity of this event. It is indicated by a integer value as follows
       (hexadecimal).
         0x001 = Monitor
         0x002 = Information
         0x004 = OK
         0x008 = Non-Critical
         0x010 = Critical
         0x020 = Non-Recoverable"
  ::= { biosPost 3 }

  biosPostTrapEventSystem OBJECT-TYPE
    SYNTAX  INTEGER
    ACCESS  read-only
    STATUS  mandatory
    DESCRIPTION
      "The major functional aspect of the product causing the fault. It is
       indicated by a integer value as follows (hexadecimal).
         0x000 = Driver
         0x001 = CI
         0x002 = SVP
         0x003 = OS
         0x004 = Body/Power
         0x005 = UPS
         0x006 = SystemBoard
         0x007 = Extended Slot
         0x008 = SCSI
         0x009 = Disk Array
         0x00A = BIOS POST
         0x00B = Cluster
         0x00C = Network"
  ::= { biosPost 4 }

  biosPostTrapEventSubsystem OBJECT-TYPE
    SYNTAX  INTEGER
    ACCESS  read-only
    STATUS  mandatory
    DESCRIPTION
      "The minor functional aspect of the product causing the fault.
       This information is useless now(reserved)."
  ::= { biosPost 5 }

  biosPostTrapEventClass OBJECT-TYPE
    SYNTAX  DisplayString (SIZE (1..256))
    ACCESS  read-only
    STATUS  mandatory
    DESCRIPTION
      "The name of the group that is associated with the event. It is
       expressed in the form of string(ASCII Code)."
  ::= { biosPost 6 }

  biosPostTrapEventInstance OBJECT-TYPE
    SYNTAX  DisplayString (SIZE (1..256))
    ACCESS  read-only
    STATUS  mandatory
    DESCRIPTION
      "A list of DMI's integer indexs that identify the instance of the
       associated group that actually generated the event. The list of
       integer indexs are represented in the value of this attribute as a string
       containing a comma-separetaed list of integers. It is expressed in the
       form of string(ASCII Code)."
  ::= { biosPost 7 }

  biosPostTrapEventGenerationTime OBJECT-TYPE
    SYNTAX  DisplayString (SIZE (1..26))
    ACCESS  read-only
    STATUS  mandatory
    DESCRIPTION
      "The time when the event has occurred. It is expressed in the form of
       string(ASCII Code)."
  ::= { biosPost 8 }

  biosPostTrapEventMessage OBJECT-TYPE
    SYNTAX  DisplayString (SIZE (1..256))
    ACCESS  read-only
    STATUS  mandatory
    DESCRIPTION
      "Auxiliary infomation related to the event. It is expressed in the form of
       string(in Japanese, Sift JIS Code)."
  ::= { biosPost 9 }

--------------------------------------------------------------------------------
  cluster OBJECT-TYPE
    SYNTAX  ClusterEntry
    ACCESS  not-accessible
    STATUS  mandatory
DESCRIPTION ""
  ::= { trap 13 }

  ClusterEntry ::= SEQUENCE
  {
    clusterTrapEventID               INTEGER,
    clusterTrapEventType             INTEGER,
    clusterTrapEventSeverity         INTEGER,
    clusterTrapEventSystem           INTEGER,
    clusterTrapEventSubsystem        INTEGER,
    clusterTrapEventClass            DisplayString,
    clusterTrapEventInstance         DisplayString,
    clusterTrapEventGenerationTime   DisplayString,
    clusterTrapEventMessage          DisplayString
  }

  clusterTrapEventID OBJECT-TYPE
    SYNTAX  INTEGER
    ACCESS  read-only
    STATUS  mandatory
    DESCRIPTION
      "The id of event that has occurred."
  ::= { cluster 1 }

  clusterTrapEventType OBJECT-TYPE
    SYNTAX  INTEGER
    ACCESS  read-only
    STATUS  mandatory
    DESCRIPTION
      "The type of event that has occurred. It is indicated by a integer value
       as follows (hexadecimal).
         0x001 = Dummy"
  ::= { cluster 2 }

  clusterTrapEventSeverity OBJECT-TYPE
    SYNTAX  INTEGER
    ACCESS  read-only
    STATUS  mandatory
    DESCRIPTION
      "The severity of this event. It is indicated by a integer value as follows
       (hexadecimal).
         0x001 = Monitor
         0x002 = Information
         0x004 = OK
         0x008 = Non-Critical
         0x010 = Critical
         0x020 = Non-Recoverable"
  ::= { cluster 3 }

  clusterTrapEventSystem OBJECT-TYPE
    SYNTAX  INTEGER
    ACCESS  read-only
    STATUS  mandatory
    DESCRIPTION
      "The major functional aspect of the product causing the fault. It is
       indicated by a integer value as follows (hexadecimal).
         0x000 = Driver
         0x001 = CI
         0x002 = SVP
         0x003 = OS
         0x004 = Body/Power
         0x005 = UPS
         0x006 = SystemBoard
         0x007 = Extended Slot
         0x008 = SCSI
         0x009 = Disk Array
         0x00A = BIOS POST
         0x00B = Cluster
         0x00C = Network"
  ::= { cluster 4 }

  clusterTrapEventSubsystem OBJECT-TYPE
    SYNTAX  INTEGER
    ACCESS  read-only
    STATUS  mandatory
    DESCRIPTION
      "The minor functional aspect of the product causing the fault.
       This information is useless now(reserved)."
  ::= { cluster 5 }

  clusterTrapEventClass OBJECT-TYPE
    SYNTAX  DisplayString (SIZE (1..256))
    ACCESS  read-only
    STATUS  mandatory
    DESCRIPTION
      "The name of the group that is associated with the event. It is
       expressed in the form of string(ASCII Code)."
  ::= { cluster 6 }

  clusterTrapEventInstance OBJECT-TYPE
    SYNTAX  DisplayString (SIZE (1..256))
    ACCESS  read-only
    STATUS  mandatory
    DESCRIPTION
      "A list of DMI's integer indexs that identify the instance of the
       associated group that actually generated the event. The list of
       integer indexs are represented in the value of this attribute as a string
       containing a comma-separetaed list of integers. It is expressed in the
       form of string(ASCII Code)."
  ::= { cluster 7 }

  clusterTrapEventGenerationTime OBJECT-TYPE
    SYNTAX  DisplayString (SIZE (1..26))
    ACCESS  read-only
    STATUS  mandatory
    DESCRIPTION
      "The time when the event has occurred. It is expressed in the form of
       string(ASCII Code)."
  ::= { cluster 8 }

  clusterTrapEventMessage OBJECT-TYPE
    SYNTAX  DisplayString (SIZE (1..256))
    ACCESS  read-only
    STATUS  mandatory
    DESCRIPTION
      "Auxiliary infomation related to the event. It is expressed in the form of
       string(in Japanese, Sift JIS Code)."
  ::= { cluster 9 }

--------------------------------------------------------------------------------
  network OBJECT-TYPE
    SYNTAX  NetworkEntry
    ACCESS  not-accessible
    STATUS  mandatory
DESCRIPTION ""
  ::= { trap 14 }

  NetworkEntry ::= SEQUENCE
  {
    networkTrapEventID               INTEGER,
    networkTrapEventType             INTEGER,
    networkTrapEventSeverity         INTEGER,
    networkTrapEventSystem           INTEGER,
    networkTrapEventSubsystem        INTEGER,
    networkTrapEventClass            DisplayString,
    networkTrapEventInstance         DisplayString,
    networkTrapEventGenerationTime   DisplayString,
    networkTrapEventMessage          DisplayString
  }

  networkTrapEventID OBJECT-TYPE
    SYNTAX  INTEGER
    ACCESS  read-only
    STATUS  mandatory
    DESCRIPTION
      "The id of event that has occurred."
  ::= { network 1 }

  networkTrapEventType OBJECT-TYPE
    SYNTAX  INTEGER
    ACCESS  read-only
    STATUS  mandatory
    DESCRIPTION
      "The type of event that has occurred. It is indicated by a integer value
       as follows (hexadecimal).
         0x001 = Dummy"
  ::= { network 2 }

  networkTrapEventSeverity OBJECT-TYPE
    SYNTAX  INTEGER
    ACCESS  read-only
    STATUS  mandatory
    DESCRIPTION
      "The severity of this event. It is indicated by a integer value as follows
       (hexadecimal).
         0x001 = Monitor
         0x002 = Information
         0x004 = OK
         0x008 = Non-Critical
         0x010 = Critical
         0x020 = Non-Recoverable"
  ::= { network 3 }

  networkTrapEventSystem OBJECT-TYPE
    SYNTAX  INTEGER
    ACCESS  read-only
    STATUS  mandatory
    DESCRIPTION
      "The major functional aspect of the product causing the fault. It is
       indicated by a integer value as follows (hexadecimal).
         0x000 = Driver
         0x001 = CI
         0x002 = SVP
         0x003 = OS
         0x004 = Body/Power
         0x005 = UPS
         0x006 = SystemBoard
         0x007 = Extended Slot
         0x008 = SCSI
         0x009 = Disk Array
         0x00A = BIOS POST
         0x00B = Cluster
         0x00C = Network"
  ::= { network 4 }

  networkTrapEventSubsystem OBJECT-TYPE
    SYNTAX  INTEGER
    ACCESS  read-only
    STATUS  mandatory
    DESCRIPTION
      "The minor functional aspect of the product causing the fault.
       This information is useless now(reserved)."
  ::= { network 5 }

  networkTrapEventClass OBJECT-TYPE
    SYNTAX  DisplayString (SIZE (1..256))
    ACCESS  read-only
    STATUS  mandatory
    DESCRIPTION
      "The name of the group that is associated with the event. It is
       expressed in the form of string(ASCII Code)."
  ::= { network 6 }

  networkTrapEventInstance OBJECT-TYPE
    SYNTAX  DisplayString (SIZE (1..256))
    ACCESS  read-only
    STATUS  mandatory
    DESCRIPTION
      "A list of DMI's integer indexs that identify the instance of the
       associated group that actually generated the event. The list of
       integer indexs are represented in the value of this attribute as a string
       containing a comma-separetaed list of integers. It is expressed in the
       form of string(ASCII Code)."
  ::= { network 7 }

  networkTrapEventGenerationTime OBJECT-TYPE
    SYNTAX  DisplayString (SIZE (1..26))
    ACCESS  read-only
    STATUS  mandatory
    DESCRIPTION
      "The time when the event has occurred. It is expressed in the form of
       string(ASCII Code)."
  ::= { network 8 }

  networkTrapEventMessage OBJECT-TYPE
    SYNTAX  DisplayString (SIZE (1..256))
    ACCESS  read-only
    STATUS  mandatory
    DESCRIPTION
      "Auxiliary infomation related to the event. It is expressed in the form of
       string(in Japanese, Sift JIS Code)."
  ::= { network 9 }

--------------------------------------------------------------------------------


--------------------------------------------------------------------------------

  systemAP        OBJECT IDENTIFIER  ::= { hitachi         7 }
  systemManager   OBJECT IDENTIFIER  ::= { systemAP       21 }

--------------------------------------------------------------------------------
-- System Manager
-- trap
--------------------------------------------------------------------------------

--------------------------------------------------------------------------------
  generalTrapUnknown TRAP-TYPE
    ENTERPRISE   systemManager
    VARIABLES
    {
      generalTrapEventComponent,
      generalTrapEventType,
      generalTrapEventSeverity,
      generalTrapEventSystem,
      generalTrapEventSubsystem,
      generalTrapEventClass,
      generalTrapEventInstance,
      generalTrapEventGenerationTime,
      generalTrapEventMessage,
      generalTrapEventSolution,
      generalTrapEventVenderSpecificData
    }
    DESCRIPTION
      "This trap signifies that System Manager recognized that the event has
       occurred (severity is unknown)."
    ::= 0

--------------------------------------------------------------------------------
  generalTrapMonitor TRAP-TYPE
    ENTERPRISE   systemManager
    VARIABLES
    {
      generalTrapEventComponent,
      generalTrapEventType,
      generalTrapEventSeverity,
      generalTrapEventSystem,
      generalTrapEventSubsystem,
      generalTrapEventClass,
      generalTrapEventInstance,
      generalTrapEventGenerationTime,
      generalTrapEventMessage,
      generalTrapEventSolution,
      generalTrapEventVenderSpecificData
    }
    DESCRIPTION
      "This trap signifies that System Manager recognized that the event has
       occurred (severity is Monitor)."
    ::= 1

--------------------------------------------------------------------------------
  generalTrapInformation TRAP-TYPE
    ENTERPRISE   systemManager
    VARIABLES
    {
      generalTrapEventComponent,
      generalTrapEventType,
      generalTrapEventSeverity,
      generalTrapEventSystem,
      generalTrapEventSubsystem,
      generalTrapEventClass,
      generalTrapEventInstance,
      generalTrapEventGenerationTime,
      generalTrapEventMessage,
      generalTrapEventSolution,
      generalTrapEventVenderSpecificData
    }
    DESCRIPTION
      "This trap signifies that System Manager recognized that the event has
       occurred (severity is Information)."
    ::= 2

--------------------------------------------------------------------------------
  generalTrapOK TRAP-TYPE
    ENTERPRISE   systemManager
    VARIABLES
    {
      generalTrapEventComponent,
      generalTrapEventType,
      generalTrapEventSeverity,
      generalTrapEventSystem,
      generalTrapEventSubsystem,
      generalTrapEventClass,
      generalTrapEventInstance,
      generalTrapEventGenerationTime,
      generalTrapEventMessage,
      generalTrapEventSolution,
      generalTrapEventVenderSpecificData
    }
    DESCRIPTION
      "This trap signifies that System Manager recognized that the event has
       occurred (severity is OK)."
    ::= 3

--------------------------------------------------------------------------------
  generalTrapNon-Critical TRAP-TYPE
    ENTERPRISE   systemManager
    VARIABLES
    {
      generalTrapEventComponent,
      generalTrapEventType,
      generalTrapEventSeverity,
      generalTrapEventSystem,
      generalTrapEventSubsystem,
      generalTrapEventClass,
      generalTrapEventInstance,
      generalTrapEventGenerationTime,
      generalTrapEventMessage,
      generalTrapEventSolution,
      generalTrapEventVenderSpecificData
    }
    DESCRIPTION
      "This trap signifies that System Manager recognized that the event has
       occurred (severity is Non-Critical)."
    ::= 4

--------------------------------------------------------------------------------
  generalTrapCritical TRAP-TYPE
    ENTERPRISE   systemManager
    VARIABLES
    {
      generalTrapEventComponent,
      generalTrapEventType,
      generalTrapEventSeverity,
      generalTrapEventSystem,
      generalTrapEventSubsystem,
      generalTrapEventClass,
      generalTrapEventInstance,
      generalTrapEventGenerationTime,
      generalTrapEventMessage,
      generalTrapEventSolution,
      generalTrapEventVenderSpecificData
    }
    DESCRIPTION
      "This trap signifies that System Manager recognized that the event has
       occurred (severity is Critical)."
    ::= 5

--------------------------------------------------------------------------------
  generalTrapNon-Recoverable TRAP-TYPE
    ENTERPRISE   systemManager
    VARIABLES
    {
      generalTrapEventComponent,
      generalTrapEventType,
      generalTrapEventSeverity,
      generalTrapEventSystem,
      generalTrapEventSubsystem,
      generalTrapEventClass,
      generalTrapEventInstance,
      generalTrapEventGenerationTime,
      generalTrapEventMessage,
      generalTrapEventSolution,
      generalTrapEventVenderSpecificData
    }
    DESCRIPTION
      "This trap signifies that System Manager recognized that the event has
       occurred (severity is Non-Recoverable)."
    ::= 6

--------------------------------------------------------------------------------
  driverTrapUnknown TRAP-TYPE
    ENTERPRISE   systemManager
    VARIABLES
    {
      driverTrapEventID,
      driverTrapEventType,
      driverTrapEventSeverity,
      driverTrapEventSystem,
      driverTrapEventSubsystem,
      driverTrapEventClass,
      driverTrapEventInstance,
      driverTrapEventGenerationTime,
      driverTrapEventMessage
    }
    DESCRIPTION
      "This trap signifies that System Manager recognized that the event has
       occurred (at driver, severity is unknown)."
    ::= 100

--------------------------------------------------------------------------------
  driverTrapMonitor TRAP-TYPE
    ENTERPRISE   systemManager
    VARIABLES
    {
      driverTrapEventID,
      driverTrapEventType,
      driverTrapEventSeverity,
      driverTrapEventSystem,
      driverTrapEventSubsystem,
      driverTrapEventClass,
      driverTrapEventInstance,
      driverTrapEventGenerationTime,
      driverTrapEventMessage
    }
    DESCRIPTION
      "This trap signifies that System Manager recognized that the event has
       occurred (at driver, severity is Monitor)."
    ::= 101

--------------------------------------------------------------------------------
  driverTrapInformation TRAP-TYPE
    ENTERPRISE   systemManager
    VARIABLES
    {
      driverTrapEventID,
      driverTrapEventType,
      driverTrapEventSeverity,
      driverTrapEventSystem,
      driverTrapEventSubsystem,
      driverTrapEventClass,
      driverTrapEventInstance,
      driverTrapEventGenerationTime,
      driverTrapEventMessage
    }
    DESCRIPTION
      "This trap signifies that System Manager recognized that the event has
       occurred (at driver, severity is Information)."
    ::= 102

--------------------------------------------------------------------------------
  driverTrapOK TRAP-TYPE
    ENTERPRISE   systemManager
    VARIABLES
    {
      driverTrapEventID,
      driverTrapEventType,
      driverTrapEventSeverity,
      driverTrapEventSystem,
      driverTrapEventSubsystem,
      driverTrapEventClass,
      driverTrapEventInstance,
      driverTrapEventGenerationTime,
      driverTrapEventMessage
    }
    DESCRIPTION
      "This trap signifies that System Manager recognized that the event has
       occurred (at driver, severity is OK)."
    ::= 103

--------------------------------------------------------------------------------
  driverTrapNon-Critical TRAP-TYPE
    ENTERPRISE   systemManager
    VARIABLES
    {
      driverTrapEventID,
      driverTrapEventType,
      driverTrapEventSeverity,
      driverTrapEventSystem,
      driverTrapEventSubsystem,
      driverTrapEventClass,
      driverTrapEventInstance,
      driverTrapEventGenerationTime,
      driverTrapEventMessage
    }
    DESCRIPTION
      "This trap signifies that System Manager recognized that the event has
       occurred (at driver, severity is Non-Critical)."
    ::= 104

--------------------------------------------------------------------------------
  driverTrapCritical TRAP-TYPE
    ENTERPRISE   systemManager
    VARIABLES
    {
      driverTrapEventID,
      driverTrapEventType,
      driverTrapEventSeverity,
      driverTrapEventSystem,
      driverTrapEventSubsystem,
      driverTrapEventClass,
      driverTrapEventInstance,
      driverTrapEventGenerationTime,
      driverTrapEventMessage
    }
    DESCRIPTION
      "This trap signifies that System Manager recognized that the event has
       occurred (at driver, severity is Critical)."
    ::= 105

--------------------------------------------------------------------------------
  driverTrapNon-Recoverable TRAP-TYPE
    ENTERPRISE   systemManager
    VARIABLES
    {
      driverTrapEventID,
      driverTrapEventType,
      driverTrapEventSeverity,
      driverTrapEventSystem,
      driverTrapEventSubsystem,
      driverTrapEventClass,
      driverTrapEventInstance,
      driverTrapEventGenerationTime,
      driverTrapEventMessage
    }
    DESCRIPTION
      "This trap signifies that System Manager recognized that the event has
       occurred (at driver, severity is Non-Recoverable)."
    ::= 106

--------------------------------------------------------------------------------
  ciTrapUnknown TRAP-TYPE
    ENTERPRISE   systemManager
    VARIABLES
    {
      ciTrapEventID,
      ciTrapEventType,
      ciTrapEventSeverity,
      ciTrapEventSystem,
      ciTrapEventSubsystem,
      ciTrapEventClass,
      ciTrapEventInstance,
      ciTrapEventGenerationTime,
      ciTrapEventMessage
    }
    DESCRIPTION
      "This trap signifies that System Manager recognized that the event has
       occurred (at ci, severity is unknown)."
    ::= 200

--------------------------------------------------------------------------------
  ciTrapMonitor TRAP-TYPE
    ENTERPRISE   systemManager
    VARIABLES
    {
      ciTrapEventID,
      ciTrapEventType,
      ciTrapEventSeverity,
      ciTrapEventSystem,
      ciTrapEventSubsystem,
      ciTrapEventClass,
      ciTrapEventInstance,
      ciTrapEventGenerationTime,
      ciTrapEventMessage
    }
    DESCRIPTION
      "This trap signifies that System Manager recognized that the event has
       occurred (at ci, severity is Monitor)."
    ::= 201

--------------------------------------------------------------------------------
  ciTrapInformation TRAP-TYPE
    ENTERPRISE   systemManager
    VARIABLES
    {
      ciTrapEventID,
      ciTrapEventType,
      ciTrapEventSeverity,
      ciTrapEventSystem,
      ciTrapEventSubsystem,
      ciTrapEventClass,
      ciTrapEventInstance,
      ciTrapEventGenerationTime,
      ciTrapEventMessage
    }
    DESCRIPTION
      "This trap signifies that System Manager recognized that the event has
       occurred (at ci, severity is Information)."
    ::= 202

--------------------------------------------------------------------------------
  ciTrapOK TRAP-TYPE
    ENTERPRISE   systemManager
    VARIABLES
    {
      ciTrapEventID,
      ciTrapEventType,
      ciTrapEventSeverity,
      ciTrapEventSystem,
      ciTrapEventSubsystem,
      ciTrapEventClass,
      ciTrapEventInstance,
      ciTrapEventGenerationTime,
      ciTrapEventMessage
    }
    DESCRIPTION
      "This trap signifies that System Manager recognized that the event has
       occurred (at ci, severity is OK)."
    ::= 203

--------------------------------------------------------------------------------
  ciTrapNon-Critical TRAP-TYPE
    ENTERPRISE   systemManager
    VARIABLES
    {
      ciTrapEventID,
      ciTrapEventType,
      ciTrapEventSeverity,
      ciTrapEventSystem,
      ciTrapEventSubsystem,
      ciTrapEventClass,
      ciTrapEventInstance,
      ciTrapEventGenerationTime,
      ciTrapEventMessage
    }
    DESCRIPTION
      "This trap signifies that System Manager recognized that the event has
       occurred (at ci, severity is Non-Critical)."
    ::= 204

--------------------------------------------------------------------------------
  ciTrapCritical TRAP-TYPE
    ENTERPRISE   systemManager
    VARIABLES
    {
      ciTrapEventID,
      ciTrapEventType,
      ciTrapEventSeverity,
      ciTrapEventSystem,
      ciTrapEventSubsystem,
      ciTrapEventClass,
      ciTrapEventInstance,
      ciTrapEventGenerationTime,
      ciTrapEventMessage
    }
    DESCRIPTION
      "This trap signifies that System Manager recognized that the event has
       occurred (at ci, severity is Critical)."
    ::= 205

--------------------------------------------------------------------------------
  ciTrapNon-Recoverable TRAP-TYPE
    ENTERPRISE   systemManager
    VARIABLES
    {
      ciTrapEventID,
      ciTrapEventType,
      ciTrapEventSeverity,
      ciTrapEventSystem,
      ciTrapEventSubsystem,
      ciTrapEventClass,
      ciTrapEventInstance,
      ciTrapEventGenerationTime,
      ciTrapEventMessage
    }
    DESCRIPTION
      "This trap signifies that System Manager recognized that the event has
       occurred (at ci, severity is Non-Recoverable)."
    ::= 206

--------------------------------------------------------------------------------
  svpTrapUnknown TRAP-TYPE
    ENTERPRISE   systemManager
    VARIABLES
    {
      svpTrapEventID,
      svpTrapEventType,
      svpTrapEventSeverity,
      svpTrapEventSystem,
      svpTrapEventSubsystem,
      svpTrapEventClass,
      svpTrapEventInstance,
      svpTrapEventGenerationTime,
      svpTrapEventMessage
    }
    DESCRIPTION
      "This trap signifies that System Manager recognized that the event has
       occurred (at svp, severity is unknown)."
    ::= 300

--------------------------------------------------------------------------------
  svpTrapMonitor TRAP-TYPE
    ENTERPRISE   systemManager
    VARIABLES
    {
      svpTrapEventID,
      svpTrapEventType,
      svpTrapEventSeverity,
      svpTrapEventSystem,
      svpTrapEventSubsystem,
      svpTrapEventClass,
      svpTrapEventInstance,
      svpTrapEventGenerationTime,
      svpTrapEventMessage
    }
    DESCRIPTION
      "This trap signifies that System Manager recognized that the event has
       occurred (at svp, severity is Monitor)."
    ::= 301

--------------------------------------------------------------------------------
  svpTrapInformation TRAP-TYPE
    ENTERPRISE   systemManager
    VARIABLES
    {
      svpTrapEventID,
      svpTrapEventType,
      svpTrapEventSeverity,
      svpTrapEventSystem,
      svpTrapEventSubsystem,
      svpTrapEventClass,
      svpTrapEventInstance,
      svpTrapEventGenerationTime,
      svpTrapEventMessage
    }
    DESCRIPTION
      "This trap signifies that System Manager recognized that the event has
       occurred (at svp, severity is Information)."
    ::= 302

--------------------------------------------------------------------------------
  svpTrapOK TRAP-TYPE
    ENTERPRISE   systemManager
    VARIABLES
    {
      svpTrapEventID,
      svpTrapEventType,
      svpTrapEventSeverity,
      svpTrapEventSystem,
      svpTrapEventSubsystem,
      svpTrapEventClass,
      svpTrapEventInstance,
      svpTrapEventGenerationTime,
      svpTrapEventMessage
    }
    DESCRIPTION
      "This trap signifies that System Manager recognized that the event has
       occurred (at svp, severity is OK)."
    ::= 303

--------------------------------------------------------------------------------
  svpTrapNon-Critical TRAP-TYPE
    ENTERPRISE   systemManager
    VARIABLES
    {
      svpTrapEventID,
      svpTrapEventType,
      svpTrapEventSeverity,
      svpTrapEventSystem,
      svpTrapEventSubsystem,
      svpTrapEventClass,
      svpTrapEventInstance,
      svpTrapEventGenerationTime,
      svpTrapEventMessage
    }
    DESCRIPTION
      "This trap signifies that System Manager recognized that the event has
       occurred (at svp, severity is Non-Critical)."
    ::= 304

--------------------------------------------------------------------------------
  svpTrapCritical TRAP-TYPE
    ENTERPRISE   systemManager
    VARIABLES
    {
      svpTrapEventID,
      svpTrapEventType,
      svpTrapEventSeverity,
      svpTrapEventSystem,
      svpTrapEventSubsystem,
      svpTrapEventClass,
      svpTrapEventInstance,
      svpTrapEventGenerationTime,
      svpTrapEventMessage
    }
    DESCRIPTION
      "This trap signifies that System Manager recognized that the event has
       occurred (at svp, severity is Critical)."
    ::= 305

--------------------------------------------------------------------------------
  svpTrapNon-Recoverable TRAP-TYPE
    ENTERPRISE   systemManager
    VARIABLES
    {
      svpTrapEventID,
      svpTrapEventType,
      svpTrapEventSeverity,
      svpTrapEventSystem,
      svpTrapEventSubsystem,
      svpTrapEventClass,
      svpTrapEventInstance,
      svpTrapEventGenerationTime,
      svpTrapEventMessage
    }
    DESCRIPTION
      "This trap signifies that System Manager recognized that the event has
       occurred (at svp, severity is Non-Recoverable)."
    ::= 306

--------------------------------------------------------------------------------
  osTrapUnknown TRAP-TYPE
    ENTERPRISE   systemManager
    VARIABLES
    {
      osTrapEventID,
      osTrapEventType,
      osTrapEventSeverity,
      osTrapEventSystem,
      osTrapEventSubsystem,
      osTrapEventClass,
      osTrapEventInstance,
      osTrapEventGenerationTime,
      osTrapEventMessage
    }
    DESCRIPTION
      "This trap signifies that System Manager recognized that the event has
       occurred (at os, severity is unknown)."
    ::= 400

--------------------------------------------------------------------------------
  osTrapMonitor TRAP-TYPE
    ENTERPRISE   systemManager
    VARIABLES
    {
      osTrapEventID,
      osTrapEventType,
      osTrapEventSeverity,
      osTrapEventSystem,
      osTrapEventSubsystem,
      osTrapEventClass,
      osTrapEventInstance,
      osTrapEventGenerationTime,
      osTrapEventMessage
    }
    DESCRIPTION
      "This trap signifies that System Manager recognized that the event has
       occurred (at os, severity is Monitor)."
    ::= 401

--------------------------------------------------------------------------------
  osTrapInformation TRAP-TYPE
    ENTERPRISE   systemManager
    VARIABLES
    {
      osTrapEventID,
      osTrapEventType,
      osTrapEventSeverity,
      osTrapEventSystem,
      osTrapEventSubsystem,
      osTrapEventClass,
      osTrapEventInstance,
      osTrapEventGenerationTime,
      osTrapEventMessage
    }
    DESCRIPTION
      "This trap signifies that System Manager recognized that the event has
       occurred (at os, severity is Information)."
    ::= 402

--------------------------------------------------------------------------------
  osTrapOK TRAP-TYPE
    ENTERPRISE   systemManager
    VARIABLES
    {
      osTrapEventID,
      osTrapEventType,
      osTrapEventSeverity,
      osTrapEventSystem,
      osTrapEventSubsystem,
      osTrapEventClass,
      osTrapEventInstance,
      osTrapEventGenerationTime,
      osTrapEventMessage
    }
    DESCRIPTION
      "This trap signifies that System Manager recognized that the event has
       occurred (at os, severity is OK)."
    ::= 403

--------------------------------------------------------------------------------
  osTrapNon-Critical TRAP-TYPE
    ENTERPRISE   systemManager
    VARIABLES
    {
      osTrapEventID,
      osTrapEventType,
      osTrapEventSeverity,
      osTrapEventSystem,
      osTrapEventSubsystem,
      osTrapEventClass,
      osTrapEventInstance,
      osTrapEventGenerationTime,
      osTrapEventMessage
    }
    DESCRIPTION
      "This trap signifies that System Manager recognized that the event has
       occurred (at os, severity is Non-Critical)."
    ::= 404

--------------------------------------------------------------------------------
  osTrapCritical TRAP-TYPE
    ENTERPRISE   systemManager
    VARIABLES
    {
      osTrapEventID,
      osTrapEventType,
      osTrapEventSeverity,
      osTrapEventSystem,
      osTrapEventSubsystem,
      osTrapEventClass,
      osTrapEventInstance,
      osTrapEventGenerationTime,
      osTrapEventMessage
    }
    DESCRIPTION
      "This trap signifies that System Manager recognized that the event has
       occurred (at os, severity is Critical)."
    ::= 405

--------------------------------------------------------------------------------
  osTrapNon-Recoverable TRAP-TYPE
    ENTERPRISE   systemManager
    VARIABLES
    {
      osTrapEventID,
      osTrapEventType,
      osTrapEventSeverity,
      osTrapEventSystem,
      osTrapEventSubsystem,
      osTrapEventClass,
      osTrapEventInstance,
      osTrapEventGenerationTime,
      osTrapEventMessage
    }
    DESCRIPTION
      "This trap signifies that System Manager recognized that the event has
       occurred (at os, severity is Non-Recoverable)."
    ::= 406

--------------------------------------------------------------------------------
  bodyTrapUnknown TRAP-TYPE
    ENTERPRISE   systemManager
    VARIABLES
    {
      bodyTrapEventID,
      bodyTrapEventType,
      bodyTrapEventSeverity,
      bodyTrapEventSystem,
      bodyTrapEventSubsystem,
      bodyTrapEventClass,
      bodyTrapEventInstance,
      bodyTrapEventGenerationTime,
      bodyTrapEventMessage
    }
    DESCRIPTION
      "This trap signifies that System Manager recognized that the event has
       occurred (at body, power unit, severity is unknown)."
    ::= 500

--------------------------------------------------------------------------------
  bodyTrapMonitor TRAP-TYPE
    ENTERPRISE   systemManager
    VARIABLES
    {
      bodyTrapEventID,
      bodyTrapEventType,
      bodyTrapEventSeverity,
      bodyTrapEventSystem,
      bodyTrapEventSubsystem,
      bodyTrapEventClass,
      bodyTrapEventInstance,
      bodyTrapEventGenerationTime,
      bodyTrapEventMessage
    }
    DESCRIPTION
      "This trap signifies that System Manager recognized that the event has
       occurred (at body, power unit, severity is Monitor)."
    ::= 501

--------------------------------------------------------------------------------
  bodyTrapInformation TRAP-TYPE
    ENTERPRISE   systemManager
    VARIABLES
    {
      bodyTrapEventID,
      bodyTrapEventType,
      bodyTrapEventSeverity,
      bodyTrapEventSystem,
      bodyTrapEventSubsystem,
      bodyTrapEventClass,
      bodyTrapEventInstance,
      bodyTrapEventGenerationTime,
      bodyTrapEventMessage
    }
    DESCRIPTION
      "This trap signifies that System Manager recognized that the event has
       occurred (at body, power unit, severity is Information)."
    ::= 502

--------------------------------------------------------------------------------
  bodyTrapOK TRAP-TYPE
    ENTERPRISE   systemManager
    VARIABLES
    {
      bodyTrapEventID,
      bodyTrapEventType,
      bodyTrapEventSeverity,
      bodyTrapEventSystem,
      bodyTrapEventSubsystem,
      bodyTrapEventClass,
      bodyTrapEventInstance,
      bodyTrapEventGenerationTime,
      bodyTrapEventMessage
    }
    DESCRIPTION
      "This trap signifies that System Manager recognized that the event has
       occurred (at body, power unit, severity is OK)."
    ::= 503

--------------------------------------------------------------------------------
  bodyTrapNon-Critical TRAP-TYPE
    ENTERPRISE   systemManager
    VARIABLES
    {
      bodyTrapEventID,
      bodyTrapEventType,
      bodyTrapEventSeverity,
      bodyTrapEventSystem,
      bodyTrapEventSubsystem,
      bodyTrapEventClass,
      bodyTrapEventInstance,
      bodyTrapEventGenerationTime,
      bodyTrapEventMessage
    }
    DESCRIPTION
      "This trap signifies that System Manager recognized that the event has
       occurred (at body, power unit, severity is Non-Critical)."
    ::= 504

--------------------------------------------------------------------------------
  bodyTrapCritical TRAP-TYPE
    ENTERPRISE   systemManager
    VARIABLES
    {
      bodyTrapEventID,
      bodyTrapEventType,
      bodyTrapEventSeverity,
      bodyTrapEventSystem,
      bodyTrapEventSubsystem,
      bodyTrapEventClass,
      bodyTrapEventInstance,
      bodyTrapEventGenerationTime,
      bodyTrapEventMessage
    }
    DESCRIPTION
      "This trap signifies that System Manager recognized that the event has
       occurred (at body, power unit, severity is Critical)."
    ::= 505

--------------------------------------------------------------------------------
  bodyTrapNon-Recoverable TRAP-TYPE
    ENTERPRISE   systemManager
    VARIABLES
    {
      bodyTrapEventID,
      bodyTrapEventType,
      bodyTrapEventSeverity,
      bodyTrapEventSystem,
      bodyTrapEventSubsystem,
      bodyTrapEventClass,
      bodyTrapEventInstance,
      bodyTrapEventGenerationTime,
      bodyTrapEventMessage
    }
    DESCRIPTION
      "This trap signifies that System Manager recognized that the event has
       occurred (at body, power unit, severity is Non-Recoverable)."
    ::= 506

--------------------------------------------------------------------------------
  powerUpsTrapUnknown TRAP-TYPE
    ENTERPRISE   systemManager
    VARIABLES
    {
      powerUpsTrapEventID,
      powerUpsTrapEventType,
      powerUpsTrapEventSeverity,
      powerUpsTrapEventSystem,
      powerUpsTrapEventSubsystem,
      powerUpsTrapEventClass,
      powerUpsTrapEventInstance,
      powerUpsTrapEventGenerationTime,
      powerUpsTrapEventMessage
    }
    DESCRIPTION
      "This trap signifies that System Manager recognized that the event has
       occurred (at UPS unit, severity is unknown)."
    ::= 600

--------------------------------------------------------------------------------
  powerUpsTrapMonitor TRAP-TYPE
    ENTERPRISE   systemManager
    VARIABLES
    {
      powerUpsTrapEventID,
      powerUpsTrapEventType,
      powerUpsTrapEventSeverity,
      powerUpsTrapEventSystem,
      powerUpsTrapEventSubsystem,
      powerUpsTrapEventClass,
      powerUpsTrapEventInstance,
      powerUpsTrapEventGenerationTime,
      powerUpsTrapEventMessage
    }
    DESCRIPTION
      "This trap signifies that System Manager recognized that the event has
       occurred (at UPS unit, severity is Monitor)."
    ::= 601

--------------------------------------------------------------------------------
  powerUpsTrapInformation TRAP-TYPE
    ENTERPRISE   systemManager
    VARIABLES
    {
      powerUpsTrapEventID,
      powerUpsTrapEventType,
      powerUpsTrapEventSeverity,
      powerUpsTrapEventSystem,
      powerUpsTrapEventSubsystem,
      powerUpsTrapEventClass,
      powerUpsTrapEventInstance,
      powerUpsTrapEventGenerationTime,
      powerUpsTrapEventMessage
    }
    DESCRIPTION
      "This trap signifies that System Manager recognized that the event has
       occurred (at UPS unit, severity is Information)."
    ::= 602

--------------------------------------------------------------------------------
  powerUpsTrapOK TRAP-TYPE
    ENTERPRISE   systemManager
    VARIABLES
    {
      powerUpsTrapEventID,
      powerUpsTrapEventType,
      powerUpsTrapEventSeverity,
      powerUpsTrapEventSystem,
      powerUpsTrapEventSubsystem,
      powerUpsTrapEventClass,
      powerUpsTrapEventInstance,
      powerUpsTrapEventGenerationTime,
      powerUpsTrapEventMessage
    }
    DESCRIPTION
      "This trap signifies that System Manager recognized that the event has
       occurred (at UPS unit, severity is OK)."
    ::= 603

--------------------------------------------------------------------------------
  powerUpsTrapNon-Critical TRAP-TYPE
    ENTERPRISE   systemManager
    VARIABLES
    {
      powerUpsTrapEventID,
      powerUpsTrapEventType,
      powerUpsTrapEventSeverity,
      powerUpsTrapEventSystem,
      powerUpsTrapEventSubsystem,
      powerUpsTrapEventClass,
      powerUpsTrapEventInstance,
      powerUpsTrapEventGenerationTime,
      powerUpsTrapEventMessage
    }
    DESCRIPTION
      "This trap signifies that System Manager recognized that the event has
       occurred (at UPS unit, severity is Non-Critical)."
    ::= 604

--------------------------------------------------------------------------------
  powerUpsTrapCritical TRAP-TYPE
    ENTERPRISE   systemManager
    VARIABLES
    {
      powerUpsTrapEventID,
      powerUpsTrapEventType,
      powerUpsTrapEventSeverity,
      powerUpsTrapEventSystem,
      powerUpsTrapEventSubsystem,
      powerUpsTrapEventClass,
      powerUpsTrapEventInstance,
      powerUpsTrapEventGenerationTime,
      powerUpsTrapEventMessage
    }
    DESCRIPTION
      "This trap signifies that System Manager recognized that the event has
       occurred (at UPS unit, severity is Critical)."
    ::= 605

--------------------------------------------------------------------------------
  powerUpsTrapNon-Recoverable TRAP-TYPE
    ENTERPRISE   systemManager
    VARIABLES
    {
      powerUpsTrapEventID,
      powerUpsTrapEventType,
      powerUpsTrapEventSeverity,
      powerUpsTrapEventSystem,
      powerUpsTrapEventSubsystem,
      powerUpsTrapEventClass,
      powerUpsTrapEventInstance,
      powerUpsTrapEventGenerationTime,
      powerUpsTrapEventMessage
    }
    DESCRIPTION
      "This trap signifies that System Manager recognized that the event has
       occurred (at UPS unit, severity is Non-Recoverable)."
    ::= 606

--------------------------------------------------------------------------------
  systenBoardTrapUnknown TRAP-TYPE
    ENTERPRISE   systemManager
    VARIABLES
    {
      systenBoardTrapEventID,
      systenBoardTrapEventType,
      systenBoardTrapEventSeverity,
      systenBoardTrapEventSystem,
      systenBoardTrapEventSubsystem,
      systenBoardTrapEventClass,
      systenBoardTrapEventInstance,
      systenBoardTrapEventGenerationTime,
      systenBoardTrapEventMessage
    }
    DESCRIPTION
      "This trap signifies that System Manager recognized that the event has
       occurred (at system board, severity is unknown)."
    ::= 700

--------------------------------------------------------------------------------
  systenBoardTrapMonitor TRAP-TYPE
    ENTERPRISE   systemManager
    VARIABLES
    {
      systenBoardTrapEventID,
      systenBoardTrapEventType,
      systenBoardTrapEventSeverity,
      systenBoardTrapEventSystem,
      systenBoardTrapEventSubsystem,
      systenBoardTrapEventClass,
      systenBoardTrapEventInstance,
      systenBoardTrapEventGenerationTime,
      systenBoardTrapEventMessage
    }
    DESCRIPTION
      "This trap signifies that System Manager recognized that the event has
       occurred (at system board, severity is Monitor)."
    ::= 701

--------------------------------------------------------------------------------
  systenBoardTrapInformation TRAP-TYPE
    ENTERPRISE   systemManager
    VARIABLES
    {
      systenBoardTrapEventID,
      systenBoardTrapEventType,
      systenBoardTrapEventSeverity,
      systenBoardTrapEventSystem,
      systenBoardTrapEventSubsystem,
      systenBoardTrapEventClass,
      systenBoardTrapEventInstance,
      systenBoardTrapEventGenerationTime,
      systenBoardTrapEventMessage
    }
    DESCRIPTION
      "This trap signifies that System Manager recognized that the event has
       occurred (at system board, severity is Information)."
    ::= 702

--------------------------------------------------------------------------------
  systenBoardTrapOK TRAP-TYPE
    ENTERPRISE   systemManager
    VARIABLES
    {
      systenBoardTrapEventID,
      systenBoardTrapEventType,
      systenBoardTrapEventSeverity,
      systenBoardTrapEventSystem,
      systenBoardTrapEventSubsystem,
      systenBoardTrapEventClass,
      systenBoardTrapEventInstance,
      systenBoardTrapEventGenerationTime,
      systenBoardTrapEventMessage
    }
    DESCRIPTION
      "This trap signifies that System Manager recognized that the event has
       occurred (at system board, severity is OK)."
    ::= 703

--------------------------------------------------------------------------------
  systenBoardTrapNon-Critical TRAP-TYPE
    ENTERPRISE   systemManager
    VARIABLES
    {
      systenBoardTrapEventID,
      systenBoardTrapEventType,
      systenBoardTrapEventSeverity,
      systenBoardTrapEventSystem,
      systenBoardTrapEventSubsystem,
      systenBoardTrapEventClass,
      systenBoardTrapEventInstance,
      systenBoardTrapEventGenerationTime,
      systenBoardTrapEventMessage
    }
    DESCRIPTION
      "This trap signifies that System Manager recognized that the event has
       occurred (at system board, severity is Non-Critical)."
    ::= 704

--------------------------------------------------------------------------------
  systenBoardTrapCritical TRAP-TYPE
    ENTERPRISE   systemManager
    VARIABLES
    {
      systenBoardTrapEventID,
      systenBoardTrapEventType,
      systenBoardTrapEventSeverity,
      systenBoardTrapEventSystem,
      systenBoardTrapEventSubsystem,
      systenBoardTrapEventClass,
      systenBoardTrapEventInstance,
      systenBoardTrapEventGenerationTime,
      systenBoardTrapEventMessage
    }
    DESCRIPTION
      "This trap signifies that System Manager recognized that the event has
       occurred (at system board, severity is Critical)."
    ::= 705

--------------------------------------------------------------------------------
  systenBoardTrapNon-Recoverable TRAP-TYPE
    ENTERPRISE   systemManager
    VARIABLES
    {
      systenBoardTrapEventID,
      systenBoardTrapEventType,
      systenBoardTrapEventSeverity,
      systenBoardTrapEventSystem,
      systenBoardTrapEventSubsystem,
      systenBoardTrapEventClass,
      systenBoardTrapEventInstance,
      systenBoardTrapEventGenerationTime,
      systenBoardTrapEventMessage
    }
    DESCRIPTION
      "This trap signifies that System Manager recognized that the event has
       occurred (at system board, severity is Non-Recoverable)."
    ::= 706

--------------------------------------------------------------------------------
  extendedSlotTrapUnknown TRAP-TYPE
    ENTERPRISE   systemManager
    VARIABLES
    {
      extendedSlotTrapEventID,
      extendedSlotTrapEventType,
      extendedSlotTrapEventSeverity,
      extendedSlotTrapEventSystem,
      extendedSlotTrapEventSubsystem,
      extendedSlotTrapEventClass,
      extendedSlotTrapEventInstance,
      extendedSlotTrapEventGenerationTime,
      extendedSlotTrapEventMessage
    }
    DESCRIPTION
      "This trap signifies that System Manager recognized that the event has
       occurred (at extended slot, severity is unknown)."
    ::= 800

--------------------------------------------------------------------------------
  extendedSlotTrapMonitor TRAP-TYPE
    ENTERPRISE   systemManager
    VARIABLES
    {
      extendedSlotTrapEventID,
      extendedSlotTrapEventType,
      extendedSlotTrapEventSeverity,
      extendedSlotTrapEventSystem,
      extendedSlotTrapEventSubsystem,
      extendedSlotTrapEventClass,
      extendedSlotTrapEventInstance,
      extendedSlotTrapEventGenerationTime,
      extendedSlotTrapEventMessage
    }
    DESCRIPTION
      "This trap signifies that System Manager recognized that the event has
       occurred (at extended slot, severity is Monitor)."
    ::= 801

--------------------------------------------------------------------------------
  extendedSlotTrapInformation TRAP-TYPE
    ENTERPRISE   systemManager
    VARIABLES
    {
      extendedSlotTrapEventID,
      extendedSlotTrapEventType,
      extendedSlotTrapEventSeverity,
      extendedSlotTrapEventSystem,
      extendedSlotTrapEventSubsystem,
      extendedSlotTrapEventClass,
      extendedSlotTrapEventInstance,
      extendedSlotTrapEventGenerationTime,
      extendedSlotTrapEventMessage
    }
    DESCRIPTION
      "This trap signifies that System Manager recognized that the event has
       occurred (at extended slot, severity is Information)."
    ::= 802

--------------------------------------------------------------------------------
  extendedSlotTrapOK TRAP-TYPE
    ENTERPRISE   systemManager
    VARIABLES
    {
      extendedSlotTrapEventID,
      extendedSlotTrapEventType,
      extendedSlotTrapEventSeverity,
      extendedSlotTrapEventSystem,
      extendedSlotTrapEventSubsystem,
      extendedSlotTrapEventClass,
      extendedSlotTrapEventInstance,
      extendedSlotTrapEventGenerationTime,
      extendedSlotTrapEventMessage
    }
    DESCRIPTION
      "This trap signifies that System Manager recognized that the event has
       occurred (at extended slot, severity is OK)."
    ::= 803

--------------------------------------------------------------------------------
  extendedSlotTrapNon-Critical TRAP-TYPE
    ENTERPRISE   systemManager
    VARIABLES
    {
      extendedSlotTrapEventID,
      extendedSlotTrapEventType,
      extendedSlotTrapEventSeverity,
      extendedSlotTrapEventSystem,
      extendedSlotTrapEventSubsystem,
      extendedSlotTrapEventClass,
      extendedSlotTrapEventInstance,
      extendedSlotTrapEventGenerationTime,
      extendedSlotTrapEventMessage
    }
    DESCRIPTION
      "This trap signifies that System Manager recognized that the event has
       occurred (at extended slot, severity is Non-Critical)."
    ::= 804

--------------------------------------------------------------------------------
  extendedSlotTrapCritical TRAP-TYPE
    ENTERPRISE   systemManager
    VARIABLES
    {
      extendedSlotTrapEventID,
      extendedSlotTrapEventType,
      extendedSlotTrapEventSeverity,
      extendedSlotTrapEventSystem,
      extendedSlotTrapEventSubsystem,
      extendedSlotTrapEventClass,
      extendedSlotTrapEventInstance,
      extendedSlotTrapEventGenerationTime,
      extendedSlotTrapEventMessage
    }
    DESCRIPTION
      "This trap signifies that System Manager recognized that the event has
       occurred (at extended slot, severity is Critical)."
    ::= 805

--------------------------------------------------------------------------------
  extendedSlotTrapNon-Recoverable TRAP-TYPE
    ENTERPRISE   systemManager
    VARIABLES
    {
      extendedSlotTrapEventID,
      extendedSlotTrapEventType,
      extendedSlotTrapEventSeverity,
      extendedSlotTrapEventSystem,
      extendedSlotTrapEventSubsystem,
      extendedSlotTrapEventClass,
      extendedSlotTrapEventInstance,
      extendedSlotTrapEventGenerationTime,
      extendedSlotTrapEventMessage
    }
    DESCRIPTION
      "This trap signifies that System Manager recognized that the event has
       occurred (at extended slot, severity is Non-Recoverable)."
    ::= 806

--------------------------------------------------------------------------------
  scsiTrapUnknown TRAP-TYPE
    ENTERPRISE   systemManager
    VARIABLES
    {
      scsiTrapEventID,
      scsiTrapEventType,
      scsiTrapEventSeverity,
      scsiTrapEventSystem,
      scsiTrapEventSubsystem,
      scsiTrapEventClass,
      scsiTrapEventInstance,
      scsiTrapEventGenerationTime,
      scsiTrapEventMessage
    }
    DESCRIPTION
      "This trap signifies that System Manager recognized that the event has
       occurred (at scsi device, severity is unknown)."
    ::= 900

--------------------------------------------------------------------------------
  scsiTrapMonitor TRAP-TYPE
    ENTERPRISE   systemManager
    VARIABLES
    {
      scsiTrapEventID,
      scsiTrapEventType,
      scsiTrapEventSeverity,
      scsiTrapEventSystem,
      scsiTrapEventSubsystem,
      scsiTrapEventClass,
      scsiTrapEventInstance,
      scsiTrapEventGenerationTime,
      scsiTrapEventMessage
    }
    DESCRIPTION
      "This trap signifies that System Manager recognized that the event has
       occurred (at scsi device, severity is Monitor)."
    ::= 901

--------------------------------------------------------------------------------
  scsiTrapInformation TRAP-TYPE
    ENTERPRISE   systemManager
    VARIABLES
    {
      scsiTrapEventID,
      scsiTrapEventType,
      scsiTrapEventSeverity,
      scsiTrapEventSystem,
      scsiTrapEventSubsystem,
      scsiTrapEventClass,
      scsiTrapEventInstance,
      scsiTrapEventGenerationTime,
      scsiTrapEventMessage
    }
    DESCRIPTION
      "This trap signifies that System Manager recognized that the event has
       occurred (at scsi device, severity is Information)."
    ::= 902

--------------------------------------------------------------------------------
  scsiTrapOK TRAP-TYPE
    ENTERPRISE   systemManager
    VARIABLES
    {
      scsiTrapEventID,
      scsiTrapEventType,
      scsiTrapEventSeverity,
      scsiTrapEventSystem,
      scsiTrapEventSubsystem,
      scsiTrapEventClass,
      scsiTrapEventInstance,
      scsiTrapEventGenerationTime,
      scsiTrapEventMessage
    }
    DESCRIPTION
      "This trap signifies that System Manager recognized that the event has
       occurred (at scsi device, severity is OK)."
    ::= 903

--------------------------------------------------------------------------------
  scsiTrapNon-Critical TRAP-TYPE
    ENTERPRISE   systemManager
    VARIABLES
    {
      scsiTrapEventID,
      scsiTrapEventType,
      scsiTrapEventSeverity,
      scsiTrapEventSystem,
      scsiTrapEventSubsystem,
      scsiTrapEventClass,
      scsiTrapEventInstance,
      scsiTrapEventGenerationTime,
      scsiTrapEventMessage
    }
    DESCRIPTION
      "This trap signifies that System Manager recognized that the event has
       occurred (at scsi device, severity is Non-Critical)."
    ::= 904

--------------------------------------------------------------------------------
  scsiTrapCritical TRAP-TYPE
    ENTERPRISE   systemManager
    VARIABLES
    {
      scsiTrapEventID,
      scsiTrapEventType,
      scsiTrapEventSeverity,
      scsiTrapEventSystem,
      scsiTrapEventSubsystem,
      scsiTrapEventClass,
      scsiTrapEventInstance,
      scsiTrapEventGenerationTime,
      scsiTrapEventMessage
    }
    DESCRIPTION
      "This trap signifies that System Manager recognized that the event has
       occurred (at scsi device, severity is Critical)."
    ::= 905

--------------------------------------------------------------------------------
  scsiTrapNon-Recoverable TRAP-TYPE
    ENTERPRISE   systemManager
    VARIABLES
    {
      scsiTrapEventID,
      scsiTrapEventType,
      scsiTrapEventSeverity,
      scsiTrapEventSystem,
      scsiTrapEventSubsystem,
      scsiTrapEventClass,
      scsiTrapEventInstance,
      scsiTrapEventGenerationTime,
      scsiTrapEventMessage
    }
    DESCRIPTION
      "This trap signifies that System Manager recognized that the event has
       occurred (at scsi device, severity is Non-Recoverable)."
    ::= 906

--------------------------------------------------------------------------------
  diskArrayTrapUnknown TRAP-TYPE
    ENTERPRISE   systemManager
    VARIABLES
    {
      diskArrayTrapEventID,
      diskArrayTrapEventType,
      diskArrayTrapEventSeverity,
      diskArrayTrapEventSystem,
      diskArrayTrapEventSubsystem,
      diskArrayTrapEventClass,
      diskArrayTrapEventInstance,
      diskArrayTrapEventGenerationTime,
      diskArrayTrapEventMessage
    }
    DESCRIPTION
      "This trap signifies that System Manager recognized that the event has
       occurred (at disk array, severity is unknown)."
    ::= 1000

--------------------------------------------------------------------------------
  diskArrayTrapMonitor TRAP-TYPE
    ENTERPRISE   systemManager
    VARIABLES
    {
      diskArrayTrapEventID,
      diskArrayTrapEventType,
      diskArrayTrapEventSeverity,
      diskArrayTrapEventSystem,
      diskArrayTrapEventSubsystem,
      diskArrayTrapEventClass,
      diskArrayTrapEventInstance,
      diskArrayTrapEventGenerationTime,
      diskArrayTrapEventMessage
    }
    DESCRIPTION
      "This trap signifies that System Manager recognized that the event has
       occurred (at disk array, severity is Monitor)."
    ::= 1001

--------------------------------------------------------------------------------
  diskArrayTrapInformation TRAP-TYPE
    ENTERPRISE   systemManager
    VARIABLES
    {
      diskArrayTrapEventID,
      diskArrayTrapEventType,
      diskArrayTrapEventSeverity,
      diskArrayTrapEventSystem,
      diskArrayTrapEventSubsystem,
      diskArrayTrapEventClass,
      diskArrayTrapEventInstance,
      diskArrayTrapEventGenerationTime,
      diskArrayTrapEventMessage
    }
    DESCRIPTION
      "This trap signifies that System Manager recognized that the event has
       occurred (at disk array, severity is Information)."
    ::= 1002

--------------------------------------------------------------------------------
  diskArrayTrapOK TRAP-TYPE
    ENTERPRISE   systemManager
    VARIABLES
    {
      diskArrayTrapEventID,
      diskArrayTrapEventType,
      diskArrayTrapEventSeverity,
      diskArrayTrapEventSystem,
      diskArrayTrapEventSubsystem,
      diskArrayTrapEventClass,
      diskArrayTrapEventInstance,
      diskArrayTrapEventGenerationTime,
      diskArrayTrapEventMessage
    }
    DESCRIPTION
      "This trap signifies that System Manager recognized that the event has
       occurred (at disk array, severity is OK)."
    ::= 1003

--------------------------------------------------------------------------------
  diskArrayTrapNon-Critical TRAP-TYPE
    ENTERPRISE   systemManager
    VARIABLES
    {
      diskArrayTrapEventID,
      diskArrayTrapEventType,
      diskArrayTrapEventSeverity,
      diskArrayTrapEventSystem,
      diskArrayTrapEventSubsystem,
      diskArrayTrapEventClass,
      diskArrayTrapEventInstance,
      diskArrayTrapEventGenerationTime,
      diskArrayTrapEventMessage
    }
    DESCRIPTION
      "This trap signifies that System Manager recognized that the event has
       occurred (at disk array, severity is Non-Critical)."
    ::= 1004

--------------------------------------------------------------------------------
  diskArrayTrapCritical TRAP-TYPE
    ENTERPRISE   systemManager
    VARIABLES
    {
      diskArrayTrapEventID,
      diskArrayTrapEventType,
      diskArrayTrapEventSeverity,
      diskArrayTrapEventSystem,
      diskArrayTrapEventSubsystem,
      diskArrayTrapEventClass,
      diskArrayTrapEventInstance,
      diskArrayTrapEventGenerationTime,
      diskArrayTrapEventMessage
    }
    DESCRIPTION
      "This trap signifies that System Manager recognized that the event has
       occurred (at disk array, severity is Critical)."
    ::= 1005

--------------------------------------------------------------------------------
  diskArrayTrapNon-Recoverable TRAP-TYPE
    ENTERPRISE   systemManager
    VARIABLES
    {
      diskArrayTrapEventID,
      diskArrayTrapEventType,
      diskArrayTrapEventSeverity,
      diskArrayTrapEventSystem,
      diskArrayTrapEventSubsystem,
      diskArrayTrapEventClass,
      diskArrayTrapEventInstance,
      diskArrayTrapEventGenerationTime,
      diskArrayTrapEventMessage
    }
    DESCRIPTION
      "This trap signifies that System Manager recognized that the event has
       occurred (at disk array, severity is Non-Recoverable)."
    ::= 1006

--------------------------------------------------------------------------------
  biosPostTrapUnknown TRAP-TYPE
    ENTERPRISE   systemManager
    VARIABLES
    {
      biosPostTrapEventID,
      biosPostTrapEventType,
      biosPostTrapEventSeverity,
      biosPostTrapEventSystem,
      biosPostTrapEventSubsystem,
      biosPostTrapEventClass,
      biosPostTrapEventInstance,
      biosPostTrapEventGenerationTime,
      biosPostTrapEventMessage
    }
    DESCRIPTION
      "This trap signifies that System Manager recognized that the event has
       occurred (bios post, severity is unknown)."
    ::= 1100

--------------------------------------------------------------------------------
  biosPostTrapMonitor TRAP-TYPE
    ENTERPRISE   systemManager
    VARIABLES
    {
      biosPostTrapEventID,
      biosPostTrapEventType,
      biosPostTrapEventSeverity,
      biosPostTrapEventSystem,
      biosPostTrapEventSubsystem,
      biosPostTrapEventClass,
      biosPostTrapEventInstance,
      biosPostTrapEventGenerationTime,
      biosPostTrapEventMessage
    }
    DESCRIPTION
      "This trap signifies that System Manager recognized that the event has
       occurred (bios post, severity is Monitor)."
    ::= 1101

--------------------------------------------------------------------------------
  biosPostTrapInformation TRAP-TYPE
    ENTERPRISE   systemManager
    VARIABLES
    {
      biosPostTrapEventID,
      biosPostTrapEventType,
      biosPostTrapEventSeverity,
      biosPostTrapEventSystem,
      biosPostTrapEventSubsystem,
      biosPostTrapEventClass,
      biosPostTrapEventInstance,
      biosPostTrapEventGenerationTime,
      biosPostTrapEventMessage
    }
    DESCRIPTION
      "This trap signifies that System Manager recognized that the event has
       occurred (bios post, severity is Information)."
    ::= 1102

--------------------------------------------------------------------------------
  biosPostTrapOK TRAP-TYPE
    ENTERPRISE   systemManager
    VARIABLES
    {
      biosPostTrapEventID,
      biosPostTrapEventType,
      biosPostTrapEventSeverity,
      biosPostTrapEventSystem,
      biosPostTrapEventSubsystem,
      biosPostTrapEventClass,
      biosPostTrapEventInstance,
      biosPostTrapEventGenerationTime,
      biosPostTrapEventMessage
    }
    DESCRIPTION
      "This trap signifies that System Manager recognized that the event has
       occurred (bios post, severity is OK)."
    ::= 1103

--------------------------------------------------------------------------------
  biosPostTrapNon-Critical TRAP-TYPE
    ENTERPRISE   systemManager
    VARIABLES
    {
      biosPostTrapEventID,
      biosPostTrapEventType,
      biosPostTrapEventSeverity,
      biosPostTrapEventSystem,
      biosPostTrapEventSubsystem,
      biosPostTrapEventClass,
      biosPostTrapEventInstance,
      biosPostTrapEventGenerationTime,
      biosPostTrapEventMessage
    }
    DESCRIPTION
      "This trap signifies that System Manager recognized that the event has
       occurred (bios post, severity is Non-Critical)."
    ::= 1104

--------------------------------------------------------------------------------
  biosPostTrapCritical TRAP-TYPE
    ENTERPRISE   systemManager
    VARIABLES
    {
      biosPostTrapEventID,
      biosPostTrapEventType,
      biosPostTrapEventSeverity,
      biosPostTrapEventSystem,
      biosPostTrapEventSubsystem,
      biosPostTrapEventClass,
      biosPostTrapEventInstance,
      biosPostTrapEventGenerationTime,
      biosPostTrapEventMessage
    }
    DESCRIPTION
      "This trap signifies that System Manager recognized that the event has
       occurred (bios post, severity is Critical)."
    ::= 1105

--------------------------------------------------------------------------------
  biosPostTrapNon-Recoverable TRAP-TYPE
    ENTERPRISE   systemManager
    VARIABLES
    {
      biosPostTrapEventID,
      biosPostTrapEventType,
      biosPostTrapEventSeverity,
      biosPostTrapEventSystem,
      biosPostTrapEventSubsystem,
      biosPostTrapEventClass,
      biosPostTrapEventInstance,
      biosPostTrapEventGenerationTime,
      biosPostTrapEventMessage
    }
    DESCRIPTION
      "This trap signifies that System Manager recognized that the event has
       occurred (bios post, severity is Non-Recoverable)."
    ::= 1106

--------------------------------------------------------------------------------
  clusterTrapUnknown TRAP-TYPE
    ENTERPRISE   systemManager
    VARIABLES
    {
      clusterTrapEventID,
      clusterTrapEventType,
      clusterTrapEventSeverity,
      clusterTrapEventSystem,
      clusterTrapEventSubsystem,
      clusterTrapEventClass,
      clusterTrapEventInstance,
      clusterTrapEventGenerationTime,
      clusterTrapEventMessage
    }
    DESCRIPTION
      "This trap signifies that System Manager recognized that the event has
       occurred (at cluster, severity is unknown)."
    ::= 1200

--------------------------------------------------------------------------------
  clusterTrapMonitor TRAP-TYPE
    ENTERPRISE   systemManager
    VARIABLES
    {
      clusterTrapEventID,
      clusterTrapEventType,
      clusterTrapEventSeverity,
      clusterTrapEventSystem,
      clusterTrapEventSubsystem,
      clusterTrapEventClass,
      clusterTrapEventInstance,
      clusterTrapEventGenerationTime,
      clusterTrapEventMessage
    }
    DESCRIPTION
      "This trap signifies that System Manager recognized that the event has
       occurred (at cluster, severity is Monitor)."
    ::= 1201

--------------------------------------------------------------------------------
  clusterTrapInformation TRAP-TYPE
    ENTERPRISE   systemManager
    VARIABLES
    {
      clusterTrapEventID,
      clusterTrapEventType,
      clusterTrapEventSeverity,
      clusterTrapEventSystem,
      clusterTrapEventSubsystem,
      clusterTrapEventClass,
      clusterTrapEventInstance,
      clusterTrapEventGenerationTime,
      clusterTrapEventMessage
    }
    DESCRIPTION
      "This trap signifies that System Manager recognized that the event has
       occurred (at cluster, severity is Information)."
    ::= 1202

--------------------------------------------------------------------------------
  clusterTrapOK TRAP-TYPE
    ENTERPRISE   systemManager
    VARIABLES
    {
      clusterTrapEventID,
      clusterTrapEventType,
      clusterTrapEventSeverity,
      clusterTrapEventSystem,
      clusterTrapEventSubsystem,
      clusterTrapEventClass,
      clusterTrapEventInstance,
      clusterTrapEventGenerationTime,
      clusterTrapEventMessage
    }
    DESCRIPTION
      "This trap signifies that System Manager recognized that the event has
       occurred (at cluster, severity is OK)."
    ::= 1203

--------------------------------------------------------------------------------
  clusterTrapNon-Critical TRAP-TYPE
    ENTERPRISE   systemManager
    VARIABLES
    {
      clusterTrapEventID,
      clusterTrapEventType,
      clusterTrapEventSeverity,
      clusterTrapEventSystem,
      clusterTrapEventSubsystem,
      clusterTrapEventClass,
      clusterTrapEventInstance,
      clusterTrapEventGenerationTime,
      clusterTrapEventMessage
    }
    DESCRIPTION
      "This trap signifies that System Manager recognized that the event has
       occurred (at cluster, severity is Non-Critical)."
    ::= 1204

--------------------------------------------------------------------------------
  clusterTrapCritical TRAP-TYPE
    ENTERPRISE   systemManager
    VARIABLES
    {
      clusterTrapEventID,
      clusterTrapEventType,
      clusterTrapEventSeverity,
      clusterTrapEventSystem,
      clusterTrapEventSubsystem,
      clusterTrapEventClass,
      clusterTrapEventInstance,
      clusterTrapEventGenerationTime,
      clusterTrapEventMessage
    }
    DESCRIPTION
      "This trap signifies that System Manager recognized that the event has
       occurred (at cluster, severity is Critical)."
    ::= 1205

--------------------------------------------------------------------------------
  clusterTrapNon-Recoverable TRAP-TYPE
    ENTERPRISE   systemManager
    VARIABLES
    {
      clusterTrapEventID,
      clusterTrapEventType,
      clusterTrapEventSeverity,
      clusterTrapEventSystem,
      clusterTrapEventSubsystem,
      clusterTrapEventClass,
      clusterTrapEventInstance,
      clusterTrapEventGenerationTime,
      clusterTrapEventMessage
    }
    DESCRIPTION
      "This trap signifies that System Manager recognized that the event has
       occurred (at cluster, severity is Non-Recoverable)."
    ::= 1206

--------------------------------------------------------------------------------
  networkTrapUnknown TRAP-TYPE
    ENTERPRISE   systemManager
    VARIABLES
    {
      networkTrapEventID,
      networkTrapEventType,
      networkTrapEventSeverity,
      networkTrapEventSystem,
      networkTrapEventSubsystem,
      networkTrapEventClass,
      networkTrapEventInstance,
      networkTrapEventGenerationTime,
      networkTrapEventMessage
    }
    DESCRIPTION
      "This trap signifies that System Manager recognized that the event has
       occurred (at network, severity is unknown)."
    ::= 1300

--------------------------------------------------------------------------------
  networkTrapMonitor TRAP-TYPE
    ENTERPRISE   systemManager
    VARIABLES
    {
      networkTrapEventID,
      networkTrapEventType,
      networkTrapEventSeverity,
      networkTrapEventSystem,
      networkTrapEventSubsystem,
      networkTrapEventClass,
      networkTrapEventInstance,
      networkTrapEventGenerationTime,
      networkTrapEventMessage
    }
    DESCRIPTION
      "This trap signifies that System Manager recognized that the event has
       occurred (at network, severity is Monitor)."
    ::= 1301

--------------------------------------------------------------------------------
  networkTrapInformation TRAP-TYPE
    ENTERPRISE   systemManager
    VARIABLES
    {
      networkTrapEventID,
      networkTrapEventType,
      networkTrapEventSeverity,
      networkTrapEventSystem,
      networkTrapEventSubsystem,
      networkTrapEventClass,
      networkTrapEventInstance,
      networkTrapEventGenerationTime,
      networkTrapEventMessage
    }
    DESCRIPTION
      "This trap signifies that System Manager recognized that the event has
       occurred (at network, severity is Information)."
    ::= 1302

--------------------------------------------------------------------------------
  networkTrapOK TRAP-TYPE
    ENTERPRISE   systemManager
    VARIABLES
    {
      networkTrapEventID,
      networkTrapEventType,
      networkTrapEventSeverity,
      networkTrapEventSystem,
      networkTrapEventSubsystem,
      networkTrapEventClass,
      networkTrapEventInstance,
      networkTrapEventGenerationTime,
      networkTrapEventMessage
    }
    DESCRIPTION
      "This trap signifies that System Manager recognized that the event has
       occurred (at network, severity is OK)."
    ::= 1303

--------------------------------------------------------------------------------
  networkTrapNon-Critical TRAP-TYPE
    ENTERPRISE   systemManager
    VARIABLES
    {
      networkTrapEventID,
      networkTrapEventType,
      networkTrapEventSeverity,
      networkTrapEventSystem,
      networkTrapEventSubsystem,
      networkTrapEventClass,
      networkTrapEventInstance,
      networkTrapEventGenerationTime,
      networkTrapEventMessage
    }
    DESCRIPTION
      "This trap signifies that System Manager recognized that the event has
       occurred (at network, severity is Non-Critical)."
    ::= 1304

--------------------------------------------------------------------------------
  networkTrapCritical TRAP-TYPE
    ENTERPRISE   systemManager
    VARIABLES
    {
      networkTrapEventID,
      networkTrapEventType,
      networkTrapEventSeverity,
      networkTrapEventSystem,
      networkTrapEventSubsystem,
      networkTrapEventClass,
      networkTrapEventInstance,
      networkTrapEventGenerationTime,
      networkTrapEventMessage
    }
    DESCRIPTION
      "This trap signifies that System Manager recognized that the event has
       occurred (at network, severity is Critical)."
    ::= 1305

--------------------------------------------------------------------------------
  networkTrapNon-Recoverable TRAP-TYPE
    ENTERPRISE   systemManager
    VARIABLES
    {
      networkTrapEventID,
      networkTrapEventType,
      networkTrapEventSeverity,
      networkTrapEventSystem,
      networkTrapEventSubsystem,
      networkTrapEventClass,
      networkTrapEventInstance,
      networkTrapEventGenerationTime,
      networkTrapEventMessage
    }
    DESCRIPTION
      "This trap signifies that System Manager recognized that the event has
       occurred (at network, severity is Non-Recoverable)."
    ::= 1306


--------------------------------------------------------------------------------

END

--------------------------------------------------------------------------------
