--
-- 	Copyright 1992, 1993, 1995, 1996 Shiva Corporation
--

SHIVA-MEM-MIB DEFINITIONS ::= BEGIN

IMPORTS
      	Counter
  		FROM RFC1155-SMI
    	OBJECT-TYPE
    		FROM RFC-1212		-- Concise MIB Definitions
    	memory
    		FROM SHIVA-MIB;

    memoryTotal OBJECT-TYPE
	SYNTAX	INTEGER
	ACCESS  read-only
	STATUS  mandatory
	DESCRIPTION
	    	"Total number of bytes of RAM installed."
	::= { memory 1 }

    memoryFree	OBJECT-TYPE
	SYNTAX	INTEGER
	ACCESS  read-only
	STATUS  mandatory
	DESCRIPTION
	    	"Total number of bytes of memory on the 'malloc'
		free list."
	::= { memory 2 }

    memoryMalloc OBJECT-TYPE
	SYNTAX	INTEGER
	ACCESS  read-only
	STATUS  mandatory
	DESCRIPTION
	    	"Total number of bytes of memory in use
		by malloc."
	::= { memory 3 }

    memoryUnused OBJECT-TYPE
	SYNTAX	INTEGER
	ACCESS  read-only
	STATUS  mandatory
	DESCRIPTION
	    	"Total number of bytes of memory not in use
		(available for either malloc or config)."
	::= { memory 4 }

    memoryConf OBJECT-TYPE
	SYNTAX	INTEGER
	ACCESS  read-only
	STATUS  mandatory
	DESCRIPTION
	    	"Total number of bytes of memory currently
		allocated for use by configuration."
	::= { memory 5 }

    memoryConfFree OBJECT-TYPE
	SYNTAX	INTEGER
	ACCESS  read-only
	STATUS  mandatory
	DESCRIPTION
	    	"Total number of bytes of memory allocated for
		configuration, but not in use."
	::= { memory 6 }

    memoryImageCode OBJECT-TYPE
	SYNTAX	INTEGER
	ACCESS  read-only
	STATUS  mandatory
	DESCRIPTION
	    	"Total number of bytes of code in the system image."
	::= { memory 7 }

    memoryImageInitialized OBJECT-TYPE
	SYNTAX	INTEGER
	ACCESS  read-only
	STATUS  mandatory
	DESCRIPTION
	    	"Total number of bytes of initialized data in the
		system image."
	::= { memory 8 }

    memoryImageUninitialized OBJECT-TYPE
	SYNTAX	INTEGER
	ACCESS  read-only
	STATUS  mandatory
	DESCRIPTION
	    	"Total number of bytes of uninitialized data in the
		system image."
	::= { memory 9 }

    memoryVromCode OBJECT-TYPE
	SYNTAX	INTEGER
	ACCESS  read-only
	STATUS  mandatory
	DESCRIPTION
	    	"Total number of bytes of code in the VROM."
	::= { memory 10 }

    memoryVromProtected OBJECT-TYPE
	SYNTAX	INTEGER
	ACCESS  read-only
	STATUS  mandatory
	DESCRIPTION
	    	"Total number of bytes of non-volatile data in the
		VROM."
	::= { memory 11 }

    memoryVromInitialized OBJECT-TYPE
	SYNTAX	INTEGER
	ACCESS  read-only
	STATUS  mandatory
	DESCRIPTION
	    	"Total number of bytes of initialized data in the
		VROM."
	::= { memory 12 }

    memoryVromUninitialized OBJECT-TYPE
	SYNTAX	INTEGER
	ACCESS  read-only
	STATUS  mandatory
	DESCRIPTION
	    	"Total number of bytes of uninitialized data in the
		VROM."
	::= { memory 13 }

-- Added at LanRover Release 3.0

    memoryUsers OBJECT-TYPE
	SYNTAX	INTEGER
	ACCESS  read-only
	STATUS  mandatory
	DESCRIPTION
	    	"Total number of bytes of memory currently
		allocated for use by user list."
	::= { memory 14 }

-- Added at LanRover Release 4.3

    memoryAllocations OBJECT-TYPE
	SYNTAX	Counter
	ACCESS  read-only
	STATUS  mandatory
	DESCRIPTION
	    	"Total number of memory allocations that have been
		made since the system was last started."
	::= { memory 15 }

    memoryFrees OBJECT-TYPE
	SYNTAX	Counter
	ACCESS  read-only
	STATUS  mandatory
	DESCRIPTION
	    	"Total number of memory de-allocations that have been
		made since the system was last started."
	::= { memory 16 }

    memoryAllocationFailures OBJECT-TYPE
	SYNTAX	Counter
	ACCESS  read-only
	STATUS  mandatory
	DESCRIPTION
	    	"Total number of memory allocations that failed
		since the system was last started."
	::= { memory 17 }

    memoryNvTotal OBJECT-TYPE
	SYNTAX	INTEGER
	ACCESS  read-only
	STATUS  mandatory
	DESCRIPTION
	    	"Total number of bytes of Non-Volatile RAM installed."
	::= { memory 18 }

    memoryNvFree	OBJECT-TYPE
	SYNTAX	INTEGER
	ACCESS  read-only
	STATUS  mandatory
	DESCRIPTION
	    	"Total number of bytes of Non-Volatile memory on the 'malloc'
		free list."
	::= { memory 19 }

END
