-- Copyright (C) 1999 Intel Corporation. All rights reserved.
--
-- 802.1Q MIB
--
-- This mib was extracted from draft-ietf-bridge-bridgemib-04.txt.
-- It has been converted to SNMPv1.
--
-- Change History:
--
-- Version 1.00
-- Date: 09/10/1999
-- 1.  Change dot1qVlanStaticTable's dot1qVlanForbiddenEgressPorts ogject to read-only.

-- *****************************************************************************
-- IEEE 802.1Q MIB
-- *****************************************************************************

SW-QBRD-MIB     DEFINITIONS ::= BEGIN
    IMPORTS
        Counter, TimeTicks          FROM RFC1155-SMI
        OBJECT-TYPE                 FROM RFC-1212
        enterprises     FROM RFC1155-SMI   
        dot1dBasePort    FROM BRIDGE-MIB;
                
    MacAddress  ::= OCTET STRING(SIZE(6))        
        
    marconi     OBJECT IDENTIFIER ::= { enterprises 326 }
    systems     OBJECT IDENTIFIER ::= { marconi 2 }
    external    OBJECT IDENTIFIER ::= { systems 20 }
    dlink       OBJECT IDENTIFIER ::= { external 1 }

    dlinkcommon OBJECT IDENTIFIER ::= { dlink 1 }

    golf        OBJECT IDENTIFIER ::= { dlink 2 }
    golfproducts        OBJECT IDENTIFIER ::= { golf 1 }
    es2000              OBJECT IDENTIFIER ::= { golfproducts 3 }

    golfcommon          OBJECT IDENTIFIER ::= { golf 2 }        

    marconi-mgmt        OBJECT IDENTIFIER ::= { golfcommon 2 }

    es2000Mgmt          OBJECT IDENTIFIER ::= { marconi-mgmt 28 }

    swL2Mgmt            OBJECT IDENTIFIER ::= { es2000Mgmt 2 }

    swVlan              OBJECT IDENTIFIER ::= { swL2Mgmt 8 }

    qBridgeMIBObjects   OBJECT IDENTIFIER ::= { swVlan 5 }

-- *****************************************************************************
-- Textual Conventions
-- *****************************************************************************
-- Declarations for SNMPv1
    EnabledStatus   ::= INTEGER { enabled(1), disabled(2) }
    Unsigned32      ::= INTEGER
    PortList        ::= OCTET STRING
    VlanIndex       ::= Unsigned32
    VlanId          ::= INTEGER (1..4094)
    DisplayString   ::= OCTET STRING (SIZE (0..255))
    TruthValue      ::= INTEGER { true(1), false(2) }
    TimeFilter      ::= INTEGER

-- *****************************************************************************
-- groups in the Q-BRIDGE MIB
-- *****************************************************************************
    dot1qBase       OBJECT IDENTIFIER ::= { qBridgeMIBObjects 1 }
    dot1qTp         OBJECT IDENTIFIER ::= { qBridgeMIBObjects 2 }
    dot1qStatic     OBJECT IDENTIFIER ::= { qBridgeMIBObjects 3 }
    dot1qVlan       OBJECT IDENTIFIER ::= { qBridgeMIBObjects 4 }

-- *****************************************************************************
-- the dot1qBase group
-- *****************************************************************************
    dot1qVlanVersionNumber OBJECT-TYPE
        SYNTAX  INTEGER {
            version1(1)
        }
        ACCESS  read-only
        STATUS  mandatory
        DESCRIPTION
            "The version number of IEEE 802.1Q that this device supports."
        REFERENCE
            "IEEE 802.1Q/D11 Section 12.10.1.1"
        ::= { dot1qBase 1 }

    dot1qMaxVlanId OBJECT-TYPE
        SYNTAX  VlanId
        ACCESS  read-only
        STATUS  mandatory
        DESCRIPTION
            "The maximum IEEE 802.1Q VLAN ID that this device supports."
        REFERENCE
            "IEEE 802.1Q/D11 Section 9.3.2.3"
        ::= { dot1qBase 2 }

    dot1qMaxSupportedVlans OBJECT-TYPE
        SYNTAX  Unsigned32
        ACCESS  read-only
        STATUS  mandatory
        DESCRIPTION
            "The maximum number of IEEE 802.1Q VLANs that this device supports."
        REFERENCE
            "IEEE 802.1Q/D11 Section 12.10.1.1"
        ::= { dot1qBase 3 }

    dot1qNumVlans OBJECT-TYPE
        SYNTAX  Unsigned32
        ACCESS  read-only
        STATUS  mandatory
        DESCRIPTION
            "The current number of IEEE 802.1Q VLANs that are configured in
             this device."
        REFERENCE
            "IEEE 802.1Q/D11 Section 12.7.1.1"
        ::= { dot1qBase 4 }

    dot1qGvrpStatus OBJECT-TYPE
        SYNTAX  EnabledStatus
        ACCESS  read-write
        STATUS  mandatory
        DESCRIPTION
            "The administrative status requested by management for GVRP.
             The value enabled(1) indicates that GVRP should be enabled on this
             device, on all ports for which it has not been specifically disabled.
             When disabled(2), GVRP is disabled on all ports and all GVRP packets
             will be forwarded transparently.
             This object affects all GVRP Applicant and Registrar state machines.
             A transition from disabled(2) to enabled(1) will cause a reset of
             all GVRP state machines on all ports."
        DEFVAL  { enabled }
        ::= { dot1qBase 5 }

-- *****************************************************************************
-- the dot1qTp group
-- *****************************************************************************
    dot1qFdbTable OBJECT-TYPE
        SYNTAX  SEQUENCE OF Dot1qFdbEntry
        ACCESS  not-accessible
        STATUS  mandatory
        DESCRIPTION
            "A table that contains configuration and control information for
             each Filtering Database currently operating on this device.
             Entries in this table appear automatically when VLANs are assigned
             FDB IDs in the dot1qVlanCurrentTable."
        ::= { dot1qTp 1 }

    dot1qFdbEntry OBJECT-TYPE
        SYNTAX  Dot1qFdbEntry
        ACCESS  not-accessible
        STATUS  mandatory
        DESCRIPTION
            "Information about a specific Filtering Database."
        INDEX   { dot1qFdbId }
        ::= { dot1qFdbTable 1 }

    Dot1qFdbEntry ::=
        SEQUENCE {
            dot1qFdbId
                Unsigned32,
            dot1qFdbDynamicCount
                Counter
        }

    dot1qFdbId OBJECT-TYPE
        SYNTAX  Unsigned32
        ACCESS  not-accessible
        STATUS  mandatory
        DESCRIPTION
            "The identity of this Filtering Database."
        ::= { dot1qFdbEntry 1 }

    dot1qFdbDynamicCount OBJECT-TYPE
        SYNTAX  Counter
        ACCESS  read-only
        STATUS  mandatory
        DESCRIPTION
            "The current number of dynamic entries in this Filtering Database."
        REFERENCE
            "IEEE 802.1Q/D11 Section 12.7.1.1.3"
        ::= { dot1qFdbEntry 2 }

-- *****************************************************************************
-- Multiple Forwarding Databases for 802.1Q Transparent devices.
-- This table is an alternative to the dot1dTpFdbTable, previously defined
-- for 802.1D devices which only support a single Forwarding Database.
-- *****************************************************************************
    dot1qTpFdbTable OBJECT-TYPE
        SYNTAX  SEQUENCE OF Dot1qTpFdbEntry
        ACCESS  not-accessible
        STATUS  mandatory
        DESCRIPTION
            "A table that contains information about unicast entries for which
             the device has forwarding and/or filtering information.
             This information is used by the transparent bridging function in
             determining how to propagate a received frame."
        REFERENCE
            "IEEE 802.1Q/D11 Section 12.7.7"
        ::= { dot1qTp 2 }

    dot1qTpFdbEntry OBJECT-TYPE
        SYNTAX  Dot1qTpFdbEntry
        ACCESS  not-accessible
        STATUS  mandatory
        DESCRIPTION
            "Information about a specific unicast MAC address for which the
             device has some forwarding and/or filtering information."
        INDEX   { dot1qFdbId, dot1qTpFdbAddress }
        ::= { dot1qTpFdbTable 1 }

    Dot1qTpFdbEntry ::=
        SEQUENCE {
            dot1qTpFdbAddress
                MacAddress,
            dot1qTpFdbPort
                INTEGER,
            dot1qTpFdbStatus
                INTEGER
        }

    dot1qTpFdbAddress OBJECT-TYPE
        SYNTAX  MacAddress
        ACCESS  not-accessible
        STATUS  mandatory
        DESCRIPTION
            "A unicast MAC address for which the device has forwarding and/or
             filtering information."
        ::= { dot1qTpFdbEntry 1 }

    dot1qTpFdbPort OBJECT-TYPE
        SYNTAX  INTEGER (0..65535)
        ACCESS  read-only
        STATUS  mandatory
        DESCRIPTION
            "Either the value '0', or the port number of the port on which
             a frame having a source address equal to the value of the
             corresponding instance of dot1qTpFdbAddress has been seen.
             A value of '0' indicates that the port number has not been learned
             but that the device does have some forwarding/filtering information
             about this address (e.g. in the dot1qStaticUnicastTable).
             Implementers are encouraged to assign the port value to this object
             whenever it is learned even for addresses for which the corresponding
             value of dot1qTpFdbStatus is not learned(3)."
        ::= { dot1qTpFdbEntry 2 }

    dot1qTpFdbStatus OBJECT-TYPE
        SYNTAX  INTEGER {
            other(1),
            invalid(2),
            learned(3),
            self(4),
            mgmt(5)
        }
        ACCESS  read-only
        STATUS  mandatory
        DESCRIPTION
            "The status of this entry. The meanings of the values are:
             other(1) - none of the following. This may include the case where
                        some other MIB object (not the corresponding instance
                        of dot1qTpFdbPort, nor an entry in the dot1qStaticUnicastTable)
                        is being used to determine if and how frames addressed to
                        the value of the corresponding instance of dot1qTpFdbAddress
                        are being forwarded.
             invalid(2) - this entry is no longer valid (e.g., it was learned
                          but has since aged out), but has not yet been flushed
                          from the table.
             learned(3) - the value of the corresponding instance of dot1qTpFdbPort
                          was learned and is being used.
             self(4) - the value of the corresponding instance of dot1qTpFdbAddress
                       represents one of the device's addresses.
                       The corresponding instance of dot1qTpFdbPort indicates
                       which of the device's ports has this address.
             mgmt(5) - the value of the corresponding instance of dot1qTpFdbAddress
                       is also the value of an existing instance of dot1qStaticAddress."
        ::= { dot1qTpFdbEntry 3 }

    dot1qTpGroupTable OBJECT-TYPE
        SYNTAX  SEQUENCE OF Dot1qTpGroupEntry
        ACCESS  not-accessible
        STATUS  mandatory
        DESCRIPTION
            "A table containing filtering information for VLANs configured into
             the bridge by (local or network) management, or learnt dynamically,
             specifying the set of ports to which frames received on a VLAN for
             this FDB and containing a specific Group destination address are
             allowed to be forwarded."
        ::= { dot1qTp 3 }

    dot1qTpGroupEntry OBJECT-TYPE
        SYNTAX  Dot1qTpGroupEntry
        ACCESS  not-accessible
        STATUS  mandatory
        DESCRIPTION
            "Filtering information configured into the bridge by management,
             or learnt dynamically, specifying the set of ports to which frames
             received on a VLAN and containing a specific Group destination
             address, are allowed to be forwarded.
             The subset of these ports learnt dynamically is also provided."
        INDEX   { dot1qVlanIndex, dot1qTpGroupAddress }
        ::= { dot1qTpGroupTable 1 }

    Dot1qTpGroupEntry ::=
        SEQUENCE {
            dot1qTpGroupAddress
                MacAddress,
            dot1qTpGroupEgressPorts
                PortList,
            dot1qTpGroupLearnt
                PortList
        }

    dot1qTpGroupAddress OBJECT-TYPE
        SYNTAX  MacAddress
        ACCESS  not-accessible
        STATUS  mandatory
        DESCRIPTION
            "The destination Group MAC address in a frame to which this entry's
             filtering information applies."
        ::= { dot1qTpGroupEntry 1 }

    dot1qTpGroupEgressPorts OBJECT-TYPE
        SYNTAX  PortList
        ACCESS  read-only
        STATUS  mandatory
        DESCRIPTION
            "The complete set of ports, in this Filtering Database, to which
             frames destined for this Group MAC address are currently being
             explicitly forwarded.
             This does not include ports for which this address is only
             implicitly forwarded, in the dot1qForwardAllPorts list."
        ::= { dot1qTpGroupEntry 2 }

    dot1qTpGroupLearnt OBJECT-TYPE
        SYNTAX  PortList
        ACCESS  read-only
        STATUS  mandatory
        DESCRIPTION
            "The subset of ports in dot1qTpGroupEgressPorts which were learnt by
             GMRP or some other dynamic mechanism, in this Filtering database."
        ::= { dot1qTpGroupEntry 3 }

-- *****************************************************************************
-- the dot1qStatic group
-- *****************************************************************************
-- *****************************************************************************
-- the dot1qVlan group
-- *****************************************************************************
    dot1qVlanNumDeletes OBJECT-TYPE
        SYNTAX  Counter
        ACCESS  read-only
        STATUS  mandatory
        DESCRIPTION
            "The number of times a VLAN entry has been deleted from the
             dot1qVlanCurrentTable (for any reason).
             If an entry is deleted, then inserted, and then deleted, this
             counter will be incremented by 2."
        ::= { dot1qVlan 1 }

    dot1qVlanCurrentTable OBJECT-TYPE
        SYNTAX  SEQUENCE OF Dot1qVlanCurrentEntry
        ACCESS  not-accessible
        STATUS  mandatory
        DESCRIPTION
            "A table containing current configuration information for each VLAN
             currently configured into the device by (local or network) management,
             or dynamically created as a result of GVRP requests received."
        ::= { dot1qVlan 2 }

    dot1qVlanCurrentEntry OBJECT-TYPE
        SYNTAX  Dot1qVlanCurrentEntry
        ACCESS  not-accessible
        STATUS  mandatory
        DESCRIPTION
            "Information for a VLAN configured into the device by (local or
             network) management, or dynamically created as a result of GVRP
             requests received."
        INDEX   { dot1qVlanTimeMark, dot1qVlanIndex }
        ::= { dot1qVlanCurrentTable 1 }

    Dot1qVlanCurrentEntry ::=
        SEQUENCE {
            dot1qVlanTimeMark
                TimeFilter,
            dot1qVlanIndex
                VlanIndex,
            dot1qVlanFdbId
                Unsigned32,
            dot1qVlanCurrentEgressPorts
                PortList,
            dot1qVlanCurrentUntaggedPorts
                PortList,
            dot1qVlanStatus
                INTEGER,
            dot1qVlanCreationTime
                TimeTicks
        }

    dot1qVlanTimeMark OBJECT-TYPE
        SYNTAX  TimeFilter
        ACCESS  not-accessible
        STATUS  mandatory
        DESCRIPTION
            "A TimeFilter for this entry. See the TimeFilter textual convention
             to see how this works."
        ::= { dot1qVlanCurrentEntry 1 }

    dot1qVlanIndex OBJECT-TYPE
        SYNTAX  VlanIndex
        ACCESS  not-accessible
        STATUS  mandatory
        DESCRIPTION
            "The VLAN-ID or other identifier refering to this VLAN."
        ::= { dot1qVlanCurrentEntry 2 }

    dot1qVlanFdbId OBJECT-TYPE
        SYNTAX  Unsigned32
        ACCESS  read-only
        STATUS  mandatory
        DESCRIPTION
            "The Filtering Database used by this VLAN. This is one of the
             dot1qFdbId values in the dot1qFdbTable.
             This value is allocated automatically by the device whenever the
             VLAN is created: either dynamically by GVRP, or by management,
             in dot1qVlanStaticTable.
             Allocation of this value follows the learning constraints defined
             for this VLAN in dot1qLearningConstraintsTable."
        ::= { dot1qVlanCurrentEntry 3 }

    dot1qVlanCurrentEgressPorts OBJECT-TYPE
        SYNTAX  PortList
        ACCESS  read-only
        STATUS  mandatory
        DESCRIPTION
            "The set of ports which are transmitting traffic for this VLAN as
             either tagged or untagged frames."
        REFERENCE
            "IEEE 802.1Q/D11 Section 12.10.2.1"
        ::= { dot1qVlanCurrentEntry 4 }

    dot1qVlanCurrentUntaggedPorts OBJECT-TYPE
        SYNTAX  PortList
        ACCESS  read-only
        STATUS  mandatory
        DESCRIPTION
            "The set of ports which are transmitting traffic for this VLAN as
             untagged frames."
        REFERENCE
            "IEEE 802.1Q/D11 Section 12.10.2.1"
        ::= { dot1qVlanCurrentEntry 5 }

    dot1qVlanStatus OBJECT-TYPE
        SYNTAX  INTEGER {
            other(1),
            permanent(2),
            dynamicGvrp(3)
        }
        ACCESS  read-only
        STATUS  mandatory
        DESCRIPTION
            "This object indicates the status of this entry.
             other(1) - this entry is currently in use but the conditions under
                        which it will remain so differ from the following values.
             permanent(2) - this entry, corresponding to an entry in
                            dot1qVlanStaticTable, is currently in use and will
                            remain so after the next reset of the device.
                            The port lists for this entry include ports from
                            the equivalent dot1qVlanStaticTable entry and ports
                            learnt dynamically.
            dynamicGvrp(3) - this entry is currently in use and will remain so
                             until removed by GVRP.
                             There is no static entry for this VLAN and it will
                             be removed when the last port leaves the VLAN."
        ::= { dot1qVlanCurrentEntry 6 }

    dot1qVlanCreationTime OBJECT-TYPE
        SYNTAX  TimeTicks
        ACCESS  read-only
        STATUS  mandatory
        DESCRIPTION
            "The value of sysUpTime when this VLAN was created."
        ::= { dot1qVlanCurrentEntry 7 }

    dot1qVlanStaticTable OBJECT-TYPE
        SYNTAX  SEQUENCE OF Dot1qVlanStaticEntry
        ACCESS  not-accessible
        STATUS  mandatory
        DESCRIPTION
            "A table containing static configuration information for each VLAN
             configured into the device by (local or network) management.
             All entries are permanent and will be restored after the device 
             is reset."
        ::= { dot1qVlan 3 }

    dot1qVlanStaticEntry OBJECT-TYPE
        SYNTAX  Dot1qVlanStaticEntry
        ACCESS  not-accessible
        STATUS  mandatory
        DESCRIPTION
            "Static information for a VLAN configured into the device by (local
             or network) management."
        INDEX   { dot1qVlanIndex }
        ::= { dot1qVlanStaticTable 1 }

    Dot1qVlanStaticEntry ::=
        SEQUENCE {
            dot1qVlanStaticName
                DisplayString,
            dot1qVlanStaticEgressPorts
                PortList,
            dot1qVlanForbiddenEgressPorts
                PortList,
            dot1qVlanStaticUntaggedPorts
                PortList,
            dot1qVlanStaticRowState
                INTEGER
        }

    dot1qVlanStaticName OBJECT-TYPE
        SYNTAX  DisplayString (SIZE (0..32))
        ACCESS  read-write
        STATUS  mandatory
        DESCRIPTION
            "An administratively assigned string, which may be used to identify
             the VLAN."
        REFERENCE
            "IEEE 802.1Q/D11 Section 12.10.2.1"
        ::= { dot1qVlanStaticEntry 1 }

    dot1qVlanStaticEgressPorts OBJECT-TYPE
        SYNTAX  PortList
        ACCESS  read-write
        STATUS  mandatory
        DESCRIPTION
            "The set of ports which are permanently assigned to the egress list
             for this VLAN by management. Changes to a bit in this object affect
             the per-port per-VLAN Registrar control for Registration Fixed for
             the relevant GVRP state machine on each port.
             A port may not be added in this set if it is already a member of
             the set of ports in dot1qVlanForbiddenEgressPorts. The default
             value of this object is a string of zeros of appropriate length,
             indicating not fixed."
        REFERENCE
            "IEEE 802.1Q/D11 Section 12.7.7.3, 11.2.3.2.3"
        ::= { dot1qVlanStaticEntry 2 }

    dot1qVlanForbiddenEgressPorts OBJECT-TYPE
        SYNTAX  PortList
        ACCESS  read-only
        STATUS  mandatory
        DESCRIPTION
            "The set of ports which are prohibited by management from being
             included in the egress list for this VLAN.
             Changes to this object that cause a port to be included or excluded
             affect the per-port per-VLAN Registrar control for Registration
             Forbidden for the relevant GVRP state machine on each port.
             A port may not be added in this set if it is already a member of
             the set of ports in dot1qVlanStaticEgressPorts.
             The default value of this object is a string of zeros of
             appropriate length, excluding all ports from the forbidden set."
        REFERENCE
            "IEEE 802.1Q/D11 Section 12.7.7.3, 11.2.3.2.3"
        ::= { dot1qVlanStaticEntry 3 }

    dot1qVlanStaticUntaggedPorts OBJECT-TYPE
        SYNTAX  PortList
        ACCESS  read-write
        STATUS  mandatory
        DESCRIPTION
            "The set of ports which should transmit egress packets for this VLAN
             as untagged. The default value of this object for the default VLAN
             (VlanId 001) is a string of appropriate length including all ports.
             There is no specified default for other VLANs.
             If a device cannot support a value being set then its agent will
             reject the set operation.
             Attempts to set more than one VLAN to be untagged on egress may be
             rejected by devices which do not support this option."
        REFERENCE
            "IEEE 802.1Q/D11 Section 12.10.2.1"
        ::= { dot1qVlanStaticEntry 4 }

    dot1qVlanStaticRowState OBJECT-TYPE
        SYNTAX  INTEGER {
            other(1),
            invalid(2),
            valid(3)
        }
        ACCESS  read-write
        STATUS  mandatory
        DESCRIPTION
            "This object indicates the status of this entry.
             other(1) - this entry is currently in use but the conditions under
                        which it will remain so are different from each of the
                        following values.
             invalid(2) - writing this value to the object, and then the
                          corresponding entry will be removed from the table.
             valid(3) - this entry is reside in the table."
        ::= { dot1qVlanStaticEntry 5 }

    dot1qPortVlanTable OBJECT-TYPE
        SYNTAX  SEQUENCE OF Dot1qPortVlanEntry
        ACCESS  not-accessible
        STATUS  mandatory
        DESCRIPTION
            "A table containing per port control and status information for VLAN
             configuration in the device."
        ::= { dot1qVlan 4 }

    dot1qPortVlanEntry OBJECT-TYPE
        SYNTAX  Dot1qPortVlanEntry
        ACCESS  not-accessible
        STATUS  mandatory
        DESCRIPTION
            "Information controlling VLAN configuration for a port on the device.
             This is indexed by dot1dBasePort."
        INDEX { dot1dBasePort }
        ::= { dot1qPortVlanTable 1 }

    Dot1qPortVlanEntry ::=
        SEQUENCE {
            dot1qPvid
                VlanIndex,
            dot1qPortIngressFiltering
                TruthValue,
            dot1qPortGvrpStatus
                EnabledStatus,
            dot1qPortGvrpFailedRegistrations
                Counter,
            dot1qPortGvrpLastPduOrigin
                MacAddress
        }

    dot1qPvid OBJECT-TYPE
        SYNTAX  VlanIndex
        ACCESS  read-write
        STATUS  mandatory
        DESCRIPTION
            "The PVID, the VLAN ID assigned to untagged frames or Prority-Tagged
             frames received on this port."
        REFERENCE
            "IEEE 802.1Q/D11 Section 12.10.1.1"
        DEFVAL  { 1 }
        ::= { dot1qPortVlanEntry 1 }

    dot1qPortIngressFiltering OBJECT-TYPE
        SYNTAX  TruthValue
        ACCESS  read-write
        STATUS  mandatory
        DESCRIPTION
            "When this is true(1) the device will discard incoming frames for
             VLANs which do not include this Port in its Member set.
             When false(2), the port will accept all incoming frames.
             This control does not affect VLAN independent BPDU frames, such
             as GVRP and STP.
             It does affect VLAN dependent BPDU frames, such as GMRP."
        REFERENCE
            "IEEE 802.1Q/D11 Section 12.10.1.4"
        DEFVAL  { false }
        ::= { dot1qPortVlanEntry 2 }

    dot1qPortGvrpStatus OBJECT-TYPE
        SYNTAX  EnabledStatus
        ACCESS  read-write
        STATUS  mandatory
        DESCRIPTION
            "The state of GVRP operation on this port.
             The value enabled(1) indicates that GVRP is enabled on this port,
             as long as dot1qGvrpStatus is also enabled for this device.
             When disabled(2) but dot1qGvrpStatus is still enabled for the
             device, GVRP is disabled on this port: any GVRP packets received
             will be silently discarded and no GVRP registrations will be
             propagated from other ports.
             This object affects all GVRP Applicant and Registrar state machines
             on this port.
             A transition from disabled(2) to enabled(1) will cause a reset of
             all GVRP state machines on this port."
        DEFVAL  { enabled }
        ::= { dot1qPortVlanEntry 3 }

    dot1qPortGvrpFailedRegistrations OBJECT-TYPE
        SYNTAX  Counter
        ACCESS  read-only
        STATUS  mandatory
        DESCRIPTION
            "The total number of failed GVRP registrations, for any reason,
             on this port."
        ::= { dot1qPortVlanEntry 4 }

    dot1qPortGvrpLastPduOrigin OBJECT-TYPE
        SYNTAX  MacAddress
        ACCESS  read-only
        STATUS  mandatory
        DESCRIPTION
            "The Source MAC Address of the last GVRP message received on this port."
        ::= { dot1qPortVlanEntry 5 }

END
