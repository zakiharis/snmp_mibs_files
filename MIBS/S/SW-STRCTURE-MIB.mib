-- Revision 1.0.0
-- Copyright 1999 D-Link, Inc.
-- All rights reserved.
--
-- The purpose of this MIB is to provide the user information to understand
-- the structure of the device.

SW-STRCTURE-MIB     DEFINITIONS ::= BEGIN
    IMPORTS
        OBJECT-TYPE     FROM RFC-1212
        DisplayString   FROM RFC1213-MIB
        TRAP-TYPE       FROM RFC-1215        
        enterprises     FROM RFC1155-SMI;        

    marconi     OBJECT IDENTIFIER ::= { enterprises 326 }
    systems     OBJECT IDENTIFIER ::= { marconi 2 }
    external    OBJECT IDENTIFIER ::= { systems 20 }
    dlink       OBJECT IDENTIFIER ::= { external 1 }

    dlinkcommon OBJECT IDENTIFIER ::= { dlink 1 }

    golf        OBJECT IDENTIFIER ::= { dlink 2 }
    golfproducts        OBJECT IDENTIFIER ::= { golf 1 }
    es2000              OBJECT IDENTIFIER ::= { golfproducts 3 }

    golfcommon          OBJECT IDENTIFIER ::= { golf 2 }

    marconi-mgmt    OBJECT IDENTIFIER ::= { golfcommon 2 }

    es2000Mgmt      OBJECT IDENTIFIER ::= { marconi-mgmt 28 }

    swStructure     OBJECT IDENTIFIER ::= { es2000Mgmt 1 }

-- *****************************************************************************
--  swStructInfo describe the device level structure information
-- *****************************************************************************
    swStructInfo    OBJECT IDENTIFIER ::= { swStructure 1 }

    swStructDevType OBJECT-TYPE
        SYNTAX  OBJECT IDENTIFIER
        ACCESS  read-only
        STATUS  mandatory
        DESCRIPTION
            "Specifies the device type."
        ::= { swStructInfo 1 }

    swStructDevDescr OBJECT-TYPE
        SYNTAX  DisplayString (SIZE(0..64))
        ACCESS  read-only
        STATUS  mandatory
        DESCRIPTION
            "Describes the type of the device."
        ::= { swStructInfo 2 }

    swStructDevPortEncodingFactor OBJECT-TYPE
        SYNTAX  INTEGER
        ACCESS  read-only
        STATUS  mandatory
        DESCRIPTION
            "The factor to encode the global port ID from unit ID and the local port ID.
             This global port ID is required to access the bridge MIB and spanning
             tree MIB defined by the standard body. This global port ID will provide
             a unigue port ID for each port across the entire device.
             Example: supoposed that the encoding factor is 16, then port 2 located on module 2 will
             be encoded as port 18"
        ::= { swStructInfo 3 }

-- +updated by Jemy 2000/1/31 01:12PM B12
    swStructDevLedInfo OBJECT-TYPE
        SYNTAX  OCTET STRING (SIZE(1))
        ACCESS  read-only
        STATUS  mandatory
        DESCRIPTION
            "Provides the LED informations of the cpu slot.
             bit7 - cpu status(always 1)
             bit6 - console status(0: console not in used, 1: console in used)
             bit5 - power status(always 1)
             bit 4 ~ bit 0 - not used."
        ::= { swStructInfo 4 }
-- -

    swStructDevMaxModuleNum OBJECT-TYPE
        SYNTAX  INTEGER
        ACCESS  read-only
        STATUS  mandatory
        DESCRIPTION
            "Maximum number of modules allowed on the unit."
        ::= { swStructInfo 5 }

    swStructDevMaxPortNum OBJECT-TYPE
        SYNTAX  INTEGER
        ACCESS  read-only
        STATUS  mandatory
        DESCRIPTION
            "Maximum number of ports allowed on the unit."
        ::= { swStructInfo 6 }

    swStructDevNumOfPortInUse OBJECT-TYPE
        SYNTAX  INTEGER
        ACCESS  read-only
        STATUS  mandatory
        DESCRIPTION
            "Number of ports which has link being connected to the port."
        ::= { swStructInfo 7 }

    swStructDevOperStatus OBJECT-TYPE
        SYNTAX  INTEGER {
            other(1),
            notAvail(2),
            removed(3),
            disabled(4),
            normal(5),
            nonFatalErr(9),
            fatalErr(10)
        }
        ACCESS  read-only
        STATUS  mandatory
        DESCRIPTION
            "Describes the operation status for the unit."
        ::= { swStructInfo 8 }

    swStructDevLastChange OBJECT-TYPE
        SYNTAX  INTEGER
        ACCESS  read-only
        STATUS  mandatory
        DESCRIPTION
            "Provides the time that the unit is up last time."
        ::= { swStructInfo 9 }

-- *****************************************************************************
--  swStructModuleTable
-- *****************************************************************************
    swStructModuleTable OBJECT-TYPE
        SYNTAX  SEQUENCE OF SwStructModuleEntry
        ACCESS  not-accessible
        STATUS  mandatory
        DESCRIPTION
            "A table that contains information about a module."
        ::= { swStructure 2 }

    swStructModuleEntry OBJECT-TYPE
        SYNTAX  SwStructModuleEntry
        ACCESS  not-accessible
        STATUS  mandatory
        DESCRIPTION
            "A list of information for a module."
        INDEX   { swStructModuleUnitIndex, swStructModuleIndex }
        ::= { swStructModuleTable 1 }

    SwStructModuleEntry ::=
        SEQUENCE {
            swStructModuleUnitIndex
                INTEGER,
            swStructModuleIndex
                INTEGER,
            swStructModuleType
                OBJECT IDENTIFIER,
            swStructModuleDescr
                DisplayString (SIZE(0..64)),
            swStructModuleVersion
                INTEGER,
            swStructModuleMaxPortNum
                INTEGER,
            swStructModuleEncodingOffset
                INTEGER,
--            swStructModuleRAM
--                INTEGER,
--            swStructModuleEPROM
--                INTEGER,
--            swStructModuleFLASH
--                INTEGER,
-- +added by Jemy 2000/1/31 01:16PM B12
            swStructModuleLEDInfo
                OCTET STRING (SIZE (0..8)),
-- -                
            swStructModuleOperStatus
                INTEGER,
            swStructModuleLastChange
                INTEGER
        }

    swStructModuleUnitIndex OBJECT-TYPE
        SYNTAX  INTEGER
        ACCESS  read-only
        STATUS  mandatory
        DESCRIPTION
            "ID of the unit in the device."
        ::= { swStructModuleEntry 1 }

    swStructModuleIndex OBJECT-TYPE
        SYNTAX  INTEGER
        ACCESS  read-only
        STATUS  mandatory
        DESCRIPTION
            "ID of the Module in the device."
        ::= { swStructModuleEntry 2 }

-- +updated by Jemy 2000/1/31 01:16PM B12
    swStructModuleType OBJECT-TYPE
        SYNTAX  OBJECT IDENTIFIER
        ACCESS  read-only
        STATUS  mandatory
        DESCRIPTION
            "Type of the module."
        ::= { swStructModuleEntry 3 }

    swStructModuleDescr OBJECT-TYPE
        SYNTAX  DisplayString (SIZE(0..64))
        ACCESS  read-only
        STATUS  mandatory
        DESCRIPTION
            "Type of the module in displayed string format."
        ::= { swStructModuleEntry 4 }

    swStructModuleVersion OBJECT-TYPE
        SYNTAX  INTEGER
        ACCESS  read-only
        STATUS  mandatory
        DESCRIPTION
            "Provides PCB version of the module."
        ::= { swStructModuleEntry 5 }

    swStructModuleMaxPortNum OBJECT-TYPE
        SYNTAX  INTEGER
        ACCESS  read-only
        STATUS  mandatory
        DESCRIPTION
            "Maximum number of ports allowed on the module."
        ::= { swStructModuleEntry 6 }

    swStructModuleEncodingOffset OBJECT-TYPE
        SYNTAX  INTEGER
        ACCESS  read-only
        STATUS  mandatory
        DESCRIPTION
            "Each module has a offset for encoding the port ID relative to a unit.
             This encoding will provide a unigue port ID for ports located on the device.
             Example: Supposed that the offset for module 2 is 16, then port 2 located on
             module 2 will be encoded as port 18"
        ::= { swStructModuleEntry 7 }

--    swStructModuleRAM OBJECT-TYPE
--        SYNTAX  INTEGER
--        ACCESS  read-only
--        STATUS  mandatory
--        DESCRIPTION
--            "Get ram size by K on specified module."
--        ::= { swStructModuleEntry 9 }

--    swStructModuleEPROM OBJECT-TYPE
--        SYNTAX  INTEGER
--        ACCESS  read-only
--        STATUS  mandatory
--        DESCRIPTION
--            "Get eprom size by K on specified module."
--        ::= { swStructModuleEntry 10 }

--    swStructModuleFLASH OBJECT-TYPE
--        SYNTAX  INTEGER
--        ACCESS  read-only
--        STATUS  mandatory
--        DESCRIPTION
--            "Get flash rom size by K on specified module."
--        ::= { swStructModuleEntry 11 }

    swStructModuleLEDInfo OBJECT-TYPE
        SYNTAX  OCTET STRING (SIZE (0..8))
        ACCESS  read-only
        STATUS  mandatory
        DESCRIPTION
            "Gets LED informations on specifiled module."
        ::= { swStructModuleEntry 8 }

    swStructModuleOperStatus OBJECT-TYPE
        SYNTAX  INTEGER {
            other(1),
            notAvail(2),
            removed(3),
            disabled(4),
            normal(5),
            nonFatalErr(9),
            fatalErr(10)
        }
        ACCESS  read-only
        STATUS  mandatory
        DESCRIPTION
            "Provides operation status of the module."
        ::= { swStructModuleEntry 9 }

    swStructModuleLastChange OBJECT-TYPE
        SYNTAX  INTEGER
        ACCESS  read-only
        STATUS  mandatory
        DESCRIPTION
            "Provides the time that the module is up last time."
        ::= { swStructModuleEntry 10 }
-- -

-- *****************************************************************************
--  swStructPowerTable describes the power supply structure information
-- *****************************************************************************
    swStructPowerTable OBJECT-TYPE
        SYNTAX  SEQUENCE OF SwStructPowerEntry
        ACCESS  not-accessible
        STATUS  mandatory
        DESCRIPTION
            "A table that contains information about every power."
        ::= { swStructure 3 }

    swStructPowerEntry OBJECT-TYPE
        SYNTAX  SwStructPowerEntry
        ACCESS  not-accessible
        STATUS  mandatory
        DESCRIPTION
            "A list of information for each power."
        INDEX   { swStructPowerIndex }
        ::= { swStructPowerTable 1 }

-- +updated by Jemy 2000/1/25 05:49PM
    SwStructPowerEntry ::=
        SEQUENCE {
            swStructPowerIndex
                INTEGER,
            swStructPowerInfo
                DisplayString(SIZE(0..20)),            
            swStructPowerTemperature
                INTEGER,
            swStructPowerVolt
                DisplayString(SIZE(0..9)),
            swStructPowerAmp
                INTEGER,
            swStructPowerFan1Status
                INTEGER,
            swStructPowerFan2Status
                INTEGER,
            swStructPowerStatus
                INTEGER                
        }
-- -

    swStructPowerIndex OBJECT-TYPE
        SYNTAX  INTEGER
        ACCESS  read-only
        STATUS  mandatory
        DESCRIPTION
            "ID of the power supply in the unit."
        ::= { swStructPowerEntry 1 }

-- +added by Jemy 2000/1/25 05:49PM        
    swStructPowerInfo OBJECT-TYPE
        SYNTAX  DisplayString (SIZE(0..20))
        ACCESS  read-only
        STATUS  mandatory
        DESCRIPTION
            "Displays informations of power. Includes vendor, version and so on."
        ::= { swStructPowerEntry 2 }
-- -
                
    swStructPowerTemperature OBJECT-TYPE
        SYNTAX  INTEGER
        ACCESS  read-only
        STATUS  mandatory
        DESCRIPTION
            "Displays temperature value of power by Fahrenheit."
        ::= { swStructPowerEntry 3 }
        
    swStructPowerVolt OBJECT-TYPE
        SYNTAX  DisplayString (SIZE(0..9))
        ACCESS  read-only
        STATUS  mandatory
        DESCRIPTION
            "Displays volt value of power by V unit."
        ::= { swStructPowerEntry 4 }
        
    swStructPowerAmp OBJECT-TYPE
        SYNTAX  INTEGER
        ACCESS  read-only
        STATUS  mandatory
        DESCRIPTION
            "Displays amp value of power by A unit."
        ::= { swStructPowerEntry 5 }

-- +added by Jemy 2000/1/25 05:49PM
    swStructPowerFan1Status OBJECT-TYPE
        SYNTAX  INTEGER {
            fanOk(1),
            fanFail(2),
            other(3)
        }
        ACCESS  read-only
        STATUS  mandatory
        DESCRIPTION
            "Describes the operation status of the power fan1."
        ::= { swStructPowerEntry 6 }
        
    swStructPowerFan2Status OBJECT-TYPE
        SYNTAX  INTEGER {
            fanOk(1),
            fanFail(2),
            other(3)
        }
        ACCESS  read-only
        STATUS  mandatory
        DESCRIPTION
            "Describes the operation status of the power fan2."
        ::= { swStructPowerEntry 7 }        
-- -
        
    swStructPowerStatus OBJECT-TYPE
        SYNTAX  INTEGER {
            acFailPsFail(1),
            acPresentPsFail(2),
            psGood(3),
            other(4)
        }
        ACCESS  read-only
        STATUS  mandatory
        DESCRIPTION
            "Describes the operation status of the power supply."
        ::= { swStructPowerEntry 8 }
        
-- *****************************************************************************
--  swStructSystemFanTable describes the system fan structure information
-- *****************************************************************************
    swStructSystemFanTable OBJECT-TYPE
        SYNTAX  SEQUENCE OF SwStructSystemFanEntry
        ACCESS  not-accessible
        STATUS  mandatory
        DESCRIPTION
            "A table that contains informations about system fans."
        ::= { swStructure 4 }

    swStructSystemFanEntry OBJECT-TYPE
        SYNTAX  SwStructSystemFanEntry
        ACCESS  not-accessible
        STATUS  mandatory
        DESCRIPTION
            "A list of informations for each system fan."
        INDEX   { swStructSystemFanIndex }
        ::= { swStructSystemFanTable 1 }

    SwStructSystemFanEntry ::=
        SEQUENCE {
            swStructSystemFanIndex
                INTEGER,
            swStructSystemFanStatus
                INTEGER
        }

    swStructSystemFanIndex OBJECT-TYPE
        SYNTAX  INTEGER
        ACCESS  read-only
        STATUS  mandatory
        DESCRIPTION
            "ID of designed system fans."
        ::= { swStructSystemFanEntry 1 }

    swStructSystemFanStatus OBJECT-TYPE
        SYNTAX  INTEGER {
            fanOk(1),
            fanFail(2),
            other(3)
        }
        ACCESS  read-only
        STATUS  mandatory
        DESCRIPTION
            "Describes the operation status of the system fans."
        ::= { swStructSystemFanEntry 2 }

-- =============================================================================
-- Trap Group Definition (added by Jemy 2000/1/28 10:25AM)
-- =============================================================================
    powerTemperatureWarnning TRAP-TYPE
        ENTERPRISE es2000 -- updated by Jemy 2000/2/21 03:10PM B17
        VARIABLES {
            swStructPowerIndex
        }
        DESCRIPTION
            "The trap is sent whenever the power state enter the temperature warnning state. "
        ::= 5
        
    powerVoltWarnning TRAP-TYPE
        ENTERPRISE es2000 -- updated by Jemy 2000/2/21 03:10PM B17
        VARIABLES {
            swStructPowerIndex
        }
        DESCRIPTION
            "The trap is sent whenever the power state enter the volt warnning state. "
        ::= 6 
        
    powerCurrentWarnning TRAP-TYPE
        ENTERPRISE es2000 -- updated by Jemy 2000/2/21 03:10PM B17
        VARIABLES {
            swStructPowerIndex
        }
        DESCRIPTION
            "The trap is sent whenever the power state enter the current warnning state. "
        ::= 7        

    powerFan1Fail TRAP-TYPE
        ENTERPRISE es2000 -- updated by Jemy 2000/2/21 03:10PM B17
        VARIABLES {
            swStructPowerIndex
        }
        DESCRIPTION
            "The trap is sent whenever the power state enter the power fan1 fail state. "
        ::= 8
        
    powerFan2Fail TRAP-TYPE
        ENTERPRISE es2000 -- updated by Jemy 2000/2/21 03:10PM B17
        VARIABLES {
            swStructPowerIndex
        }
        DESCRIPTION
            "The trap is sent whenever the power state enter the power fan2 fail state. "
        ::= 9

    systemFanFail TRAP-TYPE
        ENTERPRISE es2000 -- updated by Jemy 2000/2/21 03:10PM B17
        VARIABLES {
            swStructSystemFanIndex
        }
        DESCRIPTION
            "The trap is sent whenever the power state enter the system fans fail state. " 
        ::= 10
                
    powerRemoved TRAP-TYPE
        ENTERPRISE es2000 -- updated by Jemy 2000/2/21 03:10PM B17
        VARIABLES {
            swStructPowerIndex
        }
        DESCRIPTION
            "The trap is sent whenever the power is removed."        
        ::= 11
        
    powerInserted TRAP-TYPE
        ENTERPRISE es2000 -- updated by Jemy 2000/2/21 03:10PM B17
        VARIABLES {
            swStructPowerIndex
        }
        DESCRIPTION
            "The trap is sent whenever the power is inserted."        
        ::= 12
        
    powerBad TRAP-TYPE
        ENTERPRISE es2000 -- updated by Jemy 2000/2/21 03:10PM B17
        VARIABLES {
            swStructPowerIndex
        }
        DESCRIPTION
            "The trap is sent whenever the power is bad."        
        ::= 13      
END
