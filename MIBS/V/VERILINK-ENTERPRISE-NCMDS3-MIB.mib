VERILINK-ENTERPRISE-NCMDS3-MIB

        -- set up MIB-wide defaults
        -- all functions can use %n for object name and
        -- %t for object type, %p for parent name,
        -- %d for name of default-bearing node and %% for %

          DEFINITIONS ::= BEGIN

     IMPORTS
                Gauge
                        FROM RFC1155-SMI
            DisplayString
                     FROM RFC1213-MIB
        OBJECT-TYPE
                     FROM RFC-1212
        ncm-ds3
             FROM VERILINK-ENTERPRISE-NCMALARM-MIB;


     --  This MIB module uses the extended OBJECT-TYPE macro as
     --  defined in RFC 1212.
     --  This MIB module uses the TRAP-TYPE macro as
     --  defined in RFC 1215.


     --   verilink                    OBJECT IDENTIFIER ::= { enterprises 321 }
     --   as2000                      OBJECT IDENTIFIER ::= { verilink 1 }
     --   ncm-ds3                     OBJECT IDENTIFIER ::= { as2000 3036 }



	--
     --ncm HDM DS3 Port table
     --  
     ncmhdmDs3PortTable OBJECT-TYPE
          SYNTAX SEQUENCE OF NcmhdmDs3PortEntry
          ACCESS not-accessible
          STATUS mandatory
          DESCRIPTION
               "The HDM DS3 Port table."
                --DEFAULT test-function   ds3-test
--              DEFAULT set-function    null-set-proc
                --DEFAULT next-function   ds3-next
          ::= { ncm-ds3 9000 }

     ncmhdmDs3PortEntry OBJECT-TYPE
          SYNTAX NcmhdmDs3PortEntry
          ACCESS not-accessible
          STATUS mandatory
          DESCRIPTION
               "An entry in the dsu information table."
          INDEX   { ncmhdmDs3PortNIDIndex, ncmhdmDs3PortIndex }
          ::= { ncmhdmDs3PortTable 1 }

     NcmhdmDs3PortEntry ::= SEQUENCE {
             ncmhdmDs3PortNIDIndex
                INTEGER,
             ncmhdmDs3PortIndex
                INTEGER,
             ncmhdmDs3PerfControl
                INTEGER,
             ncmhdmDs3LBOSelection
                INTEGER,
             ncmhdmDs3DataRateMode
                INTEGER,
	     ncmhdmDs3Rate
		INTEGER,
	     ncmhdmDs3LineType
		INTEGER,
	      ncmhdmDs3LineCode
                INTEGER,
             ncmhdmDs3AISCBit
                INTEGER,
             ncmhdmDs3EquipCode
                 DisplayString,
             ncmhdmDs3LocationIDCode
                 DisplayString,
             ncmhdmDs3FrameIDCode
                 DisplayString,
             ncmhdmDs3UnitCode
                 DisplayString,
             ncmhdmDs3FacilityIDCode
                 DisplayString,
             ncmhdmDs3PortIdCode
                 DisplayString,
             ncmhdmDs3CircuitID
                 DisplayString,
             ncmhdmDs3GenIDCode
                 DisplayString,
             ncmhdmDs3Inband
                INTEGER
     }


	ncmhdmDs3PortNIDIndex OBJECT-TYPE
          SYNTAX  INTEGER (1..'7fffffff'h)
          ACCESS  read-only
          STATUS  mandatory
          DESCRIPTION
                "This variable indicates the node id value of the node."
            ::= { ncmhdmDs3PortEntry 1 }
 
     ncmhdmDs3PortIndex OBJECT-TYPE
          SYNTAX  INTEGER (1..65535)
          ACCESS  read-only
          STATUS  mandatory
          DESCRIPTION
               "The index value which uniquely identifies  the
                DS1  interface  to which this entry is applica-
                ble.  The interface identified by a  particular
                value  of  this  index is the same interface as
                identified by the same value as a dsx1LineIndex
                object instance."
            ::= { ncmhdmDs3PortEntry 2 }
 
     ncmhdmDs3PerfControl OBJECT-TYPE
          SYNTAX  INTEGER {
                disabled (1),
                enabled (2)
          }
          ACCESS  read-write
          STATUS  mandatory
          DESCRIPTION
                "Performance Control Enabled/Disabled."
            ::= { ncmhdmDs3PortEntry 3 }
 
     ncmhdmDs3LBOSelection  OBJECT-TYPE
          SYNTAX  INTEGER{
                nORMAL-CABLE (1),
                lONG-CABLE(2)
          }
          ACCESS  read-write
          STATUS  mandatory
          DESCRIPTION
               "Select the length of DS3 cable to be Normal
                (0-255 feet) or Long cable (225-450 feet)."
            ::= { ncmhdmDs3PortEntry 4 }
 
     ncmhdmDs3DataRateMode OBJECT-TYPE
          SYNTAX  INTEGER {
                only-NearEnd (1),
                both-NearEndORFarEnd (2),
		not-applicable (3)
          }
          ACCESS  read-write
          STATUS  mandatory
          DESCRIPTION
                "Data Rate Mode."
            ::= { ncmhdmDs3PortEntry 5 }


	ncmhdmDs3Rate OBJECT-TYPE
	SYNTAX INTEGER 
	ACCESS	read-write
	STATUS	mandatory
	DESCRIPTION
	"the date rate fro ds3 ."
	::= { ncmhdmDs3PortEntry 6 }
	


	 ncmhdmDs3LineType OBJECT-TYPE
          SYNTAX  INTEGER {
                dsx3M13(2),
                dSX3CBitParity (4)
          }
          ACCESS  read-write
          STATUS  mandatory
          DESCRIPTION
                "Line Type."
            ::= { ncmhdmDs3PortEntry 7 }
 
     ncmhdmDs3LineCode OBJECT-TYPE
          SYNTAX  INTEGER {
                dSX3CB3ZS (2)
          }
          ACCESS  read-write
          STATUS  mandatory
          DESCRIPTION
                "Line Code."
            ::= { ncmhdmDs3PortEntry 8 }
 
     ncmhdmDs3AISCBit OBJECT-TYPE
          SYNTAX  INTEGER {
                aISCBit (1)
          }
          ACCESS  read-write
          STATUS  mandatory
          DESCRIPTION
                "AISCBit."
            ::= { ncmhdmDs3PortEntry 9 }
 
     ncmhdmDs3EquipCode OBJECT-TYPE
          SYNTAX  DisplayString (SIZE (0..10))
          ACCESS  read-write
          STATUS  mandatory
          DESCRIPTION
               "This is the Far End Equipment Identification code
                that describes the specific piece of equipment.
                It is sent within the Path
                Identification Message."
          ::= { ncmhdmDs3PortEntry 10 }
 
     ncmhdmDs3LocationIDCode OBJECT-TYPE
          SYNTAX  DisplayString (SIZE (0..11))
          ACCESS  read-write
          STATUS  mandatory
          DESCRIPTION
               "This is the Far End Location Identification code
                that describes the specific location of the
                equipment.  It is sent within the Path
                Identification Message."
          ::= { ncmhdmDs3PortEntry 11 }
 
     ncmhdmDs3FrameIDCode OBJECT-TYPE
          SYNTAX  DisplayString (SIZE (0..10))
          ACCESS  read-write
          STATUS  mandatory
          DESCRIPTION
               "This is the Far End Frame Identification code
                that identifies where the equipment is located
                within a building at a given location.
                It is sent within the Path Identification Message."
          ::= { ncmhdmDs3PortEntry 12 }


	 ncmhdmDs3UnitCode OBJECT-TYPE
          SYNTAX  DisplayString (SIZE (0..6))
          ACCESS  read-write
          STATUS  mandatory
          DESCRIPTION
               "This is the Far End code
                that identifies the equipment location within a bay.
                It is sent within the Path
                Identification Message."
          ::= { ncmhdmDs3PortEntry 13 }
 
     ncmhdmDs3FacilityIDCode OBJECT-TYPE
          SYNTAX  DisplayString (SIZE (0..38))
          ACCESS  read-write
          STATUS  mandatory
          DESCRIPTION
               "This code identifies a specific Far End DS3 path.
                It is sent within the Path Identification Message."
          ::= { ncmhdmDs3PortEntry 14}
 
     ncmhdmDs3PortIdCode OBJECT-TYPE
          SYNTAX  DisplayString (SIZE (0..38))
          ACCESS read-write
          STATUS mandatory
          DESCRIPTION
               "Port ID."
          ::= { ncmhdmDs3PortEntry 15 }
 
     ncmhdmDs3CircuitID OBJECT-TYPE
          SYNTAX  DisplayString (SIZE (0..26))
          ACCESS read-write
          STATUS mandatory
          DESCRIPTION
               "Circuit ID."
          ::= { ncmhdmDs3PortEntry 16 }
 
     ncmhdmDs3GenIDCode OBJECT-TYPE
          SYNTAX  DisplayString (SIZE (0..38))
          ACCESS read-write
          STATUS mandatory
          DESCRIPTION
               "Test Signal Generator ID."
          ::= { ncmhdmDs3PortEntry 17 }
 
     ncmhdmDs3Inband OBJECT-TYPE
          SYNTAX  INTEGER {
                disabled (1),
                enabled (2)
          }
          ACCESS  read-write
          STATUS  mandatory
          DESCRIPTION
                "Inband signalling control."
            ::= { ncmhdmDs3PortEntry 18 }
 


	

 --  
     -- ncm HDM HSSI Port table
     --   

     ncmhdmHssi1PortTable OBJECT-TYPE
          SYNTAX SEQUENCE OF NcmhdmHssi1PortEntry
          ACCESS not-accessible
          STATUS mandatory
          DESCRIPTION
               "The HDM HSSI Port table."
                --DEFAULT test-function   ds3-hssi-test
--              DEFAULT set-function    null-set-proc
                --DEFAULT next-function   ds3-hssi-next
          ::= { ncm-ds3  9001 }

     ncmhdmHssi1PortEntry OBJECT-TYPE
          SYNTAX NcmhdmHssi1PortEntry
          ACCESS not-accessible
          STATUS mandatory
          DESCRIPTION
               "An entry in the dsu information table."
          INDEX   { ncmhdmDs3Hssi1NIDIndex, ncmhdmHssi1PortIndex }
          ::= { ncmhdmHssi1PortTable 1 }

     NcmhdmHssi1PortEntry ::= SEQUENCE {
             ncmhdmDs3Hssi1NIDIndex
                 INTEGER,
             ncmhdmHssi1PortIndex
                 INTEGER,
             ncmhdmHssi1ConfigMode
                 INTEGER,
             ncmhdmHssi1PortConfig
                 INTEGER,
             ncmhdmHssi1TestMode
                 INTEGER,
             ncmhdmHssi1DataRateMode
                 INTEGER,
             ncmhdmHssi1HssiRate
                 INTEGER,
	     ncmhdmHssi1CircuitID
 		 DisplayString
        
     }
       
     	ncmhdmDs3Hssi1NIDIndex OBJECT-TYPE
          SYNTAX  INTEGER (1..'7fffffff'h)
          ACCESS  read-only
          STATUS  mandatory
          DESCRIPTION
                "This variable indicates the node id value of the node."
            ::= { ncmhdmHssi1PortEntry 1 }
               
	ncmhdmHssi1PortIndex OBJECT-TYPE
          SYNTAX  INTEGER (1..65535)
          ACCESS  read-only
          STATUS  mandatory
          DESCRIPTION
               "The index value which uniquely identifies  the
                DS1  interface  to which this entry is applica-
                ble.  The interface identified by a  particular
                value  of  this  index is the same interface as
                identified by the same value as a dsx1LineIndex
                object instance."
            ::= { ncmhdmHssi1PortEntry 2 }
 
     	ncmhdmHssi1ConfigMode OBJECT-TYPE
          SYNTAX INTEGER {
                       aUTOMATIC(1),
                       mANUAL(2)
               } 
          ACCESS read-write
          STATUS mandatory
          DESCRIPTION
               "Set the Hssi Port to be automatic configuration
                or manual configuration. "
          ::= { ncmhdmHssi1PortEntry 3 }
 
     	ncmhdmHssi1PortConfig OBJECT-TYPE
          SYNTAX INTEGER {
                       oUT-OF-SERVICE(1),
                       iN-SERVICE(2)
               } 
          ACCESS read-write
          STATUS mandatory
          DESCRIPTION
               "Configure System - In-Service or Out of Service."
          ::= { ncmhdmHssi1PortEntry 4 }
 
     	ncmhdmHssi1TestMode OBJECT-TYPE
          SYNTAX  INTEGER{
                enabled(1),
                disabled(2)
          }
          ACCESS  read-only
          STATUS  mandatory
          DESCRIPTION
               "Report status of the test mode of HSSI port."
          ::= { ncmhdmHssi1PortEntry 5 }
 
        ncmhdmHssi1DataRateMode OBJECT-TYPE
          SYNTAX  INTEGER {
                only-NearEnd (1),
                both-NearEndORFarEnd (2),
		not-applicable (3)
          }
          ACCESS  read-write
          STATUS  mandatory
          DESCRIPTION
                "Data Rate Mode for the Hssi Ports ."
            ::= { ncmhdmHssi1PortEntry 6 }


	 ncmhdmHssi1HssiRate OBJECT-TYPE
          SYNTAX  INTEGER (0..28)
          ACCESS  read-write
          STATUS  mandatory
          DESCRIPTION
                "Data Rate in # of T1."
          ::= { ncmhdmHssi1PortEntry 7 }


	 ncmhdmHssi1CircuitID OBJECT-TYPE
           SYNTAX  DisplayString (SIZE (0..20))
           ACCESS  read-write
           STATUS  mandatory
           DESCRIPTION
                "This is the Circuit ID for the Hssi port."
           ::= { ncmhdmHssi1PortEntry 8 }



 
 
--- ncm HSSI Stats
---
     ncmhdmHssiStatTable OBJECT-TYPE
          SYNTAX SEQUENCE OF NcmhdmHssiStatEntry
          ACCESS not-accessible
          STATUS mandatory
          DESCRIPTION
               "The HDM HSSI Stats."
                --DEFAULT test-function   ds3-hssi-test
--              DEFAULT set-function    null-set-proc
                --DEFAULT next-function   ds3-hssi-next
                ::= { ncm-ds3 9002 }
 
     ncmhdmHssiStatEntry OBJECT-TYPE
          SYNTAX NcmhdmHssiStatEntry
          ACCESS not-accessible
          STATUS mandatory
          DESCRIPTION
               "An entry in the Hssi ds3 stats table."
          INDEX   { ncmhdmHssiStatNIDIndex, ncmhdmHssiStatIndex }
          ::= { ncmhdmHssiStatTable 1 }
 
     NcmhdmHssiStatEntry ::= SEQUENCE {
             ncmhdmHssiStatNIDIndex
                 INTEGER,
             ncmhdmHssiStatIndex
                 INTEGER,
             ncmhdmStatDCEReady
                 INTEGER,
             ncmhdmStatDTEReady
                 INTEGER,
             ncmhdmStatLpbkA
                 INTEGER,
             ncmhdmStatLpbkB
                 INTEGER,
             ncmhdmStatTestMode
                 INTEGER,
             ncmhdmStatPortState
                 INTEGER,
             ncmhdmStatCIMType
                 INTEGER,
             ncmhdmStatDiagStatus
                 INTEGER
     }
 
     ncmhdmHssiStatNIDIndex OBJECT-TYPE
          SYNTAX  INTEGER (1..'7fffffff'h)
          ACCESS  read-only
          STATUS  mandatory
          DESCRIPTION
                "This variable indicates the node id value of the node."
            ::= { ncmhdmHssiStatEntry 1 }


	ncmhdmHssiStatIndex OBJECT-TYPE
          SYNTAX  INTEGER (1..65535)
          ACCESS  read-only
          STATUS  mandatory
          DESCRIPTION
               "The index value which uniquely identifies  the
                DS1  interface  to which this entry is applica-
                ble.  The interface identified by a  particular
                value  of  this  index is the same interface as
                identified by the same value as a dsx1LineIndex
                object instance."
            ::= { ncmhdmHssiStatEntry 2 }
 
 
     	ncmhdmStatDCEReady OBJECT-TYPE
          SYNTAX INTEGER {
                       oFF (1),
                       oN (2)
               } 
          ACCESS read-only
          STATUS mandatory
          DESCRIPTION
               "Hssi Port DCE Ready OFF/ON. "
          ::= { ncmhdmHssiStatEntry  3 }
 
     	ncmhdmStatDTEReady OBJECT-TYPE
          SYNTAX INTEGER {
                       oFF (1),
                       oN (2)
               } 
          ACCESS read-only
          STATUS mandatory
          DESCRIPTION
               "Hssi Port DTE Ready OFF/ON. "
          ::= { ncmhdmHssiStatEntry  4 }
 
 
     	ncmhdmStatLpbkA OBJECT-TYPE
          SYNTAX INTEGER {
                       oFF (1),
                       oN (2)
               } 
          ACCESS read-only
          STATUS mandatory
          DESCRIPTION
               "Hssi Port - Loopback A OFF/ON."
          ::= { ncmhdmHssiStatEntry  5 }
 
 
     	ncmhdmStatLpbkB OBJECT-TYPE
          SYNTAX INTEGER {
                       oFF (1),
                       oN (2)
               } 
          ACCESS read-only
          STATUS mandatory
          DESCRIPTION
               "Hssi Port - Loopback B OFF/ON."
          ::= { ncmhdmHssiStatEntry  6 }


	ncmhdmStatTestMode OBJECT-TYPE
          SYNTAX INTEGER {
                       oFF (1),
                       oN (2)
               } 
          ACCESS read-only
          STATUS mandatory
          DESCRIPTION
               "Hssi Port Test Mode OFF/ON."
          ::= { ncmhdmHssiStatEntry  7  }
 
 
     	ncmhdmStatPortState OBJECT-TYPE
          SYNTAX INTEGER {
                       oUT-OF-SERVICE(1),
                       iN-SERVICE(2)
               } 
          ACCESS read-only
          STATUS mandatory
          DESCRIPTION
               "Hssi Port - In-Service or Out of Service."
          ::= { ncmhdmHssiStatEntry  8 }
 
 
     	ncmhdmStatCIMType OBJECT-TYPE
          SYNTAX INTEGER {
                       cim-2080 (44),
                       cdm-2080 (59),
		       cdm-2182 (63)
               } 
          ACCESS read-only
          STATUS mandatory
          DESCRIPTION
               "Ds3 Cim Type."
          ::= { ncmhdmHssiStatEntry 9 }
 
     	ncmhdmStatDiagStatus OBJECT-TYPE
          SYNTAX INTEGER {
                       oFF (1),
                       oN (2)
               } 
          ACCESS read-only
          STATUS mandatory
          DESCRIPTION
               "Hssi User Equipment Loopback OFF/ON."
          ::= { ncmhdmHssiStatEntry 10 }


-- the ncm HDM DS3/E3 Current
 
-- The ncm HDM DS3/E3 current table contains various statistics being
-- collected for the current 15 minute interval.
 
          ncmhdmCurrentTable OBJECT-TYPE
              SYNTAX  SEQUENCE OF NcmhdmCurrentEntry
              ACCESS  not-accessible
              STATUS  mandatory
              DESCRIPTION
                      "The DS3/E3 Current table."
                --DEFAULT test-function   ds3-test
--              DEFAULT set-function    null-set-proc
                --DEFAULT next-function   ds3-next
              ::= { ncm-ds3 9003 }
 
          ncmhdmCurrentEntry OBJECT-TYPE
              SYNTAX  NcmhdmCurrentEntry
              ACCESS  not-accessible
              STATUS  mandatory
              DESCRIPTION
                      "An entry in the DS3/E3 Current table."
              INDEX   { ncmhdmCurrentNIDIndex, ncmhdmCurrentIndex }
              ::= { ncmhdmCurrentTable 1 }
 
          NcmhdmCurrentEntry ::=
              SEQUENCE {
                  ncmhdmCurrentNIDIndex
                      INTEGER,
                  ncmhdmCurrentIndex
                      INTEGER,
                  ncmhdmCurrentCRC4Status
                      INTEGER,
                  ncmhdmCurrentTimeStampSecs
                      INTEGER,
                  ncmhdmCurrentTimeStampMSecs
                      INTEGER,
                  ncmhdmCurrentSecsElaps
                      INTEGER,
                  ncmhdmCurrentFarEndCCV
                      Gauge,
                  ncmhdmCurrentFarEndCES
                      Gauge,
                  ncmhdmCurrentFarEndCSES
                      Gauge,
                  ncmhdmCurrentFarEndLUAS
                      Gauge,
                  ncmhdmCurrentLCV
                      Gauge,
                  ncmhdmCurrentLES
                      Gauge,
                  ncmhdmCurrentLSESs
                      Gauge,
                  ncmhdmCurrentPCV
                      Gauge,
                  ncmhdmCurrentPES
                      Gauge,
                  ncmhdmCurrentPSES
                      Gauge,
                  ncmhdmCurrentCCV
                      Gauge,
                  ncmhdmCurrentCES
                      Gauge,
                  ncmhdmCurrentCSES
                      Gauge,
		 ncmhdmCurrentSEFS
                      Gauge,
                  ncmhdmCurrentAISS
                      Gauge,
                  ncmhdmCurrentOOSSs
                      Gauge,
                  ncmhdmCurrentLOSSs
                      Gauge,
                  ncmhdmCurrentLOFSs
                      Gauge
              }
 
        ncmhdmCurrentNIDIndex OBJECT-TYPE
          SYNTAX  INTEGER (1..'7fffffff'h)
          ACCESS  read-only
          STATUS  mandatory
          DESCRIPTION
                "This variable indicates the node id value of the node."
            ::= { ncmhdmCurrentEntry 1 }
               
          ncmhdmCurrentIndex OBJECT-TYPE
              SYNTAX  INTEGER (1..65535)
              ACCESS  read-only
              STATUS  mandatory
              DESCRIPTION
                      "The index value which uniquely identifies the
                      DS3/E3 interface to which this entry is
                      applicable.  The interface identified by a
                      particular value of this index is the same
                      interface as identified by the same value an
                      ncmhdmLineIndex object instance."
              ::= { ncmhdmCurrentEntry 2 }
 
          ncmhdmCurrentCRC4Status OBJECT-TYPE
                SYNTAX INTEGER {
                       disabled (1)
               } 
          ACCESS read-only
          STATUS mandatory
          DESCRIPTION
               "Current CRC4 Status."
          ::= { ncmhdmCurrentEntry  3  }
 
 
          ncmhdmCurrentTimeStampSecs OBJECT-TYPE
              SYNTAX  INTEGER (1..65535)
              ACCESS  read-only
              STATUS  mandatory
              DESCRIPTION
                      "Current Time in seconds."
              ::= { ncmhdmCurrentEntry 4 }
 
          ncmhdmCurrentTimeStampMSecs OBJECT-TYPE
              SYNTAX  INTEGER (1..65535)
              ACCESS  read-only
              STATUS  mandatory
              DESCRIPTION
                      "Current Time in milliseconds."
              ::= { ncmhdmCurrentEntry 5 }


	 ncmhdmCurrentSecsElaps OBJECT-TYPE
              SYNTAX  INTEGER (1..65535)
              ACCESS  read-only
              STATUS  mandatory
              DESCRIPTION
                      "Seconds elapsed in the current interval."
              ::= { ncmhdmCurrentEntry 6 }
 
          ncmhdmCurrentFarEndCCV OBJECT-TYPE
              SYNTAX  Gauge
              ACCESS  read-only
              STATUS  mandatory
              DESCRIPTION
                      "The counter associated with the number of
                        Far End C-bit Code Violations,
                       in the current 15 minute interval."
              ::= { ncmhdmCurrentEntry 7 }
               
          ncmhdmCurrentFarEndCES OBJECT-TYPE
              SYNTAX  Gauge
              ACCESS  read-only
              STATUS  mandatory
              DESCRIPTION
                      "The counter associated with the number of
                        Far End C-bit Errored Seconds,
                       in the current 15 minute interval."
              ::= { ncmhdmCurrentEntry 8 }
               
          ncmhdmCurrentFarEndCSES OBJECT-TYPE
              SYNTAX  Gauge
              ACCESS  read-only
              STATUS  mandatory
              DESCRIPTION
                      "The counter associated with the number of
                        Far End C-bit Severely Errored Seconds,
                       in the current 15 minute interval."
 
              ::= { ncmhdmCurrentEntry 9 }
 
          ncmhdmCurrentFarEndLUAS OBJECT-TYPE
              SYNTAX  Gauge
              ACCESS  read-only
              STATUS  mandatory
              DESCRIPTION
                      "Far End Line Unavailable Seconds. The counter associated
                      with the number of Seconds the Far End DS3 interface
                      was Out Of Service in the current 15 minute interval."
              ::= { ncmhdmCurrentEntry 10 }
               
          ncmhdmCurrentLCV OBJECT-TYPE
              SYNTAX  Gauge
              ACCESS  read-only
              STATUS  mandatory
              DESCRIPTION
                      "The counter associated with the number of Line
                      Code Violations, a bipolar or excesive zero violation,
                       in the current 15 minute interval."
              ::= { ncmhdmCurrentEntry 11 }


	 ncmhdmCurrentLES OBJECT-TYPE
              SYNTAX  Gauge
              ACCESS  read-only
              STATUS  mandatory
              DESCRIPTION
                      "Line Errored Second Total.  The counter associated
                      with the number of Seconds of in which one or more
                      LCV occurred in the current 15 minute interval."
              ::= { ncmhdmCurrentEntry 12 }
               
          ncmhdmCurrentLSESs OBJECT-TYPE
              SYNTAX  Gauge
              ACCESS  read-only
              STATUS  mandatory
              DESCRIPTION
                      "The counter associated with the number of
                       Line Severely Errored Seconds (LSES) in
                       the current 15 minute interval."
              ::= { ncmhdmCurrentEntry 13 }
               
          ncmhdmCurrentPCV OBJECT-TYPE
              SYNTAX  Gauge
              ACCESS  read-only
              STATUS  mandatory
              DESCRIPTION
                      "The counter associated with the number
                      of Parity Code Violations (locally calculated P-bits
                      disagree with those received),
                       in the current 15 minute interval."
              ::= { ncmhdmCurrentEntry 14 }
               
          ncmhdmCurrentPES OBJECT-TYPE
              SYNTAX  Gauge
              ACCESS  read-only
              STATUS  mandatory
              DESCRIPTION
                      "The counter associated with the number of Seconds
                      having at least one Parity Code Violation,
                       in the current 15 minute interval."
              ::= { ncmhdmCurrentEntry 15 }
               
          ncmhdmCurrentPSES OBJECT-TYPE
              SYNTAX  Gauge
              ACCESS  read-only
              STATUS  mandatory
              DESCRIPTION
                      "The counter associated with the number of Seconds
                      having 44 or more Parity Code Violations,
                       in the current 15 minute interval."
              ::= { ncmhdmCurrentEntry 16 }
               
          ncmhdmCurrentCCV OBJECT-TYPE
              SYNTAX  Gauge
              ACCESS  read-only
              STATUS  mandatory
              DESCRIPTION
                      "The counter associated with the number of
                        C-bit Code Violations,
                       in the current 15 minute interval."
              ::= { ncmhdmCurrentEntry 17 }


	ncmhdmCurrentCES OBJECT-TYPE
              SYNTAX  Gauge
              ACCESS  read-only
              STATUS  mandatory
              DESCRIPTION
                      "The counter associated with the number of
                        C-bit Errored Seconds,
                       in the current 15 minute interval."
              ::= { ncmhdmCurrentEntry 18 }
               
          ncmhdmCurrentCSES OBJECT-TYPE
              SYNTAX  Gauge
              ACCESS  read-only
              STATUS  mandatory
              DESCRIPTION
                      "The counter associated with the number of
                        C-bit Severely Errored Seconds,
                       in the current 15 minute interval."
              ::= { ncmhdmCurrentEntry 19 }
               
          ncmhdmCurrentSEFS OBJECT-TYPE
              SYNTAX  Gauge
              ACCESS  read-only
              STATUS  mandatory
              DESCRIPTION
                      "The counter associated with the number of seconds
                      in which one or more Out of Frame occurred
                       in the current 15 minute interval."
              ::= { ncmhdmCurrentEntry 20 }
               
          ncmhdmCurrentAISS OBJECT-TYPE
              SYNTAX  Gauge
              ACCESS  read-only
              STATUS  mandatory
              DESCRIPTION
                      "The counter associated with the number of Seconds
                      in which one or more incoming AIS was detected
                       in the current 15 minute interval."
              ::= { ncmhdmCurrentEntry 21 }
               
          ncmhdmCurrentOOSSs OBJECT-TYPE
              SYNTAX  Gauge
              ACCESS  read-only
              STATUS  mandatory
              DESCRIPTION
                      "The counter associated with the number of Seconds
                      the DS3 interface was Out Of Service
                       in the current 15 minute interval."
              ::= { ncmhdmCurrentEntry 22 }
               
          ncmhdmCurrentLOSSs OBJECT-TYPE
              SYNTAX  Gauge
              ACCESS  read-only
              STATUS  mandatory
              DESCRIPTION
                      "The counter associated with the number of Seconds
                      Of system Loss Of Signal (LOS) in the current
                      15 minute interval."
              ::= { ncmhdmCurrentEntry 23 }


	 ncmhdmCurrentLOFSs OBJECT-TYPE
              SYNTAX  Gauge
              ACCESS  read-only
              STATUS  mandatory
              DESCRIPTION
                      "The counter associated with the number of Seconds
                      Of system Loss Of Frame (LOF) in the current
                      15 minute interval."
                
              ::= { ncmhdmCurrentEntry 24 }
               
 
-- ncm DS3/E3 Specific Interval table
     -- The HDM DS3/E3 Interval table contains various statistics
     -- collected by each DS3 Interface over the previous 24 hours of
     -- operation.  The past 24 hours are broken into 96 completed
     -- 15 minute intervals.
 
 
          ncmhdmIntervalTable OBJECT-TYPE
              SYNTAX  SEQUENCE OF NcmhdmIntervalEntry
              ACCESS  not-accessible
              STATUS  mandatory
              DESCRIPTION
                      "The DS3/E3 Interval table."
                --DEFAULT test-function   ds3interval-test
                --DEFAULT next-function   ds3interval-next
              ::= { ncm-ds3 9004 }
 
          ncmhdmIntervalEntry OBJECT-TYPE
              SYNTAX  NcmhdmIntervalEntry
              ACCESS  not-accessible
              STATUS  mandatory
              DESCRIPTION
                      "An entry in the DS3/E3 Interval table."
              INDEX   { ncmhdmIntervalNIDIndex, ncmhdmIntervalIndex, ncmhdmIntervalNumber }
              ::= { ncmhdmIntervalTable 1 }
 
          NcmhdmIntervalEntry ::=
              SEQUENCE {
                  ncmhdmIntervalNIDIndex
                      INTEGER,
                  ncmhdmIntervalIndex
                      INTEGER,
                  ncmhdmIntervalNumber
                      INTEGER,
                  ncmhdmIntervalFarEndCCV
                      Gauge,
                  ncmhdmIntervalFarEndCES
                      Gauge,
                  ncmhdmIntervalFarEndCSES
                      Gauge,
                  ncmhdmIntervalFarEndLUAS
                      Gauge,
                  ncmhdmIntervalLCV
                      Gauge,
                  ncmhdmIntervalLES
                      Gauge,
                  ncmhdmIntervalLSESs
                      Gauge,
                  ncmhdmIntervalPCV
                      Gauge,
                  ncmhdmIntervalPES
                      Gauge,
		ncmhdmIntervalPSES
                      Gauge,
                  ncmhdmIntervalCCV
                      Gauge,
                  ncmhdmIntervalCES
                      Gauge,
                  ncmhdmIntervalCSES
                      Gauge,
                  ncmhdmIntervalSEFS
                      Gauge,
                  ncmhdmIntervalAISS
                      Gauge,
                  ncmhdmIntervalOOSSs
                      Gauge,
                  ncmhdmIntervalLOSSs
                      Gauge,
                  ncmhdmIntervalLOFSs
                      Gauge
              }
 
        ncmhdmIntervalNIDIndex OBJECT-TYPE
          SYNTAX  INTEGER (1..'7fffffff'h)
          ACCESS  read-only
          STATUS  mandatory
          DESCRIPTION
                "This variable indicates the node id value of the node."
            ::= { ncmhdmIntervalEntry 1 }
               
 
          ncmhdmIntervalIndex OBJECT-TYPE
              SYNTAX  INTEGER (1..65535)
              ACCESS  read-only
              STATUS  mandatory
              DESCRIPTION
                      "The index value which uniquely identifies the
                      DS3/E3 interface to which this entry is
                      applicable.  The interface identified by a
                      particular value of this index is the same
                      interface as identified by the same value an
                      ncmhdmLineIndex object instance."
              ::= { ncmhdmIntervalEntry 2 }
 
         ncmhdmIntervalNumber OBJECT-TYPE
             SYNTAX  INTEGER (1..96)
             ACCESS  read-only
             STATUS  mandatory
             DESCRIPTION
                "A number between 1 and 96, where 1 is the most
                recently completed 15 minute interval and 96 is
                the least recently completed 15 minutes  inter-
                val   (assuming   that  all  96  intervals  are
                valid)."
            ::= { ncmhdmIntervalEntry 3 }
 
 
          ncmhdmIntervalFarEndCCV OBJECT-TYPE
              SYNTAX  Gauge
              ACCESS  read-only
              STATUS  mandatory
              DESCRIPTION
                      "The counter associated with the number of
                        Far End C-bit Code Violations,
                       in the previous 15 minute interval."
              ::= { ncmhdmIntervalEntry 4 }


	ncmhdmIntervalFarEndCES OBJECT-TYPE
              SYNTAX  Gauge
              ACCESS  read-only
              STATUS  mandatory
              DESCRIPTION
                      "The counter associated with the number of
                        Far End C-bit Errored Seconds,
                       in the current 15 minute interval."
              ::= { ncmhdmIntervalEntry 5 }
               
          ncmhdmIntervalFarEndCSES OBJECT-TYPE
              SYNTAX  Gauge
              ACCESS  read-only
              STATUS  mandatory
              DESCRIPTION
                      "The counter associated with the number of
                        Far End C-bit Severely Errored Seconds,
                       in the current 15 minute interval."
 
              ::= { ncmhdmIntervalEntry 6 }
 
          ncmhdmIntervalFarEndLUAS OBJECT-TYPE
              SYNTAX  Gauge
              ACCESS  read-only
              STATUS  mandatory
              DESCRIPTION
                      "Far End Line Unavailable Seconds. The counter associated
                      with the number of Seconds the Far End DS3 interface
                      was Out Of Service in the current 15 minute interval."
              ::= { ncmhdmIntervalEntry 7 }
               
          ncmhdmIntervalLCV OBJECT-TYPE
              SYNTAX  Gauge
              ACCESS  read-only
              STATUS  mandatory
              DESCRIPTION
                      "The counter associated with the number of Line
                      Code Violations, a bipolar or excesive zero violation,
                       in the current 15 minute interval."
              ::= { ncmhdmIntervalEntry 8 }
               
          ncmhdmIntervalLES OBJECT-TYPE
              SYNTAX  Gauge
              ACCESS  read-only
              STATUS  mandatory
              DESCRIPTION
                      "Line Errored Second Total.  The counter associated
                      with the number of Seconds of in which one or more
                      LCV occurred in the current 15 minute interval."
              ::= { ncmhdmIntervalEntry 9 }
               
          ncmhdmIntervalLSESs OBJECT-TYPE
              SYNTAX  Gauge
              ACCESS  read-only
              STATUS  mandatory
              DESCRIPTION
                      "The counter associated with the number of
                       Line Severely Errored Seconds (LSES) in
                       the current 15 minute interval."
              ::= { ncmhdmIntervalEntry 10 }


	ncmhdmIntervalPCV OBJECT-TYPE
              SYNTAX  Gauge
              ACCESS  read-only
              STATUS  mandatory
              DESCRIPTION
                      "The counter associated with the number
                      of Parity Code Violations (locally calculated P-bits
                      disagree with those received),
                       in the current 15 minute interval."
              ::= { ncmhdmIntervalEntry 11 }
               
          ncmhdmIntervalPES OBJECT-TYPE
              SYNTAX  Gauge
              ACCESS  read-only
              STATUS  mandatory
              DESCRIPTION
                      "The counter associated with the number of Seconds
                      having at least one Parity Code Violation,
                       in the current 15 minute interval."
              ::= { ncmhdmIntervalEntry 12 }
               
          ncmhdmIntervalPSES OBJECT-TYPE
              SYNTAX  Gauge
              ACCESS  read-only
              STATUS  mandatory
              DESCRIPTION
                      "The counter associated with the number of Seconds
                      having 44 or more Parity Code Violations,
                       in the current 15 minute interval."
              ::= { ncmhdmIntervalEntry 13 }
               
          ncmhdmIntervalCCV OBJECT-TYPE
              SYNTAX  Gauge
              ACCESS  read-only
              STATUS  mandatory
              DESCRIPTION
                      "The counter associated with the number of
                        C-bit Code Violations,
                       in the current 15 minute interval."
              ::= { ncmhdmIntervalEntry 14 }
               
          ncmhdmIntervalCES OBJECT-TYPE
              SYNTAX  Gauge
              ACCESS  read-only
              STATUS  mandatory
              DESCRIPTION
                      "The counter associated with the number of
                        C-bit Errored Seconds,
                       in the current 15 minute interval."
              ::= { ncmhdmIntervalEntry 15 }
               
          ncmhdmIntervalCSES OBJECT-TYPE
              SYNTAX  Gauge
              ACCESS  read-only
              STATUS  mandatory
              DESCRIPTION
                      "The counter associated with the number of
                        C-bit Severely Errored Seconds,
                       in the current 15 minute interval."
              ::= { ncmhdmIntervalEntry 16 }


	 ncmhdmIntervalSEFS OBJECT-TYPE
              SYNTAX  Gauge
              ACCESS  read-only
              STATUS  mandatory
              DESCRIPTION
                      "The counter associated with the number of seconds
                      in which one or more Out of Frame occurred
                       in the current 15 minute interval."
              ::= { ncmhdmIntervalEntry 17 }
               
          ncmhdmIntervalAISS OBJECT-TYPE
              SYNTAX  Gauge
              ACCESS  read-only
              STATUS  mandatory
              DESCRIPTION
                      "The counter associated with the number of Seconds
                      in which one or more incoming AIS was detected
                       in the current 15 minute interval."
              ::= { ncmhdmIntervalEntry 18 }
               
          ncmhdmIntervalOOSSs OBJECT-TYPE
              SYNTAX  Gauge
              ACCESS  read-only
              STATUS  mandatory
              DESCRIPTION
                      "The counter associated with the number of Seconds
                      the DS3 interface was Out Of Service
                       in the current 15 minute interval."
              ::= { ncmhdmIntervalEntry 19 }
               
          ncmhdmIntervalLOSSs OBJECT-TYPE
              SYNTAX  Gauge
              ACCESS  read-only
              STATUS  mandatory
              DESCRIPTION
                      "The counter associated with the number of Seconds
                      Of system Loss Of Signal (LOS) in the current
                      15 minute interval."
              ::= { ncmhdmIntervalEntry 20 }
               
          ncmhdmIntervalLOFSs OBJECT-TYPE
              SYNTAX  Gauge
              ACCESS  read-only
              STATUS  mandatory
              DESCRIPTION
                      "The counter associated with the number of Seconds
                      Of system Loss Of Frame (LOF) in the current
                      15 minute interval."
                
              ::= { ncmhdmIntervalEntry 21 }


	-- the  ncm HDM DS3/E3 Total Table
 
          ncmhdmTotalTable OBJECT-TYPE
              SYNTAX  SEQUENCE OF NcmhdmTotalEntry
              ACCESS  not-accessible
              STATUS  mandatory
              DESCRIPTION
                      "The DS3/E3 Total table."
                --DEFAULT test-function   ds3-test
--              DEFAULT set-function    null-set-proc
                --DEFAULT next-function   ds3-next
              ::= { ncm-ds3 9005 }
 
          ncmhdmTotalEntry OBJECT-TYPE
              SYNTAX  NcmhdmTotalEntry
              ACCESS  not-accessible
              STATUS  mandatory
              DESCRIPTION
                      "An entry in the DS3/E3 Total table."
              INDEX   { ncmhdmTotalNIDIndex, ncmhdmTotalIndex }
              ::= { ncmhdmTotalTable 1 }
 
 
          NcmhdmTotalEntry ::=
              SEQUENCE {
                  ncmhdmTotalNIDIndex
                      INTEGER,
                  ncmhdmTotalIndex
                      INTEGER,
                  ncmhdmTotalCRC4Status
                      INTEGER,
                  ncmhdmTotalValidInterv
                      INTEGER,
                  ncmhdmTotalFarEndCCV
                      Gauge,
                  ncmhdmTotalFarEndCES
                      Gauge,
                  ncmhdmTotalFarEndCSES
                      Gauge,
                  ncmhdmTotalFarEndLUAS
                      Gauge,
                  ncmhdmTotalLCV
                      Gauge,
                  ncmhdmTotalLES
                      Gauge,
                  ncmhdmTotalLSESs
                      Gauge,
                  ncmhdmTotalPCV
                      Gauge,
                  ncmhdmTotalPES
                      Gauge,
                  ncmhdmTotalPSES
                      Gauge,
                  ncmhdmTotalCCV
                      Gauge,
                  ncmhdmTotalCES
                      Gauge,
                  ncmhdmTotalCSES
                      Gauge,
                  ncmhdmTotalSEFS
                      Gauge,
                  ncmhdmTotalAISS
                      Gauge,
                  ncmhdmTotalOOSSs
                      Gauge,
		ncmhdmTotalLOSSs
                      Gauge,
                  ncmhdmTotalLOFSs
                      Gauge
              }
 
        ncmhdmTotalNIDIndex OBJECT-TYPE
          SYNTAX  INTEGER (1..'7fffffff'h)
          ACCESS  read-only
          STATUS  mandatory
          DESCRIPTION
                "This variable indicates the node id value of the node."
            ::= { ncmhdmTotalEntry 1 }
               
          ncmhdmTotalIndex OBJECT-TYPE
              SYNTAX  INTEGER (1..65535)
              ACCESS  read-only
              STATUS  mandatory
              DESCRIPTION
                      "The index value which uniquely identifies the
                      DS3/E3 interface to which this entry is
                      applicable.  The interface identified by a
                      particular value of this index is the same
                      interface as identified by the same value an
                      ncmhdmLineIndex object instance."
              ::= { ncmhdmTotalEntry 2 }
 
          ncmhdmTotalCRC4Status OBJECT-TYPE
               SYNTAX INTEGER {
                       disabled (1)
               } 
              ACCESS  read-only
              STATUS  mandatory
              DESCRIPTION
                      "CRC4 Status."
              ::= { ncmhdmTotalEntry 3 }
 
          ncmhdmTotalValidInterv OBJECT-TYPE
              SYNTAX  INTEGER (1..65535)
              ACCESS  read-only
              STATUS  mandatory
              DESCRIPTION
                      "The number of valid intervals."
              ::= { ncmhdmTotalEntry 4 }
 
          ncmhdmTotalFarEndCCV OBJECT-TYPE
              SYNTAX  Gauge
              ACCESS  read-only
              STATUS  mandatory
              DESCRIPTION
                      "The counter associated with the number of
                        Far End C-bit Code Violations,
                      in the last 24 hour interval."
              ::= { ncmhdmTotalEntry 5 }
               
          ncmhdmTotalFarEndCES OBJECT-TYPE
              SYNTAX  Gauge
              ACCESS  read-only
              STATUS  mandatory
              DESCRIPTION
                      "The counter associated with the number of
                        Far End C-bit Errored Seconds,
                      in the last 24 hour interval."
              ::= { ncmhdmTotalEntry 6 }
	 ncmhdmTotalFarEndCSES OBJECT-TYPE
              SYNTAX  Gauge
              ACCESS  read-only
              STATUS  mandatory
              DESCRIPTION
                      "The counter associated with the number of
                        Far End C-bit Severely Errored Seconds,
                      in the last 24 hour interval."
 
              ::= { ncmhdmTotalEntry 7 }
 
          ncmhdmTotalFarEndLUAS OBJECT-TYPE
              SYNTAX  Gauge
              ACCESS  read-only
              STATUS  mandatory
              DESCRIPTION
                      "Far End Line Unavailable Seconds. The counter associated
                      with the number of Seconds the Far End DS3 interface
                      was Out Of Service in the last 24 hour interval."
              ::= { ncmhdmTotalEntry 8 }
               
          ncmhdmTotalLCV OBJECT-TYPE
              SYNTAX  Gauge
              ACCESS  read-only
              STATUS  mandatory
              DESCRIPTION
                      "The counter associated with the number of Line
                      Code Violations, a bipolar or excesive zero violation,
                      in the last 24 hour interval."
              ::= { ncmhdmTotalEntry 9 }
               
          ncmhdmTotalLES OBJECT-TYPE
              SYNTAX  Gauge
              ACCESS  read-only
              STATUS  mandatory
              DESCRIPTION
                      "Line Errored Second Total.  The counter associated
                      with the number of Seconds of in which one or more
                      LCV occurred in the last 24 hour interval."
              ::= { ncmhdmTotalEntry 10 }
               
          ncmhdmTotalLSESs OBJECT-TYPE
              SYNTAX  Gauge
              ACCESS  read-only
              STATUS  mandatory
              DESCRIPTION
                      "The counter associated with the number of Seconds
                      Of Line Severely Errored Seconds (LSES) in the last
                      24 hour interval."
              ::= { ncmhdmTotalEntry 11 }
               
          ncmhdmTotalPCV OBJECT-TYPE
              SYNTAX  Gauge
              ACCESS  read-only
              STATUS  mandatory
              DESCRIPTION
                      "The counter associated with the number
                      of Parity Code Violations (locally calculated P-bits
                      disagree with those received),
                      in the last 24 hour interval."
              ::= { ncmhdmTotalEntry 12 }

	 ncmhdmTotalPES OBJECT-TYPE
              SYNTAX  Gauge
              ACCESS  read-only
              STATUS  mandatory
              DESCRIPTION
                      "The counter associated with the number of Seconds
                      having at least one Parity Code Violation,
                      in the last 24 hour interval."
              ::= { ncmhdmTotalEntry 13 }
               
          ncmhdmTotalPSES OBJECT-TYPE
              SYNTAX  Gauge
              ACCESS  read-only
              STATUS  mandatory
              DESCRIPTION
                      "The counter associated with the number of Seconds
                      having 44 or more Parity Code Violations,
                      in the last 24 hour interval."
              ::= { ncmhdmTotalEntry 14 }
               
          ncmhdmTotalCCV OBJECT-TYPE
              SYNTAX  Gauge
              ACCESS  read-only
              STATUS  mandatory
              DESCRIPTION
                      "The counter associated with the number of
                        C-bit Code Violations,
                      in the last 24 hour interval."
              ::= { ncmhdmTotalEntry 15 }
               
          ncmhdmTotalCES OBJECT-TYPE
              SYNTAX  Gauge
              ACCESS  read-only
              STATUS  mandatory
              DESCRIPTION
                      "The counter associated with the number of
                        C-bit Errored Seconds,
                      in the last 24 hour interval."
              ::= { ncmhdmTotalEntry 16 }
               
          ncmhdmTotalCSES OBJECT-TYPE
              SYNTAX  Gauge
              ACCESS  read-only
              STATUS  mandatory
              DESCRIPTION
                      "The counter associated with the number of
                        C-bit Severely Errored Seconds,
                      in the last 24 hour interval."
              ::= { ncmhdmTotalEntry 17 }
               
          ncmhdmTotalSEFS OBJECT-TYPE
              SYNTAX  Gauge
              ACCESS  read-only
              STATUS  mandatory
              DESCRIPTION
                      "The counter associated with the number of seconds
                      in which one or more Out of Frame occurred
                      in the last 24 hour interval."
              ::= { ncmhdmTotalEntry 18 }


	 ncmhdmTotalAISS OBJECT-TYPE
              SYNTAX  Gauge
              ACCESS  read-only
              STATUS  mandatory
              DESCRIPTION
                      "The counter associated with the number of Seconds
                      in which one or more incoming AIS was detected
                      in the last 24 hour interval."
              ::= { ncmhdmTotalEntry 19 }
               
          ncmhdmTotalOOSSs OBJECT-TYPE
              SYNTAX  Gauge
              ACCESS  read-only
              STATUS  mandatory
              DESCRIPTION
                      "The counter associated with the number of Seconds
                      the DS3 interface was Out Of Service in the last 24
                      hour interval."
              ::= { ncmhdmTotalEntry 20 }
               
          ncmhdmTotalLOSSs OBJECT-TYPE
              SYNTAX  Gauge
              ACCESS  read-only
              STATUS  mandatory
              DESCRIPTION
                      "The counter associated with the number of Seconds
                      Of system Loss Of Signal (LOS) in the last
                      24 hour interval."
              ::= { ncmhdmTotalEntry 21 }
               
          ncmhdmTotalLOFSs OBJECT-TYPE
              SYNTAX  Gauge
              ACCESS  read-only
              STATUS  mandatory
              DESCRIPTION
                      "The counter associated with the number of Seconds
                      Of system Loss Of Frame (LOF) in the last
                      24 hour interval."
                
              ::= { ncmhdmTotalEntry 22 }
               
	--  ncm HDM DS3/E3 24 Hour SnapShot
 
-- The HDM DS3/E3 24 Hour SnapShot table contains various statistics being
-- collected for the last 24 Hours.
 
 
         ncmDs3PerformanceSnapShotTable OBJECT-TYPE
             SYNTAX  SEQUENCE OF NcmDs3PerformanceSnapShotEntry
             ACCESS  not-accessible
             STATUS  mandatory
DESCRIPTION ""
                --DEFAULT test-function   ds3-test
--              DEFAULT set-function    null-set-proc
                --DEFAULT next-function   ds3-next
            ::= { ncm-ds3 9006 }
 
 
         ncmDs3PerformanceSnapShotEntry OBJECT-TYPE
             SYNTAX  NcmDs3PerformanceSnapShotEntry
             ACCESS  not-accessible
             STATUS  mandatory
             DESCRIPTION
             "An entry in the  Ds3 Performance Snap Shot Entry table."
             INDEX   { ncmDs3SnapShotNIDIndex, ncmDs3SnapShotIndex }
            ::= { ncmDs3PerformanceSnapShotTable 1 }
 
 
        NcmDs3PerformanceSnapShotEntry ::=
         SEQUENCE {
           ncmDs3SnapShotNIDIndex
                INTEGER,
           ncmDs3SnapShotIndex
                 INTEGER,
           ncmDs3SnapShotCRC4Status
                INTEGER,
           ncmDs3SnapShot
                INTEGER,
           ncmDs3TimeStampSec
                INTEGER,
           ncmDs3TimeStampMilliSec
                 INTEGER,
           ncmDs3SnapShotSecs
                 INTEGER,
           ncmDs3ResetPerfReg
                 INTEGER
                }
          
          
       ncmDs3SnapShotNIDIndex OBJECT-TYPE
             SYNTAX  INTEGER (1..'7fffffff'h)
             ACCESS  read-only
             STATUS  mandatory
             DESCRIPTION
                "The object specifies the node id index of the node."
            ::= { ncmDs3PerformanceSnapShotEntry 1 }
 
	
        ncmDs3SnapShotIndex OBJECT-TYPE
             SYNTAX  INTEGER (1..'7fffffff'h)
             ACCESS  read-only
             STATUS  mandatory
             DESCRIPTION
                "The index value which uniquely identifies  the
                DS1  interface  to which this entry is applica-
                ble.  The interface identified by a  particular
                value  of  this  index is the same interface as
                identified by the same value as a LineIndex
                object instance."
            ::= { ncmDs3PerformanceSnapShotEntry 2 }
 
 
          ncmDs3SnapShotCRC4Status OBJECT-TYPE
               SYNTAX INTEGER {
                       disabled (1)
               } 
              ACCESS  read-only
              STATUS  mandatory
              DESCRIPTION
                      "CRC4 Status."
              ::= { ncmDs3PerformanceSnapShotEntry 3 }
 
        ncmDs3SnapShot OBJECT-TYPE
            SYNTAX INTEGER {
                                no(1),
                                yes(2)
                       } 
           ACCESS read-write
           STATUS mandatory
           DESCRIPTION
           "The variable specifies the option to initiate snap shot
               command."
 
            ::= { ncmDs3PerformanceSnapShotEntry 4 }
 
        ncmDs3TimeStampSec OBJECT-TYPE
             SYNTAX  INTEGER (1..'7fffffff'h)
           ACCESS read-only
           STATUS mandatory
           DESCRIPTION
           "The variable specifies the Time Stamp in Seconds ."
 
           ::= { ncmDs3PerformanceSnapShotEntry 5 }
 
 
        ncmDs3TimeStampMilliSec OBJECT-TYPE
            SYNTAX  INTEGER (1..65535)
           ACCESS read-only
           STATUS mandatory
           DESCRIPTION
           "The variable specifies the Time Stamp in milli  Seconds ."
 
           ::= { ncmDs3PerformanceSnapShotEntry  6 }


	
         ncmDs3SnapShotSecs OBJECT-TYPE
            SYNTAX  INTEGER (1..65535)
           ACCESS read-only
            STATUS mandatory
           DESCRIPTION
           "The variable specifies number of seconds in the current interval."
            ::= { ncmDs3PerformanceSnapShotEntry 7 }
 
         ncmDs3ResetPerfReg OBJECT-TYPE
             SYNTAX  INTEGER {
                         no(1),
                         yes(2)
                     }
             ACCESS  read-write
             STATUS  mandatory
             DESCRIPTION
                "Reset Performance Monitoring registers."
            ::= { ncmDs3PerformanceSnapShotEntry 8 }
 
	-- the Quarter-Hour AlertThreshold table
 
          ncmhdmTCAQtrTable OBJECT-TYPE
              SYNTAX  SEQUENCE OF NcmhdmTCAQtrEntry
              ACCESS  not-accessible
              STATUS  mandatory
              DESCRIPTION
                      "The quarter hour Alert Threshold Table."
                --DEFAULT test-function   ds3-test
--              DEFAULT set-function    null-set-proc
                --DEFAULT next-function   ds3-next
              ::= { ncm-ds3 9007  }
 
          ncmhdmTCAQtrEntry OBJECT-TYPE
              SYNTAX  NcmhdmTCAQtrEntry
              ACCESS  not-accessible
              STATUS  mandatory
              DESCRIPTION
                      "An entry in the DS3/E3 table."
              INDEX   { ncmhdmTCAQtrNIDIndex, ncmhdmTCAQtrIndex }
              ::= { ncmhdmTCAQtrTable 1 }
 
          NcmhdmTCAQtrEntry ::=
              SEQUENCE {
                  ncmhdmTCAQtrNIDIndex
                      INTEGER,
                  ncmhdmTCAQtrIndex
                      INTEGER,
                  ncmhdmTCAQtrDs3FarEndCCV
                      INTEGER,
                  ncmhdmTCAQtrDs3FarEndCES
                      INTEGER,
                  ncmhdmTCAQtrDs3FarEndCSES
                      INTEGER,
                  ncmhdmTCAQtrDs3FarEndLUAS
                      INTEGER,
                  ncmhdmTCAQtrDs3LCV
                      INTEGER,
                  ncmhdmTCAQtrDs3LES
                      INTEGER,
                  ncmhdmTCAQtrDs3LSESs
                      INTEGER,
                  ncmhdmTCAQtrDs3PCV
                      INTEGER,
                  ncmhdmTCAQtrDs3PES
                      INTEGER,
                  ncmhdmTCAQtrDs3PSES
                      INTEGER,
                  ncmhdmTCAQtrDs3CCV
                      INTEGER,
                  ncmhdmTCAQtrDs3CES
                      INTEGER,
                  ncmhdmTCAQtrDs3CSES
                      INTEGER,
                  ncmhdmTCAQtrDs3SEFS
                      INTEGER,
                  ncmhdmTCAQtrDs3AISS
                      INTEGER,
                  ncmhdmTCAQtrDs3LUASs
                      INTEGER,
                  ncmhdmTCAQtrDs3LOSSs
                      INTEGER,
                  ncmhdmTCAQtrDs3LOFSs
                      INTEGER
              }

	ncmhdmTCAQtrNIDIndex OBJECT-TYPE
          SYNTAX  INTEGER (1..'7fffffff'h)
          ACCESS  read-only
          STATUS  mandatory
          DESCRIPTION
                "This variable indicates the node id value of the node."
            ::= { ncmhdmTCAQtrEntry 1 }
               
          ncmhdmTCAQtrIndex OBJECT-TYPE
              SYNTAX  INTEGER (1..65535)
              ACCESS  read-only
              STATUS  mandatory
              DESCRIPTION
                      "The index value which uniquely identifies the
                      alert crossing threshold interface to which
                      this entry is applicable.  The interface
                      identified by a particular value of this
                      index is the same interface as identified
                      by the same value an plcpLineIndex object
                      instance."
              ::= { ncmhdmTCAQtrEntry 2 }
               
          ncmhdmTCAQtrDs3FarEndCCV OBJECT-TYPE
              SYNTAX  INTEGER (0..4294967295)
              ACCESS  read-write
              STATUS  mandatory
              DESCRIPTION
                      "The performance alert threshold for DS3
                        layer Far End C-bit Code Violation in 1/4 hour
                        boundary."
              ::= { ncmhdmTCAQtrEntry 3 }
               
          ncmhdmTCAQtrDs3FarEndCES OBJECT-TYPE
              SYNTAX  INTEGER (0..4294967295)
              ACCESS  read-write
              STATUS  mandatory
              DESCRIPTION
                      "The performance alert threshold for DS3
                        Far End C-bit Errored Seconds,
                        in 1/4 hour boundary."
              ::= { ncmhdmTCAQtrEntry 4 }
               
          ncmhdmTCAQtrDs3FarEndCSES OBJECT-TYPE
              SYNTAX  INTEGER (0..4294967295)
              ACCESS  read-write
              STATUS  mandatory
              DESCRIPTION
                      "The performance alert threshold for DS3
                        Far End C-bit Severely Errored Seconds,
                        in 1/4 hour boundary."
 
              ::= { ncmhdmTCAQtrEntry 5 }
 
          ncmhdmTCAQtrDs3FarEndLUAS OBJECT-TYPE
              SYNTAX  INTEGER (0..4294967295)
              ACCESS  read-write
              STATUS  mandatory
              DESCRIPTION
                      "The performance alert threshold for DS3 layer
                      Far End Line Unavailable Seconds in 1/4 hour
                        boundary."
              ::= { ncmhdmTCAQtrEntry 6 }


	ncmhdmTCAQtrDs3LCV OBJECT-TYPE
              SYNTAX  INTEGER (0..4294967295)
              ACCESS  read-write
              STATUS  mandatory
              DESCRIPTION
                      "The performance alert threshold for DS3
                        layer Line code Violation in 1/4 hour
                        boundary."
              ::= { ncmhdmTCAQtrEntry 7 }
               
          ncmhdmTCAQtrDs3LES OBJECT-TYPE
              SYNTAX  INTEGER (0..4294967295)
              ACCESS  read-write
              STATUS  mandatory
              DESCRIPTION
                        "The performance alert threshold for DS3
                        layer Line Errored Second in 1/4 hour
                        boundary."
 
              ::= { ncmhdmTCAQtrEntry 8 }
 
          ncmhdmTCAQtrDs3LSESs OBJECT-TYPE
              SYNTAX  INTEGER (0..4294967295)
              ACCESS  read-write
              STATUS  mandatory
              DESCRIPTION
                        "The performance alert threshold for DS3
                        layer Line Severely Errored Second
                        in 1/4 hour boundary."
              ::= { ncmhdmTCAQtrEntry 9 }
               
          ncmhdmTCAQtrDs3PCV OBJECT-TYPE
              SYNTAX  INTEGER (0..4294967295)
              ACCESS  read-write
              STATUS  mandatory
              DESCRIPTION
                        "The performance alert threshold for DS3
                        layer Parity Code Violation in 1/4 hour boundary."
              ::= { ncmhdmTCAQtrEntry 10 }
               
          ncmhdmTCAQtrDs3PES OBJECT-TYPE
              SYNTAX  INTEGER (0..4294967295)
              ACCESS  read-write
              STATUS  mandatory
              DESCRIPTION
                        "The performance alert threshold for DS3
                        layer Parity Errored Second in 1/4 hour boundary."
              ::= { ncmhdmTCAQtrEntry 11 }
               
          ncmhdmTCAQtrDs3PSES OBJECT-TYPE
              SYNTAX  INTEGER (0..4294967295)
              ACCESS  read-write
              STATUS  mandatory
              DESCRIPTION
                        "The performance alert threshold for DS3
                        layer Parity Severely Errored Second in 1/4 hour
                        boundary."
              ::= { ncmhdmTCAQtrEntry 12 }


	 ncmhdmTCAQtrDs3CCV OBJECT-TYPE
              SYNTAX  INTEGER (0..4294967295)
              ACCESS  read-write
              STATUS  mandatory
              DESCRIPTION
                        "The performance alert threshold for DS3
                        layer C-bit Code Violation in 1/4 hour boundary."
              ::= { ncmhdmTCAQtrEntry 13 }
               
          ncmhdmTCAQtrDs3CES OBJECT-TYPE
              SYNTAX  INTEGER (0..4294967295)
              ACCESS  read-write
              STATUS  mandatory
              DESCRIPTION
                        "The performance alert threshold for DS3
                        Far End C-bit Errored Seconds,
                        layer Errored Second in 1/4 hour boundary."
              ::= { ncmhdmTCAQtrEntry 14 }
               
          ncmhdmTCAQtrDs3CSES OBJECT-TYPE
              SYNTAX  INTEGER (0..4294967295)
              ACCESS  read-write
              STATUS  mandatory
              DESCRIPTION
                        "The performance alert threshold for DS3
                        layer C-bit Severely Errored Second in 1/4 hour
                        boundary."
              ::= { ncmhdmTCAQtrEntry 15 }
               
          ncmhdmTCAQtrDs3SEFS OBJECT-TYPE
              SYNTAX  INTEGER (0..4294967295)
              ACCESS  read-write
              STATUS  mandatory
              DESCRIPTION
                        "The performance alert threshold for DS3
                        layer Severely Errored Framing Seconds
                        in 1/4 hour boundary."
              ::= { ncmhdmTCAQtrEntry 16 }
               
          ncmhdmTCAQtrDs3AISS OBJECT-TYPE
              SYNTAX  INTEGER (0..4294967295)
              ACCESS  read-write
              STATUS  mandatory
              DESCRIPTION
                        "The performance alert threshold for DS3
                        layer Alarm Indication Signal Second
                        in 1/4 hour boundary."
              ::= { ncmhdmTCAQtrEntry 17 }
               
          ncmhdmTCAQtrDs3LUASs OBJECT-TYPE
              SYNTAX  INTEGER (0..4294967295)
              ACCESS  read-write
              STATUS  mandatory
              DESCRIPTION
                        "The performance alert threshold for DS3
                        layer Unavailable Second in 1/4 hour
                        boundary."
              ::= { ncmhdmTCAQtrEntry 18 }


	ncmhdmTCAQtrDs3LOSSs OBJECT-TYPE
              SYNTAX  INTEGER (0..4294967295)
              ACCESS  read-write
              STATUS  mandatory
              DESCRIPTION
                        "The performance alert threshold for DS3
                        Loss of Signal (LOS) Seconds in 1/4 hour
                        boundary."
              ::= { ncmhdmTCAQtrEntry 19 }
               
          ncmhdmTCAQtrDs3LOFSs OBJECT-TYPE
              SYNTAX  INTEGER (0..4294967295)
              ACCESS  read-write
              STATUS  mandatory
              DESCRIPTION
                        "The performance alert threshold for DS3
                        Loss of Frame (LOF) Seconds in 1/4 hour
                        boundary."
              ::= { ncmhdmTCAQtrEntry 20 }
               
	-- the 24-Hour AlertThreshold table
 
          ncmhdmTCADayTable OBJECT-TYPE
              SYNTAX  SEQUENCE OF NcmhdmTCADayEntry
              ACCESS  not-accessible
              STATUS  mandatory
              DESCRIPTION
                      "The 24 hour Alert Threshold Table."
                --DEFAULT test-function   ds3-test
--              DEFAULT set-function    null-set-proc
                --DEFAULT next-function   ds3-next
              ::= { ncm-ds3 9008 }
 
          ncmhdmTCADayEntry OBJECT-TYPE
              SYNTAX  NcmhdmTCADayEntry
              ACCESS  not-accessible
              STATUS  mandatory
              DESCRIPTION
                      "An entry in the 24 hour Alert Threshold Table."
              INDEX   { ncmhdmTCADayNIDIndex,  ncmhdmTCADayIndex }
              ::= { ncmhdmTCADayTable 1 }
 
          NcmhdmTCADayEntry ::=
              SEQUENCE {
                  ncmhdmTCADayNIDIndex
                      INTEGER,
                  ncmhdmTCADayIndex
                      INTEGER,
                  ncmhdmTCADayDs3FarEndCCV
                      INTEGER,
                  ncmhdmTCADayDs3FarEndCES
                      INTEGER,
                  ncmhdmTCADayDs3FarEndCSES
                      INTEGER,
                  ncmhdmTCADayDs3FarEndLUAS
                      INTEGER,
                  ncmhdmTCADayDs3LCV
                      INTEGER,
                  ncmhdmTCADayDs3LES
                      INTEGER,
                  ncmhdmTCADayDs3LSESs
                      INTEGER,
                  ncmhdmTCADayDs3PCV
                      INTEGER,
                  ncmhdmTCADayDs3PES
                      INTEGER,
                  ncmhdmTCADayDs3PSES
                      INTEGER,
                  ncmhdmTCADayDs3CCV
                      INTEGER,
                  ncmhdmTCADayDs3CES
                      INTEGER,
                  ncmhdmTCADayDs3CSES
                      INTEGER,
                  ncmhdmTCADayDs3SEFS
                      INTEGER,
                  ncmhdmTCADayDs3AISS
                      INTEGER,
                  ncmhdmTCADayDs3LUASs
                      INTEGER,
                  ncmhdmTCADayDs3LOSSs
                      INTEGER,
                  ncmhdmTCADayDs3LOFSs
                      INTEGER
              }


	ncmhdmTCADayNIDIndex OBJECT-TYPE
          SYNTAX  INTEGER (1..'7fffffff'h)
          ACCESS  read-only
          STATUS  mandatory
          DESCRIPTION
                "This variable indicates the node id value of the node."
            ::= { ncmhdmTCADayEntry 1 }
               
          ncmhdmTCADayIndex OBJECT-TYPE
              SYNTAX  INTEGER (1..65535)
              ACCESS  read-only
              STATUS  mandatory
              DESCRIPTION
                      "The index value which uniquely identifies the
                      alert crossing threshold interface to which
                      this entry is applicable.  The interface
                      identified by a particular value of this
                      index is the same interface as identified
                      by the same value an plcpLineIndex object
                      instance."
              ::= { ncmhdmTCADayEntry 2 }
               
 
          ncmhdmTCADayDs3FarEndCCV OBJECT-TYPE
              SYNTAX  INTEGER (0..4294967295)
              ACCESS  read-write
              STATUS  mandatory
              DESCRIPTION
                      "The performance alert threshold for DS3
                        layer Far End C-bit Code Violation in 24 hour
                        boundary."
              ::= { ncmhdmTCADayEntry 3 }
               
          ncmhdmTCADayDs3FarEndCES OBJECT-TYPE
              SYNTAX  INTEGER (0..4294967295)
              ACCESS  read-write
              STATUS  mandatory
              DESCRIPTION
                      "The performance alert threshold for DS3
                        Far End C-bit Errored Seconds,
                        in 24 hour boundary."
              ::= { ncmhdmTCADayEntry 4 }
               
          ncmhdmTCADayDs3FarEndCSES OBJECT-TYPE
              SYNTAX  INTEGER (0..4294967295)
              ACCESS  read-write
              STATUS  mandatory
              DESCRIPTION
                      "The performance alert threshold for DS3
                        Far End C-bit Severely Errored Seconds,
                        in 24 hour boundary."
 
              ::= { ncmhdmTCADayEntry 5 }
 
          ncmhdmTCADayDs3FarEndLUAS OBJECT-TYPE
              SYNTAX  INTEGER (0..4294967295)
              ACCESS  read-write
              STATUS  mandatory
              DESCRIPTION
                      "The performance alert threshold for DS3 layer
                      Far End Line Unavailable Seconds in 24 hour
                        boundary."
              ::= { ncmhdmTCADayEntry 6 }


	 ncmhdmTCADayDs3LCV OBJECT-TYPE
              SYNTAX  INTEGER (0..4294967295)
              ACCESS  read-write
              STATUS  mandatory
              DESCRIPTION
                      "The performance alert threshold for DS3
                        layer Line code Violation in 24 hour
                        boundary."
              ::= { ncmhdmTCADayEntry 7 }
               
          ncmhdmTCADayDs3LES OBJECT-TYPE
              SYNTAX  INTEGER (0..4294967295)
              ACCESS  read-write
              STATUS  mandatory
              DESCRIPTION
                        "The performance alert threshold for DS3
                        layer Line Errored Second in 24 hour
                        boundary."
 
              ::= { ncmhdmTCADayEntry 8 }
 
          ncmhdmTCADayDs3LSESs OBJECT-TYPE
              SYNTAX  INTEGER (0..4294967295)
              ACCESS  read-write
              STATUS  mandatory
              DESCRIPTION
                        "The performance alert threshold for DS3
                        layer Line Severely Errored Second
                        in 24 hour boundary."
              ::= { ncmhdmTCADayEntry 9 }
               
          ncmhdmTCADayDs3PCV OBJECT-TYPE
              SYNTAX  INTEGER (0..4294967295)
              ACCESS  read-write
              STATUS  mandatory
              DESCRIPTION
                        "The performance alert threshold for DS3
                        layer Parity Code Violation in 24 hour boundary."
              ::= { ncmhdmTCADayEntry 10 }
               
          ncmhdmTCADayDs3PES OBJECT-TYPE
              SYNTAX  INTEGER (0..4294967295)
              ACCESS  read-write
              STATUS  mandatory
              DESCRIPTION
                        "The performance alert threshold for DS3
                        layer Parity Errored Second in 24 hour boundary."
              ::= { ncmhdmTCADayEntry 11 }
               
          ncmhdmTCADayDs3PSES OBJECT-TYPE
              SYNTAX  INTEGER (0..4294967295)
              ACCESS  read-write
              STATUS  mandatory
              DESCRIPTION
                        "The performance alert threshold for DS3
                        layer Parity Severely Errored Second in 24 hour
                        boundary."
              ::= { ncmhdmTCADayEntry 12 }


	 ncmhdmTCADayDs3CCV OBJECT-TYPE
              SYNTAX  INTEGER (0..4294967295)
              ACCESS  read-write
              STATUS  mandatory
              DESCRIPTION
                        "The performance alert threshold for DS3
                        layer C-bit Code Violation in 24 hour boundary."
              ::= { ncmhdmTCADayEntry 13 }
               
          ncmhdmTCADayDs3CES OBJECT-TYPE
              SYNTAX  INTEGER (0..4294967295)
              ACCESS  read-write
              STATUS  mandatory
              DESCRIPTION
                        "The performance alert threshold for DS3
                        C-bit Errored Seconds, in 24 hour boundary."
              ::= { ncmhdmTCADayEntry 14 }
               
          ncmhdmTCADayDs3CSES OBJECT-TYPE
              SYNTAX  INTEGER (0..4294967295)
              ACCESS  read-write
              STATUS  mandatory
              DESCRIPTION
                        "The performance alert threshold for DS3
                        C-bit Severely Errored Seconds, in 24 hour
                        boundary."
              ::= { ncmhdmTCADayEntry 15 }
               
          ncmhdmTCADayDs3SEFS OBJECT-TYPE
              SYNTAX  INTEGER (0..4294967295)
              ACCESS  read-write
              STATUS  mandatory
              DESCRIPTION
                        "The performance alert threshold for DS3
                        layer Severely Errored Framing Seconds
                        in 24 hour boundary."
              ::= { ncmhdmTCADayEntry 16 }
               
          ncmhdmTCADayDs3AISS OBJECT-TYPE
              SYNTAX  INTEGER (0..4294967295)
              ACCESS  read-write
              STATUS  mandatory
              DESCRIPTION
                        "The performance alert threshold for DS3
                        layer Alarm Indication Signal Second
                        in 24 hour boundary."
              ::= { ncmhdmTCADayEntry 17 }
               
          ncmhdmTCADayDs3LUASs OBJECT-TYPE
              SYNTAX  INTEGER (0..4294967295)
              ACCESS  read-write
              STATUS  mandatory
              DESCRIPTION
                        "The performance alert threshold for DS3
                        layer Unavailable Second in 24 hour
                        boundary."
              ::= { ncmhdmTCADayEntry 18 }


	ncmhdmTCADayDs3LOSSs OBJECT-TYPE
              SYNTAX  INTEGER (0..4294967295)
              ACCESS  read-write
              STATUS  mandatory
              DESCRIPTION
                        "The performance alert threshold for DS3
                        Loss of Signal (LOS) Seconds in 24 hour
                        boundary."
              ::= { ncmhdmTCADayEntry 19 }
               
          ncmhdmTCADayDs3LOFSs OBJECT-TYPE
              SYNTAX  INTEGER (0..4294967295)
              ACCESS  read-write
              STATUS  mandatory
              DESCRIPTION
                        "The performance alert threshold for DS3
                        Loss of Frame (LOF) Seconds in 24 hour
                        boundary."
              ::= { ncmhdmTCADayEntry 20 }
               

	 -- Ds3 Transmit Alarm table
 
          ncmhdmTxAlarmTable OBJECT-TYPE
              SYNTAX  SEQUENCE OF NcmhdmTxAlarmEntry
              ACCESS  not-accessible
              STATUS  mandatory
              DESCRIPTION
                "DS3 Transmit alarm Table."
                --DEFAULT test-function   ds3-test
--              DEFAULT set-function    null-set-proc
                --DEFAULT next-function   ds3-next
              ::= { ncm-ds3 9009 }
 
          ncmhdmTxAlarmEntry OBJECT-TYPE
              SYNTAX  NcmhdmTxAlarmEntry
              ACCESS  not-accessible
              STATUS  mandatory
              DESCRIPTION
                      "An entry in the DS3/E3 Transmit Alarm table."
              INDEX   { ncmhdmTxAlarmNIDIndex, ncmhdmTxAlarmIndex }
              ::= { ncmhdmTxAlarmTable 1 }
 
          NcmhdmTxAlarmEntry ::=
              SEQUENCE {
                  ncmhdmTxAlarmNIDIndex
                      INTEGER,
                  ncmhdmTxAlarmIndex
                      INTEGER,
                  ncmhdmTxYellowAlarm
                      INTEGER,
                  ncmhdmTxAIS
                      INTEGER,
                  ncmhdmTxIdleSignal
                      INTEGER,
                  ncmhdmTxFEBE
                      INTEGER,
                  ncmhdmTxFEACAlarm
                      INTEGER
              }
 
        ncmhdmTxAlarmNIDIndex OBJECT-TYPE
          SYNTAX  INTEGER (1..'7fffffff'h)
          ACCESS  read-only
          STATUS  mandatory
          DESCRIPTION
                "This variable indicates the node id value of the node."
            ::= { ncmhdmTxAlarmEntry 1 }


	 ncmhdmTxAlarmIndex OBJECT-TYPE
              SYNTAX  INTEGER (1..65535)
              ACCESS  read-only
              STATUS  mandatory
              DESCRIPTION
                      "The index value which uniquely identifies the
                      Transmit Alarm interface to which
                      this entry is applicable.  The interface
                      identified by a particular value of this
                      index is the same interface as identified
                      by the same value an Dsx3LineIndex object
                      instance."
              ::= { ncmhdmTxAlarmEntry 2 }
               
          ncmhdmTxYellowAlarm OBJECT-TYPE
              SYNTAX  INTEGER{
                        eNABLE(1),
                        dISABLE(2)
                      }
              ACCESS  read-write
              STATUS  mandatory
              DESCRIPTION
                      "Transmit the near-end yellow alarm."
              ::= { ncmhdmTxAlarmEntry 3 }
 
          ncmhdmTxAIS   OBJECT-TYPE
              SYNTAX  INTEGER{
                        eNABLE(1),
                        dISABLE(2)
                      }
              ACCESS  read-write
              STATUS  mandatory
              DESCRIPTION
                      "Transmit the near-end AIS alarm."
              ::= { ncmhdmTxAlarmEntry 4 }
 
          ncmhdmTxIdleSignal OBJECT-TYPE
              SYNTAX  INTEGER{
                        eNABLE(1),
                        dISABLE(2)
                      }
              ACCESS  read-write
              STATUS  mandatory
              DESCRIPTION
                      "Transmit the near-end Idle alarm."
              ::= { ncmhdmTxAlarmEntry 5 }
 
          ncmhdmTxFEBE OBJECT-TYPE
              SYNTAX  INTEGER{
                        eNABLE(1),
                        dISABLE(2)
                      }
              ACCESS  read-write
              STATUS  mandatory
              DESCRIPTION
                      "Near end unit transmits the FEBE alarm."
              ::= { ncmhdmTxAlarmEntry 6 }


	 ncmhdmTxFEACAlarm OBJECT-TYPE
              SYNTAX  INTEGER{
                        nO-FEAC-Alarm-enabled (1),
                        eqptFailureSA-Alarm (2),
                        lOSHBER-Alarm (3),
                        oOF-Alarm (4),
                        aISReceived-Alarm (5),
                        idleReceived-Alarm (6),
                        eqptFailureNSA-Alarm (7),
                        commonEqptFailureNSA-Alarm (8)
                      }
              ACCESS  read-write
              STATUS  mandatory
              DESCRIPTION
                      "This object describes which, if any, FEAC
                        Alarm is enabled. "
              ::= { ncmhdmTxAlarmEntry 7 }
               


	--- Hdm Stats
---
     ncmhdmDs3StatTable OBJECT-TYPE
          SYNTAX SEQUENCE OF NcmhdmDs3StatEntry
          ACCESS not-accessible
          STATUS mandatory
          DESCRIPTION
               "The HDM Ds3 Stats."
                --DEFAULT test-function   ds3-test
--              DEFAULT set-function    null-set-proc
                --DEFAULT next-function   ds3-next
          ::= { ncm-ds3 9010 }
 
     ncmhdmDs3StatEntry OBJECT-TYPE
          SYNTAX NcmhdmDs3StatEntry
          ACCESS not-accessible
          STATUS mandatory
          DESCRIPTION
               "An entry in the ds3 stats table."
          INDEX   { ncmhdmDs3StatNIDIndex, ncmhdmDs3StatIndex }
          ::= { ncmhdmDs3StatTable 1 }
 
     NcmhdmDs3StatEntry ::= SEQUENCE {
             ncmhdmDs3StatNIDIndex
                 INTEGER,
             ncmhdmDs3StatIndex
                 INTEGER,
             ncmhdmDs3StatAIS
                 INTEGER,
             ncmhdmDs3StatIdle
                 INTEGER,
             ncmhdmDs3StatYellowAlm
                 INTEGER,
             ncmhdmDs3StatFrameLoss
                 INTEGER,
             ncmhdmDs3StatSigLoss
                 INTEGER,
             ncmhdmDs3StatPLCPYellow
                 INTEGER,
             ncmhdmDs3StatPLCPFrmLoss
                 INTEGER,
             ncmhdmDs3StatPLCPOOF
                 INTEGER,
             ncmhdmDs3LpbkLocal
                 INTEGER,
             ncmhdmDs3LpbkPayload
                 INTEGER,
             ncmhdmDs3LpbkFEAC
                 INTEGER,
             ncmhdmDs3LpbkFarEnd
                 INTEGER
     }


	ncmhdmDs3StatNIDIndex OBJECT-TYPE
          SYNTAX  INTEGER (1..'7fffffff'h)
          ACCESS  read-only
          STATUS  mandatory
          DESCRIPTION
                "This variable indicates the node id value of the node."
            ::= { ncmhdmDs3StatEntry 1 }
               
     ncmhdmDs3StatIndex OBJECT-TYPE
          SYNTAX  INTEGER (1..65535)
          ACCESS  read-only
          STATUS  mandatory
          DESCRIPTION
               "The index value which uniquely identifies  the
                DS1  interface  to which this entry is applica-
                ble.  The interface identified by a  particular
                value  of  this  index is the same interface as
                identified by the same value as a dsx1LineIndex
                object instance."
            ::= { ncmhdmDs3StatEntry 2 }
 
     ncmhdmDs3StatAIS OBJECT-TYPE
          SYNTAX INTEGER {
                        oFF (1),
                        oN (2)
               }
          ACCESS read-only
          STATUS mandatory
          DESCRIPTION
               "Port Status AIS off/on."
          ::= { ncmhdmDs3StatEntry 3 }
 
     ncmhdmDs3StatIdle OBJECT-TYPE
          SYNTAX INTEGER {
                        oFF (1),
                        oN (2)
               }
          ACCESS read-only
          STATUS mandatory
          DESCRIPTION
               "port Status Idle off/on."
          ::= { ncmhdmDs3StatEntry 4 }
 
     ncmhdmDs3StatYellowAlm OBJECT-TYPE
          SYNTAX INTEGER {
                        oFF (1),
                        oN (2)
               }
          ACCESS read-only
          STATUS mandatory
          DESCRIPTION
               "Port Status Yellow Alarm off/on."
          ::= { ncmhdmDs3StatEntry 5 }
 
     ncmhdmDs3StatFrameLoss OBJECT-TYPE
          SYNTAX INTEGER {
                        oFF (1),
                        oN (2)
               }
          ACCESS read-only
          STATUS mandatory
          DESCRIPTION
               "off/on."
          ::= { ncmhdmDs3StatEntry 6 }
 
	 ncmhdmDs3StatSigLoss OBJECT-TYPE
          SYNTAX INTEGER {
                        oFF (1),
                        oN (2)
               }
          ACCESS read-only
          STATUS mandatory
          DESCRIPTION
               "Port Status Signal Loss off/on."
          ::= { ncmhdmDs3StatEntry 7 }
 
     ncmhdmDs3StatPLCPYellow OBJECT-TYPE
          SYNTAX INTEGER {
                        oFF (1),
                        oN (2)
               }
          ACCESS read-only
          STATUS mandatory
          DESCRIPTION
               "Port Status PLCP Yellow Alarm off/on."
          ::= { ncmhdmDs3StatEntry 8 }
 
     ncmhdmDs3StatPLCPFrmLoss OBJECT-TYPE
          SYNTAX INTEGER {
                        oFF (1),
                        oN (2)
               }
          ACCESS read-only
          STATUS mandatory
          DESCRIPTION
               "Port Status PLCP Frame Loss off/on."
          ::= { ncmhdmDs3StatEntry 9 }
 
     ncmhdmDs3StatPLCPOOF OBJECT-TYPE
          SYNTAX INTEGER {
                        oFF (1),
                        oN (2)
               }
          ACCESS read-only
          STATUS mandatory
          DESCRIPTION
               "Port Status PLCP Out of Frame off/on."
          ::= { ncmhdmDs3StatEntry 10 }
 
     ncmhdmDs3LpbkLocal OBJECT-TYPE
          SYNTAX INTEGER {
                        disabled (1),
                        enabled (2)
               }
          ACCESS read-only
          STATUS mandatory
          DESCRIPTION
               "Local Loopback enabled/disabled."
          ::= { ncmhdmDs3StatEntry 11 }
 
     ncmhdmDs3LpbkPayload OBJECT-TYPE
          SYNTAX INTEGER {
                        disabled (1),
                        enabled (2)
               }
          ACCESS read-only
          STATUS mandatory
          DESCRIPTION
               "Payload Loopback enabled/disabled."
          ::= { ncmhdmDs3StatEntry 12 }


	 ncmhdmDs3LpbkFEAC OBJECT-TYPE
          SYNTAX INTEGER {
                        disabled (1),
                        enabled (2)
               }
          ACCESS read-only
          STATUS mandatory
          DESCRIPTION
               "FEAC Loopback enabled/disabled."
          ::= { ncmhdmDs3StatEntry 13 }
 
 
     ncmhdmDs3LpbkFarEnd OBJECT-TYPE
          SYNTAX INTEGER {
                        disabled (1),
                        enabled (2)
               }
          ACCESS read-only
          STATUS mandatory
          DESCRIPTION
               "Far end Loopback enabled/disabled."
          ::= { ncmhdmDs3StatEntry 14 }


	-- ncm HDM DS3/E3 Loopback Activate/Deactivate
 
          ncmhdmds3LPBKTable OBJECT-TYPE
              SYNTAX  SEQUENCE OF Ncmhdmds3LPBKEntry
              ACCESS  not-accessible
              STATUS  mandatory
              DESCRIPTION
                      "The DS3/E3 Current table."
                --DEFAULT test-function   ds3-test
--              DEFAULT set-function    null-set-proc
                --DEFAULT next-function   ds3-next
 
              ::= { ncm-ds3 9011 }
 
          ncmhdmds3LPBKEntry OBJECT-TYPE
              SYNTAX  Ncmhdmds3LPBKEntry
              ACCESS  not-accessible
              STATUS  mandatory
              DESCRIPTION
                      "An entry in the DS3 Loopback table."
              INDEX   { ncmhdmLPBKNIDIndex, ncmhdmds3LPBKIndex }
              ::= { ncmhdmds3LPBKTable 1 }
 
          Ncmhdmds3LPBKEntry ::=
              SEQUENCE {
                  ncmhdmLPBKNIDIndex
                      INTEGER,
                  ncmhdmds3LPBKIndex
                      INTEGER,
                  ncmhdmDs3LPBKActivation
                      INTEGER
              }
 
        ncmhdmLPBKNIDIndex OBJECT-TYPE
          SYNTAX  INTEGER (1..'7fffffff'h)
          ACCESS  read-only
          STATUS  mandatory
          DESCRIPTION
                "This variable indicates the node id value of the node."
            ::= { ncmhdmds3LPBKEntry 1 }
               
          ncmhdmds3LPBKIndex OBJECT-TYPE
              SYNTAX  INTEGER (1..65535)
              ACCESS  read-only
              STATUS  mandatory
              DESCRIPTION
                      "The index value which uniquely identifies the
                      DS3/E3 interface to which this entry is
                      applicable.  The interface identified by a
                      particular value of this index is the same
                      interface as identified by the same value an
                      ncmhdmLineIndex object instance."
              ::= { ncmhdmds3LPBKEntry 2 }


	ncmhdmDs3LPBKActivation OBJECT-TYPE
          SYNTAX INTEGER {
                        no-Loopback (1),
                        dS3-Internal-Activate (2),
                        dS3-Internal-De-activate (3),
                        dS3-Payload-Activate (4),
                        dS3-Payload-De-activate (5),
                        hSSI-A-Activate (6),
                        hSSI-A-De-activate (7),
                        hSSI-B-Activate (8),
                        hSSI-B-De-activate (9),
                        fEAC-Activate (10),
                        fEAC-De-activate (11),
                        far-End-Lpbk-Activate (12),
                        far-End-Lpbk-De-activate (13)
               }
          ACCESS read-write
          STATUS mandatory
          DESCRIPTION
               "Ds3 Loopback enabled/disabled, and Ds3 Loopback Type."
          ::= { ncmhdmds3LPBKEntry 3 }
 
     END
