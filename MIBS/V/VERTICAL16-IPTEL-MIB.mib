VERTICAL16-IPTEL-MIB DEFINITIONS ::= BEGIN

IMPORTS
			enterprises FROM RFC1155-SMI
        OBJECT-TYPE
                     FROM RFC-1212
			DisplayString FROM SNMPv2-TC
			TRAP-TYPE FROM RFC-1215;
             
vertical OBJECT IDENTIFIER ::= { enterprises 2338 }  

	--  Author  : Rajiv Anand
	--  Version : 1.0
	--  Date : May 20, 1999

	iptel	OBJECT IDENTIFIER ::= {vertical 16}

	iptelTrunkSize OBJECT-TYPE
		SYNTAX INTEGER
		ACCESS read-only
		STATUS mandatory
		DESCRIPTION "Number of Trunk"
		::= { iptel 1 }

	-- The Trunk Summary Table --

	ipTelTrunkSummary OBJECT-TYPE
		SYNTAX SEQUENCE OF TrunkInfoStruct
		ACCESS  not-accessible
		STATUS  mandatory
		DESCRIPTION	"Overview table of IPTel trunks"
		::= { iptel 2 }

	ipTelTrunkInfo OBJECT-TYPE
		SYNTAX TrunkInfoStruct
		ACCESS not-accessible
		STATUS mandatory
		DESCRIPTION "Entry in the IpTelTrunkSummary Table"
		--INDEX { TrunkIndex }
		::= { ipTelTrunkSummary 1 }

	TrunkInfoStruct ::= SEQUENCE {
		trunkIndex INTEGER,
		trunkState INTEGER,
		calledParty DisplayString,
		callingParty DisplayString,
		remoteGateway DisplayString,
		descriptionIndex INTEGER,
		localAlarmThreshold INTEGER,
		remoteAlarmThreshold INTEGER
	}

	trunkIndex OBJECT-TYPE
		SYNTAX INTEGER
		ACCESS read-only
		STATUS mandatory
		DESCRIPTION "Trunk Number in the trunk table"
		::= {ipTelTrunkInfo 1}

	trunkState OBJECT-TYPE
		SYNTAX INTEGER { not-configured(0), 
			out-of-service(1), 
			initializing(2), 
			idle(3),
			outgoing(4),
			incoming(5),
			connected(6),
			disconnecting(7) }
		ACCESS read-only
		STATUS mandatory
		DESCRIPTION "Trunk State"
		::= {ipTelTrunkInfo 2}

	calledParty OBJECT-TYPE
		SYNTAX DisplayString
		ACCESS read-only
		STATUS mandatory
		DESCRIPTION "Number of the Called Party"
		::= {ipTelTrunkInfo 3}
		
	callingParty OBJECT-TYPE
		SYNTAX DisplayString
		ACCESS read-only
		STATUS mandatory
		DESCRIPTION "Number of the Calling Party"
		::= {ipTelTrunkInfo 4}

	remoteGateway OBJECT-TYPE
		SYNTAX DisplayString
		ACCESS read-only
		STATUS mandatory
		DESCRIPTION "Remote Gateway Number"
		::= {ipTelTrunkInfo 5}

	localAlarmThreshold OBJECT-TYPE
		SYNTAX INTEGER
		ACCESS read-only
		STATUS mandatory
		DESCRIPTION "Current levels of thresholds reached.
		It is a bit	field indicating following thresholds:
		== BIT ===  === DESCRIPTION ===
			0			Jitter
			1			NetworkLost
			2			Network To Host Errors
			3			Host To Network Errors
			4			DSP To Host Errors
			5			Host to DSP Errors
		================================"
		::= {ipTelTrunkInfo 6}

	remoteAlarmThreshold OBJECT-TYPE
		SYNTAX INTEGER
		ACCESS read-only
		STATUS mandatory
		DESCRIPTION "Current levels of thresholds reached.
		For a description of bit fields refer to LocalThreshold"
		::= {ipTelTrunkInfo 7}


-- Trap definitions

ipTelReconfigComplete TRAP-TYPE
	ENTERPRISE  vertical
	VARIABLES {iptelTrunkSize}
	DESCRIPTION
		" This notification is sent when the reconfiguration command completes."
	::= 64

ipTelTrunkFailure TRAP-TYPE
	ENTERPRISE vertical
	VARIABLES {trunkIndex}
	DESCRIPTION "Issued when the specified Trunk has failed."
	::= 65

ipTelTrunkAlarmInfo TRAP-TYPE
	ENTERPRISE vertical
	VARIABLES {trunkIndex, localAlarmThreshold, remoteAlarmThreshold}
	DESCRIPTION "Informational Alarm associated with some parameter threshold
	being reached."
	::= 66

END
