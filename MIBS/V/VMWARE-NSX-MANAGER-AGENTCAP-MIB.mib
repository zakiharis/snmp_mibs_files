-- **********************************************************
-- Copyright 2016 VMware, Inc.  All rights reserved.
-- **********************************************************

VMWARE-NSX-MANAGER-AGENTCAP-MIB DEFINITIONS ::= BEGIN

IMPORTS
    MODULE-IDENTITY
       FROM SNMPv2-SMI
    vmwareAgentCapabilities
       FROM VMWARE-ROOT-MIB
    AGENT-CAPABILITIES
       FROM  SNMPv2-CONF;
vmwNSXAgentCapabilityMIB MODULE-IDENTITY
   LAST-UPDATED "201610240000Z"
   ORGANIZATION "VMware, Inc"
   CONTACT-INFO
      "VMware, Inc
      3401 Hillview Ave
      Palo Alto, CA 94304
      Tel: 1-877-486-9273 or 650-427-5000
      Fax: 650-427-5001
      Web: http://communities.vmware.com/community/developer/forums/managementapi
      "
   DESCRIPTION
     "Update release version for 2016x to was 6.2.x fronm 6.5."
   REVISION     "201610240000Z"
   DESCRIPTION
     "This module defines agent capabilities for deployed VMware NSX Manager agents by release."
   REVISION     "201606020000Z"
   DESCRIPTION
         "Capabilities for NSX Manager releases."
        ::= { vmwareAgentCapabilities 25 }

vmwNSXMCapability OBJECT IDENTIFIER ::= { vmwNSXAgentCapabilityMIB 1 }


--
-- Applies to 2016 Release and follow up patch releases
--

vmwNSXManager2016x AGENT-CAPABILITIES
  PRODUCT-RELEASE
     "6.2.x"
  STATUS  current
  DESCRIPTION
     "Release 6.2.x for VMware NSX Manager supporting only SNMPv2c trap PDUs.
     It describes all the notifications sent from the NSX Manager appliance.
     WARNING: This mib module will not be backward compatible with next version.
     "
  REFERENCE
     "http://www.vmware.com/products"
     -- REVISION 201606020000Z First Version.
     SUPPORTS VMWARE-NSX-MANAGER-MIB
     INCLUDES {
         vmwNsxManagerNotificationGroup1
     }
   ::= { vmwNSXMCapability 5 }


END
