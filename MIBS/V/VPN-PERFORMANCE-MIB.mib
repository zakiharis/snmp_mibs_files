-- extracted from draft-groom-vpn-tunnel-00.txt
-- at Sat Dec  6 06:15:55 2003

VPN-PERFORMANCE-MIB DEFINITIONS ::= BEGIN

IMPORTS
    MODULE-IDENTITY, OBJECT-TYPE, TimeTicks, Integer32, mib-2, IpAddress, 
Counter32, NOTIFICATION-TYPE FROM SNMPv2-SMI
    MODULE-COMPLIANCE, OBJECT-GROUP, NOTIFICATION-GROUP FROM SNMPv2-CONF
    DisplayString FROM SNMPv2-TC;

vpnPerformanceMIB MODULE-IDENTITY
    LAST-UPDATED "200309151900Z" -- 15 September 2003
    ORGANIZATION "Credit Suisse First Boston"
    CONTACT-INFO
	    " Peter Groom
              Credit Suisse First Boston
              One Cabot Square
	      London
	      United Kingdom
              Email: peter.groom@csfb.com"
    DESCRIPTION
	    "The MIB module for performance management of VPN tunnels."
    REVISION     "200309151900Z" -- 15 September 2003
    DESCRIPTION
            "Initial version, yet to be published as a RFC."
    ::= { mib-2 1 } -- To be assigned by IANA.
                             -- Request to assign same number as LMP
                             -- ifType.

vpnPerformanceMIBObjects OBJECT IDENTIFIER ::= { vpnPerformanceMIB 1 }

vpnPerformanceTrapNotifications OBJECT IDENTIFIER ::= { 
vpnPerformanceMIBObjects 0 }

vpnPerformance      OBJECT IDENTIFIER ::= { vpnPerformanceMIBObjects 1 }

vpnPerformanceTRAP  OBJECT IDENTIFIER ::= { vpnPerformanceMIBObjects 2 }

-- the VPN Performance MIB-Group
--
-- a collection of objects providing performance information about
-- VPN tunnels

vpnPerformanceIfTable OBJECT-TYPE
    SYNTAX     SEQUENCE OF VpnPerformanceIfEntry
    MAX-ACCESS not-accessible
    STATUS     current
    DESCRIPTION
            "The table containing line entries for each VPN tunnel."
    ::= { vpnPerformance 1 }

vpnPerformanceIfEntry OBJECT-TYPE
    SYNTAX     VpnPerformanceIfEntry
    MAX-ACCESS not-accessible
    STATUS     current
    DESCRIPTION
            "A line entry containing information about a particular
            configured tunnel."
    INDEX      { vpnPerformanceIndex }
    ::= { vpnPerformanceIfTable 1 }

VpnPerformanceIfEntry ::= SEQUENCE {
    vpnPerformanceIndex				Integer32,
    vpnPerformanceIfLocalAddress  		IpAddress,
    vpnPerformanceIfRemoteAddress 		IpAddress,
    vpnPerformanceIfPollPeriod    		TimeTicks,
    vpnPerformanceIfHighThreshold 		TimeTicks,
    vpnPerformanceIfLostPackets 		Counter32,
    vpnPerformanceIfRearmThreshold 		TimeTicks,
    vpnPerformanceIfHolddownThreshold		TimeTicks,
    vpnPerformanceIfLastRoundTripTime   	TimeTicks
}

vpnPerformanceIndex OBJECT-TYPE
    SYNTAX     Integer32 (1..2147483647)
    MAX-ACCESS not-accessible
    STATUS     current
    DESCRIPTION
            "A unique value for each table entry."
    ::= { vpnPerformanceIfEntry 1 }

vpnPerformanceIfLocalAddress OBJECT-TYPE
    SYNTAX     IpAddress
    MAX-ACCESS read-only
    STATUS     current
    DESCRIPTION
            "The address of the local VPN tunnel endpoint."
    ::= { vpnPerformanceIfEntry 2 }

vpnPerformanceIfRemoteAddress OBJECT-TYPE
    SYNTAX     IpAddress
    MAX-ACCESS read-only
    STATUS     current
    DESCRIPTION
            "The address of the remote VPN tunnel endpoint."
    ::= { vpnPerformanceIfEntry 3 }

vpnPerformanceIfPollPeriod OBJECT-TYPE
    SYNTAX     TimeTicks
    UNITS      "1/100th Seconds"
    MAX-ACCESS read-write
    STATUS     current
    DESCRIPTION
            "The time period used to send performance packets
            to the remote end of the VPN tunnel."
    ::= { vpnPerformanceIfEntry 4 }

vpnPerformanceIfHighThreshold OBJECT-TYPE
    SYNTAX     TimeTicks
    UNITS      "1/100th Seconds"
    MAX-ACCESS read-write
    STATUS     current
    DESCRIPTION
            "The time threshold used to compare round trip
            values against."
    ::= { vpnPerformanceIfEntry 5 }

vpnPerformanceIfLostPackets OBJECT-TYPE
    SYNTAX     Counter32
    MAX-ACCESS read-only
    STATUS     current
    DESCRIPTION
            "The counting threshold used to compare the number
	    of lost packet values against."
    ::= { vpnPerformanceIfEntry 6 }

vpnPerformanceIfRearmThreshold OBJECT-TYPE
    SYNTAX     TimeTicks
    UNITS      "1/100th Seconds"
    MAX-ACCESS read-write
    STATUS     current
    DESCRIPTION
            "The rearm threshold used to compare successive
	    alarm values against."
    ::= { vpnPerformanceIfEntry 7 }

vpnPerformanceIfHolddownThreshold OBJECT-TYPE
    SYNTAX     TimeTicks
    UNITS      "1/100th Seconds"
    MAX-ACCESS read-write
    STATUS     current
    DESCRIPTION
            "The holddown threshold used to compare successive
	    alarm values against."
    ::= { vpnPerformanceIfEntry 8 }

vpnPerformanceIfLastRoundTripTime OBJECT-TYPE
    SYNTAX     TimeTicks
    UNITS      "1/100th Seconds"
    MAX-ACCESS read-write
    STATUS     current
    DESCRIPTION
            "The last round trip value collected."
    ::= { vpnPerformanceIfEntry 9 }

-- the VPN Performance TRAP-Group
--
-- a collection of objects generating snmp traps based on performance
-- information about VPN tunnels

vpnPerformanceTrapTable OBJECT-TYPE
    SYNTAX     SEQUENCE OF VpnPerformanceTrapEntry
    MAX-ACCESS not-accessible
    STATUS     current
    DESCRIPTION
            "The agent's table containing the alarm information."
    ::= { vpnPerformanceTRAP 1 }

vpnPerformanceTrapEntry OBJECT-TYPE
    SYNTAX     VpnPerformanceTrapEntry
    MAX-ACCESS not-accessible
    STATUS     current
    DESCRIPTION
            "Information about the last trap generated by the agent.
            There is always one entry in this table, indexed by the
	    integer value 1."
    INDEX      { vpnPerformanceTrapIndex }
    ::= { vpnPerformanceTrapTable 1 }

VpnPerformanceTrapEntry ::= SEQUENCE {
    vpnPerformanceTrapIndex		Integer32,
    vpnPerformanceTrapSequence    	Counter32,
    vpnPerformanceTrapText        	DisplayString,
    vpnPerformanceTrapPriority    	Integer32,
    vpnPerformanceTrapTime        	Counter32,
    vpnPerformanceTrapSuspect     	IpAddress
}

vpnPerformanceTrapIndex OBJECT-TYPE
    SYNTAX     Integer32 (1..2147483647)
    MAX-ACCESS not-accessible
    STATUS     current
    DESCRIPTION
            "A unique value for each table entry."
    ::= { vpnPerformanceTrapEntry 1 }

vpnPerformanceTrapSequence OBJECT-TYPE
    SYNTAX     Counter32
    MAX-ACCESS read-only
    STATUS     current
    DESCRIPTION
            "A counter of the number of alarms generated since
            the agent for last initialised."
    ::= { vpnPerformanceTrapEntry 2 }

vpnPerformanceTrapText OBJECT-TYPE
    SYNTAX     DisplayString
    MAX-ACCESS read-write
    STATUS     current
    DESCRIPTION
            "Trap text to make the alarm obvious."
    ::= { vpnPerformanceTrapEntry 3 }

vpnPerformanceTrapPriority OBJECT-TYPE
    SYNTAX     Integer32 (1..255)
    MAX-ACCESS read-only
    STATUS     current
    DESCRIPTION
            "The priority level as set on the agent for this
            type of trap."
    ::= { vpnPerformanceTrapEntry 4 }

vpnPerformanceTrapTime OBJECT-TYPE
    SYNTAX     Counter32
    MAX-ACCESS read-only
    STATUS     current
    DESCRIPTION
            "The time that the condition or event occurred which
	    generated the alarm. The value is given in seconds
	    since 00:00:00 Greenwich Mean Time (GMT) January 1,
	    1970."
    ::= { vpnPerformanceTrapEntry 5 }

vpnPerformanceTrapSuspect OBJECT-TYPE
    SYNTAX     IpAddress
    MAX-ACCESS read-only
    STATUS     current
    DESCRIPTION
            "An ASCII string describing the host which caused the
            alarm."
    ::= { vpnPerformanceTrapEntry 6 }

vpnPerformanceTrapLostPackets NOTIFICATION-TYPE
    OBJECTS    { 	vpnPerformanceTrapSequence,
			vpnPerformanceTrapText,
	    	       	vpnPerformanceTrapPriority,
			vpnPerformanceTrapTime,
	    	      	vpnPerformanceTrapSuspect
}
    STATUS     current
    DESCRIPTION
            "The agent has detected the number of lost packets has
            exceeded a threshold."
    ::= { vpnPerformanceTrapNotifications 1 }

vpnPerformanceTrapLostPacketsOk NOTIFICATION-TYPE
    OBJECTS    { 	vpnPerformanceTrapSequence,
			vpnPerformanceTrapText,
	    	       	vpnPerformanceTrapPriority,
			vpnPerformanceTrapTime,
 	   	       	vpnPerformanceTrapSuspect
}
    STATUS     current
    DESCRIPTION
            "The agent has detected the number of lost packets has
            dropped below a threshold."
    ::= { vpnPerformanceTrapNotifications 2 }

vpnPerformanceNotificationsGroup NOTIFICATION-GROUP
    NOTIFICATIONS {	vpnPerformanceTrapLostPackets,
		        vpnPerformanceTrapLostPacketsOk
}
    STATUS     current
    DESCRIPTION
            "Generic VPN Performance Notifications."
    ::= { vpnPerformanceTrapNotifications 3 }

-- Conformance information

vpnPerformanceConformance OBJECT IDENTIFIER ::= { vpnPerformanceMIB 2 }

vpnPerformanceTrapConformance OBJECT IDENTIFIER ::= { vpnPerformanceMIB 3 }

vpnPerformanceCompliances OBJECT IDENTIFIER ::= { vpnPerformanceConformance 1 }

vpnPerformanceGroups OBJECT IDENTIFIER ::= { vpnPerformanceConformance 2 }

vpnPerformanceTrapCompliances OBJECT IDENTIFIER ::= { 
vpnPerformanceTrapConformance 1 }

vpnPerformanceTrapGroups OBJECT IDENTIFIER ::= { 
vpnPerformanceTrapConformance 2 }

-- Compliance statement

vpnPerformanceCompliance MODULE-COMPLIANCE
    STATUS     current
    DESCRIPTION
            "The compliance statement for SNMPv2 entities which
            implement the VPN performance module."
    MODULE     -- this module
    MANDATORY-GROUPS	{ vpnPerformanceGroup } ::= { 
vpnPerformanceCompliances 1 }

vpnPerformanceTrapCompliance MODULE-COMPLIANCE
    STATUS     current
    DESCRIPTION
            "The compliance statement for SNMPv2 entities which
            implement the VPN performance trap module."
    MODULE     -- this module
    MANDATORY-GROUPS	{ vpnPerformanceTrapGroup } ::= { 
vpnPerformanceTrapCompliances 1 }

-- Units of Conformance

vpnPerformanceGroup OBJECT-GROUP
    OBJECTS  {		vpnPerformanceIfLocalAddress,
			vpnPerformanceIfRemoteAddress,
			vpnPerformanceIfPollPeriod,
			vpnPerformanceIfHighThreshold,
			vpnPerformanceIfLostPackets,
			vpnPerformanceIfRearmThreshold,
			vpnPerformanceIfHolddownThreshold,
			vpnPerformanceIfLastRoundTripTime
}
    STATUS     current
    DESCRIPTION
            "The vpnPerformance group of objects providing for the
            management of VPN performance metrics."
    ::= { vpnPerformanceGroups 1 }

vpnPerformanceTrapGroup OBJECT-GROUP
    OBJECTS  {		vpnPerformanceTrapSequence,
			vpnPerformanceTrapText,
			vpnPerformanceTrapPriority,
			vpnPerformanceTrapTime,
			vpnPerformanceTrapSuspect
}
    STATUS     current
    DESCRIPTION
            "The vpnPerformance group of objects providing for the
            management of VPN performance traps."
    ::= { vpnPerformanceTrapGroups 1 }

END

-- 
-- "Copyright (C) The Internet Society (date).  All Rights Reserved.
-- 
-- This document and translations of it may be copied and furnished to others, 
-- and derivative works that comment on or otherwise explain it or assist in its 
-- implementation may be prepared, copied, published and distributed, in whole or 
-- in part, without restriction of any kind, provided that the above copyright 
-- notice and this paragraph are included on all such copies and derivative 
-- works. However, this document itself may not be modified in any way, such as 
-- by removing the copyright notice or references to the Internet Society or 
-- other Internet organizations, except as needed for the purpose of developing 
-- Internet standards in which case the procedures for copyrights defined in the 
-- Internet Standards process must be followed, or as required to translate it 
-- into languages other than English.
-- 
-- The limited permissions granted above are perpetual and will not be revoked by 
-- the Internet Society or its successors or assigns.
-- 
-- This document and the information contained herein is provided on an "AS IS" 
-- basis and THE INTERNET SOCIETY AND THE INTERNET ENGINEERING TASK FORCE 
-- DISCLAIMS ALL WARRANTIES, EXPRESS OR IMPLIED, INCLUDING BUT NOT LIMITED TO ANY 
-- WARRANTY THAT THE USE OF THE INFORMATION HEREIN WILL NOT INFRINGE ANY RIGHTS 
-- OR ANY IMPLIED WARRANTIES OF MERCHANTABILITY OR FITNESS FOR A PARTICULAR 
-- PURPOSE.
-- 
-- 
-- XII.	Disclaimer
-- 
-- The views expressed are those of the author and not necessarily those of CSFB.
