VPN-MIB DEFINITIONS ::= BEGIN

IMPORTS
		  mgmt, NetworkAddress, IpAddress, Counter, Gauge,
			  TimeTicks, enterprises
		      FROM RFC1155-SMI
		DisplayString FROM SNMPv2-TC
		TRAP-TYPE FROM RFC-1215
		  OBJECT-TYPE
			  FROM RFC-1212;


vpnet OBJECT IDENTIFIER ::= {enterprises 1866}
vpnmib OBJECT IDENTIFIER ::= {vpnet 7}
waninterface OBJECT IDENTIFIER ::= {vpnmib 1}
vpns OBJECT IDENTIFIER ::= {vpnmib 2}
log OBJECT IDENTIFIER ::= {vpnmib 3}
vsuSystem OBJECT IDENTIFIER ::= {vpnmib 4}
activeSessions OBJECT IDENTIFIER ::= {vpnmib 5}

-- object types

-- the WAN Interface group

wanIfTable OBJECT-TYPE
	SYNTAX SEQUENCE OF WanIfEntry
	ACCESS not-accessible
	STATUS mandatory
DESCRIPTION ""
	::= { waninterface 1 }

wanIfEntry  OBJECT-TYPE
	SYNTAX WanIfEntry
	ACCESS not-accessible
	STATUS mandatory
DESCRIPTION ""
	INDEX  { wanIfIndex }
	::= { wanIfTable 1 }

WanIfEntry ::=
	SEQUENCE {
		wanIfIndex
			INTEGER,
		wanIfFramesRcvd
			INTEGER,
		wanIfFramesXmit
			INTEGER,
		wanIfFramesDisc
			INTEGER,
		wanIfRcvOvrn
			INTEGER,
		wanIfRcvAbort
			INTEGER,
		wanIfRcvAlignErr
			INTEGER,
		wanIfRcvErr
			INTEGER,
		wanIfRcvFrameLong
			INTEGER,
		wanIfRcvNoBuf
			INTEGER,
		wanIfXmitUnderrun
			INTEGER,
		wanIfXmitTimeout
			INTEGER,
		wanIfXmitNoBuff
			INTEGER,
		wanIfRcvByteRate
			Counter,
		wanIfXmitByteRate
			Counter
		}

wanIfIndex  OBJECT-TYPE
	SYNTAX INTEGER
	ACCESS read-only
	STATUS mandatory
	DESCRIPTION
		"A unique value for each interface.
		1 - Private port
		2 - Public port"
	::= { wanIfEntry 1 }

wanIfFramesRcvd  OBJECT-TYPE
	SYNTAX INTEGER
	ACCESS read-only
	STATUS mandatory
	DESCRIPTION
		"Total frames received on this interface."
	::= { wanIfEntry 2 }

wanIfFramesXmit  OBJECT-TYPE
	SYNTAX INTEGER
	ACCESS read-only
	STATUS mandatory
	DESCRIPTION
		"Total frames transmitted on this interface."
	::= { wanIfEntry 3 }

wanIfFramesDisc  OBJECT-TYPE
	SYNTAX INTEGER
	ACCESS read-only
	STATUS mandatory
	DESCRIPTION
		"Total frames discarded on this interface."
	::= { wanIfEntry 4 }

wanIfRcvOvrn  OBJECT-TYPE
	SYNTAX INTEGER
	ACCESS read-only
	STATUS mandatory
	DESCRIPTION
		"Total frames received on this interface with data overrun errors."
	::= { wanIfEntry 5 }

wanIfRcvAbort  OBJECT-TYPE
	SYNTAX INTEGER
	ACCESS read-only
	STATUS mandatory
	DESCRIPTION
		"Total frames received on this interface aborted by the sender."
	::= { wanIfEntry 6 }

wanIfRcvAlignErr  OBJECT-TYPE
	SYNTAX INTEGER
	ACCESS read-only
	STATUS mandatory
	DESCRIPTION
		"Total frames received on this interface with alignment errors."
	::= { wanIfEntry 7 }

wanIfRcvCRCErr  OBJECT-TYPE
	SYNTAX INTEGER
	ACCESS read-only
	STATUS mandatory
	DESCRIPTION
		"Total frames received on this interface with CRC errors."
	::= { wanIfEntry 8 }

wanIfRcvFrameLong  OBJECT-TYPE
	SYNTAX INTEGER
	ACCESS read-only
	STATUS mandatory
	DESCRIPTION
		"Total frames received on this interface with length errors."
	::= { wanIfEntry 9 }

wanIfRcvNoBuff OBJECT-TYPE
	SYNTAX INTEGER
	ACCESS read-only
	STATUS mandatory
	DESCRIPTION
		"Total frames for which there were no receive buffers available."
	::= { wanIfEntry 10 }

wanIfXmitUnderrun  OBJECT-TYPE
	SYNTAX INTEGER
	ACCESS read-only
	STATUS mandatory
	DESCRIPTION
		"Total frames with transmit underrun errors."
	::= { wanIfEntry 11 }

wanIfXmitTimeout  OBJECT-TYPE
	SYNTAX INTEGER
	ACCESS read-only
	STATUS mandatory
	DESCRIPTION
		"Total times we've timed out trying to transmit a frame."
	::= { wanIfEntry 12 }

wanIfXmitNoBuff  OBJECT-TYPE
	SYNTAX INTEGER
	ACCESS read-only
	STATUS mandatory
	DESCRIPTION
		"Total times there were no transmit buffers available when trying to
		 transmit a frame."
	::= { wanIfEntry 13 }

wanIfRcvByteRate  OBJECT-TYPE
	SYNTAX Counter
	ACCESS read-only
	STATUS mandatory
	DESCRIPTION
		"last 16 second average KB per second of data received."
	::= { wanIfEntry 14 }

wanIfXmitByteRate  OBJECT-TYPE
	SYNTAX Counter
	ACCESS read-only
	STATUS mandatory
	DESCRIPTION
		"last 16 second average KB per second of data sent."
	::= { wanIfEntry 15 }


-- the VPN group

vpnTable OBJECT-TYPE
	SYNTAX SEQUENCE OF VpnEntry
	ACCESS not-accessible
	STATUS mandatory
DESCRIPTION ""
	::= { vpns 1 }

vpnEntry  OBJECT-TYPE
	SYNTAX VpnEntry
	ACCESS not-accessible
	STATUS mandatory
DESCRIPTION ""
        INDEX { vpnIndex }
	::= { vpnTable 1 }

VpnEntry ::=
	SEQUENCE {
		vpnIndex
			INTEGER,
		vpnDescr
			DisplayString,
		vpnSkipInPktDecap
			INTEGER,
		vpnSkipOutPktEncap
			INTEGER,
		vpnSkipInPktParseErr
			INTEGER,
		vpnSkipInKPUpdt
			INTEGER,
		vpnSkipOutKPUpdt
			INTEGER,
		vpnOutFrag
			INTEGER,
		vpnOctetsIn
			INTEGER,
		vpnOctetsOut
			INTEGER,
		vpnNOutOfOrder
			INTEGER,
		vpnSkipAlgMismatch
			INTEGER,
		vpnAuthInPktInvdSig
			INTEGER,
		vpnAuthInPktParseErr
			INTEGER,
		vpnEncryptImpEncap
			INTEGER,
		vpnEncryptInPktParseErr
			INTEGER
		}

vpnIndex  OBJECT-TYPE
	SYNTAX INTEGER
	ACCESS read-only
	STATUS mandatory
	DESCRIPTION
		"A unique value for each VPN. Ranges from 1 to (number of VPNs
		 configured + number of clients configured). So, this table will
		 not map 1-to-1 with the VPNs configured via VPNmanager when
		 VPNRemote clients are configured as part of a VPN. Each client
		 has it's own physical VPN on a VSU."
	::= { vpnEntry 1 }

vpnDescr  OBJECT-TYPE
	SYNTAX DisplayString
	ACCESS read-only
	STATUS mandatory
	DESCRIPTION
		"Textual description of this interface. Currently (1/9/98) just shows
		 the VPN decimal id."
	::= { vpnEntry 2 }

vpnSkipInPktDecap  OBJECT-TYPE
	SYNTAX INTEGER
	ACCESS read-only
	STATUS mandatory
	DESCRIPTION
		"Total incoming SKIP-decapsulated packets for this VPN."
	::= { vpnEntry 3 }

vpnSkipOutPktEncap  OBJECT-TYPE
	SYNTAX INTEGER
	ACCESS read-only
	STATUS mandatory
	DESCRIPTION
		"Total outgoing SKIP-encapsulated packets for this VPN."
	::= { vpnEntry 4 }

vpnSkipInPktParseErr  OBJECT-TYPE
	SYNTAX INTEGER
	ACCESS read-only
	STATUS mandatory
	DESCRIPTION
		"Total incoming packets for this VPN with IPSec header errors."
	::= { vpnEntry 5 }

vpnSkipInKPUpdt  OBJECT-TYPE
	SYNTAX INTEGER
	ACCESS read-only
	STATUS mandatory
	DESCRIPTION
		"Number of Kp (key material) updates for incoming traffic this VPN.
		 Not currently supported."
	::= { vpnEntry 6 }

vpnSkipOutKPUpdt  OBJECT-TYPE
	SYNTAX INTEGER
	ACCESS read-only
	STATUS mandatory
	DESCRIPTION
		"Number of Kp (key material) updates for outgoing traffic this VPN.
		 Not currently supported."
	::= { vpnEntry 7 }

vpnOutFrag  OBJECT-TYPE
	SYNTAX INTEGER
	ACCESS read-only
	STATUS mandatory
	DESCRIPTION
		"Total outgoing packets for this VPN that had to be fragmented."
	::= { vpnEntry 8 }

vpnOctetsIn  OBJECT-TYPE
	SYNTAX INTEGER
	ACCESS read-only
	STATUS mandatory
	DESCRIPTION
		"Total bytes received for this VPN."
	::= { vpnEntry 9 }

vpnOctetsOut  OBJECT-TYPE
	SYNTAX INTEGER
	ACCESS read-only
	STATUS mandatory
	DESCRIPTION
		"Total bytes sent for this VPN."
	::= { vpnEntry 10 }

vpnNOutOfOrder  OBJECT-TYPE
	SYNTAX INTEGER
	ACCESS read-only
	STATUS mandatory
	DESCRIPTION
		"Counter N out-of-order errors for this VPN. Not currently supported."
	::= { vpnEntry 11 }

vpnSkipAlgMismatch  OBJECT-TYPE
	SYNTAX INTEGER
	ACCESS read-only
	STATUS mandatory
	DESCRIPTION
		 "Total number of packets belonging to this VPN with SKIP Algorithm
		  mismatches. That is, the parameters of the VPN that this packet
		  belongs to does not match the VPN parameters in the packet's
		  SKIP header."
	::= { vpnEntry 12 }

vpnAuthInPktInvdSig OBJECT-TYPE
	SYNTAX INTEGER
	ACCESS read-only
	STATUS mandatory
	DESCRIPTION
		 "Total number of packets belonging to this VPN with SKIP Authentication
		  errors. That is, the authentication key in the offending packet was not
		  correct. This type of attack results in an authFailure trap which shows
		  up on the VPNmanager as Invalid Authentication Signature."
	::= { vpnEntry 13 }

vpnAuthInPktParseErr  OBJECT-TYPE
	SYNTAX INTEGER
	ACCESS read-only
	STATUS mandatory
	DESCRIPTION
		"Not currently supported."
	::= { vpnEntry 14 }

vpnEncryptImpEncap  OBJECT-TYPE
	SYNTAX INTEGER
	ACCESS read-only
	STATUS mandatory
	DESCRIPTION
		"Total outgoing packets encrypted for this VPN."
	::= { vpnEntry 15 }

vpnEncryptInPktParseErr OBJECT-TYPE
	SYNTAX INTEGER
	ACCESS read-only
	STATUS mandatory
	DESCRIPTION
		"Total packets belonging to this VPN that had parse errors. For example,
		 encrypted data was not on a 8-byte boundary or the ESP trailer was not
		 of the appropriate size."
	::= { vpnEntry 16 }

-- Log Entries

logTable OBJECT-TYPE
	SYNTAX SEQUENCE OF LogEntry
	ACCESS not-accessible
	STATUS mandatory
DESCRIPTION ""
	::= { log 1 }

logEntry OBJECT-TYPE
	SYNTAX LogEntry
	ACCESS not-accessible
	STATUS mandatory
DESCRIPTION ""
	INDEX  { logIndex }
	::= { logTable 1 }

LogEntry ::=
	SEQUENCE {
		logIndex
			INTEGER,
		logTime
			INTEGER,
		logAttackType
			INTEGER,
		logDescription
			DisplayString
		}

logIndex OBJECT-TYPE
	SYNTAX INTEGER
	ACCESS read-only
	STATUS mandatory
DESCRIPTION ""
	::= { logEntry 1 }

logTime OBJECT-TYPE
	SYNTAX INTEGER
	ACCESS read-only
	STATUS mandatory
DESCRIPTION ""
	::= { logEntry 2 }

logAttackType OBJECT-TYPE
	SYNTAX INTEGER
	ACCESS read-only
	STATUS mandatory
	DESCRIPTION
		"The type of packet error that caused us to perceive this as an attack.
		 1 - SKIP header error. e.g. this packet was not IPSec AH or IPSec ESP.
		 2 - SKIP Counter N error. Not currently (1/9/98) supported.
		 3 - SKIP Algorithm mismatch. The parameters of the VPN that this
		     packet belongs to does not match the VPN parameters in the SKIP
			  header.
		 4 - SKIP Authentication error. The authentication key in the offending
		     packet was not correct. This type of attack results in an authFailure
			  trap which shows up on the VPNmanager as Invalid Authentication Signature.
		 5 - SKIP Authentication Header error. Not supported.
		 6 - SKIP Encryption Header error. The packet's ESP trailer wasn't correct."
	::= { logEntry 3 }

logDescription OBJECT-TYPE
	SYNTAX DisplayString (SIZE (0..65))
	ACCESS read-only
	STATUS mandatory
DESCRIPTION ""
	::= { logEntry 4 }


-- the System group

cpuUtilization OBJECT-TYPE
	SYNTAX Counter
	ACCESS read-only
	STATUS mandatory
DESCRIPTION ""
	::= { vsuSystem 1 }


activeSessionTable OBJECT-TYPE
	SYNTAX SEQUENCE OF ActiveSessionEntry
	ACCESS not-accessible
	STATUS mandatory
DESCRIPTION ""
	::= { activeSessions 1 }

activeSessionEntry  OBJECT-TYPE
	SYNTAX ActiveSessionEntry
	ACCESS not-accessible
	STATUS mandatory
DESCRIPTION ""
	INDEX  { asName }
	::= { activeSessionTable 1 }

ActiveSessionEntry ::=
	SEQUENCE {
		asName
			DisplayString,
		asLength
			TimeTicks,
		asOrgIPAddress
			IpAddress,
		asXlateAddress
			IpAddress,
		asDescr
			DisplayString,
		asPktsIn
			Counter,
		asPktsOut
			Counter,
		asBytesIn
			Counter,
		asBytesOut
			Counter
		}

asName  OBJECT-TYPE
	SYNTAX DisplayString
	ACCESS read-only
	STATUS mandatory
	DESCRIPTION
		"A VPNremote client name or a VSU name as defined in VPNmanager."
	::= { activeSessionEntry 1 }

asLength  OBJECT-TYPE
	SYNTAX TimeTicks
	ACCESS read-only
	STATUS mandatory
	DESCRIPTION
		"Length of this session in seconds."
	::= { activeSessionEntry 2 }

asOrgIPAddress OBJECT-TYPE
	SYNTAX IpAddress
	ACCESS read-only
	STATUS mandatory
	DESCRIPTION
		"VPNremote client's originating IP address or remote VSU IP address."
	::= { activeSessionEntry 3 }

asXlateIPAddress OBJECT-TYPE
	SYNTAX IpAddress
	ACCESS read-only
	STATUS mandatory
	DESCRIPTION
		"VPNremote client's assigned address from the Client IP Address pool if configured.
       If the Client IP Address pool is not configured or this session is from a VSU then
       this attribute is empty."
	::= { activeSessionEntry 4 }

asDescr OBJECT-TYPE
	SYNTAX DisplayString
	ACCESS read-only
	STATUS mandatory
	DESCRIPTION
		"Textual description of this VPN indicating what key management is being used
       and what encryption, authentication and compression algorithms are being used.
       For example: IKE, 3DES, MD5, Compression."
	::= { activeSessionEntry 5 }

asPktsIn OBJECT-TYPE
	SYNTAX Counter
	ACCESS read-only
	STATUS mandatory
	DESCRIPTION
		"Number of packets sent to this VSU from the VPNremote Client or remote VSU
       indicated by asName during this session."
	::= { activeSessionEntry 6 }

asPktsOut OBJECT-TYPE
	SYNTAX Counter
	ACCESS read-only
	STATUS mandatory
	DESCRIPTION
		"Number of packets sent from this VSU to the VPNremote Client or remote VSU
       indicated by asName during this session."
	::= { activeSessionEntry 7 }

asBytesIn OBJECT-TYPE
	SYNTAX Counter
	ACCESS read-only
	STATUS mandatory
	DESCRIPTION
		"Number of bytes sent to this VSU from the VPNremote Client or remote VSU
       indicated by asName during this session."
	::= { activeSessionEntry 8 }

asBytesOut OBJECT-TYPE
	SYNTAX Counter
	ACCESS read-only
	STATUS mandatory
	DESCRIPTION
		"Number of bytes sent from this VSU to the VPNremote Client or remote VSU
       indicated by asName during this session."
	::= { activeSessionEntry 9 }

--------------------------Trap Descriptions----------------------------------

-- VPNet Monnitoring Traps

skipHdrErr TRAP-TYPE
	ENTERPRISE vpnet
	DESCRIPTION
		"SKIP header error. e.g. this packet was not IPSec AH or IPSec ESP."
	::= 1

skipNCounterErr TRAP-TYPE
	ENTERPRISE vpnet
	DESCRIPTION
		"SKIP Count N error. Not used."
	::= 2

skipAlgMismatch TRAP-TYPE
	ENTERPRISE vpnet
	DESCRIPTION
		"SKIP Algorithm mismatch. The parameters of the VPN that a
		 packet belonged to did not match the VPN parameters in the SKIP
	    header."
	::= 3

authFailure TRAP-TYPE
	ENTERPRISE vpnet
	DESCRIPTION
		"SKIP Authentication error. The authentication key in the offending
		 packet was not correct. This trap shows up on the VPNmanager as
		 Invalid Authentication Signature."
	::= 4

authHdrErr TRAP-TYPE
	ENTERPRISE vpnet
	DESCRIPTION
		"SKIP Authentication Header error. Not used."
	::= 5

encryptHdrErr TRAP-TYPE
	ENTERPRISE vpnet
	DESCRIPTION
		 "SKIP Encryption Header error. The packet's ESP trailer wasn't correct."
	::= 6

authFailureLimitErr TRAP-TYPE
	ENTERPRISE vpnet
	DESCRIPTION
		"Client Configuration Download failure limit reached."
	::= 7

END
