VMX-DIAL DEFINITIONS ::= BEGIN

--
-- Copyright (c) 1994 OCTel Communication Corp. All rights reserved.
--
-- This Specification is supplied AS IS, and Octel makes no warranty, 
-- expressed or implied, as to the use, operation, and performance 
-- of the Spec.
--
-- VMX-DIAL private MIB definitions for the VMX200/300 DIAL Product 
-- family.
--
-- Filename: octel-vmxdial.mib
-- This MIB definition is provided for use with OCtel's VMX200/300 
-- product only. 
-- 
-- Contact Person:
--              VMX200/300 LAN Engineering Group 
--              Octel Communication Corporation 
--              1001 Murphy Ranch Road
--              Milpitas, CA 95035
-- 
-- NOTE:
-- 1. This file will be published electronically in
--              venera.isi.edu and can be obtained using ftp anonymous.
--
-- 2. Sunnet Manager User:
--    Sunnet doesn't support multi-dimensional table. To make this file works
--    with subnet, the mnemonic for the second level table need to be replaced
--    by the number it represents. Example:
--    locEntry is a table entry, and
--       route1 is defined as locroute.1 where locroute is locEntry.7
--    the above definition need to be changed as follows:
--    . remove the definition for locroute
--    . route1 is defined as locEntry.7.1
--    This need to be done for all multi-dimensional tables.
--    
-- MODIFICATIONS:
-- Last Revision - 10/28/94
--

IMPORTS
        enterprises, NetworkAddress, IpAddress, Counter, Gauge,
                TimeTicks
            FROM RFC1155-SMI
        OBJECT-TYPE
            FROM RFC-1212
        DisplayString
            FROM RFC1213-MIB
        sysDescr
            FROM RFC1158-MIB;

octel           OBJECT IDENTIFIER ::= { enterprises 662 }
octelOIDs       OBJECT IDENTIFIER ::= { octel 1 }
octelPlatforms  OBJECT IDENTIFIER ::= { octelOIDs 1}
vmx200          OBJECT IDENTIFIER ::= { octelPlatforms 3 }
vmx300          OBJECT IDENTIFIER ::= { octelPlatforms 4 }

octelProducts   OBJECT IDENTIFIER ::= { octel 3 }
vmxDial         OBJECT IDENTIFIER ::= { octelProducts 1 }
config          OBJECT IDENTIFIER ::= { vmxDial 1 }
dNetstat        OBJECT IDENTIFIER ::= { vmxDial 2 }
location        OBJECT IDENTIFIER ::= { vmxDial 3 }
hwerr           OBJECT IDENTIFIER ::= { vmxDial 4 }

-- dNetstat subtrees
message         OBJECT IDENTIFIER ::= { dNetstat 1 }
lanCh           OBJECT IDENTIFIER ::= { dNetstat 2 }
lanConn         OBJECT IDENTIFIER ::= { dNetstat 3 }

systemName      OBJECT-TYPE
        SYNTAX  DisplayString (SIZE (0..255))
        ACCESS  read-only
        STATUS  mandatory
        DESCRIPTION
                "VMX System Name, from Configuration"
        ::= { config 1 }

sysSerialNum    OBJECT-TYPE
        SYNTAX  DisplayString (SIZE (0..255))
        ACCESS  read-only
        STATUS  mandatory
        DESCRIPTION
                "VMX System Serial Number."
        ::= { config 2 }

systemID        OBJECT-TYPE
        SYNTAX  DisplayString (SIZE (0..255))
        ACCESS  read-only
        STATUS  mandatory
        DESCRIPTION
                "VMX System Identification Number."
        ::= { config 3 }

sentVoiceMsgs   OBJECT-TYPE
        SYNTAX  Counter
        ACCESS  read-only
        STATUS  mandatory
        DESCRIPTION
                "Total number of voice messages sent to the networks"
        ::= { message 1 }

recvVoiceMsgs   OBJECT-TYPE
        SYNTAX  Counter
        ACCESS  read-only
        STATUS  mandatory
        DESCRIPTION
                "Total number of voice messages received from the networks"
        ::= { message 2 }

sentFaxMsgs   OBJECT-TYPE
        SYNTAX  Counter
        ACCESS  read-only
        STATUS  mandatory
        DESCRIPTION
                "Total number of fax messages sent to the networks"
        ::= { message 3 }

recvFaxMsgs   OBJECT-TYPE
        SYNTAX  Counter
        ACCESS  read-only
        STATUS  mandatory
        DESCRIPTION
                "Total number of fax messages received from the networks"
        ::= { message 4 }

recvNames       OBJECT-TYPE
        SYNTAX  Counter
        ACCESS  read-only
        STATUS  mandatory
        DESCRIPTION
                "Total number of name received from the networks"
        ::= { message 5 }

playedRtNames   OBJECT-TYPE
        SYNTAX  Counter
        ACCESS  read-only
        STATUS  mandatory
        DESCRIPTION
                "Total number of Real Time network name played"
        ::= { message 6 }

secSent OBJECT-TYPE
        SYNTAX  INTEGER
        ACCESS  read-only
        STATUS  mandatory
        DESCRIPTION
                "Total number of seconds of message sent to the networks"
        ::= { message 7 }

secRecv OBJECT-TYPE
        SYNTAX  INTEGER
        ACCESS  read-only
        STATUS  mandatory
        DESCRIPTION
                "Total number of seconds of message received from the networks"
        ::= { message 8 }

lchNumber       OBJECT-TYPE
        SYNTAX  INTEGER
        ACCESS  read-only
        STATUS  mandatory
        DESCRIPTION
                "Maximum number of LAN channel available in the system."
        ::= { lanCh 1 }

sec50pct        OBJECT-TYPE
        SYNTAX  INTEGER
        ACCESS  read-only
        STATUS  mandatory
        DESCRIPTION
                "Total number of second that 50 percent of lan channel is busy"
        ::= { lanCh 2 }

sec75pct        OBJECT-TYPE
        SYNTAX  INTEGER
        ACCESS  read-only
        STATUS  mandatory
        DESCRIPTION
                "Total number of second that 75 percent of lan channel is busy"
        ::= { lanCh 3 }

sec100pct       OBJECT-TYPE
        SYNTAX  INTEGER
        ACCESS  read-only
        STATUS  mandatory
        DESCRIPTION
                "Total number of second that all of lan channel is busy"
        ::= { lanCh 4 }

lchInSendSec    OBJECT-TYPE
        SYNTAX  INTEGER
        ACCESS  read-only
        STATUS  mandatory
        DESCRIPTION
                "Number of second LCH is in used for sending message"
        ::= { lanCh 5 }

lchInRecvSec    OBJECT-TYPE
        SYNTAX  INTEGER
        ACCESS  read-only
        STATUS  mandatory
        DESCRIPTION
                "Number of second LCH is in used for receiving message"
        ::= { lanCh 6 }

outAttempts     OBJECT-TYPE
        SYNTAX  Counter
        ACCESS  read-only
        STATUS  mandatory
        DESCRIPTION
                "Number of time an outgoing lan connection is attempted"
        ::= { lanConn 1 }

outRejects      OBJECT-TYPE
        SYNTAX  Counter
        ACCESS  read-only
        STATUS  mandatory
        DESCRIPTION
                "Number of time an outgoing lan connection is rejected"
        ::= { lanConn 2 }

outGotBusys     OBJECT-TYPE
        SYNTAX  Counter
        ACCESS  read-only
        STATUS  mandatory
        DESCRIPTION
                "Number of time an outgoing lan connection is rejected, 
                 due to all LCH busy"
        ::= { lanConn 3 }

inAttempts      OBJECT-TYPE
        SYNTAX  Counter
        ACCESS  read-only
        STATUS  mandatory
        DESCRIPTION
                "Number of time an incoming lan connection is requested"
        ::= { lanConn 4 }

inRejects       OBJECT-TYPE
        SYNTAX  Counter
        ACCESS  read-only
        STATUS  mandatory
        DESCRIPTION
                "Number of time an incoming lan connection is rejected"
        ::= { lanConn 5 }

inGotBusys      OBJECT-TYPE
        SYNTAX  Counter
        ACCESS  read-only
        STATUS  mandatory
        DESCRIPTION
                "Number of time an incoming lan connection is rejected, 
                 due to all LCH busy"
        ::= { lanConn 6 }

lanAvailPct     OBJECT-TYPE
        SYNTAX  INTEGER
        ACCESS  read-only
        STATUS  mandatory
        DESCRIPTION
                "Percentage of LAN availability."
        ::= { dNetstat 4 }

locTable        OBJECT-TYPE
        SYNTAX  SEQUENCE OF LocEntry 
        ACCESS  not-accessible
        STATUS  mandatory
        DESCRIPTION
                "List of active Digital Network Location."
        ::= { location 1 }

locEntry        OBJECT-TYPE
        SYNTAX  LocEntry
        ACCESS  not-accessible
        STATUS  mandatory
        DESCRIPTION    
                "Each entry contains info about the Network Location."
        INDEX   { locIndex }
        ::= { locTable 1 }
        
LocEntry        ::= SEQUENCE {
        locIndex
                INTEGER,
        locName
                DisplayString (SIZE (0..255)),
        locIpAddr
                IpAddress,
        locLinkType
                DisplayString,
        locInDomain   
                DisplayString,
        locColocated
                DisplayString,
        route1
                DisplayString (SIZE (0..255)),
        route2
                DisplayString (SIZE (0..255)),
        route3
                DisplayString (SIZE (0..255)),
        cattempts
                Counter,
        cfailures
                Counter,
        cdroppeds
                Counter,
        cbusys
                Counter,
        cdayMin
                INTEGER,
        cnightMin
                INTEGER,
        mdvcAttempts
                Counter,
        mdvcFails
                Counter,
        mdvcRetries
                Counter,
        mdfxAttempts
                Counter,
        mdfxFails
                Counter,
        mdfxRetries
                Counter,
        mdDiskfulls
                Counter,
        mdMbxfails
                Counter,
        mdMinute
                INTEGER,
        locPlayedNames
                Counter,
        locLinkdrops
                Counter,
        locAnalogstndbys
                Counter
}

locIndex        OBJECT-TYPE
        SYNTAX  INTEGER
        ACCESS  read-only
        STATUS  mandatory
        DESCRIPTION
                "Index of this Location Entry"
        ::= { locEntry 1 }

locName         OBJECT-TYPE
        SYNTAX  DisplayString (SIZE (0..255))
        ACCESS  read-only
        STATUS  mandatory
        DESCRIPTION
                "System Name of This Location Entry, SELF means this system"
        ::= { locEntry 2 }

locIpAddr       OBJECT-TYPE
        SYNTAX  IpAddress
        ACCESS  read-only
        STATUS  mandatory
        DESCRIPTION
                "Internet Address of this Location"
        ::= { locEntry 3 }

locLinkType     OBJECT-TYPE
        SYNTAX  INTEGER {
                lowspeed(1),
                highspeed(2)
                }
        ACCESS  read-only
        STATUS  mandatory
        DESCRIPTION
                "Type of the network interface"
        ::= { locEntry 4 }

locInDomain     OBJECT-TYPE
        SYNTAX  INTEGER {
                no(1),
                yes(2)
                }
        ACCESS  read-only
        STATUS  mandatory
        DESCRIPTION
                "Whether this location is in the same Uniform Numbering Plan
                 domain. "
        ::= { locEntry 5 }

locColocated    OBJECT-TYPE
        SYNTAX  INTEGER {
                no(1),
                yes(2)
                }
        ACCESS  read-only
        STATUS  mandatory
        DESCRIPTION
                "Whether this location is in the same location."
        ::= { locEntry 6 }

locroute        OBJECT IDENTIFIER ::= { locEntry 7 }

route1          OBJECT-TYPE
        SYNTAX  DisplayString (SIZE (0..255))
        ACCESS  read-only
        STATUS  mandatory
        DESCRIPTION
                "First Entry in the Route Table for this location."
        ::= { locroute 1 }

route2          OBJECT-TYPE
        SYNTAX  DisplayString (SIZE (0..255))
        ACCESS  read-only
        STATUS  mandatory
        DESCRIPTION
                "Second Entry in the Route Table for this location."
        ::= { locroute 2 }

route3          OBJECT-TYPE
        SYNTAX  DisplayString (SIZE (0..255))
        ACCESS  read-only
        STATUS  mandatory
        DESCRIPTION
                "Third Entry in the Route Table for this location."
        ::= { locroute 3 }

locConn OBJECT IDENTIFIER ::= { locEntry 8 }

cattempts       OBJECT-TYPE
        SYNTAX  Counter
        ACCESS  read-only
        STATUS  mandatory
        DESCRIPTION
                "Number of times LAN connection attempted."
        ::= { locConn 1 }

cfailures       OBJECT-TYPE
        SYNTAX  Counter
        ACCESS  read-only
        STATUS  mandatory
        DESCRIPTION
                "Number of times LAN connection to this location failed."
        ::= { locConn 2 }

cdroppeds       OBJECT-TYPE
        SYNTAX  Counter
        ACCESS  read-only
        STATUS  mandatory
        DESCRIPTION
                "Number of times LAN connection to this location dropped."
        ::= { locConn 3 }

cbusys          OBJECT-TYPE
        SYNTAX  Counter
        ACCESS  read-only
        STATUS  mandatory
        DESCRIPTION
                "Number of times All LAN Connection is busy."
        ::= { locConn 4 }

cdayMin         OBJECT-TYPE
        SYNTAX  INTEGER
        ACCESS  read-only
        STATUS  mandatory
        DESCRIPTION
                "Number of minutes(day time) LAN connection is established."
        ::= { locConn 5 }

cnightMin       OBJECT-TYPE
        SYNTAX  INTEGER
        ACCESS  read-only
        STATUS  mandatory
        DESCRIPTION
                "Number of minutes(night time) LAN connection is established."
        ::= { locConn 6 }

msgDelivery     OBJECT IDENTIFIER ::= { locEntry 9 }

mdvcAttempts    OBJECT-TYPE
        SYNTAX  Counter
        ACCESS  read-only
        STATUS  mandatory
        DESCRIPTION
                "Number of voice message delivery attempts to this location."
        ::= { msgDelivery 1 }

mdvcFails               OBJECT-TYPE
        SYNTAX  Counter
        ACCESS  read-only
        STATUS  mandatory
        DESCRIPTION
                "Number of voice message delivery failures to this location."
        ::= { msgDelivery 2 }

mdvcRetries     OBJECT-TYPE
        SYNTAX  Counter
        ACCESS  read-only
        STATUS  mandatory
        DESCRIPTION
                "Number of voice message delivery retries to this location."
        ::= { msgDelivery 3 }

mdfxAttempts    OBJECT-TYPE
        SYNTAX  Counter
        ACCESS  read-only
        STATUS  mandatory
        DESCRIPTION
                "Number of fax message delivery attempts to this location."
        ::= { msgDelivery 4 }
 
mdfxFails               OBJECT-TYPE
        SYNTAX  Counter
        ACCESS  read-only
        STATUS  mandatory
        DESCRIPTION
                "Number of fax message delivery failures to this location."
        ::= { msgDelivery 5 }

mdfxRetries     OBJECT-TYPE
        SYNTAX  Counter
        ACCESS  read-only
        STATUS  mandatory
        DESCRIPTION
                "Number of fax message delivery retries to this location."
        ::= { msgDelivery 6 }

mdDiskfulls     OBJECT-TYPE
        SYNTAX  Counter
        ACCESS  read-only
        STATUS  mandatory
        DESCRIPTION
                "Number of message delivery to this location fails due to 
                 disk full."
        ::= { msgDelivery 7 }

mdMbxfails      OBJECT-TYPE
        SYNTAX  Counter
        ACCESS  read-only
        STATUS  mandatory
        DESCRIPTION
                "Number of message delivery to this location fails due to 
                 mailbox verification failure."
        ::= { msgDelivery 8 }

mdMinute        OBJECT-TYPE
        SYNTAX  INTEGER
        ACCESS  read-only
        STATUS  mandatory
        DESCRIPTION
                "Total number of message (in minute) delivered to
                 this location."
        ::= { msgDelivery 9 }

locPlayedNames  OBJECT-TYPE
        SYNTAX  Counter
        ACCESS  read-only
        STATUS  mandatory
        DESCRIPTION
                "Number of Real Time Network Name Played from this location."
        ::= { locEntry 10 }

locLinkdrops    OBJECT-TYPE
        SYNTAX  Counter
        ACCESS  read-only
        STATUS  mandatory
        DESCRIPTION
                "Number of time LAN connection dropped, High Speed link only."
        ::= { locEntry 11 }

locAnalogstndbys OBJECT-TYPE
        SYNTAX  Counter
        ACCESS  read-only
        STATUS  mandatory
        DESCRIPTION
                "Number of times Analog Standby used to this location."
        ::= { locEntry 12 }

hwerrTable        OBJECT-TYPE
        SYNTAX  SEQUENCE OF HwerrEntry
        ACCESS  not-accessible
        STATUS  mandatory
        DESCRIPTION
                "Table of Hardware errors."
        ::= { hwerr 1 }

hwerrEntry   OBJECT-TYPE
     SYNTAX  HwerrEntry
     ACCESS  not-accessible
     STATUS  mandatory
     DESCRIPTION
             "Hardware Error table Entry"
     INDEX   { heIdx }
     ::= { hwerrTable 1 }

HwerrEntry        ::= SEQUENCE {
        heIdx
                INTEGER,
        heType
                INTEGER,
        heSlot
                INTEGER,
        heMon
                INTEGER,
        heDay
                INTEGER,
        heHour
                INTEGER,
        heMin
                INTEGER,
        heCh
                INTEGER,
        hePrio
                INTEGER,
        heCnt
                INTEGER,
        heData1
                OCTET STRING,
        heData2
                OCTET STRING,
        heData3
                OCTET STRING,
        heData4
                OCTET STRING
}

heIdx        OBJECT-TYPE
        SYNTAX  INTEGER
        ACCESS  read-only
        STATUS  mandatory
        DESCRIPTION
                "Index of this Hardware Entry"
        ::= { hwerrEntry 1 }

heType     OBJECT-TYPE
        SYNTAX  INTEGER
        ACCESS  read-only
        STATUS  mandatory
        DESCRIPTION
                "Error Type of this hardare error."
        ::= { hwerrEntry 2 }

heSlot        OBJECT-TYPE
        SYNTAX  INTEGER
        ACCESS  read-only
        STATUS  mandatory
        DESCRIPTION
                "Slot Number of this Hardware Error Entry"
        ::= { hwerrEntry 3 }

heMon        OBJECT-TYPE
        SYNTAX  INTEGER {
                jan(1),
                feb(2),
                mar(3),
                apr(4),
                may(5),
                jun(6),
                jul(7),
                aug(8),
                sep(9),
                oct(10),
                nov(11),
                dec(12)
                }
        ACCESS  read-only
        STATUS  mandatory
        DESCRIPTION
                "Month in which this Hardware Error Entry occurred"
        ::= { hwerrEntry 4 }

heDay        OBJECT-TYPE
        SYNTAX  INTEGER
        ACCESS  read-only
        STATUS  mandatory
        DESCRIPTION
                "Day on which this Hardware Error Entry occurred"
        ::= { hwerrEntry 5 }

heHour        OBJECT-TYPE
        SYNTAX  INTEGER
        ACCESS  read-only
        STATUS  mandatory
        DESCRIPTION
                "Hour on which this Hardware Error Entry occurred"
        ::= { hwerrEntry 6 }

heMin        OBJECT-TYPE
        SYNTAX  INTEGER
        ACCESS  read-only
        STATUS  mandatory
        DESCRIPTION
                "Minute on which this Hardware Error Entry occurred"
        ::= { hwerrEntry 7 }

heCh         OBJECT-TYPE
        SYNTAX  OCTET STRING
        ACCESS  read-only
        STATUS  mandatory
        DESCRIPTION
                "Channel Number of this Hardware Error Entry"
        ::= { hwerrEntry 8 }

hePrio        OBJECT-TYPE
        SYNTAX  INTEGER
        ACCESS  read-only
        STATUS  mandatory
        DESCRIPTION
                "Priority of this Hardware Error Entry"
        ::= { hwerrEntry 9 }

heCnt      OBJECT-TYPE
        SYNTAX  INTEGER
        ACCESS  read-only
        STATUS  mandatory
        DESCRIPTION
                "Frequency of this hardare error."
       ::= { hwerrEntry 10 }

heData1      OBJECT-TYPE
        SYNTAX  OCTET STRING
        ACCESS  read-only
        STATUS  mandatory
        DESCRIPTION
                "Data1 of this hardare error."
        ::= { hwerrEntry 11 }

heData2      OBJECT-TYPE
        SYNTAX  OCTET STRING
        ACCESS  read-only
        STATUS  mandatory
        DESCRIPTION
                "Data2 of this hardare error."
        ::= { hwerrEntry 12 }

heData3      OBJECT-TYPE
        SYNTAX  OCTET STRING
        ACCESS  read-only
        STATUS  mandatory
        DESCRIPTION
                "Data3 of this hardare error."
        ::= { hwerrEntry 13 }

heData4      OBJECT-TYPE
        SYNTAX  OCTET STRING
        ACCESS  read-only
        STATUS  mandatory
        DESCRIPTION
                "Data4 of this hardare error."
        ::= { hwerrEntry 14 }

hwerrTrap       TRAP-TYPE
        ENTERPRISE octel
        VARIABLES { sysDescr, heType, heSlot, heMon, heDay,
                    heHour, heMin, heCh, hePrio, heCnt,
                    heData1, heData2, heData3, heData4 }
        DESCRIPTION
                "A hwerrTrap signifies that the VMX system has hardware errors
                 logged. This trap is sent if the user has configured it."
        ::= 1

END
