--    Verax Network Management System Enterprise MIB
--    Revision 18 Feb 2010

--    Copyright 2009-2010 Verax Systems
--    All rights reserved

VERAX-NMS-AGENT-MIB DEFINITIONS ::= BEGIN

    IMPORTS
	OBJECT-TYPE, NOTIFICATION-TYPE, MODULE-IDENTITY, OBJECT-IDENTITY, DisplayString, IpAddress
		FROM SNMPv2-SMI
    OBJECT-GROUP, NOTIFICATION-GROUP               
		FROM SNMPv2-CONF		
	veraxnms
		FROM VERAX-MIB;

    veraxNmsAgent MODULE-IDENTITY
       LAST-UPDATED "201211051200Z"
       ORGANIZATION "Verax Systems"
       CONTACT-INFO
           "Verax Systems Corp.
            E-mail: office@veraxsystems.com"
       DESCRIPTION
           "This MIB module defines a set of basic objects
	   for Verax Network Management System."
       ::= { veraxnms 1 }

    adminMIB                     OBJECT IDENTIFIER ::= { veraxNmsAgent 1 } -- reserved for future use 
    agentMIB                     OBJECT IDENTIFIER ::= { veraxNmsAgent 2 } -- NMS agnet MIB  
    trapMIB	         	 OBJECT IDENTIFIER ::= { veraxNmsAgent 3 } -- contains all traps
    conformance   		 OBJECT IDENTIFIER ::= { veraxNmsAgent 4 } -- SMIv2 conformance
	
    ------------------------
    -- NMS AGENT DEFINITION
    ------------------------

    -- NMS agent
    aSystem               OBJECT IDENTIFIER ::= { agentMIB 0 }
    aPerformance          OBJECT IDENTIFIER ::= { agentMIB 1 }
    aReserved             OBJECT IDENTIFIER ::= { agentMIB 2 }
    aSharedObjects        OBJECT IDENTIFIER ::= { agentMIB 3 }
	
    asoNumber OBJECT-TYPE
    SYNTAX  INTEGER
    ACCESS  read-only
    STATUS  mandatory
    DESCRIPTION
            "The number of shared objects."
    ::= { aSharedObjects 1 }
		
	asoTable OBJECT-TYPE
    SYNTAX  SEQUENCE OF IfEntry
    ACCESS  not-accessible
    STATUS  mandatory
    DESCRIPTION
            "A list of shared objects entries.  The number of
            entries is given by the value of asoNumber."
    ::= { aSharedObjects 2 }
	
    asoEntry OBJECT-TYPE
    SYNTAX  AsoEntry
    ACCESS  not-accessible
    STATUS  mandatory
    DESCRIPTION
            "An shared object entry containing attributes of exposed object."
    INDEX   { asoIndex }
    ::= { asoTable 1 }

    AsoEntry ::=
    SEQUENCE {
        asoIndex
            INTEGER,
        asoName
            DisplayString,
        asoDescr
            DisplayString,
        asoType
            DisplayString,			
        asoDetails
            DisplayString,
        asoStatus
            INTEGER
    }

    asoIndex OBJECT-TYPE
    SYNTAX  INTEGER
    ACCESS  read-only
    STATUS  mandatory
    DESCRIPTION
            "A unique value for each shared object."
    ::= { asoEntry 1 }

    asoName OBJECT-TYPE
    SYNTAX  DisplayString (SIZE (0..255))
    ACCESS  read-only
    STATUS  mandatory
    DESCRIPTION
            "A name of shared object."
    ::= { asoEntry 2 }
	
    asoDescr OBJECT-TYPE
    SYNTAX  DisplayString (SIZE (0..255))
    ACCESS  read-only
    STATUS  mandatory
    DESCRIPTION
            "A textual string containing information about the
            object."
    ::= { asoEntry 3 }
  
    asoType OBJECT-TYPE
    SYNTAX  DisplayString (SIZE (0..255))
    ACCESS  read-only
    STATUS  mandatory
    DESCRIPTION
            "A textual string containing name of a class representing the shared object." 
    ::= { asoEntry 4 }

    asoDetails OBJECT-TYPE
    SYNTAX  DisplayString (SIZE (0..255))
    ACCESS  read-only
    STATUS  mandatory
    DESCRIPTION
            "A textual string containing object details."
    ::= { asoEntry 5 }	

    asoStatus OBJECT-TYPE
    SYNTAX INTEGER {
	       other(1),    -- none of the following
		   aspect(2),
		   device(3),
		   interface(4),
		   storage(5),
		   processor(6),
		   process(7),
		   sensor(8),
		   counter(9),
		   probe(10),
		   application(11)
	       }
    ACCESS  read-only
    STATUS  mandatory
    DESCRIPTION
            "Current status of shared object"
    ::= { asoEntry 6 }	

    					
    -- TRAPS DEFINITION 
    

    trapVariables 	 OBJECT IDENTIFIER ::= { trapMIB 0 }		
    generalTraps         OBJECT IDENTIFIER ::= { trapMIB 1 }
    probingTraps         OBJECT IDENTIFIER ::= { trapMIB 2 }
    performanceTraps     OBJECT IDENTIFIER ::= { trapMIB 3 }
    eventProcessorTraps  OBJECT IDENTIFIER ::= { trapMIB 4 }   
    customTraps          OBJECT IDENTIFIER ::= { trapMIB 5 } -- reserved for event processor rules of 3-rd parties 
	
    -- Trap variables 
    sensorId OBJECT-TYPE
    SYNTAX INTEGER
    MAX-ACCESS read-only
    STATUS current
    DESCRIPTION
        "Unique id of the probing sensor."
    ::= { trapVariables 1 }

    counterId OBJECT-TYPE
    SYNTAX INTEGER
    MAX-ACCESS read-only
    STATUS current
    DESCRIPTION
        "Unique id of the performance counter."
    ::= { trapVariables 2 }

    sourceIp OBJECT-TYPE
    SYNTAX IpAddress
    MAX-ACCESS read-only
    STATUS current
    DESCRIPTION
        "IP of object generating original event used by forwarding events."
    ::= { trapVariables 3 }
    
	sourceObjectId OBJECT-TYPE
    SYNTAX INTEGER
    MAX-ACCESS read-only
    STATUS current
    DESCRIPTION
        "Unique id of manage object associated with the event if any (e.g. interface id)."
    ::= { trapVariables 4 } 
	
	
    sourceInterfaceId OBJECT-TYPE
    SYNTAX INTEGER
    MAX-ACCESS read-only
    STATUS current
    DESCRIPTION
        "Unique id of interface associated with the event if any."
    ::= { trapVariables 5 }       
    
    name OBJECT-TYPE
    SYNTAX DisplayString (SIZE (0..255))
    MAX-ACCESS read-only
    STATUS current
    DESCRIPTION
        "Name of the device associated with the event."
    ::= { trapVariables 6 }
    
    macAddress OBJECT-TYPE
    SYNTAX DisplayString (SIZE (0..255))
    MAX-ACCESS read-only
    STATUS current
    DESCRIPTION
        "Physical address of the device associated with the event."
    ::= { trapVariables 7 }
    
    type OBJECT-TYPE
    SYNTAX DisplayString (SIZE (0..255))
    MAX-ACCESS read-only
    STATUS current
    DESCRIPTION
        "Type of the device associated with the event."
    ::= { trapVariables 8 }
    
    model OBJECT-TYPE
    SYNTAX DisplayString (SIZE (0..255))
    MAX-ACCESS read-only
    STATUS current
    DESCRIPTION
        "Model of the device associated with the event."
    ::= { trapVariables 9 }
	
	filterWindowSize OBJECT-TYPE
    SYNTAX DisplayString (SIZE (0..255))
    MAX-ACCESS read-only
    STATUS current
    DESCRIPTION
        "Sensor filter window size associated with the event."
    ::= { trapVariables 10 }
    
	sensorLastResponseTime OBJECT-TYPE
    SYNTAX DisplayString (SIZE (0..255))
    MAX-ACCESS read-only
    STATUS current
    DESCRIPTION
        "Sensor last response time associated with the event."
    ::= { trapVariables 11 }
	
	sensorLowThreshold OBJECT-TYPE
    SYNTAX DisplayString (SIZE (0..255))
    MAX-ACCESS read-only
    STATUS current
    DESCRIPTION
        "Sensor low threshold value associated with the event."
    ::= { trapVariables 12 }
	
	sensorHighThreshold OBJECT-TYPE
    SYNTAX DisplayString (SIZE (0..255))
    MAX-ACCESS read-only
    STATUS current
    DESCRIPTION
        "Sensor high threshold value associated with the event."
    ::= { trapVariables 13 }
	
	sensorTimeout OBJECT-TYPE
    SYNTAX DisplayString (SIZE (0..255))
    MAX-ACCESS read-only
    STATUS current
    DESCRIPTION
        "Sensor timeout threshold value associated with the event."
    ::= { trapVariables 14 }

	counterLastResponseTime OBJECT-TYPE
    SYNTAX DisplayString (SIZE (0..255))
    MAX-ACCESS read-only
    STATUS current
    DESCRIPTION
        "Counter last response time associated with the event."
    ::= { trapVariables 15 }

	counterCriticalHighThreshold OBJECT-TYPE
    SYNTAX DisplayString (SIZE (0..255))
    MAX-ACCESS read-only
    STATUS current
    DESCRIPTION
        "Counter critical high threshold value associated with the event."
    ::= { trapVariables 16 }

	counterCriticalLowThreshold OBJECT-TYPE
    SYNTAX DisplayString (SIZE (0..255))
    MAX-ACCESS read-only
    STATUS current
    DESCRIPTION
        "Counter critical low threshold value associated with the event."
    ::= { trapVariables 17 }

	counterWarningLowThreshold OBJECT-TYPE
    SYNTAX DisplayString (SIZE (0..255))
    MAX-ACCESS read-only
    STATUS current
    DESCRIPTION
        "Counter warning low threshold value associated with the event."
    ::= { trapVariables 18 }

	counterWarningHighThreshold OBJECT-TYPE
    SYNTAX DisplayString (SIZE (0..255))
    MAX-ACCESS read-only
    STATUS current
    DESCRIPTION
        "Counter warning high threshold value associated with the event."
    ::= { trapVariables 19 }

	counterTimeout OBJECT-TYPE
    SYNTAX DisplayString (SIZE (0..255))
    MAX-ACCESS read-only
    STATUS current
    DESCRIPTION
        "Counter timeout value associated with the event."
    ::= { trapVariables 20 }
    
            errorMessage OBJECT-TYPE
    SYNTAX DisplayString (SIZE (0..255))
    MAX-ACCESS read-only
    STATUS current
    DESCRIPTION
        "Error message associated with the event."
    ::= { trapVariables 21 }

	counterMinimumBaselineValue OBJECT-TYPE
    SYNTAX DisplayString (SIZE (0..255))
    MAX-ACCESS read-only
    STATUS current
    DESCRIPTION
        "Counter minimum baseline value."
    ::= { trapVariables 22 }

	counterMaximumBaselineValue OBJECT-TYPE
    SYNTAX DisplayString (SIZE (0..255))
    MAX-ACCESS read-only
    STATUS current
    DESCRIPTION
        "Counter maximum baseline value."
    ::= { trapVariables 23 }

        counterLastSampleValue OBJECT-TYPE
    SYNTAX DisplayString (SIZE (0..255))
    MAX-ACCESS read-only
    STATUS current
    DESCRIPTION
        "Counter last sample value."
    ::= { trapVariables 29 }

    sensorName OBJECT-TYPE
    SYNTAX DisplayString (SIZE (0..255))
    MAX-ACCESS read-only
    STATUS current
    DESCRIPTION
        "Name of the probing sensor."
    ::= { trapVariables 33 }

    counterName OBJECT-TYPE
    SYNTAX DisplayString (SIZE (0..255))
    MAX-ACCESS read-only
    STATUS current
    DESCRIPTION
        "Name of the performance counter."
    ::= { trapVariables 34 }

	aspectId OBJECT-TYPE
    SYNTAX DisplayString (SIZE (0..255))
    MAX-ACCESS read-only
    STATUS current
    DESCRIPTION
        "Aspect id."
    ::= { trapVariables 35 }

	aspectPreviousStatus OBJECT-TYPE
    SYNTAX DisplayString (SIZE (0..255))
    MAX-ACCESS read-only
    STATUS current
    DESCRIPTION
        "Aspect previous status."
    ::= { trapVariables 36 }

	aspectCurrentStatus OBJECT-TYPE
    SYNTAX DisplayString (SIZE (0..255))
    MAX-ACCESS read-only
    STATUS current
    DESCRIPTION
        "Aspect current status."
    ::= { trapVariables 37 }
	
	originalOID OBJECT-TYPE
    SYNTAX DisplayString (SIZE (0..255))
    MAX-ACCESS read-only
    STATUS current
    DESCRIPTION
        "OID of the first, deduplicated event."
    ::= { trapVariables 38 }
	
	time-stamp OBJECT-TYPE
    SYNTAX DisplayString (SIZE (0..255))
    MAX-ACCESS read-only
    STATUS current
    DESCRIPTION
        "Provides the amount of time that has elapsed between the last network reinitialization and generation of the trap."
    ::= { trapVariables 39 }
	
	generic-trap OBJECT-TYPE
    SYNTAX DisplayString (SIZE (0..255))
    MAX-ACCESS read-only
    STATUS current
    DESCRIPTION
        "Indicates one of a number of generic trap types."
    ::= { trapVariables 40 }
	
	specific-trap OBJECT-TYPE
    SYNTAX DisplayString (SIZE (0..255))
    MAX-ACCESS read-only
    STATUS current
    DESCRIPTION
        "Indicates one of a number of specific trap codes."
    ::= { trapVariables 41 }
	
	snmpVersion OBJECT-TYPE
    SYNTAX DisplayString (SIZE (0..255))
    MAX-ACCESS read-only
    STATUS current
    DESCRIPTION
        "SNMP version and type of trap message."
    ::= { trapVariables 42 }

	------------------
    --  GENERAL TRAPS
    ------------------
    genSyslogEvent NOTIFICATION-TYPE
        STATUS current
        DESCRIPTION
            "Default OID assigned to syslog events generated by EventGenerator (syslog listener)."
        ::= { generalTraps 1 }

    genDiscoveredDeviceEvent NOTIFICATION-TYPE
        STATUS current
        DESCRIPTION
           "A new device has been discovered"
        ::= { generalTraps 2 }
    --------------------------
    --  EVENT PROCESSOR TRAPS
    --------------------------
    rulePairWise         OBJECT IDENTIFIER ::= { eventProcessorTraps 0 }
    ruleDeDuplication    OBJECT IDENTIFIER ::= { eventProcessorTraps 1 }
    ruleFrequency        OBJECT IDENTIFIER ::= { eventProcessorTraps 2 }
    ruleSchedMaintenance OBJECT IDENTIFIER ::= { eventProcessorTraps 3 }
	general              OBJECT IDENTIFIER ::= { eventProcessorTraps 4 }
	ruleConnectorDown    OBJECT IDENTIFIER ::= { eventProcessorTraps 5 }

    -- PAIR WISE
    rulePWUpEventPaired NOTIFICATION-TYPE
        STATUS current
        DESCRIPTION
            "Rule Pair Wise has correlated an Up Event"
        ::= { rulePairWise 0 0 }

    rulePWDownEventPaired NOTIFICATION-TYPE
        STATUS current
        DESCRIPTION
            "Rule Pair Wise has correlated an Down Event"
        ::= { rulePairWise 0 1 }

     -- DE DUPLICATION 
    ruleDDEventsCorrelated NOTIFICATION-TYPE
        STATUS current
        DESCRIPTION
            "Events have been correlated"
        ::= { ruleDeDuplication 0 2 }
		
	  -- TIME RULE
	  ruleTRDownEventsCorrelated NOTIFICATION-TYPE
		STATUS current
		DESCRIPTION
			"Events have been correlated by lower frequency"
		::= { ruleFrequency 0 3 }
	
    ruleTRUpEventsCorrelated NOTIFICATION-TYPE
		STATUS current
		DESCRIPTION
			"Events have been correlated by higher frequency"
		::= { ruleFrequency 0 4 }
		
	 -- SCHEDULED MAINTENANCE RULE
	ruleSMEventsCorrelated NOTIFICATION-TYPE
		STATUS current
		DESCRIPTION
			"Events have been correlated by schedule maintenance rule"
		::= { ruleSchedMaintenance 0 5 }
		
	 -- GENERAL
	generalActionSuccessfullyCompleted NOTIFICATION-TYPE
		STATUS current
		DESCRIPTION
			"General action successfully compeleted."
		::= { general 0 6 }
		
	generalActionFailed NOTIFICATION-TYPE
		STATUS current
		DESCRIPTION
			"General action failed."
		::= { general 0 7 }
		
	 -- CONNECTOR DOWN RULE
	ruleCDEventsCorrelated NOTIFICATION-TYPE
		STATUS current
		DESCRIPTION
			"Events have been correlated by connector down rule"
		::= { ruleConnectorDown 0 8 }


    ------------------------
    --  PROBING SENSOR TRAPS
    ------------------------   
    psThresholds         OBJECT IDENTIFIER ::= { probingTraps 1 }
    psInterfaces         OBJECT IDENTIFIER ::= { probingTraps 2 }	
    psStorages	         OBJECT IDENTIFIER ::= { probingTraps 3 }
    psProcesses			 OBJECT IDENTIFIER ::= { probingTraps 4 }
    psErrors			 OBJECT IDENTIFIER ::= { probingTraps 5 }
    psBaselines			 OBJECT IDENTIFIER ::= { probingTraps 6 }
    psIpmiEvents		 OBJECT IDENTIFIER ::= { probingTraps 7 }
    psBioStar		 OBJECT IDENTIFIER ::= { probingTraps 8 }
    psVeraxNMS		 OBJECT IDENTIFIER ::= { probingTraps 9 }
    psVirtualHost		 OBJECT IDENTIFIER ::= { probingTraps 10 }

	-- tresholds
    psWarningThresholdExceeded NOTIFICATION-TYPE
        OBJECTS { sensorId }
        STATUS current        
        DESCRIPTION
            "Warning threshold has been exceeded."
        ::= { psThresholds 0 1 }

    psCriticalThresholdExceeded NOTIFICATION-TYPE
        OBJECTS { sensorId }
        STATUS current
        DESCRIPTION
            "Critical threshold has been exceeded."
       ::= { psThresholds 0 2 }

    psTimeoutReached NOTIFICATION-TYPE
        OBJECTS { sensorId }
        STATUS current
        DESCRIPTION
            "Timeout threshold has been exceeded."
       ::= { psThresholds 0 3 }

    psThresholdAlarmClearing NOTIFICATION-TYPE
        OBJECTS { sensorId }
        STATUS current
        DESCRIPTION
            "Variable has reached alarm clearing threshold. Variable gone back to the normal level."
       ::= { psThresholds 0 4 }
       
	-- interfaces   
    psInterfaceDown NOTIFICATION-TYPE
        OBJECTS { sensorId }
        STATUS current
        DESCRIPTION
            "Interface gone down."
       ::= { psInterfaces 0 1 }
            
	  psInterfaceDisabled NOTIFICATION-TYPE
        OBJECTS { sensorId }
        STATUS current
        DESCRIPTION
            "Interface disabled."
       ::= { psInterfaces 0 2 }
       
    psInterfaceUnknown NOTIFICATION-TYPE
        OBJECTS { sensorId }
        STATUS current
        DESCRIPTION
            "Interface unknown state."
       ::= { psInterfaces 0 3 }
       
    psInterfaceAlarmCleared NOTIFICATION-TYPE
        OBJECTS { sensorId }
        STATUS current
        DESCRIPTION
            "Interface gone up."
       ::= { psInterfaces 0 4 }      

	psInterfaceReindexation NOTIFICATION-TYPE
        OBJECTS { sensorId }
        STATUS current
        DESCRIPTION
            "Interface index changed."
       ::= { psInterfaces 0 5 }
	   
	psInterfaceDiscovered NOTIFICATION-TYPE
        OBJECTS { sensorId }
        STATUS current
        DESCRIPTION
            "New interface has been discovered."
       ::= { psInterfaces 0 6 }
	   
	psInterfaceRemoved NOTIFICATION-TYPE
        OBJECTS { sensorId }
        STATUS current
        DESCRIPTION
            "Non existing interface has been removed."
       ::= { psInterfaces 0 7 }
	   
	psUnauthorizedMacAddressDetected NOTIFICATION-TYPE
        OBJECTS { sensorId }
        STATUS current
        DESCRIPTION
            "Unauthorized MAC address X detected on port Y."
       ::= { psInterfaces 0 8 }	   
	   
	-- storages
	psNewRemovableMediaAppeared NOTIFICATION-TYPE
		OBJECTS { sensorId }
		STATUS current
		DESCRIPTION
            "New removable media X appeared for device Y."
		::= { psStorages 0 1 }   
		
	psDiskPartitionDisappeared NOTIFICATION-TYPE
		OBJECTS { sensorId }
			STATUS current
			DESCRIPTION
				"Disk (partition) X disappeared for device Y."
			::= { psStorages 0 2 }

	psNewFixedDiskAppeared NOTIFICATION-TYPE
		OBJECTS { sensorId }
		STATUS current
		DESCRIPTION
            "New fixed disk X appeared for device Y."
		::= { psStorages 0 3 }   

	psRemovableMediaDisappeared NOTIFICATION-TYPE
		OBJECTS { sensorId }
		STATUS current
		DESCRIPTION
            "Removable media X disappeared for device Y."
		::= { psStorages 0 4 }   
		
	-- processes
	psProcessNotFound NOTIFICATION-TYPE
		OBJECTS { sensorId }
			STATUS current
			DESCRIPTION
				"Process X not found."
			::= { psProcesses 0 1 }


	psProcessFound NOTIFICATION-TYPE
		OBJECTS { sensorId }
			STATUS current
			DESCRIPTION
				"Process X found."
			::= { psProcesses 0 2 }

    --errors
    psReceiveExpectedResponseFailed NOTIFICATION-TYPE
        OBJECTS { sensorId }
        STATUS current
        DESCRIPTION
            "Received different response than expected."
        ::= { psErrors 0 1 }
        
    psDataAcquisitionFailed NOTIFICATION-TYPE
        OBJECTS { sensorId }
        STATUS current
        DESCRIPTION
            "Failed to acquire data from device."
        ::= { psErrors 0 2 }
        
    --baselines
    psBaselineMinimumExceeded NOTIFICATION-TYPE
        OBJECTS { sensorId }
        STATUS current
        DESCRIPTION
            "Current counter value is below the minimum baseline value."
        ::= { psBaselines 0 1 }
    
    psBaselineMaximumExceeded NOTIFICATION-TYPE
        OBJECTS { sensorId }
        STATUS current
        DESCRIPTION
            "Current counter value is over the maximum baseline value."
        ::= { psBaselines 0 2 }

    psBaselineAlarmCleared NOTIFICATION-TYPE
        OBJECTS { sensorId }
        STATUS current
        DESCRIPTION
            "Current counter value back to normal baseline range."
        ::= { psBaselines 0 3 }

	--ipmi events
	psAssertion			OBJECT IDENTIFIER ::= { psIpmiEvents 0 }
	psDeassertion		OBJECT IDENTIFIER ::= { psIpmiEvents 1 }
	
	psOk				OBJECT IDENTIFIER ::= { psAssertion 0 }
	psWarning			OBJECT IDENTIFIER ::= { psAssertion 1 }
	psError				OBJECT IDENTIFIER ::= { psAssertion 3 }
	
	psOk				OBJECT IDENTIFIER ::= { psDeassertion 0 }
	psWarning			OBJECT IDENTIFIER ::= { psDeassertion 1 }
	psError				OBJECT IDENTIFIER ::= { psDeassertion 3 }
	
	--BioStar
        psBioStarEvent NOTIFICATION-TYPE
        STATUS current
        DESCRIPTION
            "Default OID assigned to BioStar events generated by BioStarSensor."
        ::= { psBioStar 0 1 }
        
        --VeraxNms
       	psVeraxNmsEvents			OBJECT IDENTIFIER ::= { psVeraxNMS 1 }

        psConnectionFailedAlarmGenerated NOTIFICATION-TYPE
        OBJECTS { sensorId }
        STATUS current
        DESCRIPTION
            "Connection to the slave NMS failed or not authorized."
            ::= { psVeraxNmsEvents 1 }

        psConnectionFailedAlarmCleared NOTIFICATION-TYPE
        OBJECTS { sensorId }
        STATUS current
        DESCRIPTION
            "Connection to the slave NMS return to the normal state"
            ::= { psVeraxNmsEvents 2 }

        psStatusChangedAlarmGenerated NOTIFICATION-TYPE
        OBJECTS { sensorId }
        STATUS current
        DESCRIPTION
            "Status of the object has been changed."
            ::= { psVeraxNmsEvents 3 }

        psStatusChangedAlarmCleared NOTIFICATION-TYPE
        OBJECTS { sensorId }
        STATUS current
        DESCRIPTION
            "Status of the object returned to the normal state."
            ::= { psVeraxNmsEvents 4 }

        --VirtualHost
       	psVirtualHostEvents			OBJECT IDENTIFIER ::= { psVirtualHost 1 }

        psVirtualHostThresholdExceededAlarmGenerated NOTIFICATION-TYPE
        OBJECTS { sensorId }
        STATUS current
        DESCRIPTION
            "High critical threshold exceeded for host"
            ::= { psVirtualHostEvents 1 }

        psVirtualHostThresholdExceededAlarmCleared NOTIFICATION-TYPE
        OBJECTS { sensorId }
        STATUS current
        DESCRIPTION
            "High critical threshold alarm cleared for host"
            ::= { psVirtualHostEvents 2 }

        psVirtualMachineAdded NOTIFICATION-TYPE
        OBJECTS { sensorId }
        STATUS current
        DESCRIPTION
            "Virtual Machine has been added to the host"
            ::= { psVirtualHostEvents 3 }

        psVirtualMachineDeleted NOTIFICATION-TYPE
        OBJECTS { sensorId }
        STATUS current
        DESCRIPTION
            "Virtual Machine has been deleted from the host"
            ::= { psVirtualHostEvents 4 }

        psVirtualMachineThresholdExceededAlarmGenerated NOTIFICATION-TYPE
        OBJECTS { sensorId }
        STATUS current
        DESCRIPTION
            "High critical threshold exceeded for virtual machine"
            ::= { psVirtualHostEvents 5 }

        psVirtualMachineThresholdExceededAlarmCleared NOTIFICATION-TYPE
        OBJECTS { sensorId }
        STATUS current
        DESCRIPTION
            "High critical threshold alarm cleared for virtual machine"
            ::= { psVirtualHostEvents 6 }

        psVirtualMachineHalted NOTIFICATION-TYPE
        OBJECTS { sensorId }
        STATUS current
        DESCRIPTION
            "Virtual machine has been halted"
            ::= { psVirtualHostEvents 7 }

        psVirtualMachineRunning NOTIFICATION-TYPE
        OBJECTS { sensorId }
        STATUS current
        DESCRIPTION
            "Virtual machine is running"
            ::= { psVirtualHostEvents 8 }

    ------------------------------
    --  PERFORMANCE COUNTERS TRAPS
    ------------------------------
    pcThresholds         OBJECT IDENTIFIER ::= { performanceTraps 1 }
    pcInterfaces         OBJECT IDENTIFIER ::= { performanceTraps 2 }	
    
    pcWarningHighThresholdExceeded NOTIFICATION-TYPE
        OBJECTS { counterId }
        STATUS current
        DESCRIPTION
            "Warning high threshold has been exceeded."
        ::= { pcThresholds 0 1 }

    pcCriticalHighThresholdExceeded NOTIFICATION-TYPE
        OBJECTS { counterId }
        STATUS current
        DESCRIPTION
            "Critical high threshold has been exceeded."
       ::= { pcThresholds 0 2 }

    pcWarningLowThresholdDeceeded NOTIFICATION-TYPE
        OBJECTS { counterId }
        STATUS current
        DESCRIPTION
            "Warning low threshold has been deceeded."
        ::= { pcThresholds 0 3 }

    pcCriticalLowThresholdDeceeded NOTIFICATION-TYPE
        OBJECTS { counterId }
        STATUS current
        DESCRIPTION
            "Critical low threshold has been deceeded."
       ::= { pcThresholds 0 4 }

    pcThresholdAlarmClearing NOTIFICATION-TYPE
        OBJECTS { counterId }
        STATUS current
        DESCRIPTION
            "Alarm clearing threshold has been reached. Variable gone back to the normal level."
       ::= { pcThresholds 0 5 }
	   
	pcTimeoutReached NOTIFICATION-TYPE
        OBJECTS { counterId }
        STATUS current
        DESCRIPTION
            "Timeout threshold has been exceeded."
       ::= { pcThresholds 0 6 }
	   
	pcTimeoutAlarmClearing NOTIFICATION-TYPE
        OBJECTS { counterId }
        STATUS current
        DESCRIPTION
            "Response time has reached alarm clearing threshold. Variable gone back to the normal level."
       ::= { pcThresholds 0 7 }
	  
	pcAspectStatusThresholdExceeded NOTIFICATION-TYPE
        OBJECTS { aspectName, treeItemId }
        STATUS current
        DESCRIPTION
            "Aspect status changed from X to Y."
       ::= { pcThresholds 0 8 }  
	
	pcAspectStatusThresholdAlarmClearing NOTIFICATION-TYPE
        OBJECTS { aspectName, treeItemId }
        STATUS current
        DESCRIPTION
            "Aspect status changed from X to Y."
       ::= { pcThresholds 0 9 }
	   
	-- Conformance information
	cnGroups      OBJECT IDENTIFIER ::= { conformance   1 }
	cnCompliances OBJECT IDENTIFIER ::= { conformance   2 }

	-- Compliance requirement for fully compliant implementations.
	cnBasicGroup   OBJECT-GROUP
     OBJECTS {
		sensorId,
		counterId
        }

     STATUS  current
     DESCRIPTION
         "Collection of objects that are required in all
          implementations that support the MIB module."
     ::= { cnGroups 1 }

    cnNotificationGroup NOTIFICATION-GROUP
     NOTIFICATIONS {
		rulePWUpEventPaired,
		rulePWDownEventPaired,
		ruleDDEventsCorrelated,
		ruleTRUpEventsCorrelated,
		ruleTRDownEventsCorrelated,
		ruleSMEventsCorrelated,
		psWarningThresholdExceeded,
		psCriticalThresholdExceeded,
		psTimeoutReached,
		psThresholdAlarmClearing,
		psInterfaceDown,  
		psInterfaceDisabled,
		psInterfaceUnknown,
		psInterfaceAlarmCleared,
		pcWarningHighThresholdExceeded,
		pcCriticalHighThresholdExceeded,
		pcWarningLowThresholdDeceeded,
		pcCriticalLowThresholdDeceeded,
		pcThresholdAlarmClearing
        }

     STATUS  current
     DESCRIPTION
         "Collection PW notifications objects."
     ::= { cnGroups 2 }
	 
       
    END
