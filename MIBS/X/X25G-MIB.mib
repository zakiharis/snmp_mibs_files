-- MIB File Generated on 20-Nov-1995 at 09:47:32

X25G-MIB DEFINITIONS ::= BEGIN

IMPORTS
   enterprises,
   experimental,
   IpAddress,
   TimeTicks,
   Gauge,
   Counter
      FROM RFC1155-SMI
   DisplayString
      FROM RFC1213-MIB
   OBJECT-TYPE
      FROM RFC-1212;


usr OBJECT IDENTIFIER ::= { enterprises 429 }

nas OBJECT IDENTIFIER ::= { usr 1 }

x25g OBJECT IDENTIFIER ::= { nas 11 }

-- The X.25 Card Identification Group.

x25gwId OBJECT IDENTIFIER ::= { x25g 1 }

x25gwIdTable OBJECT-TYPE
SYNTAX SEQUENCE OF X25gwIdEntry
ACCESS not-accessible
STATUS mandatory
DESCRIPTION
"A table that contains information that identifies the 
hardware and software that make up the specified X.25 card."
::= { x25gwId 1 }

x25gwIdEntry OBJECT-TYPE
SYNTAX X25gwIdEntry
ACCESS not-accessible
STATUS mandatory
DESCRIPTION
"There is one entry in this table for every X.25 card in the 
chassis."
INDEX { x25gwIdIndex }
::= { x25gwIdTable 1 }

X25gwIdEntry ::=
SEQUENCE {
x25gwIdIndex
    INTEGER,
x25gwIdHardwareSerNum
    DisplayString,
x25gwIdHardwareRev
    DisplayString,
x25gwIdSoftwareRev
    DisplayString,
x25gwIdCpuType
    INTEGER,
x25gwIdRamInstalled
    INTEGER,
x25gwIdFlashInstalled
    INTEGER,
x25gwIdOperCfgSts
    INTEGER,
x25gwIdSelfTestResult
    INTEGER,
x25gwIdMgmtConnect
    INTEGER
}

x25gwIdIndex OBJECT-TYPE
SYNTAX INTEGER
ACCESS read-only
STATUS mandatory
DESCRIPTION
"An index that uniquely identifies the X.25 card for which 
this row in the table pertains.  The value of this index 
matches the value of the index for the corresponding entity 
in the entity table of the chassis MIB."
::= { x25gwIdEntry 1 }

x25gwIdHardwareSerNum OBJECT-TYPE
SYNTAX DisplayString
ACCESS read-only
STATUS mandatory
DESCRIPTION
"The X.25 card's hardware serial number as stored in 
EEPROM."
::= { x25gwIdEntry 2 }

x25gwIdHardwareRev OBJECT-TYPE
SYNTAX DisplayString
ACCESS read-only
STATUS mandatory
DESCRIPTION
"The hardware revision of the specified X.25 card as stored 
in its EEPROM."
::= { x25gwIdEntry 3 }

x25gwIdSoftwareRev OBJECT-TYPE
SYNTAX DisplayString
ACCESS read-only
STATUS mandatory
DESCRIPTION
"The revision of the software being executed in the 
specified X.25 card."
::= { x25gwIdEntry 4 }

x25gwIdCpuType OBJECT-TYPE
SYNTAX INTEGER{
  i80386(1),
  i80486(2)
}
ACCESS read-only
STATUS mandatory
DESCRIPTION
"Defines the type of CPU present on the X.25 Gateway NAC."
::= { x25gwIdEntry 5 }

x25gwIdRamInstalled OBJECT-TYPE
SYNTAX INTEGER
ACCESS read-only
STATUS mandatory
DESCRIPTION
"Specifies the amount of DRAM installed on the X.25 Gateway 
NAC in Kbytes."
::= { x25gwIdEntry 6 }

x25gwIdFlashInstalled OBJECT-TYPE
SYNTAX INTEGER
ACCESS read-only
STATUS mandatory
DESCRIPTION
"Specifies the amount of Flash Rom installed on the X.25 
Gateway NAC in Kbytes."
::= { x25gwIdEntry 7 }

x25gwIdOperCfgSts OBJECT-TYPE
SYNTAX INTEGER{
  operNvram(1),
  adminChanged(2),
  adminNvram(3)
}
ACCESS read-only
STATUS mandatory
DESCRIPTION
"Informs the operator as to whether the operational 
parameters are the NVRAM parameters or if the 
administrative parameters have been saved to NVRAM."
::= { x25gwIdEntry 8 }

x25gwIdSelfTestResult OBJECT-TYPE
SYNTAX INTEGER
ACCESS read-only
STATUS mandatory
DESCRIPTION
"Displays the results of the most resent self test performed 
by the X.25 Gateway NAC.  If all tests have passed a value 
of 0 is returned."
::= { x25gwIdEntry 9 }

x25gwIdMgmtConnect OBJECT-TYPE
SYNTAX INTEGER{
  inactive(1),
  active(2)
}
ACCESS read-only
STATUS mandatory
DESCRIPTION
"Indicates the current status of X.25 gateway user 
interface."
::= { x25gwIdEntry 10 }

-- The X.25 Card Command Group.

x25gwCmd OBJECT IDENTIFIER ::= { x25g 2 }

x25gwCmdTable OBJECT-TYPE
SYNTAX SEQUENCE OF X25gwCmdEntry
ACCESS not-accessible
STATUS mandatory
DESCRIPTION
"The X.25 Card Command table contains an entry for each of 
the manageable X.25 Cards in the chassis.  It provides a 
means through which to take specific actions on one or more 
X.25 cards in the NAS chassis.  The number of entries in 
this table is given by the value of x25gwIdNumber."
::= { x25gwCmd 1 }

x25gwCmdEntry OBJECT-TYPE
SYNTAX X25gwCmdEntry
ACCESS not-accessible
STATUS mandatory
DESCRIPTION
"There is one X.25 Card Command entry per X.25 Card in the 
chassis."
INDEX { x25gwCmdIndex }
::= { x25gwCmdTable 1 }

X25gwCmdEntry ::=
SEQUENCE {
x25gwCmdIndex
    INTEGER,
x25gwCmdMgtStationId
    OCTET STRING,
x25gwCmdReqId
    INTEGER,
x25gwCmdFunction
    INTEGER,
x25gwCmdForce
    INTEGER,
x25gwCmdParam
    OCTET STRING,
x25gwCmdResult
    INTEGER,
x25gwCmdCode
    INTEGER
}

x25gwCmdIndex OBJECT-TYPE
SYNTAX INTEGER
ACCESS read-only
STATUS mandatory
DESCRIPTION
"A unique value for each X.25 Card in the chassis.  The 
value of this object matches the value of the index of the 
corresponding X.25 Card's entry in the entity table of the 
chassis MIB."
::= { x25gwCmdEntry 1 }

x25gwCmdMgtStationId OBJECT-TYPE
SYNTAX OCTET STRING (SIZE(0..8))
ACCESS read-write
STATUS mandatory
DESCRIPTION
"This object is a generic read-write variable that a 
Management Station (MS) can use to guarantee that the 
results from a given command are the results of a command 
issued by that specific MS.  Each MS must SET a unique 
value to this object when doing commands and GET the value 
of this object together with x25gwCmdReqId and 
x25gwCmdResult to detect interference from other MSs."
::= { x25gwCmdEntry 2 }

x25gwCmdReqId OBJECT-TYPE
SYNTAX INTEGER
ACCESS read-only
STATUS mandatory
DESCRIPTION
"This object contains the value of the request-id field in 
the SNMP PDU which invoked the current or most recent 
command or test on this X.25 Card.  If the request-id is 
unknown or undefined, this object contains the value zero."
::= { x25gwCmdEntry 3 }

x25gwCmdFunction OBJECT-TYPE
SYNTAX INTEGER{
  noCommand(1),
  saveToNVRAM(2),
  restoreFromDefault(4),
  nonDisruptSelfTest(5),
  disruptSelfTest(6),
  softwareReset(7),
  downloadCfgFile(8),
  uploadCfgFile(9)
}
ACCESS read-write
STATUS mandatory
DESCRIPTION
"This object contains a value which describes the command 
which is being invoked."
::= { x25gwCmdEntry 4 }

x25gwCmdForce OBJECT-TYPE
SYNTAX INTEGER
ACCESS read-write
STATUS mandatory
DESCRIPTION
"In some cases, the X.25 Card may be in a state such that 
certain commands could adversely affect connections.  In 
such cases, a command request with this object not present 
or set to noForce will result in a warning.  If the 
operator elects to ignore such warnings, this object can be 
set to force in a subsequent issue of the command to cause 
the command to be carried out regardless of its potentially 
hazzardous effects."
::= { x25gwCmdEntry 5 }

x25gwCmdParam OBJECT-TYPE
SYNTAX OCTET STRING
ACCESS read-write
STATUS mandatory
DESCRIPTION
"This object contains parameters that are specific to the 
particular command being issued.  In some cases, there will 
be no aditional parameters required."
::= { x25gwCmdEntry 6 }

x25gwCmdResult OBJECT-TYPE
SYNTAX INTEGER{
  none(1),
  success(2),
  inProgress(3),
  notSupported(4),
  unAbleToRun(5),
  aborted(6),
  failed(7)
}
ACCESS read-only
STATUS mandatory
DESCRIPTION
"This object contains the result of the most recently 
requested command or test, or the value none(1) if no 
commands have been requested since the last reset."
::= { x25gwCmdEntry 7 }

x25gwCmdCode OBJECT-TYPE
SYNTAX INTEGER{
  noError(1),
  unable(2),
  unrecognizedCommand(6),
  slotEmpty(8),
  noResponse(12),
  unsupportedCommand(20),
  deviceDisabled(22),
  fileTooBig(46),
  userInterfaceActive(58),
  badFlashRomID(61),
  badFlashVoltage(62),
  flashEraseError(63),
  eraseSequenceError(64),
  eraseExecutionError(65),
  receiveBufferOverflow(66),
  badProgramVoltage(68),
  programmingDataError(69),
  programCodeError(70),
  invalidCodeError(71),
  romCrcBad(72),
  pendingSoftwareDownload(73),
  ramCrcBad(74),
  invalidRomId(75),
  cardIdMismatch(84),
  cardIdUnknown(85),
  tftpTimeout(86),
  flashEraseTimeout(87),
  invalidFileHeader(88),
  bulkTransferInProcess(93)
}
ACCESS read-only
STATUS mandatory
DESCRIPTION
"The Value of this object is value of this object is 
noError(1) if the command was successful, and indicates a 
further description of what went wrong if it was 
unsuccessful."
::= { x25gwCmdEntry 8 }

-- The X.25 Card Configuration Group.

x25gwCfg OBJECT IDENTIFIER ::= { x25g 3 }

x25gwCfgTable OBJECT-TYPE
SYNTAX SEQUENCE OF X25gwCfgEntry
ACCESS not-accessible
STATUS mandatory
DESCRIPTION
"A table of configurable parameters specific to the X.25 
Gateway NAC."
::= { x25gwCfg 1 }

x25gwCfgEntry OBJECT-TYPE
SYNTAX X25gwCfgEntry
ACCESS not-accessible
STATUS mandatory
DESCRIPTION
""
INDEX { x25gwCfgIndex }
::= { x25gwCfgTable 1 }

X25gwCfgEntry ::=
SEQUENCE {
x25gwCfgIndex
    INTEGER,
x25gwCfgUiPort
    INTEGER,
x25gwCfgLocModemConn
    INTEGER,
x25gwCfgRoutingType
    INTEGER,
x25gwCfgCudRoutStr
    DisplayString,
x25gwCfgX121SubAddr
    INTEGER,
x25gwCfgSysDate
    DisplayString,
x25gwCfgSysTime
    DisplayString
}

x25gwCfgIndex OBJECT-TYPE
SYNTAX INTEGER
ACCESS read-only
STATUS mandatory
DESCRIPTION
"A unique value for each X.25 NAC installed in the chassis.  
The value of this index is identical to the index in the 
USR chassis MIB associates with the X.25 Gateway Card 
entity."
::= { x25gwCfgEntry 1 }

x25gwCfgUiPort OBJECT-TYPE
SYNTAX INTEGER{
  normal(1),
  padAccess(2)
}
ACCESS read-only
STATUS mandatory
DESCRIPTION
"Defines how the user interface port on the X.25 NIC will be 
used.  When configured for PAD access the UI port will 
provide a means of accessing the X.25 network via a direct 
connected serial device."
::= { x25gwCfgEntry 2 }

x25gwCfgLocModemConn OBJECT-TYPE
SYNTAX INTEGER{
  direct(1),
  dial(2)
}
ACCESS read-write
STATUS mandatory
DESCRIPTION
"Defines whether the gateway UI access will be via direct 
attachment or by Dial up Modem."
::= { x25gwCfgEntry 3 }

x25gwCfgRoutingType OBJECT-TYPE
SYNTAX INTEGER{
  none(1),
  subAddr(2),
  callUserData(3),
  both(4),
  managmentOnly(5)
}
ACCESS read-write
STATUS mandatory
DESCRIPTION
"Determines the means by which X.25 call will be routed to 
the NMC or modem. Default=None(1)."
::= { x25gwCfgEntry 4 }

x25gwCfgCudRoutStr OBJECT-TYPE
SYNTAX DisplayString (SIZE(0..12))
ACCESS read-write
STATUS mandatory
DESCRIPTION
"Call user data string is used to compare to the incoming 
X.25 call request CUD. If they match then the call is 
routed to the NMC. 
Default=MGMTOVX25. "

::= { x25gwCfgEntry 5 }

x25gwCfgX121SubAddr OBJECT-TYPE
SYNTAX INTEGER (0..99)
ACCESS read-write
STATUS mandatory
DESCRIPTION
"X.121 Subaddress is used to compare to the incoming X.25 
call request Subaddress. If they match then the call is 
routed to the NMC. Default=99."
::= { x25gwCfgEntry 6 }

x25gwCfgSysDate OBJECT-TYPE
SYNTAX DisplayString (SIZE(5..8))
ACCESS read-write
STATUS mandatory
DESCRIPTION
"X.25 gateway system date.  Default = 01-01-95."
::= { x25gwCfgEntry 7 }

x25gwCfgSysTime OBJECT-TYPE
SYNTAX DisplayString (SIZE(5..8))
ACCESS read-write
STATUS mandatory
DESCRIPTION
"X.25 gateway system time.  Default = 00:00:00."
::= { x25gwCfgEntry 8 }

-- The X.25 Trap Enable Group.

x25gwTrapEna OBJECT IDENTIFIER ::= { x25g 4 }

x25gwTrapEnaTable OBJECT-TYPE
SYNTAX SEQUENCE OF X25gwTrapEnaEntry
ACCESS not-accessible
STATUS mandatory
DESCRIPTION
"Table containing objects to enable traps on the X.25 Cards 
in the chassis."
::= { x25gwTrapEna 1 }

x25gwTrapEnaEntry OBJECT-TYPE
SYNTAX X25gwTrapEnaEntry
ACCESS not-accessible
STATUS mandatory
DESCRIPTION
"There is one entry for each X.25 Card in the chassis."
INDEX { x25gwTrapEnaIndex }
::= { x25gwTrapEnaTable 1 }

X25gwTrapEnaEntry ::=
SEQUENCE {
x25gwTrapEnaIndex
    INTEGER,
x25gwTrapEnaUiReset
    INTEGER
}

x25gwTrapEnaIndex OBJECT-TYPE
SYNTAX INTEGER
ACCESS read-only
STATUS mandatory
DESCRIPTION
"A unique index identifying the X.25 Card to which the trap 
enable objects pertain."
::= { x25gwTrapEnaEntry 1 }

x25gwTrapEnaUiReset OBJECT-TYPE
SYNTAX INTEGER{
  enable(1),
  disable(2)
}
ACCESS read-write
STATUS mandatory
DESCRIPTION
"Enables reporting of NAC Reset by user interface command 
traps. Default=disable(2)."
::= { x25gwTrapEnaEntry 2 }

END
