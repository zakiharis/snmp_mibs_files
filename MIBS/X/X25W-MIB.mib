-- MIB File Generated on 31-Oct-1995 at 13:59:17

X25W-MIB DEFINITIONS ::= BEGIN

IMPORTS
   enterprises,
   experimental,
   IpAddress,
   TimeTicks,
   Gauge,
   Counter
      FROM RFC1155-SMI
   DisplayString
      FROM RFC1213-MIB
   OBJECT-TYPE
      FROM RFC-1212;


usr OBJECT IDENTIFIER ::= { enterprises 429 }

nas OBJECT IDENTIFIER ::= { usr 1 }

x25w OBJECT IDENTIFIER ::= { nas 8 }

x25wanAdmn OBJECT IDENTIFIER ::= { x25w 1 }

x25wanAdmnTable OBJECT-TYPE
SYNTAX SEQUENCE OF X25wanAdmnEntry
ACCESS not-accessible
STATUS mandatory
DESCRIPTION
"The x25 WAN Admn table contains an entry for each 
manageable X.25 Subnet in the chassis.  It provides a means 
to configure serial interface associated with the subnet."
::= { x25wanAdmn 1 }

x25wanAdmnEntry OBJECT-TYPE
SYNTAX X25wanAdmnEntry
ACCESS not-accessible
STATUS mandatory
DESCRIPTION
"There is one x25 WAN Cfg entry per x.25 subnet in the NAS 
chassis."
INDEX { x25wanAdmnIndex }
::= { x25wanAdmnTable 1 }

X25wanAdmnEntry ::=
SEQUENCE {
x25wanAdmnIndex
    INTEGER,
x25wanAdmnType
    INTEGER,
x25wanAdmnSpeed
    INTEGER,
x25wanAdmnLinkAvailable
    INTEGER,
x25wanAdmnClockSouce
    INTEGER,
x25wanAdmnMaxFrmSize
    INTEGER
}

x25wanAdmnIndex OBJECT-TYPE
SYNTAX INTEGER
ACCESS read-only
STATUS mandatory
DESCRIPTION
"A unique value for each X.25 Subnet in the chassis.  The 
value of this object matches the value of the index of the 
corresponding X.25 Subnet's entry in the entity table of 
the chassis MIB."
::= { x25wanAdmnEntry 1 }

x25wanAdmnType OBJECT-TYPE
SYNTAX INTEGER{
  rs232(1),
  v35(2)
}
ACCESS read-write
STATUS mandatory
DESCRIPTION
"Defines which physical serial interface type is 
implemented."
::= { x25wanAdmnEntry 2 }

x25wanAdmnSpeed OBJECT-TYPE
SYNTAX INTEGER (0..393216)
ACCESS read-write
STATUS mandatory
DESCRIPTION
"Defines the serial port speed used in applications where 
the Gateway NAC generates a clock.  This object will not 
effect the clock speed when the host provides the clock 
source. Default=57600."

::= { x25wanAdmnEntry 3 }

x25wanAdmnLinkAvailable OBJECT-TYPE
SYNTAX INTEGER{
  dsr(1),
  dcd(2)
}
ACCESS read-write
STATUS mandatory
DESCRIPTION
"Defines whether the WAN interface looks at DCD rather than 
DSR to determine that the physical layer is active."
::= { x25wanAdmnEntry 4 }

x25wanAdmnClockSouce OBJECT-TYPE
SYNTAX INTEGER{
  dceRxTx(1),
  dceRxOnly(2),
  brgRxTx(3)
}
ACCESS read-write
STATUS mandatory
DESCRIPTION
"Determines the source of the synchronous data clock."
::= { x25wanAdmnEntry 5 }

x25wanAdmnMaxFrmSize OBJECT-TYPE
SYNTAX INTEGER (0..519)
ACCESS read-write
STATUS mandatory
DESCRIPTION
"Determines the maximum received frame size allowed on the 
X.25 WAN. Default=300."
::= { x25wanAdmnEntry 6 }

x25wanOper OBJECT IDENTIFIER ::= { x25w 2 }

x25wanOperTable OBJECT-TYPE
SYNTAX SEQUENCE OF X25wanOperEntry
ACCESS not-accessible
STATUS mandatory
DESCRIPTION
""
::= { x25wanOper 1 }

x25wanOperEntry OBJECT-TYPE
SYNTAX X25wanOperEntry
ACCESS not-accessible
STATUS mandatory
DESCRIPTION
""
INDEX { x25wanOperIndex }
::= { x25wanOperTable 1 }

X25wanOperEntry ::=
SEQUENCE {
x25wanOperIndex
    INTEGER,
x25wanOperType
    INTEGER,
x25wanOperSpeed
    INTEGER,
x25wanOperLinkAvailable
    INTEGER,
x25wanOperClockSource
    INTEGER,
x25wanOperMaxFrmSize
    INTEGER
}

x25wanOperIndex OBJECT-TYPE
SYNTAX INTEGER
ACCESS read-only
STATUS mandatory
DESCRIPTION
""
::= { x25wanOperEntry 1 }

x25wanOperType OBJECT-TYPE
SYNTAX INTEGER{
  rs232(1),
  v35(2)
}
ACCESS read-only
STATUS mandatory
DESCRIPTION
""
::= { x25wanOperEntry 2 }

x25wanOperSpeed OBJECT-TYPE
SYNTAX INTEGER (0..393216)
ACCESS read-only
STATUS mandatory
DESCRIPTION
""
::= { x25wanOperEntry 3 }

x25wanOperLinkAvailable OBJECT-TYPE
SYNTAX INTEGER{
  dsr(1),
  dcd(2)
}
ACCESS read-only
STATUS mandatory
DESCRIPTION
""
::= { x25wanOperEntry 4 }

x25wanOperClockSource OBJECT-TYPE
SYNTAX INTEGER{
  dceRxTx(1),
  dceRxOnly(2),
  brgRxTx(3)
}
ACCESS read-only
STATUS mandatory
DESCRIPTION
""
::= { x25wanOperEntry 5 }

x25wanOperMaxFrmSize OBJECT-TYPE
SYNTAX INTEGER (0..519)
ACCESS read-only
STATUS mandatory
DESCRIPTION
""
::= { x25wanOperEntry 6 }

-- The X.25 WAN Statistics Group.

x25wanStats OBJECT IDENTIFIER ::= { x25w 3 }

x25wanStatsTable OBJECT-TYPE
SYNTAX SEQUENCE OF X25wanStatsEntry
ACCESS not-accessible
STATUS mandatory
DESCRIPTION
"The x25wanStatsTable is composed of counters which allow 
the operator to view activity which can indicate the health 
of the WAN connection."
::= { x25wanStats 1 }

x25wanStatsEntry OBJECT-TYPE
SYNTAX X25wanStatsEntry
ACCESS not-accessible
STATUS mandatory
DESCRIPTION
"There is one X.25 WAN status entry for each x.25 subnet 
installed in the NAS chassis."
INDEX { x25wanStatsIndex }
::= { x25wanStatsTable 1 }

X25wanStatsEntry ::=
SEQUENCE {
x25wanStatsIndex
    INTEGER,
x25wanStatsGoodFramesTxs
    Counter,
x25wanStatsGoodFramesRxs
    Counter,
x25wanStatsTxUnderruns
    Counter,
x25wanStatsRxOverruns
    Counter,
x25wanStatsRxCrcErrs
    Counter,
x25wanStatsRxFrameNoBufs
    Counter,
x25wanStatsUnrecoveredRxs
    Counter,
x25wanStatsRxOverflows
    Counter,
x25wanStatsRxAborts
    Counter,
x25wanStatsRxTooLongs
    Counter,
x25wanStatsTxTooShorts
    Counter,
x25wanStatsRxTooShorts
    Counter,
x25wanStatsTxBadPackets
    Counter,
x25wanStatsTxRingQFulls
    Counter,
x25wanStatsRxRingQSize
    INTEGER,
x25wanStatsDSR
    INTEGER,
x25wanStatsCTS
    INTEGER,
x25wanStatsDCD
    INTEGER
}

x25wanStatsIndex OBJECT-TYPE
SYNTAX INTEGER
ACCESS read-only
STATUS mandatory
DESCRIPTION
"A unique value for each X25 WAN port in the NAS chassis.  
The value of this index matches is the entity index 
associated with this X25 subnet found in the USR Chassis 
MIB."
::= { x25wanStatsEntry 1 }

x25wanStatsGoodFramesTxs OBJECT-TYPE
SYNTAX Counter
ACCESS read-only
STATUS mandatory
DESCRIPTION
"A count of the number of good frames transmitted since this 
entity was initialized."
::= { x25wanStatsEntry 2 }

x25wanStatsGoodFramesRxs OBJECT-TYPE
SYNTAX Counter
ACCESS read-only
STATUS mandatory
DESCRIPTION
"A count of the good frames received since this entity was 
intitalized."
::= { x25wanStatsEntry 3 }

x25wanStatsTxUnderruns OBJECT-TYPE
SYNTAX Counter
ACCESS read-only
STATUS mandatory
DESCRIPTION
"A count of the number of transmit underruns that have been 
seen by this entity since initialization."
::= { x25wanStatsEntry 4 }

x25wanStatsRxOverruns OBJECT-TYPE
SYNTAX Counter
ACCESS read-only
STATUS mandatory
DESCRIPTION
"The number of receiver overruns detected by this entity 
since intitialization."
::= { x25wanStatsEntry 5 }

x25wanStatsRxCrcErrs OBJECT-TYPE
SYNTAX Counter
ACCESS read-only
STATUS mandatory
DESCRIPTION
"The number of received crc errors since this entity was 
intitialized."
::= { x25wanStatsEntry 6 }

x25wanStatsRxFrameNoBufs OBJECT-TYPE
SYNTAX Counter
ACCESS read-only
STATUS mandatory
DESCRIPTION
"The number of times this entity has recieved data without a 
buffer to place it into."
::= { x25wanStatsEntry 7 }

x25wanStatsUnrecoveredRxs OBJECT-TYPE
SYNTAX Counter
ACCESS read-only
STATUS mandatory
DESCRIPTION
"The number of overrun frames that the entity was unable to 
recover."
::= { x25wanStatsEntry 8 }

x25wanStatsRxOverflows OBJECT-TYPE
SYNTAX Counter
ACCESS read-only
STATUS mandatory
DESCRIPTION
"The number of receive buffer overflows seen by this entity 
since initialization."
::= { x25wanStatsEntry 9 }

x25wanStatsRxAborts OBJECT-TYPE
SYNTAX Counter
ACCESS read-only
STATUS mandatory
DESCRIPTION
"The number of recieve frame aborts seen by this entity 
since initialization."
::= { x25wanStatsEntry 10 }

x25wanStatsRxTooLongs OBJECT-TYPE
SYNTAX Counter
ACCESS read-only
STATUS mandatory
DESCRIPTION
"The number of frames recieved that exceeded the defined 
maximum receive frame size."
::= { x25wanStatsEntry 11 }

x25wanStatsTxTooShorts OBJECT-TYPE
SYNTAX Counter
ACCESS read-only
STATUS mandatory
DESCRIPTION
"The number of times that the upper protocol layers 
attempted to transmit too small a frame."
::= { x25wanStatsEntry 12 }

x25wanStatsRxTooShorts OBJECT-TYPE
SYNTAX Counter
ACCESS read-only
STATUS mandatory
DESCRIPTION
"A count of the number of frames received that were smaller 
than the minimum frame size."

::= { x25wanStatsEntry 13 }

x25wanStatsTxBadPackets OBJECT-TYPE
SYNTAX Counter
ACCESS read-only
STATUS mandatory
DESCRIPTION
"The number of bad packets that the WAN interface received 
for transmission from the upper layers of the X.25 protocol 
stack."
::= { x25wanStatsEntry 14 }

x25wanStatsTxRingQFulls OBJECT-TYPE
SYNTAX Counter
ACCESS read-only
STATUS mandatory
DESCRIPTION
"A count of the number of times the circular buffer used for 
transmission was full when a transmission was attempted by 
the upper layers of the X.25 protocol stack."
::= { x25wanStatsEntry 15 }

x25wanStatsRxRingQSize OBJECT-TYPE
SYNTAX INTEGER
ACCESS read-only
STATUS mandatory
DESCRIPTION
"A number that indicates the received circular queue size on 
the X.25 WAN."
::= { x25wanStatsEntry 16 }

x25wanStatsDSR OBJECT-TYPE
SYNTAX INTEGER{
  off(1),
  on(2)
}
ACCESS read-only
STATUS mandatory
DESCRIPTION
"X.25 WAN interface DSR signal status."
::= { x25wanStatsEntry 17 }

x25wanStatsCTS OBJECT-TYPE
SYNTAX INTEGER{
  off(1),
  on(2)
}
ACCESS read-only
STATUS mandatory
DESCRIPTION
"X.25 WAN interface CTS signal status."
::= { x25wanStatsEntry 18 }

x25wanStatsDCD OBJECT-TYPE
SYNTAX INTEGER{
  off(1),
  on(2)
}
ACCESS read-only
STATUS mandatory
DESCRIPTION
"X.25 WAN interface DCD signal status."
::= { x25wanStatsEntry 19 }

x25wanTrapEna OBJECT IDENTIFIER ::= { x25w 4 }

x25wanTrapEnaTable OBJECT-TYPE
SYNTAX SEQUENCE OF X25wanTrapEnaEntry
ACCESS not-accessible
STATUS mandatory
DESCRIPTION
"The x25 WAN Trap Enable table contains an entry for each 
manageable X.25 Subnet in the chassis.  It provides a means 
to enable reporting of traps associated with the subnet."
::= { x25wanTrapEna 1 }

x25wanTrapEnaEntry OBJECT-TYPE
SYNTAX X25wanTrapEnaEntry
ACCESS not-accessible
STATUS mandatory
DESCRIPTION
"There is one x25 WAN Cfg entry per x.25 subnet in the NAS 
chassis."
INDEX { x25wanTrapEnaIndex }
::= { x25wanTrapEnaTable 1 }

X25wanTrapEnaEntry ::=
SEQUENCE {
x25wanTrapEnaIndex
    INTEGER,
x25wanTrapEnaOutOfSvc
    INTEGER,
x25wanTrapEnaLinkActive
    INTEGER
}

x25wanTrapEnaIndex OBJECT-TYPE
SYNTAX INTEGER
ACCESS read-only
STATUS mandatory
DESCRIPTION
"A unique value for each X.25 Subnet in the chassis.  The 
value of this object matches the value of the index of the 
corresponding X.25 Subnet's entry in the entity table of 
the chassis MIB."
::= { x25wanTrapEnaEntry 1 }

x25wanTrapEnaOutOfSvc OBJECT-TYPE
SYNTAX INTEGER{
  enable(1),
  disable(2)
}
ACCESS read-write
STATUS mandatory
DESCRIPTION
"Enables generation of a trap when the WAN port status 
changes from Link Active to Out Of Service."
::= { x25wanTrapEnaEntry 2 }

x25wanTrapEnaLinkActive OBJECT-TYPE
SYNTAX INTEGER{
  enable(1),
  disable(2)
}
ACCESS read-write
STATUS mandatory
DESCRIPTION
"Enables generation of a trap when the WAN port status 
changes from Out Of Service to Link Active."
::= { x25wanTrapEnaEntry 3 }

END
