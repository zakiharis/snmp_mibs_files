--
-- zyxel-zywallidp10.mib version 1.00 2005/05/30
--
--
-- Protected as an unpublished work.
-- Private Enterprise MIB definition

ZYXEL-ZYWALLIDP10-MIB DEFINITIONS ::= BEGIN

    IMPORTS
	OBJECT-TYPE 
		FROM RFC-1212	
	DisplayString 
	  	FROM RFC1213-MIB	  	
	zywallidp10
		FROM ZYXEL-MIB;


	-- ZyWALL common managed objects
	zywallIDP10System			OBJECT IDENTIFIER ::= { zywallidp10 1 }
	zywallIDP10Network			OBJECT IDENTIFIER ::= { zywallidp10 2 }
	
	networkInterfaceLinkStatus		OBJECT IDENTIFIER ::= { zywallIDP10Network 1 }
	networkMTUSize				OBJECT IDENTIFIER ::= { zywallIDP10Network 2 }
	networkTraffic				OBJECT IDENTIFIER ::= { zywallIDP10Network 3 }
	networkInterfaceUtilization		OBJECT IDENTIFIER ::= { zywallIDP10Network 4 }
	networkPacketStatistic			OBJECT IDENTIFIER ::= { zywallIDP10Network 5 }
		

	-- The system group
	
	sysFirmwareVersion OBJECT-TYPE
		SYNTAX  DisplayString
		ACCESS  read-only
		STATUS  mandatory
		DESCRIPTION
			"This is the firmware version number."
		::= { zywallIDP10System 1 }
	
	sysPolicyVersion OBJECT-TYPE
		SYNTAX  DisplayString
		ACCESS  read-only
		STATUS  mandatory
		DESCRIPTION
			"Show the intrusion signature set version number.
			DisplayString = Major + . + Minor, ex: 2.88"
		::= { zywallIDP10System 2 }
	
	sysCPUUsage OBJECT-TYPE
		SYNTAX  INTEGER
		ACCESS  read-only
		STATUS  mandatory
		DESCRIPTION
			"Show device CPU load in %, it's the snapshot of CPU load when 
			getting the values."
		::= { zywallIDP10System 3 }

	sysFlashUsage OBJECT-TYPE
		SYNTAX  INTEGER
		ACCESS  read-only
		STATUS  mandatory
		DESCRIPTION
			"Show device flash load in %, it's the snapshot of the flash load 
			when getting the value."
		::= { zywallIDP10System 4 }

	sysRAMUsage OBJECT-TYPE
		SYNTAX  INTEGER
		ACCESS  read-only
		STATUS  mandatory
		DESCRIPTION
			"Show device RAM load in %, it's the snapshot of RAM load when 
			getting the values."
		::= { zywallIDP10System 5 }
	
	sysTCPSession OBJECT-TYPE
		SYNTAX  INTEGER
		ACCESS  read-only
		STATUS  mandatory
		DESCRIPTION
			"Show number of TCP sessions currently established"
		::= { zywallIDP10System 6 }
	
	sysPolicyNumber OBJECT-TYPE
		SYNTAX  INTEGER
		ACCESS  read-only
		STATUS  mandatory
		DESCRIPTION
			"Show the number of signature, rules, for the displayed policy version."
		::= { zywallIDP10System 7 }
	
	sysState OBJECT-TYPE
		SYNTAX  DisplayString
		ACCESS  read-only
		STATUS  mandatory
		DESCRIPTION
			"Show whether the ZyWALL is Inline (configure an action 
			for  suspicious packets), Monitor (send out alerts only for suspicious packets)
			 or Bypass (all traffic can pass through the ZyWALL without inspection)."
		::= { zywallIDP10System 8 }
	
	sysRegistrationStatus OBJECT-TYPE
		SYNTAX  DisplayString
		ACCESS  read-only
		STATUS  mandatory
		DESCRIPTION
			"Show Registration Status."
		::= { zywallIDP10System 9 }     
	
	sysAttackNumbers OBJECT-TYPE
		SYNTAX  INTEGER
		ACCESS  read-only
		STATUS  mandatory
		DESCRIPTION
			"Counter for attacks."
		::= { zywallIDP10System 10 }
	
	sysWarningNumbers OBJECT-TYPE
		SYNTAX  INTEGER
		ACCESS  read-only
		STATUS  mandatory
		DESCRIPTION
			"Counter for warnigns."
		::= { zywallIDP10System 11 }
	
	-- The Network group
	-- networkInterfaceLinkStatus Group
	linkStatusWANPort OBJECT-TYPE
		SYNTAX  DisplayString
		ACCESS  read-only
		STATUS  mandatory
		DESCRIPTION
			"Show link-status for WAN port."
		::= { networkInterfaceLinkStatus 1 }
		
	linkStatusLANPort OBJECT-TYPE
		SYNTAX  DisplayString
		ACCESS  read-only
		STATUS  mandatory
		DESCRIPTION
			"Show link-status for LAN port."
		::= { networkInterfaceLinkStatus 2 }
	
	linkStatusMGMTPort OBJECT-TYPE
		SYNTAX  DisplayString
		ACCESS  read-only
		STATUS  mandatory
		DESCRIPTION
			"Show link-status for MGMT port."
		::= { networkInterfaceLinkStatus 3 }
	
	-- The Network group
	-- networkMTUSize Group
	mtuSizeWANPort OBJECT-TYPE
		SYNTAX  INTEGER
		ACCESS  read-only
		STATUS  mandatory
		DESCRIPTION
			"Show MTU size for WAN port."
		::= { networkMTUSize 1 }
	
	mtuSizeLANPort OBJECT-TYPE
		SYNTAX  INTEGER
		ACCESS  read-only
		STATUS  mandatory
		DESCRIPTION
			"Show MTU size for LAN port."
		::= { networkMTUSize 2 }
	
	mtuSizeMGMTPort OBJECT-TYPE
		SYNTAX  INTEGER
		ACCESS  read-only
		STATUS  mandatory
		DESCRIPTION
			"Show MTU size for MGMT port."
		::= { networkMTUSize 3 }
	
	-- The Network group
	-- networkTraffic Group
	trafficWANPortIn OBJECT-TYPE
		SYNTAX  INTEGER
		ACCESS  read-only
		STATUS  mandatory
		DESCRIPTION
			"Current traffic in for WAN port."
		::= { networkTraffic 1 }
	
	trafficWANPortOut OBJECT-TYPE
		SYNTAX  INTEGER
		ACCESS  read-only
		STATUS  mandatory
		DESCRIPTION
			"Current traffic out for WAN port."
		::= { networkTraffic 2 }
	
	trafficLANPortIn OBJECT-TYPE
		SYNTAX  INTEGER
		ACCESS  read-only
		STATUS  mandatory
		DESCRIPTION
			"Current traffic in for LAN port."
		::= { networkTraffic 3 }
	
	trafficLANPortOut OBJECT-TYPE
		SYNTAX  INTEGER
		ACCESS  read-only
		STATUS  mandatory
		DESCRIPTION
			"Current traffic out for LAN port."
		::= { networkTraffic 4 }
	
	trafficMGMTPortIn OBJECT-TYPE
		SYNTAX  INTEGER
		ACCESS  read-only
		STATUS  mandatory
		DESCRIPTION
			"Current traffic in for MGMT port."
		::= { networkTraffic 5 }
	
	trafficMGMTPortOut OBJECT-TYPE
		SYNTAX  INTEGER
		ACCESS  read-only
		STATUS  mandatory
		DESCRIPTION
			"Current traffic out for MGMT port."
		::= { networkTraffic 6 }
	
	-- The Network group
	-- networkInterfaceUtilization Group
	intUtilizationWANPort OBJECT-TYPE
		SYNTAX  INTEGER
		ACCESS  read-only
		STATUS  mandatory
		DESCRIPTION
			"Current WAN port utilization."
		::= { networkInterfaceUtilization 1 }
	
	intUtilizationLANPort OBJECT-TYPE
		SYNTAX  INTEGER
		ACCESS  read-only
		STATUS  mandatory
		DESCRIPTION
			"Current LAN port utilization."
		::= { networkInterfaceUtilization 2 }
	
	intUtilizationMGMTPort OBJECT-TYPE
		SYNTAX  INTEGER
		ACCESS  read-only
		STATUS  mandatory
		DESCRIPTION
			"Current MGMT port utilization."
		::= { networkInterfaceUtilization 3 }
	
	-- The Network group
	-- networkPacketStatistic Group
	packetDroppedWANPort OBJECT-TYPE
		SYNTAX  INTEGER
		ACCESS  read-only
		STATUS  mandatory
		DESCRIPTION
			"Counter for WAN port about dropped packets."
		::= { networkPacketStatistic 1 }
	
	packetBlockedWANPort OBJECT-TYPE
		SYNTAX  INTEGER
		ACCESS  read-only
		STATUS  mandatory
		DESCRIPTION
			"Counter for WAN port about blocked packets."
		::= { networkPacketStatistic 2 }
	
	packetForwardedWANPort OBJECT-TYPE
		SYNTAX  INTEGER
		ACCESS  read-only
		STATUS  mandatory
		DESCRIPTION
			"Counter for WAN port about forwarded packets."
		::= { networkPacketStatistic 3 }
	
	packetDroppedLANPort OBJECT-TYPE
		SYNTAX  INTEGER
		ACCESS  read-only
		STATUS  mandatory
		DESCRIPTION
			"Counter for LAN port about dropped packets."
		::= { networkPacketStatistic 4 }
	
	packetBlockedLANPort OBJECT-TYPE
		SYNTAX  INTEGER
		ACCESS  read-only
		STATUS  mandatory
		DESCRIPTION
			"Counter for LAN port about blocked packets."
		::= { networkPacketStatistic 5 }
	
	packetForwardedLANPort OBJECT-TYPE
		SYNTAX  INTEGER
		ACCESS  read-only
		STATUS  mandatory
		DESCRIPTION
			"Counter for LAN port about forwarded packets."
		::= { networkPacketStatistic 6 }
	
			
END
