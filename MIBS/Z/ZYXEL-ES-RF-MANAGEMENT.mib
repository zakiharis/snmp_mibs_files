-- **********************************************
-- ZyXEL Communications Corporation
--
-- Enterprise Solution MIB definitions
-- RF MANAGEMENT MIBs
--
-- Copyright by ZyXEL Communications Corp.
-- All rights reserved.
-- **********************************************

ZYXEL-ES-RF-MANAGEMENT DEFINITIONS ::= BEGIN

IMPORTS

	MODULE-IDENTITY,
	OBJECT-IDENTITY,
	OBJECT-TYPE			FROM SNMPv2-SMI

	OBJECT-GROUP,
	MODULE-COMPLIANCE	FROM SNMPv2-CONF

	esMgmt				FROM ZYXEL-ES-SMI;


--
-- Node: esRFMgmt
--

esRFMgmt MODULE-IDENTITY
	LAST-UPDATED		"201009200000Z"
	ORGANIZATION	"Enterprise Solution ZyXEL"
	CONTACT-INFO		""
	DESCRIPTION
		"The sub tree for RF management information"
	::= { esMgmt 6 }
                       
                       
                       
rfMgmtConfig		OBJECT-IDENTITY
	STATUS		current
	DESCRIPTION
		"The subtree for CAPWAP"
	::= { esRFMgmt 1 }

rfMgmtInfo			OBJECT-IDENTITY
	STATUS		current
	DESCRIPTION
		"The subtree for CAPWAP"
	::= { esRFMgmt 2 }


                       
rfMgmtDCS OBJECT-TYPE
	SYNTAX INTEGER {
		enable(1),
		disable(2)
	}
	MAX-ACCESS  read-write
	STATUS      current
	DESCRIPTION
		"Enable/disable Wireless Dynamic Channel Selection."
	::= { rfMgmtConfig 1 }  
	
rfMgmtUnClassAP OBJECT-TYPE
	SYNTAX	  INTEGER
	MAX-ACCESS  read-only
	STATUS	current
	DESCRIPTION
		"Total Un-Classified APs."
	::= { rfMgmtInfo 1 }


rfMgmtRogueAP OBJECT-TYPE
	SYNTAX	  INTEGER
	MAX-ACCESS  read-only
	STATUS	current
	DESCRIPTION
		"Total Rogue APs."
	::= { rfMgmtInfo 2 }


rfMgmtFriendlyAP OBJECT-TYPE
	SYNTAX	  INTEGER
	MAX-ACCESS  read-only
	STATUS	current
	DESCRIPTION
		"Total Friendly APs."
	::= { rfMgmtInfo 3 }
                              
END
