-- **********************************************
-- ZyXEL Communications Corporation
--
-- Enterprise Solution MIB definitions
-- ProWLAN MIBs
--
-- Vincent Liu
--
-- Copyright by ZyXEL Communications Corp.
-- All rights reserved.
-- **********************************************

ZYXEL-ES-Outsourcing DEFINITIONS ::= BEGIN

IMPORTS

	MODULE-IDENTITY,
	OBJECT-IDENTITY,
	OBJECT-TYPE		FROM SNMPv2-SMI

	OBJECT-GROUP,
	MODULE-COMPLIANCE	FROM SNMPv2-CONF

	DisplayString, MacAddress, DateAndTime	FROM SNMPv2-TC

	esProductSpecific			FROM ZYXEL-ES-SMI;

--
-- Node: esOutsourcing
-- includes wireless, deviceTraps
--

esOutsourcing MODULE-IDENTITY
	LAST-UPDATED	"201012120000Z"
	ORGANIZATION "Enterprise Solution ZyXEL"
	CONTACT-INFO
		""
	DESCRIPTION
		"The subtree for Outsourcing product line"
	::= { esProductSpecific 2 }

--
-- Node: wireless
-- includes wlanRadioTable, wlanSecurityControl, wlanStatistics
--

  wireless   OBJECT-IDENTITY
		STATUS	current
		DESCRIPTION
			"Read/Write Wlan UI Setting"
	::= { esOutsourcing 1 }

  wlanRadioTable    OBJECT-IDENTITY
		STATUS	current
		DESCRIPTION
			"Read/Write Wlan Radio Setting"
	::= { wireless 1 }

	wlanESSID  OBJECT-TYPE
		SYNTAX	  OCTET STRING (SIZE (0..32))
		MAX-ACCESS  read-write
		STATUS	current
		DESCRIPTION
			"Controls for wireless ESSID"
	::= { wlanRadioTable	1 }

	wlanChannel  OBJECT-TYPE
		SYNTAX	  INTEGER {
 			device-is-disable(0),
 			channel-01-2412mhz(1),
 			channel-02-2417mhz(2),
 			channel-03-2422mhz(3),
 			channel-04-2427mhz(4),
			channel-05-2432mhz(5),
			channel-06-2437mhz(6),
			channel-07-2442mhz(7),
			channel-08-2447mhz(8),
			channel-09-2452mhz(9),
			channel-10-2457mhz(10),
			channel-11-2462mhz(11),
			channel-12-2467mhz(12),
			channel-13-2472mhz(13)
 		}
		MAX-ACCESS  read-write
		STATUS	current
		DESCRIPTION
			"control for wireless channel"
	::= { wlanRadioTable	2 }

	wlanRadioMode  OBJECT-TYPE
		SYNTAX	  INTEGER {
			mode-802-11bgn(1),
			mode-802-11ng(2),
			mode-802-11bg(3),
			mode-802-11n(4),
			mode-802-11g(5),
			mode-802-11b(6)
		}
		MAX-ACCESS  read-write
		STATUS	current
		DESCRIPTION
			"control for wireless radio mode(802.11bgn / 802.11ng / 802.11bg / 802.11n only / 802.11g only / 802.11b only)"
	::= { wlanRadioTable	3 }

	wlanChannelWidth  OBJECT-TYPE
		SYNTAX	  INTEGER {
			channelwidth-auto(1),
			channelwidth-20MHz(2)
		}
		MAX-ACCESS  read-write
		STATUS	current
		DESCRIPTION
			"control for wireless channel width(Auto / 20MHz)"
	::= { wlanRadioTable	4 }

	wlanTransmitPower  OBJECT-TYPE
		SYNTAX	  INTEGER {
			txpower-25(1),
			txpower-50(2),
			txpower-100(3)
		}
		MAX-ACCESS  read-write
		STATUS	current
		DESCRIPTION
			"control for wireless transmit power(25% / 50% / 100%)"
	::= { wlanRadioTable	5 }

	wlanBeaconInterval  OBJECT-TYPE
		SYNTAX	  INTEGER (1..1000)
		MAX-ACCESS  read-write
		STATUS	current
		DESCRIPTION
			"control for wireless beacon interval(1~1000, default: 100)"
	::= { wlanRadioTable	6 }

	wlanRTSThreshold  OBJECT-TYPE
		SYNTAX	  INTEGER (256..2432)
		MAX-ACCESS  read-write
		STATUS	current
		DESCRIPTION
			"control for wireless RTS threshold (256~2432, default: 2432)"
	::= { wlanRadioTable	7 }

	wlanFragmentationThreshold  OBJECT-TYPE
		SYNTAX	  INTEGER (800..2432)
		MAX-ACCESS  read-write
		STATUS	current
		DESCRIPTION
			"control for wireless fragmentation threshold (800~2432, default:2346, even number only)"
	::= { wlanRadioTable	8 }

	wlanPreambleType  OBJECT-TYPE
		SYNTAX	  INTEGER {
			preambletype-dynamic(1),
			preambletype-short(2),
			preambletype-long(3)
		}
		MAX-ACCESS  read-write
		STATUS	current
		DESCRIPTION
			"control for wireless preamble type (dynamic / short / long)"
	::= { wlanRadioTable	9 }

  wlanSecurityControl     OBJECT-IDENTITY
		STATUS	current
		DESCRIPTION
			"Read/Write Wlan Security Control"
	::= { wireless 2 }

	wlanSecMode  OBJECT-TYPE
		SYNTAX	  INTEGER {
			disable(1),
			wpa(2),
			wpa2(3),
			wpa-wpa2(4),
			wep(5)
		}
		MAX-ACCESS  read-write
		STATUS	current
		DESCRIPTION
			"Controls for wireless security mode. (Disable / WPA / WPA2 / WPA/WPA2 / WEP)"
	::= { wlanSecurityControl	1 }

	wlanWPAGroupKeyRekey  OBJECT-TYPE
		SYNTAX	  INTEGER
		MAX-ACCESS  read-write
		STATUS	current
		DESCRIPTION
			"The re-key interval for WPA/WP2 Group Key. (default 86400 second. 1~86400)"
	::= { wlanSecurityControl	2 }

	wlan8021xSupport  OBJECT-TYPE
		SYNTAX	  INTEGER {
			wlan8021x-disable(1),
			wlan8021x-enable(2)
		}
		MAX-ACCESS  read-write
		STATUS	current
		DESCRIPTION
			"Controls for 802.1x support. Disable(WPA with pre-shared key), Enable(WPA with Radius server)"
	::= { wlanSecurityControl	3 }

	wlanWPAPreSharedKey  OBJECT-TYPE
		SYNTAX	  OCTET STRING (SIZE (8..63))
		MAX-ACCESS  read-write
		STATUS	current
		DESCRIPTION
			"WPA pre-shared key(ASCII, 8~63 characters)"
	::= { wlanSecurityControl	4 }

	wlanRadiusSrvInfo  OBJECT-TYPE
		SYNTAX	  OCTET STRING
		MAX-ACCESS  read-write
		STATUS	current
		DESCRIPTION
			"Radius server IP/domain(ASCII)"
	::= { wlanSecurityControl	5 }

	wlanRadiusSrvAuthPort  OBJECT-TYPE
		SYNTAX	  INTEGER
		MAX-ACCESS  read-write
		STATUS	current
		DESCRIPTION
			"Radius server authentication port (1~65535)"
	::= { wlanSecurityControl	6 }

	wlanRadiusSrvSharedSecretKey  OBJECT-TYPE
		SYNTAX	  OCTET STRING
		MAX-ACCESS  read-write
		STATUS	current
		DESCRIPTION
			"Radius server shared secret key"
	::= { wlanSecurityControl	7 }

	wlanRadiusSrvAuthMethod  OBJECT-TYPE
		SYNTAX	  INTEGER {
			authmethod-opensystem(1),
			authmethod-sharedkey(2),
			authmethod-both(3)
		}
		MAX-ACCESS  read-write
		STATUS	current
		DESCRIPTION
			"802.1x authentication method. Open System/Shared Key/Both"
	::= { wlanSecurityControl	8 }

	wlanWEPEncryption  OBJECT-TYPE
		SYNTAX	  INTEGER {
			encrypt-64-bit(1),
			encyrpt-128-bit(2)
		}
		MAX-ACCESS  read-write
		STATUS	current
		DESCRIPTION
			"WEP encryption(64/128 bit)"
	::= { wlanSecurityControl	9 }

	wlanWEPMode  OBJECT-TYPE
		SYNTAX	  INTEGER {
			wepmode-hex(1),
			wepmode-ascii(2)
		}
		MAX-ACCESS  read-write
		STATUS	current
		DESCRIPTION
			"WEP mode(HEX/ASCII)"
	::= { wlanSecurityControl	10 }

	wlanWEPKeyIndex  OBJECT-TYPE
		SYNTAX	  INTEGER
		MAX-ACCESS  read-write
		STATUS	current
		DESCRIPTION
			"WEP Key Index"
	::= { wlanSecurityControl	11 }

	wlanWEPKey1  OBJECT-TYPE
		SYNTAX	  OCTET STRING (SIZE (1..26))
		MAX-ACCESS  read-write
		STATUS	current
		DESCRIPTION
			"WEP Key 1 passphrase"
	::= { wlanSecurityControl	12 }

	wlanWEPKey2  OBJECT-TYPE
		SYNTAX	  OCTET STRING (SIZE (1..26))
		MAX-ACCESS  read-write
		STATUS	current
		DESCRIPTION
			"WEP Key 2 passphrase"
	::= { wlanSecurityControl	13 }

	wlanWEPKey3  OBJECT-TYPE
		SYNTAX	  OCTET STRING (SIZE (1..26))
		MAX-ACCESS  read-write
		STATUS	current
		DESCRIPTION
			"WEP Key 3 passphrase"
	::= { wlanSecurityControl	14 }

	wlanWEPKey4  OBJECT-TYPE
		SYNTAX	  OCTET STRING (SIZE (1..26))
		MAX-ACCESS  read-write
		STATUS	current
		DESCRIPTION
			"WEP Key 4 passphrase"
	::= { wlanSecurityControl	15 }

	wlanWEPAuthMethod  OBJECT-TYPE
		SYNTAX	  INTEGER {
			authmethod-opensystem(1),
			authmethod-sharedkey(2),
			authmethod-both(3)
		}
		MAX-ACCESS  read-write
		STATUS	current
		DESCRIPTION
			"WEP authentication method. Open System/Shared Key/Both"
	::= { wlanSecurityControl	16 }

  wlanStatistics      OBJECT-IDENTITY
		STATUS	current
		DESCRIPTION
			"Wlan Statistics"
	::= { wireless 3 }

	dot11TransmittedCount  OBJECT-TYPE
		SYNTAX	  INTEGER
		MAX-ACCESS  read-only
		STATUS	current
		DESCRIPTION
			"This counter shows total bytes transmitted"
	::= { wlanStatistics	1 }

	dot11ReceivedCount  OBJECT-TYPE
		SYNTAX	  INTEGER
		MAX-ACCESS  read-only
		STATUS	current
		DESCRIPTION
			"This counter shows total bytes received"
	::= { wlanStatistics	2 }

	dot11RetryCount  OBJECT-TYPE
		SYNTAX	  INTEGER
		MAX-ACCESS  read-only
		STATUS	current
		DESCRIPTION
			"This counter shall increment when an MSDU is successfully transmitted after one or more retransmissions."
	::= { wlanStatistics	3 }

	wlanStationCount  OBJECT-TYPE
		SYNTAX	  INTEGER
		MAX-ACCESS  read-only
		STATUS	current
		DESCRIPTION
			"number of associated stations"
	::= { wlanStatistics	4 }

  wlanTraps      OBJECT-IDENTITY
		STATUS	current
		DESCRIPTION
			"Wlan Traps"
	::= { wireless 4 }

  wlanTrapsControl			OBJECT-IDENTITY
		STATUS		current
		DESCRIPTION
			"The subtree for Wlan Traps"
		::= { wlanTraps 1 }

 	trapWirelessControl OBJECT-TYPE
 		SYNTAX INTEGER {
 			enable(1),
 			disable(2)
 		}
 		MAX-ACCESS	read-write
 		STATUS		current
 		DESCRIPTION
			"Controls wireless group traps enable(1) or disable(2)."
		::= { wlanTrapsControl 1 }

  wlanTrapsFormat			OBJECT-IDENTITY
		STATUS		current
		DESCRIPTION
			"The subtree for Wlan Traps Format"
		::= { wlanTraps 2 }

 	trapGenericMessage OBJECT-TYPE
		SYNTAX		DisplayString
	    	MAX-ACCESS	accessible-for-notify
	    	STATUS		current
	    	DESCRIPTION
			"Provide generic information on traps."
		::= { wlanTrapsFormat 1 }

	trapMACAddress OBJECT-TYPE
	    	SYNTAX		MacAddress
	    	MAX-ACCESS	accessible-for-notify
	    	STATUS		current
	    	DESCRIPTION
			"Represents MAC address of the device or the host which triggers the trap."
		::= { wlanTrapsFormat 2 }

	trapWlanSSID OBJECT-TYPE
	    	SYNTAX		DisplayString
	    	MAX-ACCESS	accessible-for-notify
	    	STATUS		current
	    	DESCRIPTION
			"The SSID name which the wireless client associates."
		::= { wlanTrapsFormat 3 }

  wlanTrapsItems			OBJECT-IDENTITY
		STATUS		current
		DESCRIPTION
			"The subtree for Wlan Traps Items"
		::= { wlanTraps 3 }

	wlanStaAssociation NOTIFICATION-TYPE
		STATUS		current
		DESCRIPTION
			"Wireless client assocication notification."
		::= { wlanTrapsItems 1 }

	wlanStaDisassociation	NOTIFICATION-TYPE
		STATUS			current
		DESCRIPTION
			"Wireless client disassocication notification."
		::= { wlanTrapsItems 2 }

	wlanStaAuthFail	NOTIFICATION-TYPE
		STATUS		current
		DESCRIPTION
			"Wireless client authentication failed."
		::= { wlanTrapsItems 3 }

--
-- Node: deviceTraps
-- includes deviceTrapsControl, deviceTrapsItems
--

 	deviceTraps    OBJECT-IDENTITY
		STATUS	current
		DESCRIPTION
			"Device Traps"
	::= { esOutsourcing 2 }

  deviceTrapsControl       OBJECT-IDENTITY
		STATUS	current
		DESCRIPTION
			"Device Traps Control"
	::= { deviceTraps 1 }

	trapDeviceInfoControl  OBJECT-TYPE
 		SYNTAX INTEGER {
 			enable(1),
 			disable(2)
 		}
		MAX-ACCESS  read-write
		STATUS	current
		DESCRIPTION
			"Controls devices information traps"
	::= { deviceTrapsControl	1 }

  deviceTrapsItems       OBJECT-IDENTITY
		STATUS	current
		DESCRIPTION
			"Device Traps Items"
	::= { deviceTraps 2 }

	trapDeviceEthIPAddr  NOTIFICATION-TYPE
		STATUS	current
		DESCRIPTION
			"Devices Ethernet IP address"
	::= { deviceTrapsItems	1 }

	trapDeviceEthMACAddr  NOTIFICATION-TYPE
		STATUS	current
		DESCRIPTION
			"Devices Ethernet MAC address"
	::= { deviceTrapsItems	2 }

END
