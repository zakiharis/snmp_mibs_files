--
-- comRadiusClient.mib
-- MIB generated by MG-SOFT Visual MIB Builder Version 3.0 Build 285
-- Saturday, February 17, 2007 at 14:31:56
--

    ZHONE-RADIUS-CLIENT DEFINITIONS ::= BEGIN
 
        IMPORTS
            ifIndex            
                FROM IF-MIB            
            DisplayString            
                FROM RFC1213-MIB            
            OBJECT-GROUP            
                FROM SNMPv2-CONF            
            Integer32, OBJECT-TYPE, MODULE-IDENTITY, OBJECT-IDENTITY            
                FROM SNMPv2-SMI            
            RowStatus            
                FROM SNMPv2-TC            
            zhoneRadius, zhoneModules            
                FROM Zhone;
    
    
-- To generate protection layer:
-- /vob/zhonetools/bin/pahrser.pl iftype.mib Zhone.mib Zhone-TC.mib
--    rfc2514.mib rfc2233.mib rfc2571.mib comRadiusClient.mib
-- 
-- To generate mib handlers:
-- /vob/EPILOGUE/binaries/emissary/solaris/mibcomp rfc2514.mib 
--    rfc1907.mib iftype.mib Zhone.mib Zhone-TC.mib rfc2233.mib
--    rfc2571.mib -stub -o comBondingHdlr.c comRadius.mib
-- 
-- 
-- 
        -- 1.3.6.1.4.1.5504.6.112
        comRadiusClient MODULE-IDENTITY 
            LAST-UPDATED "200611151230Z"		-- November 15, 2006 at 12:30 GMT
            ORGANIZATION 
                "Zhone Technologies, Inc."
            CONTACT-INFO 
                "  Postal: 
                           Zhone Technologies, Inc.
                           @ Zhone Way
                           7001 Oakport Street
                           Oakland, CA  94621
                           USA
                Toll-Free: +1 877-ZHONE20 (+1 877-946-6320)
                      Tel: +1-510-777-7000
                      Fax: +1-510-777-7001
                   E-mail: support@zhone.com"
            DESCRIPTION 
                "This is the Zhone module identifier for the Zhone Bonding module."
            REVISION "200611151407Z"		-- November 15, 2006 at 14:07 GMT
            DESCRIPTION 
                "Version 1.0.0 - initial creation of
                Zhone Radius MIB."
            ::= { zhoneModules 112 }

        
    
    
    
--
-- Node definitions
--
    
        -- 1.3.6.1.4.1.5504.4.14.1
        zhoneRadiusClient OBJECT-IDENTITY
            STATUS current
            DESCRIPTION 
                "Start of the Zhone RADIUS Client MIB."
            ::= { zhoneRadius 1 }

        
        -- 1.3.6.1.4.1.5504.4.14.1.1
        zhoneRadiusClientTable OBJECT-TYPE
            SYNTAX SEQUENCE OF ZhoneRadiusClientEntry
            MAX-ACCESS not-accessible
            STATUS current
            DESCRIPTION
                "The ZhoneRadiusClientTable contains the information
                required to authenticate a user using the RADIUS
                protocol. One entry exists per RADIUS server.
                "
            ::= { zhoneRadiusClient 1 }

        
        -- 1.3.6.1.4.1.5504.4.14.1.1.1
        zhoneRadiusClientEntry OBJECT-TYPE
            SYNTAX ZhoneRadiusClientEntry
            MAX-ACCESS not-accessible
            STATUS current
            DESCRIPTION
                "An entry in the Zhone Radius Client table.
                "
            INDEX { zhoneRadiusClientIndex, zhoneRadiusClientId }
            ::= { zhoneRadiusClientTable 1 }

        
        ZhoneRadiusClientEntry ::=
            SEQUENCE { 
                zhoneRadiusClientIndex
                    INTEGER,
                zhoneRadiusClientId
                    INTEGER,
                zhoneRadiusClientRowStatus
                    RowStatus,
                zhoneRadiusClientServerName
                    DisplayString,
                zhoneRadiusClientUdpPortNumber
                    Integer32,
                zhoneRadiusClientSharedSecret
                    DisplayString,
                zhoneRadiusClientRetryCount
                    Integer32,
                zhoneRadiusClientRetryInterval
                    Integer32
             }

        -- 1.3.6.1.4.1.5504.4.14.1.1.1.1
        zhoneRadiusClientIndex OBJECT-TYPE
            SYNTAX INTEGER (1..2137483647)
            MAX-ACCESS not-accessible
            STATUS current
            DESCRIPTION
                "This index is used to group serveral RADIUS server
                description together. This index is used in various 
                Zhone provisioning information to specify which group
                of entries to use for a specific task or purpose.
                "
            ::= { zhoneRadiusClientEntry 1 }

        
        -- 1.3.6.1.4.1.5504.4.14.1.1.1.2
        zhoneRadiusClientId OBJECT-TYPE
            SYNTAX INTEGER (1..2137483647)
            MAX-ACCESS not-accessible
            STATUS current
            DESCRIPTION
                "This index specifies the specific RADIUS server information
                into a group of entries. When this group is provisioned
                for a task, this index is the order in which the servers
                will be contacted by the client.
                "
            ::= { zhoneRadiusClientEntry 2 }

        
        -- 1.3.6.1.4.1.5504.4.14.1.1.1.3
        zhoneRadiusClientRowStatus OBJECT-TYPE
            SYNTAX RowStatus
            MAX-ACCESS read-create
            STATUS current
            DESCRIPTION
                "Entry row status for SNMP create-and-go operation.
                "
            ::= { zhoneRadiusClientEntry 3 }

        
        -- 1.3.6.1.4.1.5504.4.14.1.1.1.4
        zhoneRadiusClientServerName OBJECT-TYPE
            SYNTAX DisplayString
            MAX-ACCESS read-create
            STATUS current
            DESCRIPTION
                "Radius server host name or IP address."
            ::= { zhoneRadiusClientEntry 4 }

        
        -- 1.3.6.1.4.1.5504.4.14.1.1.1.5
        zhoneRadiusClientUdpPortNumber OBJECT-TYPE
            SYNTAX Integer32 (0..65535)
            MAX-ACCESS read-create
            STATUS current
            DESCRIPTION
                "The destination UDP port number for RADIUS authentication packets
                when authenticating using this server.
                "
            DEFVAL { 1812 }
            ::= { zhoneRadiusClientEntry 5 }

        
        -- 1.3.6.1.4.1.5504.4.14.1.1.1.6
        zhoneRadiusClientSharedSecret OBJECT-TYPE
            SYNTAX DisplayString
            MAX-ACCESS read-create
            STATUS current
            DESCRIPTION
                "This is the shared secret used by the RADIUS client and server
                for authentication and packet encryption.
                "
            ::= { zhoneRadiusClientEntry 6 }

        
        -- 1.3.6.1.4.1.5504.4.14.1.1.1.7
        zhoneRadiusClientRetryCount OBJECT-TYPE
            SYNTAX Integer32 (1..255)
            MAX-ACCESS read-create
            STATUS current
            DESCRIPTION
                "The number of times to retry a failed request before we rotate to
                the next server in the list.
                "
            DEFVAL { 5 }
            ::= { zhoneRadiusClientEntry 7 }

        
        -- 1.3.6.1.4.1.5504.4.14.1.1.1.8
        zhoneRadiusClientRetryInterval OBJECT-TYPE
            SYNTAX Integer32 (1..60)
            MAX-ACCESS read-create
            STATUS current
            DESCRIPTION
                "This is the minimum time (in seconds) the device will wait before 
                asuuming an error occurred and the request is retried.
                "
            DEFVAL { 1 }
            ::= { zhoneRadiusClientEntry 8 }

        
        -- 1.3.6.1.4.1.5504.4.14.2
        zhoneRadiusObjectGroup OBJECT-GROUP
            OBJECTS { zhoneRadiusClientServerName, zhoneRadiusClientUdpPortNumber, zhoneRadiusClientSharedSecret, zhoneRadiusClientRetryCount, zhoneRadiusClientRetryInterval
                 }
            STATUS current
            DESCRIPTION 
                "Description."
            ::= { zhoneRadius 2 }

        
    
    END

--
-- comRadiusClient.mib
--
