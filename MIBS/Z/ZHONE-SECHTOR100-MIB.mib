--
-- zhoneSechtor100.mib
-- MIB generated by MG-SOFT Visual MIB Builder Version 2.1 Build 205
-- Tuesday, October 16, 2001 at 09:18:01
--

    ZHONE-SECHTOR100-MIB DEFINITIONS ::= BEGIN

        IMPORTS 
            Integer32, OBJECT-TYPE, MODULE-IDENTITY, OBJECT-IDENTITY, NOTIFICATION-TYPE            
                FROM SNMPv2-SMI            
            MacAddress, TruthValue            
                FROM SNMPv2-TC            
            sechtor100, zhoneModules, zhoneShelfIndex, zhoneSlotIndex            
                FROM Zhone            
            ZhoneRowStatus            
                FROM Zhone-TC;
    
    
--  
-- 
-- 
-- 
        zhoneSechtor100 MODULE-IDENTITY
            LAST-UPDATED "200109281029Z"
            ORGANIZATION
                "Zhone Technologies, Inc"
            CONTACT-INFO
                "  Postal: 
                           Zhone Technologies, Inc.
                           @ Zhone Way
                           7001 Oakport Street
                           Oakland, CA  94621
                           USA
                Toll-Free: +1 877-ZHONE20 (+1 877-946-6320)
                      Tel: +1-510-777-7000
                      Fax: +1-510-777-7001
                   E-mail: support@zhone.com"
            DESCRIPTION
                "MIB module for elements specific to Sechtor 100 products."
            REVISION "200109281029Z"
            DESCRIPTION
                "V01.01.00 Introduce sechtor100ConfigTable"
            REVISION "200012271117Z"
            DESCRIPTION
                "V01.00.01 - Add Zhone keywording"
            REVISION "200012211700Z"
            DESCRIPTION
                "V01.00.00 - Initial Release"
            ::= { zhoneModules 19 }
        
    
    
--
-- Node definitions
--
    
-- Currently, there are environmental variables for monitoring
-- fans and thermometers.
-- 
-- There are two thermometers on the Sechtor 100 board. In this
-- MIB, thermometers 'A' and 'B' are used to differentiate
-- these two thermometers:
-- 
-- Thermometer A - the thermometer located near the 750
-- processor. It is expected that this thermometer have a higher
-- temperature reading than thermometer B because of the heat
-- generated by the processor. It is recommended that a higher
-- upper threshold is set for this thermometer.
-- 
-- Thermometer B - the thermometer located near the outlet on
-- the right side of the Sechtor 100 board.
        sechtor100Environment OBJECT-IDENTITY
            STATUS deprecated
            DESCRIPTION
                "All the scalar objects under sechor100Environment are deprecated 
                and replaced by their respective objects indexed by zhoneShelfIndex 
                and zhoneSlotIndex.
                "
            ::= { sechtor100 1 }
        
-- 
        s100FanOperationalStatus OBJECT-TYPE
            SYNTAX INTEGER
                {
                operational(1),
                fanFailure(2)
                }
            MAX-ACCESS read-only
            STATUS deprecated
            DESCRIPTION
                "This variable describes the working status of the four fans
                for the Sechtor 100. If any one of the four fans is not
                running correctly, this variable shows 'fanFailure'. When
                all the fans are working, the value of this variable is
                'operational'.
                "
            ::= { sechtor100Environment 1 }
        
-- 
        s100ThermoAUpperThreshold OBJECT-TYPE
            SYNTAX Integer32 (45..80)
            MAX-ACCESS read-write
            STATUS deprecated
            DESCRIPTION
                "This variable specifies the upper threshold for thermometer
                A in degrees Celsius. When s100ThermoATemperature is
                above this value, s100ThermoAOperationalStatus would be
                'overUpperThreshold' and a trap will be generated.
                
                Valid range is 45..80 degrees Celsius and the default
                is 65 degrees Celsius."
            ::= { sechtor100Environment 2 }
        
-- 
        s100ThermoBUpperThreshold OBJECT-TYPE
            SYNTAX Integer32 (45..80)
            MAX-ACCESS read-write
            STATUS deprecated
            DESCRIPTION
                "This variable specifies the upper threshold for thermometer
                B in degrees Celsius. When s100ThermoBTemperature is
                above this value, s100ThermoBOperationalStatus would be
                'overUpperThreshold' and a trap will be generated.
                
                Valid range is 45..80 degrees Celsius and the default
                is 60 degrees Celsius."
            ::= { sechtor100Environment 3 }
        
-- 
        s10ThermoALowerThreshold OBJECT-TYPE
            SYNTAX Integer32 (-10..5)
            MAX-ACCESS read-write
            STATUS deprecated
            DESCRIPTION
                "This variable specifies the lower threshold for thermometer
                A in degrees Celsius. When s100ThermoATemperature is
                below this value, s100ThermoAOperationalStatus would be
                'belowLowerThreshold' and a trap will be generated.
                
                Valid range is -10..5 degrees Celsius and the default
                is -5 degrees Celsius."
            ::= { sechtor100Environment 4 }
        
-- 
        s100ThermoBLowerThreshold OBJECT-TYPE
            SYNTAX Integer32 (-10..5)
            MAX-ACCESS read-write
            STATUS deprecated
            DESCRIPTION
                "This variable specifies the lower threshold for thermometer
                B in degrees Celsius. When s100ThermoATemperature is
                below this value, s100ThermoBOperationalStatus would be
                'belowLowerThreshold' and a trap will be generated.
                
                Valid range is -10..5 degrees Celsius and the default
                is -5 degrees Celsius."
            ::= { sechtor100Environment 5 }
        
-- 
        s100ThermoATemperature OBJECT-TYPE
            SYNTAX Integer32 (-55..125)
            MAX-ACCESS read-only
            STATUS deprecated
            DESCRIPTION
                "The temperature in degrees Celsius read by the IC 
                thermometer sensor A on the PCB board. It is effectively
                the internal ambient temperature inside the enclosure
                where thermometer A is located.
                
                The valid temperature range for the thermometer is
                -55..125 degrees Celsius."
            ::= { sechtor100Environment 6 }
        
-- 
        s100ThermoBTemperature OBJECT-TYPE
            SYNTAX Integer32 (-55..125)
            MAX-ACCESS read-only
            STATUS deprecated
            DESCRIPTION
                "The temperature in degrees Celsius read by the IC 
                thermometer sensor B on the PCB board. It is effectively
                the internal ambient temperature inside the enclosure
                where thermometer B is located.
                
                
                The valid temperature range for the thermometer is
                -55..125 degrees Celsius."
            ::= { sechtor100Environment 7 }
        
-- 
        s100ThermoAOperationalStatus OBJECT-TYPE
            SYNTAX INTEGER
                {
                withinOperationalRange(1),
                overUpperThreshold(2),
                belowLowerThreshold(3)
                }
            MAX-ACCESS read-only
            STATUS deprecated
            DESCRIPTION
                "The operational status indicator for thermometer A.
                
                Valid values are:
                * withinOperationalRange - s100ThermoATemperature is within
                  its lower and upper threshold range.
                * overUpperThreshold - s100ThermoATemperature is higher
                  than its upper threshold.
                * belowLowerThreshold - s100ThermoATemperature is lower
                  than its lower threshold."
            ::= { sechtor100Environment 8 }
        
-- 
        s100ThermoBOperationalStatus OBJECT-TYPE
            SYNTAX INTEGER
                {
                withinOperationalRange(1),
                overUpperThreshold(2),
                belowLowerThreshold(3)
                }
            MAX-ACCESS read-only
            STATUS deprecated
            DESCRIPTION
                "The operational status indicator for thermometer B.
                
                Valid values are:
                * withinOperationalRange - s100ThermoBTemperature is within
                  its lower and upper threshold range.
                * overUpperThreshold - s100ThermoBTemperature is higher
                  than its upper threshold.
                * belowLowerThreshold - s100ThermoBTemperature is lower
                  than its lower threshold."
            ::= { sechtor100Environment 9 }
        
        sechtor100Traps OBJECT-IDENTITY
            STATUS current
            DESCRIPTION
                "All Sechtor 100 MIB traps are defined under sechtor100Traps."
            ::= { sechtor100 2 }
        
        sechtor100TrapsPrefix OBJECT-IDENTITY
            STATUS current
            DESCRIPTION
                "Prefix 0 for Sechtor 100 MIB traps as required by SNMPv2."
            ::= { sechtor100Traps 0 }
        
        s100FanStatusChange NOTIFICATION-TYPE
            OBJECTS { s100FanOperationalStatus }
            STATUS deprecated
            DESCRIPTION
                "This trap is generated whenever the value of
                s100FanOperationalStatus changes.
                
                This trap is deprecated and is replaced by sechtor100FanStatusChange."
            ::= { sechtor100TrapsPrefix 1 }
        
        s100ThermoStatusChange NOTIFICATION-TYPE
            OBJECTS { s100ThermoATemperature, s100ThermoBTemperature, s100ThermoAOperationalStatus, s100ThermoBOperationalStatus }
            STATUS deprecated
            DESCRIPTION
                "This trap is generated whenever sechtor100ThermoAOperationalStatus
                or sechtor100ThermoBOperationalStatus changes its value.
                
                This trap is deprecated and is replaced by sechtor100ThermoStatusChange."
            ::= { sechtor100TrapsPrefix 2 }
        
        sechtor100FanStatusChange NOTIFICATION-TYPE
            OBJECTS { sechtor100FanOperationalStatus }
            STATUS current
            DESCRIPTION
                "This trap is generated whenever the value of
                sechtor100FanOperationalStatus changes.
                
                The Sechtor 100 is identified by the shelf and slot number from 
                instance OID's contained in the trap VarBind objects."
            ::= { sechtor100TrapsPrefix 3 }
        
        sechtor100ThermoStatusChange NOTIFICATION-TYPE
            OBJECTS { sechtor100ThermoATemperature, sechtor100ThermoBTemperature, sechtor100ThermoAOperationalStatus, sechtor100ThermoBOperationalStatus }
            STATUS current
            DESCRIPTION
                "This trap is generated whenever sechtor100ThermoAOperationalStatus
                or sechtor100ThermoBOperationalStatus changes its value.
                
                The Sechtor 100 is identified by the shelf and slot number from 
                instance OID's contained in the trap VarBind objects."
            ::= { sechtor100TrapsPrefix 4 }
        
        sechtor100ConfigTable OBJECT-TYPE
            SYNTAX SEQUENCE OF Sechtor100ConfigEntry
            MAX-ACCESS not-accessible
            STATUS current
            DESCRIPTION
                "This table contains redundancy variables and environmental 
                variables for monitoring fans and thermometers.
                
                For redundancy, the peer MAC address is maintained in this 
                table. Also, one variable specifies whether redundancy is 
                enabled or not.
                
                There are two thermometers on the Sechtor 100 board. In this
                MIB, thermometers 'A' and 'B' are used to differentiate
                these two thermometers:
                
                Thermometer A - the thermometer located near the 750
                processor. It is expected that this thermometer have a higher
                temperature reading than thermometer B because of the heat
                generated by the processor. It is recommended that a higher
                upper threshold is set for this thermometer.
                
                Thermometer B - the thermometer located near the outlet on
                the right side of the Sechtor 100 board.
                
                The profile for this table will be auto-created as 1/1 with
                the sechtor100RedundancyEnable variable set to FALSE.
                
                This profile should not be deleted except for the following 
                two cases:
                
                1) When a unit operating in simplex mode is intended to be used
                   in duplex mode as the slot 2 of the redundant system. The
                   user needs to create a 1/2 profile.
                
                2) The unit configured as slot 2 of a redundant system is intended
                   to be used in simplex mode. Then the 1/2 profile should be
                   deleted and replaced with a 1/1 profile."
            ::= { sechtor100 3 }
        
        sechtor100ConfigEntry OBJECT-TYPE
            SYNTAX Sechtor100ConfigEntry
            MAX-ACCESS not-accessible
            STATUS current
            DESCRIPTION
                "An entry in the sechtor100ConfigTable."
            INDEX { zhoneShelfIndex, zhoneSlotIndex }
            ::= { sechtor100ConfigTable 1 }
        
        Sechtor100ConfigEntry ::=
            SEQUENCE { 
                sechtor100PeerMacAddress
                    MacAddress,
                sechtor100RedundancyEnable
                    TruthValue,
                sechtor100FanOperationalStatus
                    INTEGER,
                sechtor100ThermoAUpperThreshold
                    Integer32,
                sechtor100ThermoBUpperThreshold
                    Integer32,
                sechtor100ThermoALowerThreshold
                    Integer32,
                sechtor100ThermoBLowerThreshold
                    Integer32,
                sechtor100ThermoATemperature
                    Integer32,
                sechtor100ThermoBTemperature
                    Integer32,
                sechtor100ThermoAOperationalStatus
                    INTEGER,
                sechtor100ThermoBOperationalStatus
                    INTEGER,
                sechtor100RowStatus
                    ZhoneRowStatus
             }

        sechtor100PeerMacAddress OBJECT-TYPE
            SYNTAX MacAddress
            MAX-ACCESS read-write
            STATUS current
            DESCRIPTION
                "This is the Mac address of the peer s100 unit."
            ::= { sechtor100ConfigEntry 1 }
        
        sechtor100RedundancyEnable OBJECT-TYPE
            SYNTAX TruthValue
            MAX-ACCESS read-write
            STATUS current
            DESCRIPTION
                "Whether or not the redundancy functionality has been enabled.
                If this value is false, redundancy is not enable. "
            ::= { sechtor100ConfigEntry 2 }
        
-- 
        sechtor100FanOperationalStatus OBJECT-TYPE
            SYNTAX INTEGER
                {
                operational(1),
                fanFailure(2)
                }
            MAX-ACCESS read-only
            STATUS current
            DESCRIPTION
                "This variable describes the working status of the four fans
                for the Sechtor 100. If any one of the four fans is not
                running correctly, this variable shows 'fanFailure'. When
                all the fans are working, the value of this variable is
                'operational'."
            ::= { sechtor100ConfigEntry 3 }
        
-- 
        sechtor100ThermoAUpperThreshold OBJECT-TYPE
            SYNTAX Integer32 (45..80)
            MAX-ACCESS read-write
            STATUS current
            DESCRIPTION
                "This variable specifies the upper threshold for thermometer
                A in degrees Celsius. When s100ThermoATemperature is
                above this value, s100ThermoAOperationalStatus would be
                'overUpperThreshold' and a trap will be generated.
                
                Valid range is 45..80 degrees Celsius and the default
                is 65 degrees Celsius."
            DEFVAL { 65 }
            ::= { sechtor100ConfigEntry 4 }
        
        sechtor100ThermoBUpperThreshold OBJECT-TYPE
            SYNTAX Integer32 (45..80)
            MAX-ACCESS read-write
            STATUS current
            DESCRIPTION
                "This variable specifies the upper threshold for thermometer
                B in degrees Celsius. When s100ThermoBTemperature is
                above this value, s100ThermoBOperationalStatus would be
                'overUpperThreshold' and a trap will be generated.
                
                Valid range is 45..80 degrees Celsius and the default
                is 60 degrees Celsius."
            DEFVAL { 60 }
            ::= { sechtor100ConfigEntry 5 }
        
        sechtor100ThermoALowerThreshold OBJECT-TYPE
            SYNTAX Integer32 (-10..5)
            MAX-ACCESS read-write
            STATUS current
            DESCRIPTION
                "This variable specifies the lower threshold for thermometer
                A in degrees Celsius. When s100ThermoATemperature is
                below this value, s100ThermoAOperationalStatus would be
                'belowLowerThreshold' and a trap will be generated.
                
                Valid range is -10..5 degrees Celsius and the default
                is -5 degrees Celsius."
            DEFVAL { -5 }
            ::= { sechtor100ConfigEntry 6 }
        
-- 
        sechtor100ThermoBLowerThreshold OBJECT-TYPE
            SYNTAX Integer32 (-10..5)
            MAX-ACCESS read-write
            STATUS current
            DESCRIPTION
                "This variable specifies the lower threshold for thermometer
                B in degrees Celsius. When s100ThermoATemperature is
                below this value, s100ThermoBOperationalStatus would be
                'belowLowerThreshold' and a trap will be generated.
                
                Valid range is -10..5 degrees Celsius and the default
                is -5 degrees Celsius."
            DEFVAL { -5 }
            ::= { sechtor100ConfigEntry 7 }
        
-- 
        sechtor100ThermoATemperature OBJECT-TYPE
            SYNTAX Integer32 (-55..125)
            MAX-ACCESS read-only
            STATUS current
            DESCRIPTION
                "The temperature in degrees Celsius read by the IC 
                thermometer sensor A on the PCB board. It is effectively
                the internal ambient temperature inside the enclosure
                where thermometer A is located.
                
                The valid temperature range for the thermometer is
                -55..125 degrees Celsius."
            ::= { sechtor100ConfigEntry 8 }
        
-- 
        sechtor100ThermoBTemperature OBJECT-TYPE
            SYNTAX Integer32 (-55..125)
            MAX-ACCESS read-only
            STATUS current
            DESCRIPTION
                "The temperature in degrees Celsius read by the IC 
                thermometer sensor B on the PCB board. It is effectively
                the internal ambient temperature inside the enclosure
                where thermometer B is located.
                
                
                The valid temperature range for the thermometer is
                -55..125 degrees Celsius."
            ::= { sechtor100ConfigEntry 9 }
        
        sechtor100ThermoAOperationalStatus OBJECT-TYPE
            SYNTAX INTEGER
                {
                withinOperationalRange(1),
                overUpperThreshold(2),
                belowLowerThreshold(3)
                }
            MAX-ACCESS read-only
            STATUS current
            DESCRIPTION
                "The operational status indicator for thermometer A.
                
                Valid values are:
                * withinOperationalRange - s100ThermoATemperature is within
                  its lower and upper threshold range.
                * overUpperThreshold - s100ThermoATemperature is higher
                  than its upper threshold.
                * belowLowerThreshold - s100ThermoATemperature is lower
                  than its lower threshold."
            ::= { sechtor100ConfigEntry 10 }
        
-- 
        sechtor100ThermoBOperationalStatus OBJECT-TYPE
            SYNTAX INTEGER
                {
                withinOperationalRange(1),
                overUpperThreshold(2),
                belowLowerThreshold(3)
                }
            MAX-ACCESS read-only
            STATUS current
            DESCRIPTION
                "The operational status indicator for thermometer B.
                
                Valid values are:
                * withinOperationalRange - s100ThermoBTemperature is within
                  its lower and upper threshold range.
                * overUpperThreshold - s100ThermoBTemperature is higher
                  than its upper threshold.
                * belowLowerThreshold - s100ThermoBTemperature is lower
                  than its lower threshold."
            ::= { sechtor100ConfigEntry 11 }
        
        sechtor100RowStatus OBJECT-TYPE
            SYNTAX ZhoneRowStatus
            MAX-ACCESS read-create
            STATUS current
            DESCRIPTION
                "Used to control row creation and deletion. 
                
                A row in this table is created using a single 
                SNMP SET request with varbinds for:
                a) sechtor100RowStatus set to'CreateAndGo', 
                b) the following READ-CREATE object(s):
                   * 
                
                If 'createAndGo' successfully created a new row, 
                the RowStatus will be 'active'.  Subsequent to 
                successful row creation, the RowStatus can be 
                retrieved via an SNMP GET and the returned 
                RowStatus value is active.  If the 'createAndGo' 
                was unsuccessful an SNMP error will be returned 
                and a subsequent GET on the non-existent row 
                will also return an SNMP error of noSuchInstance.  
                An SNMP SET with the RowStatus value of 'destroy' 
                indicates that the agent should remove the row 
                from service and then delete it."
            ::= { sechtor100ConfigEntry 12 }
        
    
    END

--
-- zhoneSechtor100.mib
--
