-- Copyright (C) 2011-2012 by Zhone Technologies.  All Rights Reserved.

-- ======================================================================
-- ==                                                                  ==
-- ==                    ZHNGPONLINK MIB                              ==
-- ==                                                                  ==
-- ==  Copyright (C) 2011-2012 Zhone Technologies, Inc.                     ==
-- ==  Confidential, Unpublished Property of Zhone Technologies.       ==
-- ==  Rights Reserved Under the Copyright Laws of the United States.  ==
-- ==                                                                  ==
-- ======================================================================

ZHNGPONLINK DEFINITIONS ::= BEGIN

IMPORTS
    MODULE-IDENTITY , OBJECT-TYPE , enterprises,
    Integer32, Unsigned32, IpAddress
        FROM SNMPv2-SMI
    MODULE-COMPLIANCE, OBJECT-GROUP
        FROM SNMPv2-CONF
    zhoneWtn
        FROM Zhone;

-- 1.3.6.1.4.1.5504.2.5.43
zhnGPONLink  MODULE-IDENTITY
    LAST-UPDATED "201202031346Z"            -- February 03, 2012 at 13:46 GMT
    ORGANIZATION
        "Zhone Technologies, Inc."
    CONTACT-INFO 
        "Zhone Technologies, Inc.
         Florida Design Center
         8545 126th Avenue North
         Largo, FL 33773

	 Toll-Free: +1 877-ZHONE20 (+1 877-946-6320)
	 Tel: +1-510-777-7000
	 Fax: +1-510-777-7001
	 E-mail: support@zhone.com"


    DESCRIPTION
        "This file defines the private Enterprise MIB extensions
         that define GPON interface related objects supported 
	 by the Zhone VoIP CPEs."


    REVISION "201202031346Z"                -- February 03, 2012 at 13:46 GMT
    DESCRIPTION "Added the following objects:
                     txPower 
                     txBiasCurrent
                     gponTemperature
                     gponVcc
                "
    REVISION "201101120000Z" -- Jan 12, 2011
    DESCRIPTION "First Draft"

::= { zhoneWtn 43 }



-- 1.3.6.1.4.1.5504.2.5.43.1
zhnGPONLinkObjects           OBJECT IDENTIFIER ::= { zhnGPONLink 1 }


--
-- Textual Conventions
--
GPONLinkStatusValues ::= TEXTUAL-CONVENTION
  STATUS        current
  DESCRIPTION   "GPON interface status. An enumeration of: 
                     Up
	             Down
	             Initializing
		     Unavailable
		"
  SYNTAX OCTET STRING (SIZE (0..32))


GPONEnabledDisabledStatusValues ::= TEXTUAL-CONVENTION
  STATUS        current
  DESCRIPTION   "GPON RF Video status. An enumeration of: 
                     Disabled
	             Enabled
		"
  SYNTAX OCTET STRING (SIZE (0..32))


GPONStateValues ::= TEXTUAL-CONVENTION
  STATUS        current
  DESCRIPTION   "GPON ONU state. An enumeration of: 
                     INIT
                     STANDBY
                     SERIAL NUMBER
                     RANGING
                     OPERATIONAL
                     POPUP
                     EMERGENCY STOP
                     DEACTIVATED
		"
  SYNTAX OCTET STRING (SIZE (0..32))


GPONOnOffAlarmValues ::= TEXTUAL-CONVENTION
  STATUS        current
  DESCRIPTION   "GPON Alarm status. An enumeration of: 
                     On
	             Off
		"
  SYNTAX OCTET STRING (SIZE (0..32))



--
-- GPON Link Objects 
--
-- 1.3.6.1.4.1.5504.2.5.43.1.1
--
gponInterfaceNumberOfEntries OBJECT-TYPE
  SYNTAX        Unsigned32
  MAX-ACCESS    read-only
  STATUS        current
  DESCRIPTION
    "Number of instances of GPON interfaces for this ONU."
  ::= { zhnGPONLinkObjects 1}


--
-- GPON Link Objects 
-- InternetGatewayDevice.X_ZHONE_COM_GPON
--
-- 1.3.6.1.4.1.5504.2.5.43.1.2
--
gponLinkStatusTable OBJECT-TYPE
  SYNTAX        SEQUENCE OF GponLinkStatusEntry
  MAX-ACCESS    not-accessible
  STATUS        current
  DESCRIPTION
    "Table of GPON link status information."
  ::= { zhnGPONLinkObjects 2}

gponLinkStatusEntry OBJECT-TYPE
  SYNTAX        GponLinkStatusEntry
  MAX-ACCESS    not-accessible
  STATUS        current
  DESCRIPTION
    "Table of GPON link status information."
  INDEX        { gponIfIndex  }
  ::= { gponLinkStatusTable 1}

GponLinkStatusEntry ::=
  SEQUENCE {
      gponIfIndex                            Unsigned32,
      gponOperStatus                         GPONLinkStatusValues,
      gponLinkUpTransitions                  Unsigned32,
      rfVideo                                GPONEnabledDisabledStatusValues,
      gponOnuId                              Unsigned32,
      gponState                              GPONStateValues,
      rxLevel                                OCTET STRING,
      txPower                                OCTET STRING,
      txBiasCurrent                          OCTET STRING,
      gponTemperature                        OCTET STRING,
      gponVcc                                OCTET STRING
  }

gponIfIndex OBJECT-TYPE
  SYNTAX        Unsigned32
  MAX-ACCESS    not-accessible
  STATUS        current
  DESCRIPTION
    "GPON Interface index."
  ::= { gponLinkStatusEntry 1}

gponOperStatus OBJECT-TYPE
  SYNTAX        GPONLinkStatusValues
  MAX-ACCESS    read-only
  STATUS        current
  DESCRIPTION
    "Indicates the status of this GPON interface. Enumeration of:
        Up
	Down
        Initializing	
	Unavailable
    "
  ::= { gponLinkStatusEntry 2}

gponLinkUpTransitions OBJECT-TYPE
  SYNTAX        Unsigned32
  MAX-ACCESS    read-only
  STATUS        current
  DESCRIPTION
    "Number of times the GPON link has transitioned from down to up."
  ::= { gponLinkStatusEntry 3}

rfVideo OBJECT-TYPE
  SYNTAX        GPONEnabledDisabledStatusValues
  MAX-ACCESS    read-write
  STATUS        current
  DESCRIPTION
    "Indicates if the RF Video over the GPON interface is enabled or disabled. 
     Enumeration of:
        Disabled
        Enabled
    "
  ::= { gponLinkStatusEntry 4}

gponOnuId OBJECT-TYPE
  SYNTAX        Unsigned32
  MAX-ACCESS    read-only
  STATUS        current
  DESCRIPTION
    "Optical network unit identifier."
  ::= { gponLinkStatusEntry 5}

gponState OBJECT-TYPE
  SYNTAX        GPONStateValues
  MAX-ACCESS    read-only
  STATUS        current
  DESCRIPTION
    "Optical network unit state. Enumeration of:
         INIT
         STANDBY
         SERIAL NUMBER
         RANGING
         OPERATIONAL
         POPUP
         EMERGENCY STOP
         DEACTIVATED
    "
  ::= { gponLinkStatusEntry 6}

rxLevel OBJECT-TYPE
  SYNTAX        OCTET STRING
  MAX-ACCESS    read-only
  STATUS        current
  DESCRIPTION
    "GPON interface receive level, in dBm."
  ::= { gponLinkStatusEntry 7}

txPower OBJECT-TYPE
  SYNTAX        OCTET STRING
  MAX-ACCESS    read-only
  STATUS        current
  DESCRIPTION
    "GPON interface transmit power, in dBm."
  ::= { gponLinkStatusEntry 8}

txBiasCurrent OBJECT-TYPE
  SYNTAX        OCTET STRING
  MAX-ACCESS    read-only
  STATUS        current
  DESCRIPTION
    "GPON interface transmit bias current, in mA."
  ::= { gponLinkStatusEntry 9}

gponTemperature OBJECT-TYPE
  SYNTAX        OCTET STRING
  MAX-ACCESS    read-only
  STATUS        current
  DESCRIPTION
    "GPON interface diplexer/triplexer temperature, in Celsius."
  ::= { gponLinkStatusEntry 10}

gponVcc OBJECT-TYPE
  SYNTAX        OCTET STRING
  MAX-ACCESS    read-only
  STATUS        current
  DESCRIPTION
    "GPON interface voltage, in volts."
  ::= { gponLinkStatusEntry 11}


--
-- GPON Link Objects 
-- InternetGatewayDevice.X_ZHONE_COM_GPON
--
-- 1.3.6.1.4.1.5504.2.5.43.1.3
--
gponAlarmStatusTable OBJECT-TYPE
  SYNTAX        SEQUENCE OF GponAlarmStatusEntry
  MAX-ACCESS    not-accessible
  STATUS        current
  DESCRIPTION
    "Table of GPON alarm status information."
  ::= { zhnGPONLinkObjects 3}

gponAlarmStatusEntry OBJECT-TYPE
  SYNTAX        GponAlarmStatusEntry
  MAX-ACCESS    not-accessible
  STATUS        current
  DESCRIPTION
    "Table of GPON alarm status information."
  INDEX        { gponIfIndex  }
  ::= { gponAlarmStatusTable 1}


GponAlarmStatusEntry ::=
  SEQUENCE {
      gponAlarmAutoPowerControlFail      GPONOnOffAlarmValues,
      gponAlarmLOS                       GPONOnOffAlarmValues,
      gponAlarmLOL                       GPONOnOffAlarmValues,
      gponAlarmLOF                       GPONOnOffAlarmValues,
      gponAlarmLCDG                      GPONOnOffAlarmValues,
      gponAlarmFailedSignal              GPONOnOffAlarmValues,
      gponAlarmDegradedSignal            GPONOnOffAlarmValues,
      gponAlarmStartupFail               GPONOnOffAlarmValues,
      gponAlarmMsgErrorMsg               GPONOnOffAlarmValues,
      gponAlarmDeactivateOnuId           GPONOnOffAlarmValues,
      gponAlarmDisabledOnu               GPONOnOffAlarmValues,
      gponAlarmPEE                       GPONOnOffAlarmValues
  }

gponAlarmAutoPowerControlFail OBJECT-TYPE
  SYNTAX        GPONOnOffAlarmValues
  MAX-ACCESS    read-only
  STATUS        current
  DESCRIPTION
    "If the value of this object is ON, the automatic power-control 
     has failed.
    "
  ::= { gponAlarmStatusEntry 1 }

gponAlarmLOS OBJECT-TYPE
  SYNTAX        GPONOnOffAlarmValues
  MAX-ACCESS    read-only
  STATUS        current
  DESCRIPTION
    "If the value of this object is ON, no input signal has been detected. 
     Make sure fiber is plugged in.
    "
  ::= { gponAlarmStatusEntry 2 }

gponAlarmLOL OBJECT-TYPE
  SYNTAX        GPONOnOffAlarmValues
  MAX-ACCESS    read-only
  STATUS        current
  DESCRIPTION
    "If the value of this object is ON, the GPON link has detected a
     Loss of Link condition.
    "
  ::= { gponAlarmStatusEntry 3 }

gponAlarmLOF OBJECT-TYPE
  SYNTAX        GPONOnOffAlarmValues
  MAX-ACCESS    read-only
  STATUS        current
  DESCRIPTION
    "If the value of this object is ON, the GPON link has detected a
     Loss Of Frame condition.
    "
  ::= { gponAlarmStatusEntry 4 }

gponAlarmLCDG OBJECT-TYPE
  SYNTAX        GPONOnOffAlarmValues
  MAX-ACCESS    read-only
  STATUS        current
  DESCRIPTION
    "If the value of this object is ON, the GPON link has detected a
     Loss of GEM Channel Delineation condition.
    "
  ::= { gponAlarmStatusEntry 5 }

gponAlarmFailedSignal OBJECT-TYPE
  SYNTAX        GPONOnOffAlarmValues
  MAX-ACCESS    read-only
  STATUS        current
  DESCRIPTION
    "If the value of this object is ON, the GPON link has detected a
     bit error rate greater than 10E-5.
    "
  ::= { gponAlarmStatusEntry 6 }

gponAlarmDegradedSignal OBJECT-TYPE
  SYNTAX        GPONOnOffAlarmValues
  MAX-ACCESS    read-only
  STATUS        current
  DESCRIPTION
    "If the value of this object is ON, the GPON link has detected a
     bit error rate greater than 10E-6.
    "
  ::= { gponAlarmStatusEntry 7 }

gponAlarmStartupFail OBJECT-TYPE
  SYNTAX        GPONOnOffAlarmValues
  MAX-ACCESS    read-only
  STATUS        current
  DESCRIPTION
    "If the value of this object is ON, the GPON link has detected an
     error during startup.
    "
  ::= { gponAlarmStatusEntry 8 }

gponAlarmMsgErrorMsg OBJECT-TYPE
  SYNTAX        GPONOnOffAlarmValues
  MAX-ACCESS    read-only
  STATUS        current
  DESCRIPTION
    "If the value of this object is ON, the GPON link has received an
     unknown PLOAM message.
    "
  ::= { gponAlarmStatusEntry 9 }

gponAlarmDeactivateOnuId OBJECT-TYPE
  SYNTAX        GPONOnOffAlarmValues
  MAX-ACCESS    read-only
  STATUS        current
  DESCRIPTION
    "If the value of this object is ON, the GPON link has received a
     de-activate request and has successfully de-activated the link.
    "
  ::= { gponAlarmStatusEntry 10 }

gponAlarmDisabledOnu OBJECT-TYPE
  SYNTAX        GPONOnOffAlarmValues
  MAX-ACCESS    read-only
  STATUS        current
  DESCRIPTION
    "If the value of this object is ON, the GPON link has been disabled 
     by the OLT or the ONU Serial Number is not configured on the OLT.
    "
  ::= { gponAlarmStatusEntry 11 }

gponAlarmPEE OBJECT-TYPE
  SYNTAX        GPONOnOffAlarmValues
  MAX-ACCESS    read-only
  STATUS        current
  DESCRIPTION
    "If the value of this object is ON, the GPON link has detected a
     physical equipment error which may indicate a possible hardware
     problem.
    "
  ::= { gponAlarmStatusEntry 12 }



--
-- GPON Link Objects 
-- InternetGatewayDevice.X_ZHONE_COM_GPONStats
--
-- 1.3.6.1.4.1.5504.2.5.43.1.4
--
gponDataGemStatsTable OBJECT-TYPE
  SYNTAX        SEQUENCE OF GponDataGemStatsEntry
  MAX-ACCESS    not-accessible
  STATUS        current
  DESCRIPTION
    "Table of GPON Encapsulation Method (GEM) VoIP and Internet 
     traffic statistics for the Data GEM port."
  ::= { zhnGPONLinkObjects 4}

gponDataGemStatsEntry OBJECT-TYPE
  SYNTAX        GponDataGemStatsEntry
  MAX-ACCESS    not-accessible
  STATUS        current
  DESCRIPTION
    "Table of GPON Encapsulation Method (GEM) VoIP and Internet 
     traffic statistics for the Data GEM port."
  INDEX        { gponIfIndex  }
  ::= { gponDataGemStatsTable 1}


GponDataGemStatsEntry ::=
  SEQUENCE {
      dataGemPortRxBytes                     Unsigned32,
      dataGemPortRxFragments                 Unsigned32,
      dataGemPortRxFrames                    Unsigned32,
      dataGemPortRxDroppedFrames             Unsigned32,
      dataGemPortTxBytes                     Unsigned32,
      dataGemPortTxFragments                 Unsigned32,
      dataGemPortTxFrames                    Unsigned32,
      dataGemPortTxDroppedFrames             Unsigned32,
      dataGemPortAcceptedMulticastFrames     Unsigned32,
      dataGemPortDroppedMulticastFrames      Unsigned32
  }

dataGemPortRxBytes OBJECT-TYPE
  SYNTAX        Unsigned32
  MAX-ACCESS    read-only
  STATUS        current
  DESCRIPTION
    "Number of bytes received on the data GEM port, not including GEM headers. 
    "
  ::= { gponDataGemStatsEntry 1 }

dataGemPortRxFragments OBJECT-TYPE
  SYNTAX        Unsigned32
  MAX-ACCESS    read-only
  STATUS        current
  DESCRIPTION
    "Number of GEM fragments received on the data GEM port.
    "
  ::= { gponDataGemStatsEntry 2 }

dataGemPortRxFrames OBJECT-TYPE
  SYNTAX        Unsigned32
  MAX-ACCESS    read-only
  STATUS        current
  DESCRIPTION
    "Number of ethernet frames received on the data GEM port.
    "
  ::= { gponDataGemStatsEntry 3 }

dataGemPortRxDroppedFrames OBJECT-TYPE
  SYNTAX        Unsigned32
  MAX-ACCESS    read-only
  STATUS        current
  DESCRIPTION
    "Number of receive ethernet frames dropped due to congestion or because 
    frame is undersized.
    "
  ::= { gponDataGemStatsEntry 4 }

dataGemPortTxBytes OBJECT-TYPE
  SYNTAX        Unsigned32
  MAX-ACCESS    read-only
  STATUS        current
  DESCRIPTION
    "Number of bytes transmitted on the data GEM port, not including GEM headers.
    "
  ::= { gponDataGemStatsEntry 5 }

dataGemPortTxFragments OBJECT-TYPE
  SYNTAX        Unsigned32
  MAX-ACCESS    read-only
  STATUS        current
  DESCRIPTION
    "Number of GEM fragments transmitted on the data GEM port.
    "
  ::= { gponDataGemStatsEntry 6 }

dataGemPortTxFrames OBJECT-TYPE
  SYNTAX        Unsigned32
  MAX-ACCESS    read-only
  STATUS        current
  DESCRIPTION
    "Number of ethernet frames transmitted on the data GEM port.
    "
  ::= { gponDataGemStatsEntry 7 }

dataGemPortTxDroppedFrames OBJECT-TYPE
  SYNTAX        Unsigned32
  MAX-ACCESS    read-only
  STATUS        current
  DESCRIPTION
    "Number of ethernet frames dropped due to congestion.
    "
  ::= { gponDataGemStatsEntry 8 }

dataGemPortAcceptedMulticastFrames OBJECT-TYPE
  SYNTAX        Unsigned32
  MAX-ACCESS    read-only
  STATUS        current
  DESCRIPTION
    "Number of multicast frames accepted by the Multicast Filtering Function. 
    "
  ::= { gponDataGemStatsEntry 9 }

dataGemPortDroppedMulticastFrames OBJECT-TYPE
  SYNTAX        Unsigned32
  MAX-ACCESS    read-only
  STATUS        current
  DESCRIPTION
    "Number of multicast frames dropped by the Multicast Filtering Function.
    "
  ::= { gponDataGemStatsEntry 10 }


--
-- GPON Link Objects 
-- InternetGatewayDevice.X_ZHONE_COM_GPONStats
--
-- 1.3.6.1.4.1.5504.2.5.43.1.5
--
gponVideoGemStatsTable OBJECT-TYPE
  SYNTAX        SEQUENCE OF GponVideoGemStatsEntry
  MAX-ACCESS    not-accessible
  STATUS        current
  DESCRIPTION
    "Table of GPON Encapsulation Method (GEM) Video
     traffic statistics for the Data GEM port."
  ::= { zhnGPONLinkObjects 5}

gponVideoGemStatsEntry OBJECT-TYPE
  SYNTAX        GponVideoGemStatsEntry
  MAX-ACCESS    not-accessible
  STATUS        current
  DESCRIPTION
    "Table of GPON Encapsulation Method (GEM) Video
     traffic statistics for the Video GEM port."
  INDEX        { gponIfIndex  }
  ::= { gponVideoGemStatsTable 1}


GponVideoGemStatsEntry ::=
  SEQUENCE {
      videoGemPortRxBytes                     Unsigned32,
      videoGemPortRxFragments                 Unsigned32,
      videoGemPortRxFrames                    Unsigned32,
      videoGemPortRxDroppedFrames             Unsigned32,
      videoGemPortTxBytes                     Unsigned32,
      videoGemPortTxFragments                 Unsigned32,
      videoGemPortTxFrames                    Unsigned32,
      videoGemPortTxDroppedFrames             Unsigned32,
      videoGemPortAcceptedMulticastFrames     Unsigned32,
      videoGemPortDroppedMulticastFrames      Unsigned32
  }

videoGemPortRxBytes OBJECT-TYPE
  SYNTAX        Unsigned32
  MAX-ACCESS    read-only
  STATUS        current
  DESCRIPTION
    "Number of bytes received on the video GEM port, not including GEM headers. 
    "
  ::= { gponVideoGemStatsEntry 1 }

videoGemPortRxFragments OBJECT-TYPE
  SYNTAX        Unsigned32
  MAX-ACCESS    read-only
  STATUS        current
  DESCRIPTION
    "Number of GEM fragments received on the video GEM port.
    "
  ::= { gponVideoGemStatsEntry 2 }

videoGemPortRxFrames OBJECT-TYPE
  SYNTAX        Unsigned32
  MAX-ACCESS    read-only
  STATUS        current
  DESCRIPTION
    "Number of ethernet frames received on the video GEM port.
    "
  ::= { gponVideoGemStatsEntry 3 }

videoGemPortRxDroppedFrames OBJECT-TYPE
  SYNTAX        Unsigned32
  MAX-ACCESS    read-only
  STATUS        current
  DESCRIPTION
    "Number of receive ethernet frames dropped due to congestion or because 
    frame is undersized.
    "
  ::= { gponVideoGemStatsEntry 4 }

videoGemPortTxBytes OBJECT-TYPE
  SYNTAX        Unsigned32
  MAX-ACCESS    read-only
  STATUS        current
  DESCRIPTION
    "Number of bytes transmitted on the video GEM port, not including GEM headers.
    "
  ::= { gponVideoGemStatsEntry 5 }

videoGemPortTxFragments OBJECT-TYPE
  SYNTAX        Unsigned32
  MAX-ACCESS    read-only
  STATUS        current
  DESCRIPTION
    "Number of GEM fragments transmitted on the video GEM port.
    "
  ::= { gponVideoGemStatsEntry 6 }

videoGemPortTxFrames OBJECT-TYPE
  SYNTAX        Unsigned32
  MAX-ACCESS    read-only
  STATUS        current
  DESCRIPTION
    "Number of ethernet frames transmitted on the video GEM port.
    "
  ::= { gponVideoGemStatsEntry 7 }

videoGemPortTxDroppedFrames OBJECT-TYPE
  SYNTAX        Unsigned32
  MAX-ACCESS    read-only
  STATUS        current
  DESCRIPTION
    "Number of ethernet frames dropped due to congestion.
    "
  ::= { gponVideoGemStatsEntry 8 }

videoGemPortAcceptedMulticastFrames OBJECT-TYPE
  SYNTAX        Unsigned32
  MAX-ACCESS    read-only
  STATUS        current
  DESCRIPTION
    "Number of multicast frames accepted by the Multicast Filtering Function. 
    "
  ::= { gponVideoGemStatsEntry 9 }

videoGemPortDroppedMulticastFrames OBJECT-TYPE
  SYNTAX        Unsigned32
  MAX-ACCESS    read-only
  STATUS        current
  DESCRIPTION
    "Number of multicast frames dropped by the Multicast Filtering Function.
    "
  ::= { gponVideoGemStatsEntry 10 }



--
-- GPON Link Objects 
-- InternetGatewayDevice.X_ZHONE_COM_GPONStats
--
-- 1.3.6.1.4.1.5504.2.5.43.1.6
--
gponGtcStatsTable OBJECT-TYPE
  SYNTAX        SEQUENCE OF GponGtcStatsEntry
  MAX-ACCESS    not-accessible
  STATUS        current
  DESCRIPTION
    "Table of GPON Transmission Convergence (GTC) 
     statistics for the Data GEM port."
  ::= { zhnGPONLinkObjects 6}

gponGtcStatsEntry OBJECT-TYPE
  SYNTAX        GponGtcStatsEntry
  MAX-ACCESS    not-accessible
  STATUS        current
  DESCRIPTION
    "Table of GPON Transmission Convergence (GTC) 
     statistics for the Data GEM port."
  INDEX        { gponIfIndex  }
  ::= { gponGtcStatsTable 1}


GponGtcStatsEntry ::=
  SEQUENCE {
      gtcBipErrors                          Unsigned32,
      gtcFecCorrectedCodewords              Unsigned32,
      gtcFecUncorrectableCodewords          Unsigned32,
      gtcTotalRxDsFecCodewords              Unsigned32,
      gtcFecCorrectionSeconds               Unsigned32,
      gtcCorrectedHecErrorsGemFrames        Unsigned32,
      gtcUncorrectableHecErrorsGemFrames    Unsigned32
  }

gtcBipErrors OBJECT-TYPE
  SYNTAX        Unsigned32
  MAX-ACCESS    read-only
  STATUS        current
  DESCRIPTION
    "Bit Interleaved Parity Errors.
    "
  ::= { gponGtcStatsEntry 1 }

gtcFecCorrectedCodewords OBJECT-TYPE
  SYNTAX        Unsigned32
  MAX-ACCESS    read-only
  STATUS        current
  DESCRIPTION
    "Forward Error Coding Corrected Codewords.
    "
  ::= { gponGtcStatsEntry 2 }

gtcFecUncorrectableCodewords OBJECT-TYPE
  SYNTAX        Unsigned32
  MAX-ACCESS    read-only
  STATUS        current
  DESCRIPTION
    "Forward Error Coding Uncorrectable Codewords.
    "
  ::= { gponGtcStatsEntry 3 }

gtcTotalRxDsFecCodewords OBJECT-TYPE
  SYNTAX        Unsigned32
  MAX-ACCESS    read-only
  STATUS        current
  DESCRIPTION
    "Total Received Downstream Forward Error Coding Codewords.
    "
  ::= { gponGtcStatsEntry 4 }

gtcFecCorrectionSeconds OBJECT-TYPE
  SYNTAX        Unsigned32
  MAX-ACCESS    read-only
  STATUS        current
  DESCRIPTION
    "Number of seconds during which there was a FEC correction anomaly.
    "
  ::= { gponGtcStatsEntry 5 }

gtcCorrectedHecErrorsGemFrames OBJECT-TYPE
  SYNTAX        Unsigned32
  MAX-ACCESS    read-only
  STATUS        current
  DESCRIPTION
    "Number of GEM frames with corrected HEC errors.
    "
  ::= { gponGtcStatsEntry 6 }

gtcUncorrectableHecErrorsGemFrames OBJECT-TYPE
  SYNTAX        Unsigned32
  MAX-ACCESS    read-only
  STATUS        current
  DESCRIPTION
    "Number of GEM frames with uncorrectable HEC errors.
    "
  ::= { gponGtcStatsEntry 7 }

  
  
--
-- GPON Link Objects 
-- InternetGatewayDevice.X_ZHONE_COM_GPONStats
--
-- 1.3.6.1.4.1.5504.2.5.43.1.7
--
gponPloamStatsTable OBJECT-TYPE
  SYNTAX        SEQUENCE OF GponPloamStatsEntry
  MAX-ACCESS    not-accessible
  STATUS        current
  DESCRIPTION
    "Table of GPON Physical Layer Operation, Administration and 
    Management (PLOAM) statistics for the Data GEM port."
  ::= { zhnGPONLinkObjects 7}

gponPloamStatsEntry OBJECT-TYPE
  SYNTAX        GponPloamStatsEntry
  MAX-ACCESS    not-accessible
  STATUS        current
  DESCRIPTION
    "Table of GPON Physical Layer Operation, Administration and 
    Management (PLOAM) statistics for the Data GEM port."
  INDEX        { gponIfIndex  }
  ::= { gponPloamStatsTable 1}


GponPloamStatsEntry ::=
  SEQUENCE {
      msgsCrcError                Unsigned32,
      msgsRxTotal                 Unsigned32,
      msgsRxUnicast               Unsigned32,
      msgsRxBroadcast             Unsigned32,
      msgsRxDiscarded             Unsigned32,
      msgsRxNonStandard           Unsigned32,
      msgsTxTotal                 Unsigned32,
      msgsTxNonStandard           Unsigned32
  }

msgsCrcError OBJECT-TYPE
  SYNTAX        Unsigned32
  MAX-ACCESS    read-only
  STATUS        current
  DESCRIPTION
    "Messages received in error and discarded.
    "
  ::= { gponPloamStatsEntry 1 }

msgsRxTotal OBJECT-TYPE
  SYNTAX        Unsigned32
  MAX-ACCESS    read-only
  STATUS        current
  DESCRIPTION
    "Total Number of CRC correct downstream PLOAM messages received.
    "
  ::= { gponPloamStatsEntry 2 }

msgsRxUnicast OBJECT-TYPE
  SYNTAX        Unsigned32
  MAX-ACCESS    read-only
  STATUS        current
  DESCRIPTION
    "Number of CRC correct downstream PLOAM messages with ONU ID matching 
    this ONU's ID.
    "
  ::= { gponPloamStatsEntry 3 }

msgsRxBroadcast OBJECT-TYPE
  SYNTAX        Unsigned32
  MAX-ACCESS    read-only
  STATUS        current
  DESCRIPTION
    "Number of CRC correct broadcast downstream PLOAM messages.
    "
  ::= { gponPloamStatsEntry 4 }

msgsRxDiscarded OBJECT-TYPE
  SYNTAX        Unsigned32
  MAX-ACCESS    read-only
  STATUS        current
  DESCRIPTION
    "Number of downstream PLOAM messages discarded, because the message 
    is unknown and not registered, or because the message is not valid 
    in the current state.
    "
  ::= { gponPloamStatsEntry 5 }

msgsRxNonStandard OBJECT-TYPE
  SYNTAX        Unsigned32
  MAX-ACCESS    read-only
  STATUS        current
  DESCRIPTION
    "Number of non-standard downstream PLOAM messages received from the OLT.
    "
  ::= { gponPloamStatsEntry 6 }

msgsTxTotal OBJECT-TYPE
  SYNTAX        Unsigned32
  MAX-ACCESS    read-only
  STATUS        current
  DESCRIPTION
    "Total number of PLOAM messages transmitted upstream to the OLT.
    "
  ::= { gponPloamStatsEntry 7 }

msgsTxNonStandard OBJECT-TYPE
  SYNTAX        Unsigned32
  MAX-ACCESS    read-only
  STATUS        current
  DESCRIPTION
    "Number of non-standard PLOAM messages transmitted upstream to the OLT.
    "
  ::= { gponPloamStatsEntry 8 }

  
  
  
-- ****************************************************************************
--
-- Conformance Information
--

zhnGPONLinkConformance OBJECT IDENTIFIER ::= { zhnGPONLink 2 }

zhnGPONLinkGroups OBJECT IDENTIFIER ::= { zhnGPONLinkConformance 1}
zhnGPONLinkCompliances OBJECT IDENTIFIER ::= { zhnGPONLinkConformance 2}
 
--
-- Compliance Statements
--

zhnGPONLinkCompliance  MODULE-COMPLIANCE
  STATUS        current
  DESCRIPTION
        "The Compliance statement for SNMP entities which
         manage the Zhone ONU GPON Interfaces"
  MODULE  -- this module
  MANDATORY-GROUPS {
         zhnGPONStatusGroup,
         zhnGPONAlarmGroup,
         zhnGPONDataGemStatsGroup,
         zhnGPONVideoGemStatsGroup,
	 zhnGPONGtcStatsGroup,
	 zhnGPONPloamStatsGroup
  }
  ::= {zhnGPONLinkCompliances 1}

  
--
-- Units of Conformance
--

zhnGPONStatusGroup OBJECT-GROUP
   OBJECTS {
      gponInterfaceNumberOfEntries,
      gponOperStatus,
      gponLinkUpTransitions,
      rfVideo,
      gponOnuId,
      gponState,
      rxLevel,
      txPower,
      txBiasCurrent,
      gponTemperature,
      gponVcc
   }
   STATUS current
   DESCRIPTION
      "A collection of Zhone GPON link objects that describe the 
      status and state of the GPON links of the ONU."
   ::= { zhnGPONLinkGroups 1}

zhnGPONAlarmGroup OBJECT-GROUP
   OBJECTS {
      gponAlarmAutoPowerControlFail,
      gponAlarmLOS,
      gponAlarmLOL,
      gponAlarmLOF,
      gponAlarmLCDG,
      gponAlarmFailedSignal,
      gponAlarmDegradedSignal,
      gponAlarmStartupFail,
      gponAlarmMsgErrorMsg,
      gponAlarmDeactivateOnuId,
      gponAlarmDisabledOnu,
      gponAlarmPEE
   }
   STATUS current
   DESCRIPTION
      "A collection of Zhone GPON Link objects that identify the 
       current alarms detected by the ONU."
   ::= { zhnGPONLinkGroups 2}

zhnGPONDataGemStatsGroup OBJECT-GROUP
   OBJECTS {
      dataGemPortRxBytes,
      dataGemPortRxFragments,
      dataGemPortRxFrames,
      dataGemPortRxDroppedFrames,
      dataGemPortTxBytes,
      dataGemPortTxFragments,
      dataGemPortTxFrames,
      dataGemPortTxDroppedFrames,
      dataGemPortAcceptedMulticastFrames,
      dataGemPortDroppedMulticastFrames
   }
   STATUS current
   DESCRIPTION
      "A collection of Zhone GPON Link objects that identify the
       GPON Encapsulation Method VoIP and Internet traffic statistics 
       for the Data GEM port."
   ::= { zhnGPONLinkGroups 3}

zhnGPONVideoGemStatsGroup OBJECT-GROUP
   OBJECTS {
      videoGemPortRxBytes,
      videoGemPortRxFragments,
      videoGemPortRxFrames,
      videoGemPortRxDroppedFrames,
      videoGemPortTxBytes,
      videoGemPortTxFragments,
      videoGemPortTxFrames,
      videoGemPortTxDroppedFrames,
      videoGemPortAcceptedMulticastFrames,
      videoGemPortDroppedMulticastFrames
   }
   STATUS current
   DESCRIPTION
      "A collection of Zhone GPON Link objects that identify the
       GPON Encapsulation Method Port statistics for the Video GEM 
       port."
   ::= { zhnGPONLinkGroups 4}

zhnGPONGtcStatsGroup OBJECT-GROUP
   OBJECTS {
      gtcBipErrors,
      gtcFecCorrectedCodewords,
      gtcFecUncorrectableCodewords,
      gtcTotalRxDsFecCodewords,
      gtcFecCorrectionSeconds,
      gtcCorrectedHecErrorsGemFrames,
      gtcUncorrectableHecErrorsGemFrames
   }
   STATUS current
   DESCRIPTION
      "A collection of Zhone GPON Link objects that identify the
       GPON Transmission Convergence statistics."
   ::= { zhnGPONLinkGroups 5}

zhnGPONPloamStatsGroup OBJECT-GROUP
   OBJECTS {
      msgsCrcError,
      msgsRxTotal,
      msgsRxUnicast,
      msgsRxBroadcast,
      msgsRxDiscarded,
      msgsRxNonStandard,
      msgsTxTotal,
      msgsTxNonStandard
   }
   STATUS current
   DESCRIPTION
      "A collection of Zhone GPON Link objects that identify the
       GPON Physical Layer Operation, Administration and Management
       (PLOAM) message statistics."
   ::= { zhnGPONLinkGroups 6}

END
