-- Copyright (C) 2012 by Zhone Technologies.  All Rights Reserved.

-- ======================================================================
-- ==                                                                  ==
-- ==                    ZHNWIRELESS MIB                               ==
-- ==                                                                  ==
-- ==  Copyright (C) 2012 Zhone Technologies, Inc.                     ==
-- ==  Confidential, Unpublished Property of Zhone Technologies.       ==
-- ==  Rights Reserved Under the Copyright Laws of the United States.  ==
-- ==                                                                  ==
-- ======================================================================

ZHNWIRELESS DEFINITIONS ::= BEGIN

IMPORTS
    MODULE-IDENTITY , OBJECT-TYPE , enterprises,
    Integer32, Unsigned32, IpAddress, Gauge32
        FROM SNMPv2-SMI
    MODULE-COMPLIANCE, OBJECT-GROUP
        FROM SNMPv2-CONF
    TEXTUAL-CONVENTION, MacAddress, TruthValue
        FROM SNMPv2-TC
    ZhoneRowStatus			
        FROM Zhone-TC
    zhoneWtn
        FROM Zhone;

-- 1.3.6.1.4.1.5504.2.5.46
zhnWireless  MODULE-IDENTITY
    LAST-UPDATED  "201207111200Z" -- July 11, 2012 at 12:00 GMT
    ORGANIZATION
        "Zhone Technologies, Inc."
    CONTACT-INFO 
        "Zhone Technologies, Inc.
         Florida Design Center
         8545 126th Avenue North
         Largo, FL 33773

	 Toll-Free: +1 877-ZHONE20 (+1 877-946-6320)
	 Tel: +1-510-777-7000
	 Fax: +1-510-777-7001
	 E-mail: support@zhone.com"


    DESCRIPTION
        "This file defines the private Enterprise MIB extensions
         that define Wireless configuration and status objects
	     supported by the Zhone ZNID CPEs."

    REVISION "201207111200Z" -- July 11, 2012 at 12:00 GMT
    DESCRIPTION "add wlVirtualEnable to WlVirtualIntfEntry"

    REVISION "201206211200Z" -- June 21, 2012 at 12:00 GMT
    DESCRIPTION "changed wlSecurityWepStatus to read-write"

    REVISION "201205161200Z" -- May 16, 2012 at 12:00 GMT
    DESCRIPTION "Added security objects:
        wlBaseCfgWpsAddClientMethod
        wlBaseCfgWpsApMode
        wlBaseCfgWpsConfigAp
        wlBaseCfgWpsDevicePIN
        wlBaseCfgWpsAddEnrollee
        wlBaseCfgWpsStationPIN
        wlBaseCfgBridgeRestrictMode
        wlBaseCfgBridgeRefresh"

    REVISION "201204181200Z" -- Apr 18, 2012 at 12:00 GMT
    DESCRIPTION 
        "added auto to Wl54gMulticastRates
         changed wlBaseCfgCurrentChannel to read-only
         changed wlSecurityWepStatus to WlWepModes
        "

    REVISION "201201301200Z"  -- Jan 30, 2012
    DESCRIPTION "First Draft"

::= { zhoneWtn 46 }



-- 1.3.6.1.4.1.5504.2.5.46.1
zhnWirelessObjects           OBJECT IDENTIFIER ::= { zhnWireless 1 }

WlChannelSelections ::= TEXTUAL-CONVENTION
  STATUS        current
  DESCRIPTION   "Broadcast channel selections."
  SYNTAX        INTEGER {
                  channel1(1),
                  channel2(2),
                  channel3(3),
                  channel4(4),
                  channel5(5),
                  channel6(6),
                  channel7(7),
                  channel8(8),
                  channel9(9),
                  channel10(10),
                  channel11(11),
                  channel12(12),
                  channel13(13),
                  auto(14)
                }

WlMimoNEwcModes ::= TEXTUAL-CONVENTION
  STATUS        current
  DESCRIPTION   "802.11n MIMO EWC modes of operation."
  SYNTAX        INTEGER {
                  auto(1),
                  disabled(2)
                }

WlMimoNRates ::= TEXTUAL-CONVENTION
  STATUS        current
  DESCRIPTION   "Supported 802.11n MIMO rates, in Mbps."
  SYNTAX        INTEGER {
                  auto(1),
                  use54g(2),
                  rate6Dot5M(3),
                  rate13M(4),
                  rate19Dot5M(5),
                  rate26M(6),
                  rate39M(7),
                  rate52M(8),
                  rate58Dot5M(9),
                  rate65M(10),
                  rate78M(11),
                  rate104M(12),
                  rate117M(13),
                  rate130M(14)
                }

WlMimoNProtectionModes ::= TEXTUAL-CONVENTION
  STATUS        current
  DESCRIPTION   "802.11n MIMO protection modes."
  SYNTAX        INTEGER {
                  off(1),
                  auto(2)
                }

Wl54gMulticastRates ::= TEXTUAL-CONVENTION
  STATUS        current
  DESCRIPTION   "Supported 802.11g and multicast rates, in Mbps."
  SYNTAX        INTEGER {
                  rate1M(1),
                  rate2M(2),
                  rate5Dot5M(3),
                  rate6M(4),
                  rate9M(5),
                  rate11M(6),
                  rate12M(7),
                  rate18M(8),
                  rate24M(9),
                  rate36M(10),
                  rate48M(11),
                  rate54M(12),
                  auto(13)
                }

WlBasicRates ::= TEXTUAL-CONVENTION
  STATUS        current
  DESCRIPTION   "Supported basic 802.11b/g rates, in Mbps."
  SYNTAX        INTEGER {
                  default(1),        -- use the factory defaulted basic rate
                  all(2),            -- allow all supported basic rates
                  rate1And2(3),      -- restrict the basic rates to 1Mbps and 2Mbps
                  stdRates(4)        -- restrict the basic rates to the standard rates of
                                     -- 1Mbps, 2Mbps, 5.5Mbps, 6Mbps, 11Mbps, 12Mbps, 24Mbps
                }

WlWepModes ::= TEXTUAL-CONVENTION
  STATUS        current
  DESCRIPTION   "WEP mode."
  SYNTAX        INTEGER {
                  disabled(1),
                  enabled(2)
                }

WlWpaModes ::= TEXTUAL-CONVENTION
  STATUS        current
  DESCRIPTION   "WPA Mode"
  SYNTAX        INTEGER {
                  tkip(1),
                  aes(2),
                  tkipAes(3)
                }

WlAuthenticationModes ::= TEXTUAL-CONVENTION
  STATUS        current
  DESCRIPTION   "WPA Mode"
  SYNTAX        INTEGER {
                  mode8011x(1),
                  open(2),
                  shared(3),
                  wpa(4),
                  wpa2(5),
                  wpaPsk(6),
                  wpa2Psk(7),
                  mixedWpa2Wpa(8),
                  mixedWpa2WpaPsk(9)
                }

WlSecurityKeyCodes ::= TEXTUAL-CONVENTION
  STATUS        current
  DESCRIPTION   "WEP Encryption strength code"
  SYNTAX        INTEGER {
                  bit64(1),
                  bit128(2)
                }

WlMACFilterModes ::= TEXTUAL-CONVENTION
  STATUS        current
  DESCRIPTION   "MAC Filter Modes"
  SYNTAX        INTEGER {
                  allow(1),
                  deny(2),
                  disable(3)
                }

WlBridgeAPModes ::= TEXTUAL-CONVENTION
  STATUS        current
  DESCRIPTION   "Wireless Bridge Modes of operation"
  SYNTAX        INTEGER {
                  accessPoint(1),
                  wirelessBridge(2)
                }

WlBridgeRestrictModes ::= TEXTUAL-CONVENTION
  STATUS        current
  DESCRIPTION   "Wireless Bridge Restriction Modes of operation"
  SYNTAX        INTEGER {
                  enable(1),
                  enableScan(2),
                  disable(3)
                }



WlCountryCodes ::= TEXTUAL-CONVENTION
  STATUS        current
  DESCRIPTION   "Two-character country code:
			AF    -- AFGHANISTAN
			AL    -- ALBANIA
			DZ    -- ALGERIA
			AS    -- AMERICAN SAMOA
			AO    -- ANGOLA
			AI    -- ANGUILLA
			AG    -- ANTIGUA AND BARBUDA
			AR    -- ARGENTINA
			AM    -- ARMENIA
			AW    -- ARUBA
			AU    -- AUSTRALIA
			AT    -- AUSTRIA
			AZ    -- AZERBAIJAN
			BS    -- BAHAMAS
			BH    -- BAHRAIN
			BD    -- BANGLADESH
			BB    -- BARBADOS
			BY    -- BELARUS
			BE    -- BELGIUM
			BZ    -- BELIZE
			BJ    -- BENIN
			BM    -- BERMUDA
			BT    -- BHUTAN
			BO    -- BOLIVIA
			BA    -- BOSNIA AND HERZEGOVINA
			BW    -- BOTSWANA
			BR    -- BRAZIL
			IO    -- BRITISH INDIAN OCEAN TERRITORY
			BN    -- BRUNEI DARUSSALAM
			BG    -- BULGARIA
			BF    -- BURKINA FASO
			BI    -- BURUNDI
			KH    -- CAMBODIA
			CM    -- CAMEROON
			CA    -- CANADA
			CV    -- CAPE VERDE
			KY    -- CAYMAN ISLANDS
			CF    -- CENTRAL AFRICAN REPUBLIC
			TD    -- CHAD
			CL    -- CHILE
			CN    -- CHINA
			CX    -- CHRISTMAS ISLAND
			CO    -- COLOMBIA
			KM    -- COMOROS
			CG    -- CONGO
			CD    -- CONGO, THE DEMOCRATIC REPUBLIC OF THE
			CR    -- COSTA RICA
			CI    -- COTE D'IVOIRE
			HR    -- CROATIA
			CU    -- CUBA
			CY    -- CYPRUS
			CZ    -- CZECH REPUBLIC
			DK    -- DENMARK
			DJ    -- DJIBOUTI
			DM    -- DOMINICA
			DO    -- DOMINICAN REPUBLIC
			EC    -- ECUADOR
			EG    -- EGYPT
			SV    -- EL SALVADOR
			GQ    -- EQUATORIAL GUINEA
			ER    -- ERITREA
			EE    -- ESTONIA
			ET    -- ETHIOPIA
			FK    -- FALKLAND ISLANDS (MALVINAS)
			FO    -- FAROE ISLANDS
			FJ    -- FIJI
			FI    -- FINLAND
			FR    -- FRANCE
			GF    -- FRENCH GUIANA
			PF    -- FRENCH POLYNESIA
			TF    -- FRENCH SOUTHERN TERRITORIES
			GA    -- GABON
			GM    -- GAMBIA
			GE    -- GEORGIA
			GH    -- GHANA
			GI    -- GIBRALTAR
			DE    -- GERMANY
			GR    -- GREECE
			GD    -- GRENADA
			GP    -- GUADELOUPE
			GU    -- GUAM
			GT    -- GUATEMALA
			GG    -- GUERNSEY
			GN    -- GUINEA
			GW    -- GUINEA-BISSAU
			GY    -- GUYANA
			HT    -- HAITI
			VA    -- HOLY SEE (VATICAN CITY STATE)
			HN    -- HONDURAS
			HK    -- HONG KONG
			HU    -- HUNGARY
			IS    -- ICELAND
			IN    -- INDIA
			ID    -- INDONESIA
			IQ    -- IRAQ
			IE    -- IRELAND
			IL    -- ISRAEL
			IT    -- ITALY
			JM    -- JAMAICA
			JP    -- JAPAN
			JE    -- JERSEY
			JO    -- JORDAN
			KZ    -- KAZAKHSTAN
			KE    -- KENYA
			KI    -- KIRIBATI
			KR    -- KOREA, REPUBLIC OF
			KW    -- KUWAIT
			KG    -- KYRGYZSTAN
			LA    -- LAO PEOPLE'S DEMOCRATIC REPUBLIC
			LV    -- LATVIA
			LB    -- LEBANON
			LS    -- LESOTHO
			LR    -- LIBERIA
			LY    -- LIBYAN ARAB JAMAHIRIYA
			LI    -- LIECHTENSTEIN
			LT    -- LITHUANIA
			LU    -- LUXEMBOURG
			MK    -- MACEDONIA, THE FORMER YUGOSLAV REPUBLIC OF
			MG    -- MADAGASCAR
			MW    -- MALAWI
			MO    -- MACAO
			MY    -- MALAYSIA
			MV    -- MALDIVES
			ML    -- MALI
			MT    -- MALTA
			IM    -- MAN, ISLE OF
			MQ    -- MARTINIQUE
			MR    -- MAURITANIA
			MU    -- MAURITIUS
			YT    -- MAYOTTE
			MX    -- MEXICO
			FM    -- MICRONESIA, FEDERATED STATES OF
			MD    -- MOLDOVA, REPUBLIC OF
			MC    -- MONACO
			MN    -- MONGOLIA
			ME    -- MONTENEGRO
			MS    -- MONTSERRAT
			MA    -- MOROCCO
			MZ    -- MOZAMBIQUE
			MM    -- MYANMAR
			NA    -- NAMIBIA
			NR    -- NAURU
			NP    -- NEPAL
			NL    -- NETHERLANDS
			AN    -- NETHERLANDS ANTILLES
			NC    -- NEW CALEDONIA
			NZ    -- NEW ZEALAND
			NI    -- NICARAGUA
			NE    -- NIGER
			NG    -- NIGERIA
			NU    -- NIUE
			NF    -- NORFOLK ISLAND
			MP    -- NORTHERN MARIANA ISLANDS
			NO    -- NORWAY
			OM    -- OMAN
			PK    -- PAKISTAN
			PW    -- PALAU
			PA    -- PANAMA
			PG    -- PAPUA NEW GUINEA
			PY    -- PARAGUAY
			PE    -- PERU
			PH    -- PHILIPPINES
			PL    -- POLAND
			PT    -- PORTUGAL
			PR    -- PUERTO RICO
			QA    -- QATAR
			RE    -- REUNION
			RO    -- ROMANIA
			RW    -- RWANDA
			KN    -- SAINT KITTS AND NEVIS
			LC    -- SAINT LUCIA
			RU    -- RUSSIAN FEDERATION
			PM    -- SAINT PIERRE AND MIQUELON
			VC    -- SAINT VINCENT AND THE GRENADINES
			WS    -- SAMOA
			SM    -- SAN MARINO
			ST    -- SAO TOME AND PRINCIPE
			SA    -- SAUDI ARABIA
			SN    -- SENEGAL
			RS    -- SERBIA
			SC    -- SEYCHELLES
			SL    -- SIERRA LEONE
			SG    -- SINGAPORE
			SK    -- SLOVAKIA
			SI    -- SLOVENIA
			SB    -- SOLOMON ISLANDS
			SO    -- SOMALIA
			ZA    -- SOUTH AFRICA
			ES    -- SPAIN
			LK    -- SRI LANKA
			SR    -- SURINAME
			SZ    -- SWAZILAND
			SE    -- SWEDEN
			CH    -- SWITZERLAND
			TW    -- TAIWAN, PROVINCE OF CHINA
			TJ    -- TAJIKISTAN
			TZ    -- TANZANIA, UNITED REPUBLIC OF
			TH    -- THAILAND
			TG    -- TOGO
			TO    -- TONGA
			TT    -- TRINIDAD AND TOBAGO
			TN    -- TUNISIA
			TR    -- TURKEY
			TM    -- TURKMENISTAN
			TC    -- TURKS AND CAICOS ISLANDS
			TV    -- TUVALU
			UG    -- UGANDA
			UA    -- UKRAINE
			AE    -- UNITED ARAB EMIRATES
			GB    -- UNITED KINGDOM
			US    -- UNITED STATES
			UM    -- UNITED STATES MINOR OUTLYING ISLANDS
			UY    -- URUGUAY
			UZ    -- UZBEKISTAN
			VU    -- VANUATU
			VE    -- VENEZUELA
			VN    -- VIET NAM
			VG    -- VIRGIN ISLANDS, BRITISH
			VI    -- VIRGIN ISLANDS, U.S.
			WF    -- WALLIS AND FUTUNA
			EH    -- WESTERN SAHARA
			YE    -- YEMEN
			ZM    -- ZAMBIA
			ZW    -- ZIMBABWE
		"
  SYNTAX        OCTET STRING (SIZE(2)) 

WlWpsAddClientMethod ::= TEXTUAL-CONVENTION
  STATUS        current
  DESCRIPTION   "WPS Add Client Method"
  SYNTAX        INTEGER {
                  pushButton(1),
                  accessPointPIN(2),
                  stationPIN(3)
                }  

--
-- 1.3.6.1.4.1.5504.2.5.46.1.1
-- InternetGatewayDevice.LANDevice.{i}.WLANConfiguration.{i}.X_BROADCOM_COM_WlanAdapter.WlBaseCfg
-- InternetGatewayDevice.LANDevice.{i}.WLANConfiguration.{i}.X_BROADCOM_COM_WlanAdapter.WlMimoCfg
--
wlBaseCfgTable OBJECT-TYPE
  SYNTAX        SEQUENCE OF WlBaseCfgEntry
  MAX-ACCESS    not-accessible
  STATUS        current
  DESCRIPTION
    "Table of basic Wireless Adapter Configuration objects."
  ::= { zhnWirelessObjects 1 }

wlBaseCfgEntry OBJECT-TYPE
  SYNTAX        WlBaseCfgEntry
  MAX-ACCESS    not-accessible
  STATUS        current
  DESCRIPTION
    "Table of entries of basic Wireless Adapter Configuration objects."
  INDEX        { wlBaseCfgIndex }
  ::= { wlBaseCfgTable 1}

WlBaseCfgEntry ::=
  SEQUENCE {
        wlBaseCfgIndex               Unsigned32,
        wlBaseCfgEnable              TruthValue,
        wlBaseCfgBand                OCTET STRING,
        wlBaseCfgChannel             WlChannelSelections,
        wlBaseCfgCurrentChannel      WlChannelSelections,
        wlBaseCfgBandwidth           OCTET STRING,
        wlBaseCfgAutoScanTimer       Unsigned32,
        wlBaseCfgMimoNEwc            WlMimoNEwcModes,
        wlBaseCfgMimoNRate           WlMimoNRates,
        wlBaseCfgMimoNProtection     WlMimoNProtectionModes,
        wlBaseCfgNClientsOnly        TruthValue,
        wlBaseCfg54gRate             Wl54gMulticastRates,
        wlBaseCfgMulticastRate       Wl54gMulticastRates,
        wlBaseCfgBasicRate           WlBasicRates,
        wlBaseCfgFragThreshold       Unsigned32,
        wlBaseCfgRTSThreshold        Unsigned32,
        wlBaseCfgDTIMInterval        Unsigned32,
        wlBaseCfgBeaconInterval      Unsigned32,
        wlBaseCfgGlobalMaxClients    Unsigned32,
        wlBaseCfgXPress              TruthValue,
        wlBaseCfgTxPowerPercent      Unsigned32,
        wlBaseCfgWMMEnable           TruthValue,
        wlBaseCfgWMMNoAck            TruthValue,
        wlBaseCfgWMMApsd             TruthValue,
        wlBaseCfgWpsAddClientMethod  WlWpsAddClientMethod,
        wlBaseCfgWpsApMode           TruthValue,
        wlBaseCfgWpsConfigAp         TruthValue,
        wlBaseCfgWpsDevicePIN        OCTET STRING,
        wlBaseCfgWpsAddEnrollee      TruthValue,
        wlBaseCfgWpsStationPIN       OCTET STRING,
        wlBaseCfgBridgeRestrictMode  WlBridgeRestrictModes,
        wlBaseCfgBridgeRefresh       TruthValue
  }

wlBaseCfgIndex OBJECT-TYPE
  SYNTAX        Unsigned32
  MAX-ACCESS    not-accessible
  STATUS        current
  DESCRIPTION
    "Basic wireless adapter interface index."
  ::= { wlBaseCfgEntry 1}

wlBaseCfgEnable OBJECT-TYPE
  SYNTAX        TruthValue
  MAX-ACCESS    read-write
  STATUS        current
  DESCRIPTION
    "Enable or disable the wireless adapter."
  ::= { wlBaseCfgEntry 2 }

wlBaseCfgBand OBJECT-TYPE
  SYNTAX        OCTET STRING
  MAX-ACCESS    read-only
  STATUS        current
  DESCRIPTION
    "Broadcast band (e.g. 2.4GHz operation)."
  ::= { wlBaseCfgEntry 3 }

wlBaseCfgChannel OBJECT-TYPE
  SYNTAX        WlChannelSelections
  MAX-ACCESS    read-write
  STATUS        current
  DESCRIPTION
    "The configured wifi channel number or 'auto' for 
     automatic selection of a channel with low interference."
  ::= { wlBaseCfgEntry 4}

wlBaseCfgCurrentChannel OBJECT-TYPE
  SYNTAX        WlChannelSelections
  MAX-ACCESS    read-only
  STATUS        current
  DESCRIPTION
    "The actual wifi channel number in use."
  ::= { wlBaseCfgEntry 5}

wlBaseCfgBandwidth OBJECT-TYPE
  SYNTAX        OCTET STRING
  MAX-ACCESS    read-only
  STATUS        current
  DESCRIPTION
    "Aggregate radio bandwidth."
  ::= { wlBaseCfgEntry 6}

wlBaseCfgAutoScanTimer OBJECT-TYPE
  SYNTAX        Unsigned32
  MAX-ACCESS    read-write
  STATUS        current
  DESCRIPTION
    "When configured for auto mode, this timer value specifies how
     often to re-analyze the spectrum to select a low interference
     channel. Note: auto channel rescan will only occur when there
     are no actively connected devices."
  ::= { wlBaseCfgEntry 7}

wlBaseCfgMimoNEwc OBJECT-TYPE
  SYNTAX        WlMimoNEwcModes
  MAX-ACCESS    read-write
  STATUS        current
  DESCRIPTION
    "Radio 802.11n Enhanced Wireless Consortium (EWC) mode:
           auto(1)
	   disable(2)
    "
  ::= { wlBaseCfgEntry 8 }

wlBaseCfgMimoNRate OBJECT-TYPE
  SYNTAX        WlMimoNRates
  MAX-ACCESS    read-write
  STATUS        current
  DESCRIPTION
    "The configured Multiple Input Multiple Output (MIMO) 802.11n rate. 
     Enumeration of:
                  auto(1),
                  use54g(2),
                  rate6Dot5(3),
                  rate13(4),
                  rate19Dot5(5),
                  rate26(6),
                  rate39(7),
                  rate52(8),
                  rate58Dot5(9),
                  rate65(10),
                  rate78(11),
                  rate104(12),
                  rate117(13),
                  rate130(14)
    "
  ::= { wlBaseCfgEntry 9 }

wlBaseCfgMimoNProtection OBJECT-TYPE
  SYNTAX        WlMimoNProtectionModes
  MAX-ACCESS    read-write
  STATUS        current
  DESCRIPTION
    "Multiple Input Multiple Output(MIMO) 802.11n protection mode. 
     Enumeration of:
           off(1),
           auto(2),
    "
  ::= { wlBaseCfgEntry 10 }

wlBaseCfgNClientsOnly OBJECT-TYPE
  SYNTAX        TruthValue
  MAX-ACCESS    read-write
  STATUS        current
  DESCRIPTION
    "Enable or disable the restriction of access to 802.11n
     clients, only. When enabled, prevent 802.11b/g clients 
     from connecting."
  ::= { wlBaseCfgEntry 11}

wlBaseCfg54gRate OBJECT-TYPE
  SYNTAX        Wl54gMulticastRates
  MAX-ACCESS    read-write
  STATUS        current
  DESCRIPTION
    "The rate when the radio is operating in 802.11g mode. This
     object only applies when the Multiple Input Multiple Output
     (MIMO) 802.11n Rate is set to use54g(2). Enumeration of:
                  rate1M(1),
                  rate2M(2),
                  rate5Dot5M(3),
                  rate6M(4),
                  rate9M(5),
                  rate11M(6),
                  rate12M(7),
                  rate18M(8),
                  rate24M(9),
                  rate36M(10),
                  rate48M(11),
                  rate54M(12)
    "
  ::= { wlBaseCfgEntry 12}

wlBaseCfgMulticastRate OBJECT-TYPE
  SYNTAX        Wl54gMulticastRates
  MAX-ACCESS    read-write
  STATUS        current
  DESCRIPTION
    "The rate for multicast traffic. Enumeration of:
                  rate1M(1),
                  rate2M(2),
                  rate5Dot5M(3),
                  rate6M(4),
                  rate9M(5),
                  rate11M(6),
                  rate12M(7),
                  rate18M(8),
                  rate24M(9),
                  rate36M(10),
                  rate48M(11),
                  rate54M(12)
    "
  ::= { wlBaseCfgEntry 13}

wlBaseCfgBasicRate OBJECT-TYPE
  SYNTAX        WlBasicRates
  MAX-ACCESS    read-write
  STATUS        current
  DESCRIPTION
    "The rate when the radio is operating in basic 802.11b/g mode.
     Enumeration of:
            default(1),        -- use the factory defaulted basic rate
            all(2),            -- allow all supported basic rates
            rate1And2(3),      -- restrict the basic rates to 1Mbps and 2Mbps
            stdRates(4)        -- restrict the basic rates to the standard rates of
                               -- 1Mbps, 2Mbps, 5.5Mbps, 6Mbps, 11Mbps, 12Mbps, 24Mbps
    "
  ::= { wlBaseCfgEntry 14}

wlBaseCfgFragThreshold OBJECT-TYPE
  SYNTAX        Unsigned32
  MAX-ACCESS    read-write
  STATUS        current
  DESCRIPTION
    "The threshold at which packets are fragmented."
  ::= { wlBaseCfgEntry 15}

wlBaseCfgRTSThreshold OBJECT-TYPE
  SYNTAX        Unsigned32
  MAX-ACCESS    read-write
  STATUS        current
  DESCRIPTION
    "The packet size of a request-to-send (RTS) transmission. A low
     threshold implies RTS packets are sent more frequently, thus
     requiring more bandwidth but ensuring packet transmission on
     a busy network."
  ::= { wlBaseCfgEntry 16}

wlBaseCfgDTIMInterval OBJECT-TYPE
  SYNTAX        Unsigned32
  MAX-ACCESS    read-write
  STATUS        current
  DESCRIPTION
    "The interval at which Delivery Traffic Indication Messages (DTIM)
     are generated. A DTIM message notifies a wireless client that 
     a packet is waiting for tranmission."
  ::= { wlBaseCfgEntry 17}

wlBaseCfgBeaconInterval OBJECT-TYPE
  SYNTAX        Unsigned32
  MAX-ACCESS    read-write
  STATUS        current
  DESCRIPTION
    "The interval at which Beacons are generated."
  ::= { wlBaseCfgEntry 18}

wlBaseCfgGlobalMaxClients OBJECT-TYPE
  SYNTAX        Unsigned32
  MAX-ACCESS    read-write
  STATUS        current
  DESCRIPTION
    "The maximum number of wireless client devices that may be simultaneously
     connected to the radio. This value should include the sum total of all 
     clients on all active SSIDs."
  ::= { wlBaseCfgEntry 19}

wlBaseCfgXPress OBJECT-TYPE
  SYNTAX        TruthValue
  MAX-ACCESS    read-write
  STATUS        current
  DESCRIPTION
    "Enable or disable the XPress(TM) Technology."
  ::= { wlBaseCfgEntry 20}

wlBaseCfgTxPowerPercent OBJECT-TYPE
  SYNTAX        Unsigned32
  MAX-ACCESS    read-write
  STATUS        current
  DESCRIPTION
    "The percentage of total power that should be used for data transmissions."
  ::= { wlBaseCfgEntry 21}

wlBaseCfgWMMEnable OBJECT-TYPE
  SYNTAX        TruthValue
  MAX-ACCESS    read-write
  STATUS        current
  DESCRIPTION
    "Enable or disable Wifi Multimedia. When set to TRUE, audio,
     video and voice application data is prioritized over other network
     traffic."
  ::= { wlBaseCfgEntry 22}

wlBaseCfgWMMNoAck OBJECT-TYPE
  SYNTAX        TruthValue
  MAX-ACCESS    read-write
  STATUS        current
  DESCRIPTION
    "Enable or disable the suppression of acknowledgements for frames
     that do not require a QOS Acknowledgement. This avoids the unnecessary
     transmission of acknowledgements for highly time-critical data."
  ::= { wlBaseCfgEntry 23}

wlBaseCfgWMMApsd OBJECT-TYPE
  SYNTAX        TruthValue
  MAX-ACCESS    read-write
  STATUS        current
  DESCRIPTION
    "Enable or disable the Automatic Power Save Delivery (APSD) power
     management method. This feature is useful for bi-directional applications,
     such as VoIp phones."
  ::= { wlBaseCfgEntry 24}

wlBaseCfgWpsAddClientMethod OBJECT-TYPE
  SYNTAX        WlWpsAddClientMethod
  MAX-ACCESS    read-write
  STATUS        current
  DESCRIPTION
    "Configure the method of adding Clients:
                  pushButton(1),
                  accessPointPIN(2),
                  stationPIN(3)
    "
  ::= { wlBaseCfgEntry 25 }

wlBaseCfgWpsApMode  OBJECT-TYPE
  SYNTAX        TruthValue
  MAX-ACCESS    read-only
  STATUS        current
  DESCRIPTION
    "Enable or disable WiFi Protected Setup (WPS) AP mode. If your provider
     is using an external registrar for security, select true(1).
     The PIN for AP mode is specified by the registrar. Provide this PIN to the
     client. Select wlBaseCfgWpsConfigAp to begin the registration process with
     the client."
  ::= { wlBaseCfgEntry 26 }

wlBaseCfgWpsConfigAp  OBJECT-TYPE
  SYNTAX        TruthValue
  MAX-ACCESS    read-only
  STATUS        current
  DESCRIPTION
    "Start AP configuration. If your provider is using an external registrar
     for security, wlBaseCfgWpsApMode then select true(1) to begin the
     registration process with the client."
  ::= { wlBaseCfgEntry 27 }

wlBaseCfgWpsDevicePIN OBJECT-TYPE
  SYNTAX        OCTET STRING (SIZE(8))
  MAX-ACCESS    read-only
  STATUS        current
  DESCRIPTION
    "Device PIN provided by external registrar."
  ::= { wlBaseCfgEntry 28 }

wlBaseCfgWpsAddEnrollee  OBJECT-TYPE
  SYNTAX        TruthValue
  MAX-ACCESS    read-only
  STATUS        current
  DESCRIPTION
    "Start AP configuration. If wlBaseCfgWpsAddClientMethod is set for
     pushButton(1), then the user must simultaneously push the WPS button
     on the rear panel of the wireless zNID and set this object to true(1)
     for push button registration on the client device."
  ::= { wlBaseCfgEntry 29 }

wlBaseCfgWpsStationPIN OBJECT-TYPE
  SYNTAX        OCTET STRING (SIZE(8))
  MAX-ACCESS    read-only
  STATUS        current
  DESCRIPTION
    "Station PIN provided by user."
  ::= { wlBaseCfgEntry 30 }

wlBaseCfgBridgeRestrictMode OBJECT-TYPE
  SYNTAX        WlBridgeRestrictModes
  MAX-ACCESS    read-write
  STATUS        current
  DESCRIPTION
    "Configure the bridge restriction mode:
                  enable(1),
                  enableScan(2),
                  disable(3),
    "
  ::= { wlBaseCfgEntry 31 }

wlBaseCfgBridgeRefresh  OBJECT-TYPE
  SYNTAX        TruthValue
  MAX-ACCESS    read-only
  STATUS        current
  DESCRIPTION
    "Scans for any wireless bridge devices in range and displays them in
     the Remote Bridge MAC Address table. Selecting true(1) will update the
     wireless bridge devices in range. Wait for a few seconds for the update.
    "
  ::= { wlBaseCfgEntry 32 }




--
-- 1.3.6.1.4.1.5504.2.5.46.1.2
-- InternetGatewayDevice.LANDevice.{i}.WLANConfiguration.{i}.X_BROADCOM_COM_WlanAdapter.VirtIntf.{i}
--
wlVirtualIntfTable OBJECT-TYPE
  SYNTAX        SEQUENCE OF WlVirtualIntfEntry
  MAX-ACCESS    not-accessible
  STATUS        current
  DESCRIPTION
    "Table of Wireless Virtual LAN Interface Configuration, Status and Statistics objects."
  ::= { zhnWirelessObjects 2 }

wlVirtualIntfEntry OBJECT-TYPE
  SYNTAX        WlVirtualIntfEntry
  MAX-ACCESS    not-accessible
  STATUS        current
  DESCRIPTION
    "Entries in Wireless Vitrual LAN Interface Table."
  INDEX        { wlBaseCfgIndex, wlVirtualIndex }
  ::= { wlVirtualIntfTable 1 }

WlVirtualIntfEntry ::=
  SEQUENCE {
        wlVirtualIndex               Unsigned32,
        wlVirtualHide                TruthValue,
        wlVirtualAPIsolation         TruthValue,
        wlVirtualDisableWme          TruthValue,
        wlVirtualEnableWmf           TruthValue,
        wlVirtualSsid                OCTET STRING,
        wlVirtualBssMacAddr          MacAddress,
        wlVirtualCountryCode         WlCountryCodes,
        wlVirtualMaxClients          Unsigned32,
        wlVirtualEnable              TruthValue
}
wlVirtualIndex OBJECT-TYPE
  SYNTAX        Unsigned32
  MAX-ACCESS    not-accessible
  STATUS        current
  DESCRIPTION
    "Basic access point interface index. Guest (or Virtual) access points begin
     with index = 2."
  ::= { wlVirtualIntfEntry 1 }

wlVirtualHide OBJECT-TYPE
  SYNTAX        TruthValue
  MAX-ACCESS    read-write
  STATUS        current
  DESCRIPTION
    "Enable or disable the suppression of the advertising of the access point's SSID.
     If enabled, clients will need to configure the SSID to associate."
  ::= { wlVirtualIntfEntry 2 }

wlVirtualAPIsolation OBJECT-TYPE
  SYNTAX        TruthValue
  MAX-ACCESS    read-write
  STATUS        current
  DESCRIPTION
    "Enable or disable the isolation of clients by enabling or disabling secure
     forwarding mode. This will preventpreventing one client from sending packets 
     directly to another client. All packets are forwarded upstream on the WAN 
     interface."
  ::= { wlVirtualIntfEntry 3 }

wlVirtualDisableWme OBJECT-TYPE
  SYNTAX        TruthValue
  MAX-ACCESS    read-write
  STATUS        current
  DESCRIPTION
    "Enable or disable the Wireless Multi-Media mode."
  ::= { wlVirtualIntfEntry 4 }

wlVirtualEnableWmf OBJECT-TYPE
  SYNTAX        TruthValue
  MAX-ACCESS    read-write
  STATUS        current
  DESCRIPTION
    "Enable or disable Wireless Multicast Forwarding."
  ::= { wlVirtualIntfEntry 5 }

wlVirtualSsid OBJECT-TYPE
  SYNTAX        OCTET STRING (SIZE(0..72))
  MAX-ACCESS    read-write
  STATUS        current
  DESCRIPTION
    "Configure the Primary SSID assigned to the wl0 interface,
     or the Guest SSIDs assigned to the virtual wireless
     interfaces."
  ::= { wlVirtualIntfEntry 6 }

wlVirtualBssMacAddr OBJECT-TYPE
  SYNTAX        MacAddress
  MAX-ACCESS    read-only
  STATUS        current
  DESCRIPTION
    "MAC Address assigned to the primary SSID."
  ::= { wlVirtualIntfEntry 7 }

wlVirtualCountryCode OBJECT-TYPE
  SYNTAX        WlCountryCodes
  MAX-ACCESS    read-only
  STATUS        current
  DESCRIPTION
    "Two character country code. The country code is automatically configured
     based upon the model number of the unit. All countries with 100mW EIRP 
     maximum transmit power use the United Kingdom country code. North American 
     models may use the maximum transmit power of 300mW EIRP."
  ::= { wlVirtualIntfEntry 8 }

wlVirtualMaxClients OBJECT-TYPE
  SYNTAX        Unsigned32
  MAX-ACCESS    read-write
  STATUS        current
  DESCRIPTION
    "Maximum number of client devices that may be simultaneously connected 
     to this SSID. The maximum clients value assigned to each access points
     must not exceed the global maximum clients value."
  ::= { wlVirtualIntfEntry 9 }

wlVirtualEnable OBJECT-TYPE
  SYNTAX        TruthValue
  MAX-ACCESS    read-write
  STATUS        current
  DESCRIPTION
    "Enable or disable a single Wireless Virtual LAN Interface"
  ::= { wlVirtualIntfEntry 10 }


--
-- 1.3.6.1.4.1.5504.2.5.46.1.3
-- InternetGatewayDevice.LANDevice.{i}.WLANConfiguration.{i}.X_BROADCOM_COM_WlanAdapter.VirtIntfCfg.{i}
-- InternetGatewayDevice.LANDevice.{i}.WLANConfiguration.{i}.X_BROADCOM_COM_WlanAdapter.VirtIntf.{i}.WlKey64Cfg.{i}
-- InternetGatewayDevice.LANDevice.{i}.WLANConfiguration.{i}.X_BROADCOM_COM_WlanAdapter.VirtIntf.{i}.WlKey128Cfg.{i}
--
wlSecurityTable OBJECT-TYPE
  SYNTAX        SEQUENCE OF WlSecurityEntry
  MAX-ACCESS    not-accessible
  STATUS        current
  DESCRIPTION
    "Table of Wireless Security Configuration, Status and Statistics objects
     for virtual LAN interfaces."
  ::= { zhnWirelessObjects 3 }

wlSecurityEntry OBJECT-TYPE
  SYNTAX        WlSecurityEntry
  MAX-ACCESS    not-accessible
  STATUS        current
  DESCRIPTION
    "Table of entries, per virtual LAN interface, of Wireless Security objects."
  INDEX        { wlBaseCfgIndex, wlVirtualIndex }
  ::= { wlSecurityTable 1 }

WlSecurityEntry ::=
  SEQUENCE {
        wlSecuritySsid                   OCTET STRING,
        wlSecurityWps                    TruthValue,
        wlSecurityAuthMode               WlAuthenticationModes,
        wlSecurityWpaPsk                 OCTET STRING,
        wlSecurityWpaGTKRekey            Unsigned32,
        wlSecurityWpaMode                WlWpaModes,
        wlSecurityWepStatus              WlWepModes,
        wlSecurityRadiusServerIP         IpAddress,
        wlSecurityRadiusPort             Unsigned32,
        wlSecurityRadiusKey              OCTET STRING,
        wlSecurityWepKey                 WlSecurityKeyCodes,
        wlSecurityCurrentWepKeyIndex64   Unsigned32,
        wlSecurityCurrentWepKeyIndex128  Unsigned32,
        wlSecurityWep64Key1              OCTET STRING,
        wlSecurityWep64Key2              OCTET STRING,
        wlSecurityWep64Key3              OCTET STRING,
        wlSecurityWep64Key4              OCTET STRING,
        wlSecurityWep128Key1             OCTET STRING,
        wlSecurityWep128Key2             OCTET STRING,
        wlSecurityWep128Key3             OCTET STRING,
        wlSecurityWep128Key4             OCTET STRING,
        wlSecurityWpa2Preauth            TruthValue,
        wlSecurityWpa2NetReauth          Unsigned32,
        wlSecurityMACFilterMode          WlMACFilterModes
  }

wlSecuritySsid OBJECT-TYPE
  SYNTAX        OCTET STRING (SIZE(0..72))
  MAX-ACCESS    read-only
  STATUS        current
  DESCRIPTION
    "The primary SSID assigned to the wl0 interface,
     or the Guest SSIDs assigned to this virtual wireless
     interface."
  ::= { wlSecurityEntry 1 }

wlSecurityWps  OBJECT-TYPE
  SYNTAX        TruthValue
  MAX-ACCESS    read-only
  STATUS        current
  DESCRIPTION
    "Enable or disable WiFi Protected Setup (WPS) security method. If
     WPS is disabled, the network authentication method, the data encryption, 
     and network key should also be configured in order to authenticate to 
     this wireless network."
  ::= { wlSecurityEntry 2 }

wlSecurityAuthMode OBJECT-TYPE
  SYNTAX        WlAuthenticationModes
  MAX-ACCESS    read-write
  STATUS        current
  DESCRIPTION
    "Configure the network authentication method: 
                  mode8011x(1),
                  open(2),
                  shared(3),
                  wpa(4),
                  wpa2(5),
                  wpaPsk(6),
                  wpa2Psk(7),
                  mixedWpa2Wpa(8),
                  mixedWpa2WpaPsk(9)
    "
  ::= { wlSecurityEntry 3 }

wlSecurityWpaPsk OBJECT-TYPE
  SYNTAX        OCTET STRING (SIZE(0..72))
  MAX-ACCESS    read-write
  STATUS        current
  DESCRIPTION
    "WPA/WPAI Passphrase. This field cannot contain a SPACE and is 
     returned as a string of asterisks."
  ::= { wlSecurityEntry 4 }

wlSecurityWpaGTKRekey OBJECT-TYPE
  SYNTAX        Unsigned32(0..2147483647)
  MAX-ACCESS    read-write
  STATUS        current
  DESCRIPTION
    "WPA Group Rekey Interval."
  ::= { wlSecurityEntry 5 }

wlSecurityWpaMode OBJECT-TYPE
  SYNTAX        WlWpaModes
  MAX-ACCESS    read-write
  STATUS        current
  DESCRIPTION
    "WPA/WAPI Encryption mode:
                  tkip(1),
                  aes(2),
                  tkipAes(3)
    "
  ::= { wlSecurityEntry 6 }

wlSecurityWepStatus OBJECT-TYPE
  SYNTAX        WlWepModes
  MAX-ACCESS    read-write
  STATUS        current
  DESCRIPTION
    "Status of Wireless Encryption Protocol (WEP) encryption: 
                  disabled(1)
                  enabled(2)
    "
  ::= { wlSecurityEntry 7 }

wlSecurityRadiusServerIP OBJECT-TYPE
  SYNTAX        IpAddress
  MAX-ACCESS    read-write
  STATUS        current
  DESCRIPTION
    "IP address of the Remote Authentication Dial In User Server (RADIUS)
     used for 802.1x authentication."
  ::= { wlSecurityEntry 8 }

wlSecurityRadiusPort OBJECT-TYPE
  SYNTAX        Unsigned32 (0..65535)
  MAX-ACCESS    read-write
  STATUS        current
  DESCRIPTION
    "UDP port to use for accessing the Remote Authentication Dial In User 
     Server (RADIUS)."

  ::= { wlSecurityEntry 9 }

wlSecurityRadiusKey OBJECT-TYPE
  SYNTAX        OCTET STRING (SIZE(0..72))
  MAX-ACCESS    read-write
  STATUS        current
  DESCRIPTION
    "Remote Authentication Dial In User Server (RADIUS) authentication key. 
     This field cannot contain a SPACE and is returned as a string of asterisks."
  ::= { wlSecurityEntry 10 }

wlSecurityWepKey OBJECT-TYPE
  SYNTAX        WlSecurityKeyCodes
  MAX-ACCESS    read-write
  STATUS        current
  DESCRIPTION
    "Security encryption strength:
                  bit64(1)
                  bit128(2)
    "
  ::= { wlSecurityEntry 11 }

wlSecurityCurrentWepKeyIndex64 OBJECT-TYPE
  SYNTAX        Unsigned32(1..4)
  MAX-ACCESS    read-write
  STATUS        current
  DESCRIPTION
    "Index into array of 64-bit encryption keys."
  ::= { wlSecurityEntry 12 }

wlSecurityCurrentWepKeyIndex128 OBJECT-TYPE
  SYNTAX        Unsigned32(1..4)
  MAX-ACCESS    read-write
  STATUS        current
  DESCRIPTION
    "Index into array of 128-bit encryption keys."
  ::= { wlSecurityEntry 13 }

wlSecurityWep64Key1 OBJECT-TYPE
  SYNTAX        OCTET STRING (SIZE(5..10))
  MAX-ACCESS    read-write
  STATUS        current
  DESCRIPTION
    "WEP 64-bit encryption key 1 string, which must consist of 5 ASCII characters
     or 10 hexadecimal digits."
  ::= { wlSecurityEntry 14 }

wlSecurityWep64Key2 OBJECT-TYPE
  SYNTAX        OCTET STRING (SIZE(5..10))
  MAX-ACCESS    read-write
  STATUS        current
  DESCRIPTION
    "WEP 64-bit encryption key 2 string, which must consist of 5 ASCII characters
     or 10 hexadecimal digits."
  ::= { wlSecurityEntry 15 }

wlSecurityWep64Key3 OBJECT-TYPE
  SYNTAX        OCTET STRING (SIZE(5..10))
  MAX-ACCESS    read-write
  STATUS        current
  DESCRIPTION
    "WEP 64-bit encryption key 3 string, which must consist of 5 ASCII characters
     or 10 hexadecimal digits."
  ::= { wlSecurityEntry 16 }

wlSecurityWep64Key4 OBJECT-TYPE
  SYNTAX        OCTET STRING (SIZE(5..10))
  MAX-ACCESS    read-write
  STATUS        current
  DESCRIPTION
    "WEP 64-bit encryption key 4 string, which must consist of 5 ASCII characters
     or 10 hexadecimal digits."
  ::= { wlSecurityEntry 17 }

wlSecurityWep128Key1 OBJECT-TYPE
  SYNTAX        OCTET STRING (SIZE(13..26))
  MAX-ACCESS    read-write
  STATUS        current
  DESCRIPTION
    "WEP 128-bit encryption key 1 string, which must consist of 13 ASCII characters
     or 26 hexadecimal digits."
  ::= { wlSecurityEntry 18 }

wlSecurityWep128Key2 OBJECT-TYPE
  SYNTAX        OCTET STRING (SIZE(13..26))
  MAX-ACCESS    read-write
  STATUS        current
  DESCRIPTION
    "WEP 128-bit encryption key 2 string, which must consist of 13 ASCII characters
     or 26 hexadecimal digits."
  ::= { wlSecurityEntry 19 }

wlSecurityWep128Key3 OBJECT-TYPE
  SYNTAX        OCTET STRING (SIZE(13..26))
  MAX-ACCESS    read-write
  STATUS        current
  DESCRIPTION
    "WEP 128-bit encryption key 3 string, which must consist of 13 ASCII characters
     or 26 hexadecimal digits."
  ::= { wlSecurityEntry 20 }

wlSecurityWep128Key4 OBJECT-TYPE
  SYNTAX        OCTET STRING (SIZE(13..26))
  MAX-ACCESS    read-write
  STATUS        current
  DESCRIPTION
    "WEP 128-bit encryption key 4 string, which must consist of 13 ASCII characters
     or 26 hexadecimal digits."
  ::= { wlSecurityEntry 21 }

wlSecurityWpa2Preauth OBJECT-TYPE
  SYNTAX        TruthValue
  MAX-ACCESS    read-write
  STATUS        current
  DESCRIPTION
    "Enable or disable WPA2 pre-authentication."
  ::= { wlSecurityEntry 22 }

wlSecurityWpa2NetReauth OBJECT-TYPE
  SYNTAX        Unsigned32(0..604800)
  MAX-ACCESS    read-write
  STATUS        current
  DESCRIPTION
    "Configure the WPA2 network re-authentication time, in seconds."
  ::= { wlSecurityEntry 23 }

wlSecurityMACFilterMode OBJECT-TYPE
  SYNTAX        WlMACFilterModes
  MAX-ACCESS    read-write
  STATUS        current
  DESCRIPTION
    "Configure the MAC Filter mode. The MAC Filter rules defined in the 
     wlMACFilterTable will be ignored when this object is set to disable(3)."
  ::= { wlSecurityEntry 24 }



--
-- 1.3.6.1.4.1.5504.2.5.46.1.4
-- InternetGatewayDevice.LANDevice.{i}.WLANConfiguration.{i}.X_BROADCOM_COM_WlanAdapter.VirtIntf.{i}.WlMacFltCfg.{i}
--
wlMACFilterTable OBJECT-TYPE
  SYNTAX        SEQUENCE OF WlMACFilterEntry
  MAX-ACCESS    not-accessible
  STATUS        current
  DESCRIPTION
    "Table of Wireless MAC filter rules for a virtual wireless interface.
     The MAC Filter table contains a list of MAC addresses for devices that
     are permitted to connect, or prevented from connecting to the wireless
     service."
  ::= { zhnWirelessObjects 4 }

wlMACFilterEntry OBJECT-TYPE
  SYNTAX        WlMACFilterEntry
  MAX-ACCESS    not-accessible
  STATUS        current
  DESCRIPTION
    "Entries in the Wireless MAC filter rules for a virtual wireless interface."
  INDEX        { wlBaseCfgIndex, wlVirtualIndex, wlMACFilterIndex }
  ::= { wlMACFilterTable 1 }

WlMACFilterEntry ::=
  SEQUENCE {
        wlMACFilterIndex               Unsigned32,
        wlMACFilterSsid                OCTET STRING,
        wlMACFilterMacAddr             MacAddress,
        wlMACFilterIfName              OCTET STRING,
        wlMACFilterRowStatus           ZhoneRowStatus
  }

wlMACFilterIndex OBJECT-TYPE
  SYNTAX        Unsigned32
  MAX-ACCESS    not-accessible
  STATUS        current
  DESCRIPTION
    "The Wireless MAC filter table index."
  ::= { wlMACFilterEntry 1 }

wlMACFilterSsid OBJECT-TYPE
  SYNTAX        OCTET STRING (SIZE(0..72))
  MAX-ACCESS    read-only
  STATUS        current
  DESCRIPTION
    "The primary SSID assigned to the wl0 interface,
     or the Guest SSIDs assigned to this virtual wireless
     interface."
  ::= { wlMACFilterEntry 2 }

wlMACFilterMacAddr OBJECT-TYPE
  SYNTAX        MacAddress
  MAX-ACCESS    read-only
  STATUS        current
  DESCRIPTION
    "The MAC address which to apply to the filter rule."
  ::= { wlMACFilterEntry 3 }

wlMACFilterIfName OBJECT-TYPE
  SYNTAX        OCTET STRING (SIZE(0..72))
  MAX-ACCESS    read-only
  STATUS        current
  DESCRIPTION
    "The virtual interface name to which this rule applies."
  ::= { wlMACFilterEntry 4 }

wlMACFilterRowStatus OBJECT-TYPE
  SYNTAX        ZhoneRowStatus
  MAX-ACCESS    read-create
  STATUS current
  DESCRIPTION
  "The SNMP RowStatus of the current row. When creating a new
   MAC Filter entry for a virtual wireless interface, only the
   MAC Address must be specified. The wlVirtualIndex will 
   be used to determine the SSID and the filter mode to 
   apply. "
  ::= { wlMACFilterEntry 5 }

 
--
-- 1.3.6.1.4.1.5504.2.5.46.1.5
-- InternetGatewayDevice.LANDevice.{i}.WLANConfiguration.{i}.X_BROADCOM_COM_WlanAdapter.WlStaticWdsCfg.{i}.
--
wlStaticWdsMACAddrTable OBJECT-TYPE
  SYNTAX        SEQUENCE OF WlStaticWdsMACAddrEntry
  MAX-ACCESS    not-accessible
  STATUS        current
  DESCRIPTION
    "Table of statically configured Remote MAC Addresses which are permitted
     to bridge to the wireless LAN interfaces when the Bridge restriction mode 
     is enabled."
  ::= {  zhnWirelessObjects 5 }

wlStaticWdsMACAddrEntry OBJECT-TYPE
  SYNTAX        WlStaticWdsMACAddrEntry
  MAX-ACCESS    not-accessible
  STATUS        current
  DESCRIPTION
    "Table of statically configured Remote MAC Addresses which are permitted
     to bridge to the wireless LAN interfaces when the Bridge restriction mode 
     is enabled."
  INDEX        { wlBaseCfgIndex, wlStaticWdsMACIndex }
  ::= { wlStaticWdsMACAddrTable 1 }

WlStaticWdsMACAddrEntry ::=
  SEQUENCE {
        wlStaticWdsMACIndex                 Unsigned32,
        wlStaticWdsRemoteMACAddr            MacAddress
  }


wlStaticWdsMACIndex OBJECT-TYPE
  SYNTAX        Unsigned32
  MAX-ACCESS    not-accessible
  STATUS        current
  DESCRIPTION
    "The index into the static WDS Remote MAC Address table for a wireless LAN
     interface."
  ::= { wlStaticWdsMACAddrEntry 1 }

wlStaticWdsRemoteMACAddr OBJECT-TYPE
  SYNTAX        MacAddress
  MAX-ACCESS    read-write
  STATUS        current
  DESCRIPTION
    "The MAC address that is permitted WDS bridge access to the wireless LAN 
     interface."
  ::= { wlStaticWdsMACAddrEntry 2 }


--
-- 1.3.6.1.4.1.5504.2.5.46.1.6
-- InternetGatewayDevice.LANDevice.{i}.WLANConfiguration.{i}.X_BROADCOM_COM_WlanAdapter.WlScanWdsCfg.{i}.
--
wlScanWdsMACAddrTable OBJECT-TYPE
  SYNTAX        SEQUENCE OF WlScanWdsMACAddrEntry
  MAX-ACCESS    not-accessible
  STATUS        current
  DESCRIPTION
    "Table of scanned Remote MAC Addresses which are permitted to 
     bridge to the wireless LAN interfaces when the Bridge restriction
     mode is enabled."
  ::= {  zhnWirelessObjects 6 }

wlScanWdsMACAddrEntry OBJECT-TYPE
  SYNTAX        WlScanWdsMACAddrEntry
  MAX-ACCESS    not-accessible
  STATUS        current
  DESCRIPTION
    "Table of scanned Remote MAC Addresses which are permitted to 
     bridge to the wireless LAN interfaces when the Bridge restriction
     mode is enabled."
  INDEX        { wlBaseCfgIndex, wlScanWdsMACIndex }
  ::= { wlScanWdsMACAddrTable 1 }

WlScanWdsMACAddrEntry ::=
  SEQUENCE {
        wlScanWdsMACIndex                 Unsigned32,
        wlScanWdsRemoteMACAddr            MacAddress
  }

wlScanWdsMACIndex OBJECT-TYPE
  SYNTAX        Unsigned32
  MAX-ACCESS    not-accessible
  STATUS        current
  DESCRIPTION
    "The index into the WDS scanned table of Remote MAC Addresses that may
     access a wireless LAN interface."
  ::= { wlScanWdsMACAddrEntry 1 }

wlScanWdsRemoteMACAddr OBJECT-TYPE
  SYNTAX        MacAddress
  MAX-ACCESS    read-only
  STATUS        current
  DESCRIPTION
    "The MAC address previously scanned that is permitted WDS bridge access to
     the wireless LAN interface."
  ::= { wlScanWdsMACAddrEntry 2 }


--
-- 1.3.6.1.4.1.5504.2.5.46.1.4.7
--
wlAuthStationsTable OBJECT-TYPE
  SYNTAX        SEQUENCE OF WlAuthStationsEntry
  MAX-ACCESS    not-accessible
  STATUS        current
  DESCRIPTION
    "Table of authenicated wireless stations and their status information."
  ::= {  zhnWirelessObjects 7 }

wlAuthStationsEntry OBJECT-TYPE
  SYNTAX        WlAuthStationsEntry
  MAX-ACCESS    not-accessible
  STATUS        current
  DESCRIPTION
    "Table of authenicated wireless stations and their status information."
  INDEX        { wlAuthStationIndex }
  ::= { wlAuthStationsTable 1 }

WlAuthStationsEntry ::=
  SEQUENCE {
        wlAuthStationIndex                    Unsigned32,
        wlAuthStationMACAddr                  MacAddress,
        wlAuthStationAssociationStatus        TruthValue,         
        wlAuthStationAuthorizationStatus      TruthValue,
        wlAuthStationSSID                     OCTET STRING,
        wlAuthStationInterface                OCTET STRING
  }

wlAuthStationIndex OBJECT-TYPE
  SYNTAX        Unsigned32
  MAX-ACCESS    not-accessible
  STATUS        current
  DESCRIPTION
    "The index into the Authentication Stations table."
  ::= { wlAuthStationsEntry 1 }

wlAuthStationMACAddr OBJECT-TYPE
  SYNTAX        MacAddress
  MAX-ACCESS    read-only
  STATUS        current
  DESCRIPTION
    "The MAC address of the authenticated station."
  ::= { wlAuthStationsEntry 2 }

wlAuthStationAssociationStatus OBJECT-TYPE
  SYNTAX        TruthValue
  MAX-ACCESS    read-only
  STATUS        current
  DESCRIPTION
    "True if the station has been associated."
  ::= { wlAuthStationsEntry 3 }

wlAuthStationAuthorizationStatus OBJECT-TYPE
  SYNTAX        TruthValue
  MAX-ACCESS    read-only
  STATUS        current
  DESCRIPTION
    "True if the station has been authorized."
  ::= { wlAuthStationsEntry 4 }

wlAuthStationSSID OBJECT-TYPE
  SYNTAX        OCTET STRING
  MAX-ACCESS    read-only
  STATUS        current
  DESCRIPTION
    "SSID with which the station has authenticated."
  ::= { wlAuthStationsEntry 5 }

wlAuthStationInterface OBJECT-TYPE
  SYNTAX        OCTET STRING
  MAX-ACCESS    read-only
  STATUS        current
  DESCRIPTION
    "Interface through which the station has authenticated."
  ::= { wlAuthStationsEntry 6 }



-- ****************************************************************************
--
-- Conformance Information
--

zhnWirelessConformance OBJECT IDENTIFIER ::= { zhnWireless 2 }

zhnWirelessGroups OBJECT IDENTIFIER ::= { zhnWirelessConformance 1}
zhnWirelessCompliances OBJECT IDENTIFIER ::= { zhnWirelessConformance 2}
 
--
-- Compliance Statements
--

zhnWirelessCompliance  MODULE-COMPLIANCE
  STATUS        current
  DESCRIPTION
        "The Compliance statement for SNMP entities which
         manage the Zhone CPE Wireless Configuration, Status and 
	 Statistics Information"
  MODULE  -- this module
  MANDATORY-GROUPS {
         zhnWlBaseCfgGroup,
         zhnWlVirtualCfgGroup,
         zhnWlSecurityGroup,
         zhnWlMACFilterGroup,
         zhnWlStaticWdsMACAddrGroup,
         zhnWlScanWdsMACAddrGroup,
         zhnWlAuthStationsGroup
  }
  ::= {zhnWirelessCompliances 1}


--
-- Units of Conformance
--
zhnWlBaseCfgGroup OBJECT-GROUP
    OBJECTS {
        wlBaseCfgEnable,
        wlBaseCfgBand,
        wlBaseCfgChannel,
        wlBaseCfgCurrentChannel,
        wlBaseCfgBandwidth,
        wlBaseCfgAutoScanTimer,
        wlBaseCfgMimoNEwc,
        wlBaseCfgMimoNRate,
        wlBaseCfgMimoNProtection,
        wlBaseCfgNClientsOnly,
        wlBaseCfg54gRate,
        wlBaseCfgMulticastRate,
        wlBaseCfgBasicRate,
        wlBaseCfgFragThreshold,
        wlBaseCfgRTSThreshold,
        wlBaseCfgDTIMInterval,
        wlBaseCfgBeaconInterval,
        wlBaseCfgGlobalMaxClients,
        wlBaseCfgXPress,
        wlBaseCfgTxPowerPercent,
        wlBaseCfgWMMEnable,
        wlBaseCfgWMMNoAck,
        wlBaseCfgWMMApsd,
        wlBaseCfgWpsAddClientMethod,
        wlBaseCfgWpsApMode,
        wlBaseCfgWpsConfigAp,
        wlBaseCfgWpsDevicePIN,
        wlBaseCfgWpsAddEnrollee,
        wlBaseCfgWpsStationPIN,
        wlBaseCfgBridgeRestrictMode,
        wlBaseCfgBridgeRefresh
   }
   STATUS current
   DESCRIPTION
      "A collection of Zhone Wireless objects that describe the WLAN
       adapter basic configuration and status information."
   ::= { zhnWirelessGroups 1}


zhnWlVirtualCfgGroup OBJECT-GROUP
   OBJECTS {
        wlVirtualHide,
        wlVirtualAPIsolation,
        wlVirtualDisableWme,
        wlVirtualEnableWmf,
        wlVirtualSsid,
        wlVirtualBssMacAddr,
        wlVirtualCountryCode,
        wlVirtualMaxClients,
        wlVirtualEnable
   }
   STATUS current
   DESCRIPTION
      "A collection of Zhone Wireless objects that describe the WLAN
       virtual interface configuration and status information."
   ::= { zhnWirelessGroups 2}


zhnWlSecurityGroup OBJECT-GROUP
   OBJECTS {
        wlSecuritySsid,
        wlSecurityWps,
        wlSecurityAuthMode,
        wlSecurityWpaPsk,
        wlSecurityWpaGTKRekey,
        wlSecurityWpaMode,
        wlSecurityWepStatus,
        wlSecurityRadiusServerIP,
        wlSecurityRadiusPort,
        wlSecurityRadiusKey,
        wlSecurityWepKey,
        wlSecurityCurrentWepKeyIndex64,
        wlSecurityCurrentWepKeyIndex128,
        wlSecurityWep64Key1,
        wlSecurityWep64Key2,
        wlSecurityWep64Key3,
        wlSecurityWep64Key4,
        wlSecurityWep128Key1,
        wlSecurityWep128Key2,
        wlSecurityWep128Key3,
        wlSecurityWep128Key4,
        wlSecurityWpa2Preauth,
        wlSecurityWpa2NetReauth,
        wlSecurityMACFilterMode
   }
   STATUS current
   DESCRIPTION
      "A collection of Zhone Wireless objects that describe the WLAN
       virtual interface security information."
   ::= { zhnWirelessGroups 3}


zhnWlMACFilterGroup OBJECT-GROUP
   OBJECTS {
        wlMACFilterSsid,
        wlMACFilterMacAddr,
        wlMACFilterIfName,
        wlMACFilterRowStatus
   }
   STATUS current
   DESCRIPTION
      "A collection of Zhone Wireless objects that describe the WLAN
       MAC filter rules."
   ::= { zhnWirelessGroups 4}


zhnWlStaticWdsMACAddrGroup OBJECT-GROUP
   OBJECTS {
        wlStaticWdsRemoteMACAddr
   }
   STATUS current
   DESCRIPTION
      "A collection of Zhone Wireless objects that describe the WLAN
       statically configured WDS MAC addresses."
   ::= { zhnWirelessGroups 5}


zhnWlScanWdsMACAddrGroup OBJECT-GROUP
   OBJECTS {
        wlScanWdsRemoteMACAddr
   }
   STATUS current
   DESCRIPTION
      "A collection of Zhone Wireless objects that describe the WLAN
       WDS Scanned MAC addresses."
   ::= { zhnWirelessGroups 6}

zhnWlAuthStationsGroup OBJECT-GROUP
   OBJECTS {
        wlAuthStationMACAddr,
        wlAuthStationAssociationStatus,
        wlAuthStationAuthorizationStatus,
        wlAuthStationSSID,
        wlAuthStationInterface
   }
   STATUS current
   DESCRIPTION
      "A collection of Zhone Wireless objects that indentify the 
       stations that have authenticated with the Access Point." 
   ::= { zhnWirelessGroups 7}


END
