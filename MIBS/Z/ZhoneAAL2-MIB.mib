--
-- comAtmAal2.mib
-- MIB generated by MG-SOFT Visual MIB Builder Version 3.0 Build 285
-- Tuesday, March 02, 2004 at 12:02:15
--

    ZhoneAAL2-MIB DEFINITIONS ::= BEGIN
 
        IMPORTS
            atmVclVpi, atmVclVci            
                FROM ATM-MIB            
            AtmVpIdentifier, AtmVcIdentifier, AtmVorXAdminStatus, AtmVorXOperStatus, AtmVorXLastChange            
                FROM ATM-TC-MIB            
            ifIndex            
                FROM IF-MIB            
            Integer32, Gauge32, Counter32, OBJECT-TYPE, MODULE-IDENTITY, 
            OBJECT-IDENTITY, NOTIFICATION-TYPE            
                FROM SNMPv2-SMI            
            subVoiceAal2Cid            
                FROM ZHONE-GEN-SUBSCRIBER            
            zhoneAtm            
                FROM Zhone            
            ZhoneRowStatus            
                FROM Zhone-TC;
    
    
--     
-- 
--  
-- 
-- 
--  
-- 
-- 
-- 
-- 
-- 
-- 
-- Voice Over ATM Adaptation Layer 2 (AAL2)
-- 
        -- 1.3.6.1.4.1.5504.4.2.1
        zhoneAtmAAl2 MODULE-IDENTITY 
            LAST-UPDATED "200403021202Z"		-- March 02, 2004 at 12:02 GMT
            ORGANIZATION 
                "Zhone Technologies, Inc."
            CONTACT-INFO 
                "  Postal: 
                Zhone Technologies, Inc.
                @ Zhone Way
                7001 Oakport Street
                Oakland, CA  94621
                USA
                Toll-Free: +1 877-ZHONE20 (+1 877-946-6320)
                Tel: +1-510-777-7000
                Fax: +1-510-777-7001
                E-mail: support@zhone.com"
            DESCRIPTION 
                "ATM Adaptation Layer 2 (AAL2) MIB"
            REVISION "200311191800Z"		-- November 19, 2003 at 18:00 GMT
            DESCRIPTION 
                "V01.03.12
                Added aal2ElcpIgTable."
            REVISION "200311141419Z"		-- November 14, 2003 at 14:19 GMT
            DESCRIPTION 
                "V01.03.11
                -- Add new trunk type "
            REVISION "200310031145Z"		-- October 03, 2003 at 11:45 GMT
            DESCRIPTION 
                "V01.03.10
                Added enum option 'enabledDynamic'
                to audio service selection for AAL2 VCL,
                CID and ELCP Port tables."
            REVISION "200309021130Z"		-- September 02, 2003 at 11:30 GMT
            DESCRIPTION 
                "V01.03.09
                Added enum option 'enabledEchoCancelOff'
                to audio service selection for AAL2 VCL,
                CID and ELCP Port tables."
            REVISION "200301211650Z"		-- January 21, 2003 at 16:50 GMT
            DESCRIPTION 
                "V01.03.08
                Added aal2ElcpPortTable."
            REVISION "200210011059Z"		-- October 01, 2002 at 10:59 GMT
            DESCRIPTION 
                "V01.03.07
                Added traps aal2PerfCellLossThreshTrap and aal2PerfCongestionThreshTrap 
                Added new leaf aal2CpsPerfCongestion in aal2CpsPerformanceTable 
                Added aal2AlarmConfigTable "
            REVISION "200205291415Z"		-- May 29, 2002 at 14:15 GMT
            DESCRIPTION 
                "V01.03.06 -
                Added the aal2CidCompletedCalls
                and aal2CidBlockedCallsNoBandwidth
                objects to the aal2CidTable."
            REVISION "200112071723Z"		-- December 07, 2001 at 17:23 GMT
            DESCRIPTION 
                "V01.03.05 -
                Removed all jetstreamdata references.
                Updated the description for:
                aal2VclMinCidForAal2UserChannels
                aal2VclMaxCidForAal2UserChannels
                aal2VclSscsDefaultType"
            REVISION "200111161025Z"		-- November 16, 2001 at 10:25 GMT
            DESCRIPTION 
                "V01.03.05 - Updated INDEX clauses for aal2SscsI3662PerfEntry
                and aal2SscsI3662PerfEntry."
            REVISION "200110091028Z"		-- October 09, 2001 at 10:28 GMT
            DESCRIPTION 
                "V01.03.04 - Added Jestream App Id to atmVccAal2AppId"
            REVISION "200107111358Z"		-- July 11, 2001 at 13:58 GMT
            DESCRIPTION 
                "V01.03.03 - Add comment for validation rule for aal2VclTable."
            REVISION "200104110955Z"		-- April 11, 2001 at 09:55 GMT
            DESCRIPTION 
                "V01.03.02 - modify default value for preferred-ap-index.
                "
            REVISION "200101291710Z"		-- January 29, 2001 at 17:10 GMT
            DESCRIPTION 
                "V01.03.01 - modify default value for preferred-ap-index"
            REVISION "200012201102Z"		-- December 20, 2000 at 11:02 GMT
            DESCRIPTION 
                "V01.03.00 Added packet length to the
                Audio Profiles. Changed Packet Time and
                Sequence to tenths of milliseconds from
                microseconds.
                "
            REVISION "200011061854Z"		-- November 06, 2000 at 18:54 GMT
            DESCRIPTION 
                "V01.02.00 - Update traps to point to subscriber MIB for CID 
                definition and remove unnecessary trap fields. 
                Fix Zhone keywords for statistic table key information."
            REVISION "200010301158Z"		-- October 30, 2000 at 11:58 GMT
            DESCRIPTION 
                "V01.01.00 - Marked not-supported
                field for FCS. (i.e. ZHONE_KEYWORD_PROFILE_LABEL to
                FOR_FUTURE_RELEASE_ZHONE_KEYWORD_PROFILE_LABEL).
                 "
            REVISION "200009111453Z"		-- September 11, 2000 at 14:53 GMT
            DESCRIPTION 
                "V01.00.00 - Initial Release."
            ::= { zhoneAtm 1 }

        
    
    
--
-- Node definitions
--
    
        -- 1.3.6.1.4.1.5504.4.2.1.0
        aal2Traps OBJECT-IDENTITY
            STATUS current
            DESCRIPTION 
                "Traps for the AAL2 MIB."
            ::= { zhoneAtmAAl2 0 }

        
        -- 1.3.6.1.4.1.5504.4.2.1.0.1
        aal2ExternalAIS NOTIFICATION-TYPE
            OBJECTS { ifIndex, aal2vpi, aal2Vci }
            STATUS current
            DESCRIPTION 
                "Alarm Indication Signal - a signal, associated with a
                maintenance alarm detected on a defective maintenance
                span, that is transmitted in the direction of the defect
                as a substitute for the normal signal.  Its purpose is to
                show downstream entities that a defect has been identified,        so that other maintenance alarms consequent to this first
                defect can be inhibited.  The external bit stream
                representation of AIS may be an all 1s signal.
                "
            ::= { aal2Traps 1 }

        
        -- 1.3.6.1.4.1.5504.4.2.1.0.2
        aal2ExternalRAI NOTIFICATION-TYPE
            OBJECTS { ifIndex, aal2vpi, aal2Vci }
            STATUS current
            DESCRIPTION 
                "Remote Alarm Indication - a signal transmitted upstream
                from a terminal that has detected defects persisting long
                enough to constitute a received signal failure.  Its purpose
                is to report in the backward direction that there is an
                interruption of service in the forward direction.
                "
            ::= { aal2Traps 2 }

        
        -- 1.3.6.1.4.1.5504.4.2.1.0.3
        aal2InternalAIS NOTIFICATION-TYPE
            OBJECTS { ifIndex, aal2vpi, aal2Vci, subVoiceAal2Cid }
            STATUS current
            DESCRIPTION 
                "Alarm Indication Signal - a signal transmitted in the
                downstream direction from the AAL type 2 connecting point
                that first detects a defect affecting the AAL type 2
                connection; this includes defects indicated by lower layers."
            ::= { aal2Traps 3 }

        
        -- 1.3.6.1.4.1.5504.4.2.1.0.4
        aal2InternalRDI NOTIFICATION-TYPE
            OBJECTS { ifIndex, aal2vpi, aal2Vci, subVoiceAal2Cid }
            STATUS current
            DESCRIPTION 
                "Remote Defect Indication - a signal transmitted upstream by
                an AAL type 2 endpoint that is in an alarm state as the result
                of having received an AAL type 2 connection AIS or having
                detected a defect that affects the AAL type 2 connection."
            ::= { aal2Traps 4 }

        
        -- 1.3.6.1.4.1.5504.4.2.1.0.5
        aal2PvcDown NOTIFICATION-TYPE
            OBJECTS { ifIndex, aal2vpi, aal2Vci }
            STATUS current
            DESCRIPTION 
                "Indicates the the status of the PVC has gone down."
            ::= { aal2Traps 5 }

        
        -- 1.3.6.1.4.1.5504.4.2.1.0.6
        aal2PerfCellLossThreshTrap NOTIFICATION-TYPE
            OBJECTS { aal2CpsPerfSTFBadSeq, aal2AlarmConfigThreshCellLoss }
            STATUS current
            DESCRIPTION 
                "This trap is generated when the number of Bad Sequence errors
                exceeds the aal2AlarmConfigThreshCellLoss for a 15-minute interval.
                A bad sequence error is detected when some cells have been lost."
            ::= { aal2Traps 6 }

        
        -- 1.3.6.1.4.1.5504.4.2.1.0.7
        aal2PerfCongestionThreshTrap NOTIFICATION-TYPE
            OBJECTS { aal2CpsPerfCongestion, aal2AlarmConfigThreshCongestion }
            STATUS current
            DESCRIPTION 
                "This trap is generated when the number of congestion events
                exceeds the aal2AlarmConfigThreshCongestion for a 15-minute interval."
            ::= { aal2Traps 7 }

        
        -- 1.3.6.1.4.1.5504.4.2.1.0.8
        aal2ElcpIgOperStatusChange NOTIFICATION-TYPE
            OBJECTS { aal2ElcpIgOperStatus }
            STATUS current
            DESCRIPTION 
                "A notification is sent when the operational status of an ELCP interface 
                group changes."
            ::= { aal2Traps 8 }

        
-- The ATM Interface AAL2 VCL Table
-- 
        -- 1.3.6.1.4.1.5504.4.2.1.1
        aal2VclTable OBJECT-TYPE
            SYNTAX SEQUENCE OF Aal2VclEntry
            MAX-ACCESS not-accessible
            STATUS current
            DESCRIPTION
                "The AAL2 Virtual Channel Link (VCL) Table
                
                This table contains configuration and state 
                information of a bi-directional AAL2 Virtual 
                Channel Link (VCL) at an ATM interface. Each 
                VCL entry has an associated Connection 
                Identifier (CID) table, comprised of one or
                more CID entries.  Each VCL entry refers to
                an Audio Profile (AP) by type (pre-defined or 
                user-defined) and index into an AP table.
                
                An AAL2 VCL entry is created by the agent 
                when an RFC2515 (ATM-MIB) atmVclEntry of 
                atmVccAalType 2 is created.  Objects in the 
                row entry can by modified by CLI or ZMS if 
                the connection is down.  Deletion of AAL2 VCL 
                entries is controlled by the rfc2515 (ATM-MIB) 
                atmVclRowStatus."
            REFERENCE
                "
                A. Perez, 'AAL Type 2 Functional Specification'
                
                A. Perez, aal2Provision.h, aal2rpAudioProfileAPI.h
                
                A. Perez, 'AAL2 Entity Relational Diagram'
                
                ITU-T, 'I.366.1, Segmentation and Reassembly 
                Service Specific Convergence Sublayer for the 
                AAL type 2'
                
                ITU-T, 'I.366.2, AAL type 2 service specific
                convergence sublayer for trunking'
                
                ITU-T, 'I.363.2, B-ISDN ATM Adaptation layer 
                specification:Type 2 AAL'
                
                ATM Forum, 'Voice and Multimedia Over ATM - Loop
                Emulation Service Using AAL2'
                
                ATM Forum, 'Protocol Independent MIB for ATM 
                Trunking using AAL2 for Narrowband Services 
                (Addendum to af-vtoa-0113.000)'
                
                ATM Forum, 'ATM Forum Well-known Addresses and 
                Assigned Codes', 5/25/2000.
                "
            ::= { zhoneAtmAAl2 1 }

        
        -- 1.3.6.1.4.1.5504.4.2.1.1.1
        aal2VclEntry OBJECT-TYPE
            SYNTAX Aal2VclEntry
            MAX-ACCESS not-accessible
            STATUS current
            DESCRIPTION
                "An entry in the AAL2 Virtual Channel Link (VCL)
                Table.  Indexed by ifIndex, atmVclVpi from 
                atmVclTable, and atmVclVci from atmVclTable.
                
                An AAL2 VCL entry or row (aal2VclEntry) is 
                'automatically' created by the agent when an 
                rfc2515 (ATM-MIB) atmVclEntry with atmVccAalType 
                2 is created.   The request to create an RFC2515 
                atmVclEntry can originate at either CLI or ZMS.  
                Once the row exists, objects within the row with 
                read-write access can by modified by CLI or ZMS 
                if the connection is down.  Deletion of an 
                aal2VclEntry is managed by the rfc2515 (ATM-MIB) 
                atmVclRowStatus.
                
                Note there is no RowStatus in the aal2VclEntry, 
                whereas there is an atmVclRowStatus in the 
                rfc2515 atmVclEntry."
            INDEX { ifIndex, atmVclVpi, atmVclVci }
            ::= { aal2VclTable 1 }

        
        Aal2VclEntry ::=
            SEQUENCE { 
                atmVccAal2AppId
                    INTEGER,
                atmVccAal2VccI
                    Integer32,
                atmVccAal2SigVccI
                    Integer32,
                aal2VclAudioProfileIdentifier
                    Integer32,
                aal2VclSscsDefaultType
                    INTEGER,
                aal2VclMaxCpsSduSize
                    Integer32,
                aal2VclMaxNumberMultiplexChannels
                    Integer32,
                aal2VclMinCidForAal2UserChannels
                    Integer32,
                aal2VclMaxCidForAal2UserChannels
                    Integer32,
                aal2VclNextCid
                    Integer32,
                aal2VclTimerCU
                    Integer32,
                aal2VclAudioService
                    INTEGER,
                aal2VclCircuitModeData
                    INTEGER,
                aal2VclFrameModeData
                    INTEGER,
                aal2VclFaxDemoRemo
                    INTEGER,
                aal2VclCAS
                    INTEGER,
                aal2VclTrunkType
                    INTEGER,
                aal2VclDTMFDialedDigits
                    INTEGER,
                aal2VclMfR1DialedDigits
                    INTEGER,
                aal2VclMfR2DialedDigits
                    INTEGER,
                aal2VclPCMEncoding
                    INTEGER,
                aal2VclMaxLengthFrame
                    Integer32,
                aal2VclMaxSDULength
                    Integer32,
                aal2VclRasTimer
                    Integer32,
                aal2VclCellsReceived
                    Gauge32,
                aal2VclCellsSent
                    Gauge32,
                aal2VclStatsTimeElapsed
                    Integer32
             }

-- For atmVccAalType == aal2.
-- 
-- For all objects the max/min/default are defined in 
-- STR-VMOA-LES-01-00 Appendix E
--  
-- 
        -- 1.3.6.1.4.1.5504.4.2.1.1.1.1
        atmVccAal2AppId OBJECT-TYPE
            SYNTAX INTEGER
                {
                casPotsOnlyNoElcp(10),
                pstnPotsOnlyNoElcp(11),
                pstnPotsOnlyElcp(12),
                dss1BriOnlyNoElcp(13),
                dss1BriOnlyElcp(14),
                casPotsDss1BriNoElcp(15),
                pstnPotsDss1BriNoElcp(16),
                pstnPotsDss1BriElcp(17),
                otherCcs(18),
                jetstream(255)
                }
            MAX-ACCESS read-write
            STATUS current
            DESCRIPTION
                "STR-VMOA-LES-01-00 4.1.1 Application Identifier (AppId)
                
                The Application Identifier (AppId) specifies protocol 
                combinations used between IWFs.  
                
                The following AppId values can be found at the 
                ATM Forum public web site in section 5 of 'ATM 
                Forum Well-known Addresses and Assigned Codes'.
                
                0000000A      Loop Emulation Service using CAS (POTS only)
                              without ELCP
                0000000B      Loop Emulation Service using PSTN signalling (POTS only)
                              without ELCP. Note: This application is not currently 
                              supported.
                0000000C      Loop Emulation Service using PSTN signalling (POTS only)
                              with ELCP. Note: This application is not currently supported.
                0000000D      Loop Emulation Service using DSS1 in support of BRI
                              (BRI only) without ELCP
                0000000E      Loop Emulation Service using DSS1 in support of BRI
                              (BRI only) with ELCP. Note: This application is not currently
                              supported.   
                0000000F      Loop Emulation Service using CAS in support of POTS,
                              and DSS1 in support of BRI (without ELCP). Note: This 
                              application is not currently supported.   
                00000010      Loop Emulation Service using PSTN signalling in support
                              of POTS, and DSS1 in support of BRI (without ELCP).Note:
                              This application is not currently supported 
                00000011      Loop Emulation Service using PSTN signalling in support
                              of POTS,and DSS1 in support of BRI (with ELCP). Note: This
                              application is not currently supported.
                00000012      Loop Emulation Service using other variety of CCS. Note: 
                              This application is not currently supported. 
                00000013      Unspecified mode of Loop Emulation Service. Note: This 
                              application is not currently supported. 
                000000FF      This is a Zhone proprietary application id and indicates
                              that the protocol is Jetstream Aal2.
                By default this value is set to casPotsOnlyNoElcp."
            REFERENCE
                "STR-VMOA-LES-01-00 Section 4.1.1, ATM Forum Well-known 
                Addresses and Assigned Codes, Section 5"
            ::= { aal2VclEntry 1 }

        
-- 
        -- 1.3.6.1.4.1.5504.4.2.1.1.1.2
        atmVccAal2VccI OBJECT-TYPE
            SYNTAX Integer32
            MAX-ACCESS read-write
            STATUS current
            DESCRIPTION
                "STR-VMOA-LES-01-00 4.1.2 VCC Identifier (VCCI)
                
                To distinguish multiple VCCs, each shall be 
                assigned a VCCI. The creator of an SVC shall 
                assign its VCCI.  The VCCI of a PVC is 
                mutually provisioned.
                
                The VCCI shall be unique for all VCCs between a 
                CP-IWF and a CO-IWF, but may be repeated with 
                other CP-IWF/CO-IWF pairings.  Between a CP-IWF 
                and CO-IWF, a VCCI + CID pair is enough to 
                identify an AAL2 channel."
            REFERENCE
                "STR-VMOA-LES-01-00 Section 4.1.2"
            ::= { aal2VclEntry 2 }

        
-- Switched Vccs are not currently supported.
-- 
        -- 1.3.6.1.4.1.5504.4.2.1.1.1.3
        atmVccAal2SigVccI OBJECT-TYPE
            SYNTAX Integer32
            MAX-ACCESS read-write
            STATUS current
            DESCRIPTION
                "STR-VMOA-LES-01-00 4.1.3 Signaling VCC Identifier (SigVCCI)
                
                If an AAL2 VCC is controlled by CCS, then 
                SigVCCI = VCCI is indicated.  Conversely if 
                SigVCCI = VCCI then the AAL2 VCC contains CCS, 
                which controls the AAL2 channels within that VCC."
            REFERENCE
                "STR-VMOA-LES-01-00 Section 4.1.3"
            ::= { aal2VclEntry 3 }

        
-- Audio Profile sources can be either pre-defined or 
-- user-defined.  The AAL2 Audio Profile Table, 
-- aal2AudioProfileTable, accomodates both pre-defined 
-- and user-defined profile types.  The range of values
-- for the Audio Profile Identifier determines whether 
-- a profile entry (row) is pre-defined or user-defined.
-- 
-- Audio Profile objects (columns in the entry or row)
-- are defined to have READ-CREATE max-access.
-- However, the agent and ZMS implement pre-defined 
-- audio profile entry rows as having READ-ONLY 
-- columns whereas user-defined audio profile columns
-- are implemented as READ-CREATE objects.
-- 
-- All pre-defined profiles entries have well-known 
-- Identifier values in the 1..255 range and are 
-- implicitly READ-ONLY in access.  Both the agent 
-- and ZMS should ensure that pre-defined audio 
-- profiles are treated as READ-ONLY.  The agent 
-- will create the pre-defined audio profile entry 
-- rows.
-- 
-- User-defined audio profile entries have Identifier 
-- values in the 256..512 range and have READ-CREATE 
-- access.  User-defined audio profile instances can 
-- be created by either CLI or ZMS.
-- 
-- The "user" or creator (ie, agent, ZMS) of user-
-- defined audio profile entries is responsible for 
-- assigning a valid user-defined identifier value 
-- from the 256..512 range as well as conforming to 
-- the pre-defined audio profile identifier numbering 
-- convention defined by STR-VMOA-LES-01-00 Annex A.
-- 
-- Each identifier can have multiple auto profiles
-- eg, identifier 7 pcm-64, adpcm-32, silence has 
-- 3 audio profile rows.  An audio profile index 
-- (not identifier) identifies each audio profile 
-- row. The AAL2 User Defined Audio Profile Next 
-- Index table tells ZMS/agent the next index to 
-- use for a given identifier.
-- 
-- See the descriptions for the AAL2 Audio Profile 
-- tables.
-- 
-- 
        -- 1.3.6.1.4.1.5504.4.2.1.1.1.4
        aal2VclAudioProfileIdentifier OBJECT-TYPE
            SYNTAX Integer32 (1..512)
            MAX-ACCESS read-write
            STATUS current
            DESCRIPTION
                "The Audio Profile for this VCL entry is specified
                by the Audio Profile identifier.  The range of 
                valid Audio Profile identifiers is well-defined. 
                The Audio Profile identifier indexes into the AAL2 
                Audio Profile table containing the audio profiles 
                corresponding to the specific identifier.
                
                For pre-defined audio profiles, the range of valid
                Identifier values is 1..255.  From STR-VMOA-LES-01-00 
                Annex A, Identifiers defined by the ATM Forum are:
                * 1-6, allocated to af-vtoa-0113.000
                * 7: PCM-64, ADPCM-32 and silence (pcm64Adpcm32Silence)
                * 8: PCM-64 and silence (pcm64Silence)
                * 9: PCM-64 without silence (pcm64)
                * 10: PCM-64, ADPCM-32 without silence (pcm64Adpcm32)
                *11-255: Reserved for future ATM Forum assignment
                
                
                
                If the Audio Profile is user-defined, the range of
                valid identifiers is 256..512.
                
                See the descriptions for the AAL2 Audio Profile 
                tables."
            REFERENCE
                "STR-VMOA-LES-01-00 Annex A "
            ::= { aal2VclEntry 4 }

        
-- 
-- Only SSCS type 2 (I.366.2) will be supported 
-- for FCS.
-- 
-- 
        -- 1.3.6.1.4.1.5504.4.2.1.1.1.5
        aal2VclSscsDefaultType OBJECT-TYPE
            SYNTAX INTEGER
                {
                i3661(1),
                i3662(2),
                jetstreamvoice(3)
                }
            MAX-ACCESS read-write
            STATUS current
            DESCRIPTION
                "STR-VMOA-LES-01-00 4.1.4 SSCS Type
                
                The SSCS type that applies to each channel of 
                an AAL2 VCC will vary according to the usage 
                of that channel.  Channels that are used to 
                carry media streams (POTS or ISDN B-channels) 
                shall use the SSCS defined in I.366.2.  
                Channels that are used to carry control and 
                management plane traffic (CCS, ELCP, ISDN 
                D-channels and LES-EOC) shall use the SSCS 
                defined in I.366.1.
                
                
                Channels that are used to carry Jetstream Voice
                shall use SSCS value of jetstreamvoice.
                
                Valid values are i3661 (I.366.1), i3662
                (I.366.2), jetstreamvoice."
            REFERENCE
                "STR-VMOA-LES-01-00 Annex A, I.366.2 Section 1"
            ::= { aal2VclEntry 5 }

        
-- AAL2 CPS Parameters. 
-- 
-- This values are defined in I.363.2 Section 11 
-- and STR-VMOA-LES-01-00 Appendix E
--  
-- I.363.2 Section 11 Summary of parameters and 
-- values for the AAL type 2
-- 
-- Determination of the values, the system 
-- resources listed in Table 7 must be made 
-- before individual AAL type 2 channels can 
-- be established. Such determination may be 
-- made via provisioning or signalling in a 
-- manner outside the scope of this Recommendation. 
-- In the absence of provisioning or signalling 
-- (ATM level control), the default values 
-- apply. The values of these AAL type 2 
-- system parameters may differ from one ATM 
-- VCC to another.
-- 
-- 
-- 
        -- 1.3.6.1.4.1.5504.4.2.1.1.1.6
        aal2VclMaxCpsSduSize OBJECT-TYPE
            SYNTAX Integer32 (45 | 64)
            UNITS "octets"
            MAX-ACCESS read-write
            STATUS current
            DESCRIPTION
                "Maximum length of a CPS-SDU (Max_CPS-SDU_Length).
                Permitted values: 45 or 64 octets.  "
            REFERENCE
                "I.363.2 Section 11, STR-VMOA-LES-01-00 Appendix E"
            ::= { aal2VclEntry 6 }

        
-- 
        -- 1.3.6.1.4.1.5504.4.2.1.1.1.7
        aal2VclMaxNumberMultiplexChannels OBJECT-TYPE
            SYNTAX Integer32 (1..255)
            UNITS "channels"
            MAX-ACCESS read-write
            STATUS current
            DESCRIPTION
                "Maximum number of multiplexed channels. 
                Peer-to-peer significance. Valid range
                of values is 1..255.  "
            REFERENCE
                "I.363.2 Section 11, STR-VMOA-LES-01-00 Appendix E"
            ::= { aal2VclEntry 7 }

        
-- 
        -- 1.3.6.1.4.1.5504.4.2.1.1.1.8
        aal2VclMinCidForAal2UserChannels OBJECT-TYPE
            SYNTAX Integer32 (1..255)
            MAX-ACCESS read-write
            STATUS current
            DESCRIPTION
                "Minimum CID value for AAL2 user channels.
                Valid range is 1..255.
                
                If the field atmVccAal2AppId is set to casPotsOnlyNoElcp
                then the valid range for aal2VclMinCidForAal2UserChannels
                and aal2VclMinCidForAal2UserChannels is between 16 and 128.
                
                If the field atmVccAal2AppId is set to dss1BriOnlyNoElcp
                then the valid range for aal2VclMinCidForAal2UserChannels
                and aal2VclMinCidForAal2UserChannels is between 129 and 223.
                
                Also the aal2VclMaxCidForAal2UserChannels must be greater
                than aal2VclMinCidForAal2UserChannels.
                
                For Jetstream app-id, this Cid value represents the port number
                which the phone is on and the valid range is 1 to 254.
                
                The range for non-Jetstream applications is 16 to 255.
                
                By default because atmVccAal2AppId is set to casPotsOnlyNoElcp
                the default value of this field is 16."
            REFERENCE
                "STR-VMOA-LES-01-00 Appendix E"
            ::= { aal2VclEntry 8 }

        
-- 
        -- 1.3.6.1.4.1.5504.4.2.1.1.1.9
        aal2VclMaxCidForAal2UserChannels OBJECT-TYPE
            SYNTAX Integer32 (1..255)
            MAX-ACCESS read-write
            STATUS current
            DESCRIPTION
                "Maximum CID value for AAL2 user channels.  Valid 
                range is 1..255. Maximum CID is 255.
                
                If the field atmVccAal2AppId is set to casPotsOnlyNoElcp
                then the valid range for aal2VclMinCidForAal2UserChannels
                and aal2VclMinCidForAal2UserChannels is between 16 and 128.
                
                If the field atmVccAal2AppId is set to dss1BriOnlyNoElcp
                then the valid range for aal2VclMinCidForAal2UserChannels
                and aal2VclMinCidForAal2UserChannels is between 129 and 223.
                
                Also the aal2VclMaxCidForAal2UserChannels must be greater 
                than aal2VclMinCidForAal2UserChannels.
                
                For Jetstream app-id, this Cid value represents the port number
                which the phone is on and the valid range is 1 to 254.
                
                The range for non-Jetstream applications is 16 to 255.
                
                By default because atmVccAal2AppId is set to casPotsOnlyNoElcp
                the default value of this field is 127."
            REFERENCE
                "STR-VMOA-LES-01-00 Appendix E"
            ::= { aal2VclEntry 9 }

        
-- The Channel Table Index
-- 
        -- 1.3.6.1.4.1.5504.4.2.1.1.1.10
        aal2VclNextCid OBJECT-TYPE
            SYNTAX Integer32 (0 | 1..255)
            MAX-ACCESS read-only
            STATUS current
            DESCRIPTION
                "The Channel Identifier is one of the indicies for
                the CID table, aal2CidTable.  The  Application Identifier, 
                atmVccAal2AppId, determines the valid range of values for
                the aal2Cid.  The next CID, aal2VclNextCid, indicates 
                the next valid aal2Cid that can be used to create a new
                row in the aal2CidTable.  A value of 0 indicates that an 
                aal2Cid is not available for a given atmVccAal2AppId.
                The agent manages this value.  Range of valid values is 
                0, 16..255.   Also see the description for aal2Cid."
            REFERENCE
                "STR-VMOA-LES-01-00 Section 4.4"
            ::= { aal2VclEntry 10 }

        
-- 
        -- 1.3.6.1.4.1.5504.4.2.1.1.1.11
        aal2VclTimerCU OBJECT-TYPE
            SYNTAX Integer32
            MAX-ACCESS read-write
            STATUS current
            DESCRIPTION
                "Value of the 'combined use' Timer_CU.  
                The combined use Timer_CU assures that CPS-Packets 
                with one or more octets already packed, wait at 
                most the duration of Timer_CU before being 
                scheduled for transmission (actual transmission 
                takes place after receipt of a MAAL_SEND.request 
                primitive from Layer Management)."
            REFERENCE
                "I.363.2 Section 11, STR-VMOA-LES-01-00 Appendix E"
            ::= { aal2VclEntry 11 }

        
-- SSCS Default Parameters. Please refer to I.366.2
-- and STR-VMOA-LES-01-00 Appendix E
-- 
-- STR-VMOA-LES-01-00 4.1.5 Default SSCS Parameter 
-- Values.  The SSCS parameters of operation are 
-- used to ensure that interconnected CP- and 
-- CO-IWFs agree on the set of capabilities to 
-- be applied to a VCC. The parameters are defined 
-- in I.366.1 and I.366.2.
-- 
-- From among the SSCS parameter values supported 
-- by both IWFs, one specific set of values may be 
-- designated the default for an AAL2 VCC. Different 
-- AAL2 VCCs between the same two IWFs may have 
-- different default SSCS parameter values. In 
-- the absence of signaling or provisioning on 
-- a per-AAL2 channel basis, either explicit or 
-- implicit, the default SSCS parameter values 
-- shall apply to each AAL2 channel within the 
-- ATM AAL2 VCC.
-- 
-- 
        -- 1.3.6.1.4.1.5504.4.2.1.1.1.12
        aal2VclAudioService OBJECT-TYPE
            SYNTAX INTEGER
                {
                enabled(1),
                disabled(2),
                enabledEchoCancelOff(3),
                enabledDynamic(4)
                }
            MAX-ACCESS read-write
            STATUS current
            DESCRIPTION
                "The service provided is the transfer of audio 
                signals (voice, voiceband data, and facsimile).
                
                The data unit traversing the SAP (SSCS SDU) 
                contains either a voice encoding or a silence 
                encoding. Silences are conveyed across the SAP 
                either explicitly by a Silence Insertion 
                Descriptor (SID) data unit, or implicitly by 
                a Null data unit.
                
                Valid values are:
                - enabled.
                - disabled.
                - enabledEchoCancelOff: audio service enabled with echo 
                  cancellation and silence supression off.
                - enabledDynamic: audio service enabled with ability to
                  dynamically disable silence supression, silence detection,
                  echo cancellation and compression algorithms on a per-call
                  basis."
            REFERENCE
                "I.366.2, STR-VMOA-LES-01-00 Appendix E"
            ::= { aal2VclEntry 12 }

        
-- Not currently supported.
-- 
        -- 1.3.6.1.4.1.5504.4.2.1.1.1.13
        aal2VclCircuitModeData OBJECT-TYPE
            SYNTAX INTEGER
                {
                enabled(1),
                disabled(2)
                }
            MAX-ACCESS read-write
            STATUS current
            DESCRIPTION
                "The service provided is the transfer of circuit 
                mode data. The circuit mode data service is an 
                emulation of the N*64 kbit/s (N = 1, 2, ..., 30)
                unrestricted, 8 kHz structured circuit mode 
                service of Recommendations I.231.1 and 
                I.231.10. The value N = 31 is also allowed. 
                The value of N does not change during the 
                lifetime of a call.
                
                Valid values are enabled and disabled.  "
            REFERENCE
                "I.366.2, STR-VMOA-LES-01-00 Appendix E"
            ::= { aal2VclEntry 13 }

        
-- 
        -- 1.3.6.1.4.1.5504.4.2.1.1.1.14
        aal2VclFrameModeData OBJECT-TYPE
            SYNTAX INTEGER
                {
                enabled(1),
                disabled(2)
                }
            MAX-ACCESS read-write
            STATUS current
            DESCRIPTION
                "Frame mode data is an intermittent data stream 
                containing delimited units of information, 
                possibly of varying size, with idle intervals 
                between them.
                
                The service provided is the transport of data 
                units as specified in the Transmission Error 
                Detection service of Recommendation I.366.1. 
                There is no assurance of data unit delivery, 
                but if delivered, the relative sequence and 
                the bit integrity of data units are assured. 
                This service corresponds to the service provided 
                by the Common Part of AAL type 5, Recommendation 
                I.363.5, except that the option of corrupted 
                data delivery is not available.
                
                Valid values are enabled and disabled.  "
            REFERENCE
                "I.366.2, STR-VMOA-LES-01-00 Appendix E"
            ::= { aal2VclEntry 14 }

        
-- Not currently supported.
-- 
        -- 1.3.6.1.4.1.5504.4.2.1.1.1.15
        aal2VclFaxDemoRemo OBJECT-TYPE
            SYNTAX INTEGER
                {
                enabled(1),
                disabled(2)
                }
            MAX-ACCESS read-write
            STATUS current
            DESCRIPTION
                "Facsimile Demodulation/Remodulation is the 
                process of detecting facsimile traffic, 
                extracting digital information from the 
                incoming analogue modulated signal, 
                transporting this across a trunk in packet 
                formats, and reproducing the facsimile control 
                and image information by remodulation at the 
                other end.
                
                The service provided is the transfer of 
                demodulated facsimile image information and 
                control information, from the demodulating 
                User to the remodulating User.
                
                Valid values are enabled and disabled.  "
            REFERENCE
                "I.366.2, STR-VMOA-LES-01-00 Appendix E"
            ::= { aal2VclEntry 15 }

        
-- 
        -- 1.3.6.1.4.1.5504.4.2.1.1.1.16
        aal2VclCAS OBJECT-TYPE
            SYNTAX INTEGER
                {
                enabled(1),
                disabled(2)
                }
            MAX-ACCESS read-write
            STATUS current
            DESCRIPTION
                "Channel Associated Signalling Bits are bits
                dedicated for connection control across a 1544 
                kbit/s or 2048 kbit/s interface that carries 
                64 kbit/s channels. Procedures are based on 
                the state of up to four signalling bits (A, B, 
                C, D) that are allocated per channel per 
                multiframe. See I.366.2 3.1.3.2/G.704 and 
                5.1.3.2/G.704.
                
                The service provided is the transfer of channel 
                associated signalling information, i.e. the 
                transfer of ABCD bits. Typically, the value of 
                the (A,B,C,D) vector does not change for extended 
                periods of time.
                
                Valid values are enabled and disabled.  
                
                For jetstream atmVccAal2AppId the only valid value is disabled."
            REFERENCE
                "I.366.2, STR-VMOA-LES-01-00 Appendix E"
            ::= { aal2VclEntry 16 }

        
-- 
        -- 1.3.6.1.4.1.5504.4.2.1.1.1.17
        aal2VclTrunkType OBJECT-TYPE
            SYNTAX INTEGER
                {
                unknown(1),
                loopstart(2),
                groundstart(3),
                loopreversebattery(4)
                }
            MAX-ACCESS read-write
            STATUS current
            DESCRIPTION
                "Trunk type specifies the signaling method currently
                used. Valid types are loop start,ground start and
                loop reverse battery. The default value is loop start.
                An instance of this object only exists when the 
                atmVccAal2AppId is set to casPotsOnlyNoElcp. 
                If the atmVccAal2AppId is not equal to casPotsOnlyNoElcp
                the entry should be set unknown."
            ::= { aal2VclEntry 17 }

        
-- Dialed Digits are multifrequency audio tones 
-- typically used for inter-register signalling of 
-- addresses during call set-up or for end-to-end 
-- device control during an established call. 
-- Depending on the system, codes are defined for 
-- the digits 0-9 of a telephone keypad and other 
-- auxiliary signals.
-- 
-- The service provided is the transfer of dialed 
-- digits, namely, the transfer of five descriptors: 
-- digit type, digit character, start time, end time, 
-- and power level of the dual frequency pulse. 
-- 
-- Not currently supported.
-- 
-- 
        -- 1.3.6.1.4.1.5504.4.2.1.1.1.18
        aal2VclDTMFDialedDigits OBJECT-TYPE
            SYNTAX INTEGER
                {
                enabled(1),
                disabled(2)
                }
            MAX-ACCESS read-write
            STATUS current
            DESCRIPTION
                "DTMF Dialed Digits
                
                Dialed Digits are multifrequency audio tones 
                typically used for inter-register signalling of 
                addresses during call set-up or for end-to-end 
                device control during an established call. 
                Depending on the system, codes are defined for 
                the digits 0-9 of a telephone keypad and other 
                auxiliary signals.
                
                The service provided is the transfer of dialed 
                digits, namely, the transfer of five descriptors: 
                digit type, digit character, start time, end time, 
                and power level of the dual frequency pulse. 
                
                Valid values are enabled and disabled.  "
            REFERENCE
                "I.366.2, STR-VMOA-LES-01-00 Appendix E"
            ::= { aal2VclEntry 18 }

        
-- Not currently supported.
-- 
-- 
        -- 1.3.6.1.4.1.5504.4.2.1.1.1.19
        aal2VclMfR1DialedDigits OBJECT-TYPE
            SYNTAX INTEGER
                {
                enabled(1),
                disabled(2)
                }
            MAX-ACCESS read-write
            STATUS current
            DESCRIPTION
                "MF-R1 Dialed Digits.
                
                See description for atmVccAal2DTMFDialedDigits.
                
                Valid values are enabled and disabled.  "
            REFERENCE
                "I.366.2, STR-VMOA-LES-01-00 Appendix E"
            ::= { aal2VclEntry 19 }

        
-- Not currently supported.
-- 
-- 
        -- 1.3.6.1.4.1.5504.4.2.1.1.1.20
        aal2VclMfR2DialedDigits OBJECT-TYPE
            SYNTAX INTEGER
                {
                enabled(1),
                disabled(2)
                }
            MAX-ACCESS read-write
            STATUS current
            DESCRIPTION
                "MF-R2 Dialed Digits.
                
                See description for atmVccAal2DTMFDialedDigits.
                
                Valid values are enabled and disabled.  "
            REFERENCE
                "I.366.2, STR-VMOA-LES-01-00 Appendix E"
            ::= { aal2VclEntry 20 }

        
-- 
        -- 1.3.6.1.4.1.5504.4.2.1.1.1.21
        aal2VclPCMEncoding OBJECT-TYPE
            SYNTAX INTEGER
                {
                muLaw(1),
                aLaw(2)
                }
            MAX-ACCESS read-write
            STATUS current
            DESCRIPTION
                "Encoding Data Unit is an octet-aligned 
                concatenation of one or more frames of an 
                audio algorithm, entailing a specific format 
                of the bits.  Every audio packet and SDU 
                contains an integral number of EDUs. 
                Predefined profiles reference the EDUs that 
                are defined in I.366.2 Annexes B through I.
                
                Valid values are muLaw and aLaw.  "
            REFERENCE
                "I.366.2, STR-VMOA-LES-01-00 Appendix E, Table A-2"
            ::= { aal2VclEntry 21 }

        
-- 
        -- 1.3.6.1.4.1.5504.4.2.1.1.1.22
        aal2VclMaxLengthFrame OBJECT-TYPE
            SYNTAX Integer32 (1..65535)
            UNITS "octets"
            MAX-ACCESS read-write
            STATUS current
            DESCRIPTION
                "Maximum length for frame mode data. 
                
                Valid values are 1..65535.  "
            REFERENCE
                "I.366.2, STR-VMOA-LES-01-00 Appendix E"
            ::= { aal2VclEntry 22 }

        
-- SSCS Default Parameters. Please refer to I.366.1
-- See 7.7.1 for description.
-- 
-- 
        -- 1.3.6.1.4.1.5504.4.2.1.1.1.23
        aal2VclMaxSDULength OBJECT-TYPE
            SYNTAX Integer32 (1..65568)
            UNITS "octets"
            MAX-ACCESS read-write
            STATUS current
            DESCRIPTION
                "Max_SDU_Length indicates the maximum size 
                SSSAR-SDU, in octets, that is allowed to be 
                reassembled.  Significance to peer-to-peer.
                
                The maximum size of an SSSAR-SDU may be 
                restricted on a per SSSAR-connection basis with 
                the parameter 'Max_SDU_Length'. This parameter 
                is negotiated by signalling or management 
                procedures.
                
                Valid values are 1..65568.  "
            REFERENCE
                "I.366.1 Section 7.7.1, Table 6/I.366.1 (Parameters
                for Segmentation and Reassembly)"
            ::= { aal2VclEntry 23 }

        
-- It has been suggested that since there is no restriction 
-- on the delay from the DSP implementation perspective (as 
-- the DSP sends the packet on the fly to the host), that 
-- the RAS timer should be provisioned after a data channel 
-- is open in a similar fashion to the maximum SDU length.
-- 
-- 
        -- 1.3.6.1.4.1.5504.4.2.1.1.1.24
        aal2VclRasTimer OBJECT-TYPE
            SYNTAX Integer32
            UNITS "milliseconds"
            MAX-ACCESS read-write
            STATUS current
            DESCRIPTION
                "The reassembly timer RAS_Timer assures that the 
                reassembly of an SSSAR-SDU does not exceed a 
                certain time; if such timer supervision is not 
                required, the timer is disabled by setting the 
                timer value to 0.
                
                If the timer is exceeded the i366.1 receive state 
                machine goes into the abort state, look for the 
                end of the frame and goes back to idle. See figure
                8.1 I.366.2 State transition diagram.
                
                The default is 0 milliseconds.  Value of 0 means the 
                timer is disabled."
            REFERENCE
                "I.366.1 7.7.1, I.366.2 State transition diagram figure 8.1"
            ::= { aal2VclEntry 24 }

        
-- 
        -- 1.3.6.1.4.1.5504.4.2.1.1.1.25
        aal2VclCellsReceived OBJECT-TYPE
            SYNTAX Gauge32
            UNITS "cells"
            MAX-ACCESS read-only
            STATUS current
            DESCRIPTION
                "Total cells received"
            ::= { aal2VclEntry 25 }

        
-- 
        -- 1.3.6.1.4.1.5504.4.2.1.1.1.26
        aal2VclCellsSent OBJECT-TYPE
            SYNTAX Gauge32
            UNITS "cells"
            MAX-ACCESS read-only
            STATUS current
            DESCRIPTION
                "Total cells sent"
            ::= { aal2VclEntry 26 }

        
-- 
        -- 1.3.6.1.4.1.5504.4.2.1.1.1.27
        aal2VclStatsTimeElapsed OBJECT-TYPE
            SYNTAX Integer32
            UNITS "seconds"
            MAX-ACCESS read-only
            STATUS current
            DESCRIPTION
                "The number of seconds that have elapsed since 
                the beginning of the current collection
                period.  If, for some reason, such as an
                adjustment in the system's time-of-day clock, 
                the current interval exceeds the maximum value,
                the agent will return the maximum value."
            ::= { aal2VclEntry 27 }

        
-- The AAL2 Channel Identifier Table
-- 
-- atmVccAal2AppId values for applications running 
-- over Common Channel Signaling can cause the 
-- auto-creation of an AAL2 CID entry. However,
-- for FCS, there is no auto-creation of AAL2
-- CID entries.
-- 
        -- 1.3.6.1.4.1.5504.4.2.1.2
        aal2CidTable OBJECT-TYPE
            SYNTAX SEQUENCE OF Aal2CidEntry
            MAX-ACCESS not-accessible
            STATUS current
            DESCRIPTION
                "The AAL2 Channel Identifier (CID) Table
                
                The AAL2 Channel Identifier Table contains 
                status, I.366.2 SSCS parameters, and I.366.1 
                SSCS parameters for the channel identifier. 
                Default values for these objects are defined
                in the AAL2 VCL entry.  Values in the AAL2 
                Channel Identifier entry can supercede the 
                defaults specified in the AAL2 VCL entry.
                
                The maximum number of connections or CIDs
                allowed per ATM VCL is 255.
                
                Certain atmVccAal2AppID values (ie, any app
                running over Common Channel Signaling) can 
                cause the auto-creation of an AAL2 CID entry.
                When the creation of an AAL2 VCL entry does 
                not lead to the auto-creation of an AAL2 CID 
                entry by the agent, a CLI or ZMS request from 
                the CLI or ZMS can use the AAL2 CID entry 
                RowStatus object, aal2CidRowStatus, to create 
                an aal2CidEntry instance.  In this case, an 
                rfc2515 (ATM-MIB) atmVclEntry must exist prior 
                to creating an AAL2 CID entry.
                
                AAL2 CID entry deletion is accomplished with 
                the AAL2 CID entry RowStatus object, 
                aal2CidRowStatus.  If an AAL2 VCL entry
                is deleted, then the agent cleans up all
                associated AAL2 CID entries."
            REFERENCE
                "STR-VMOA-LES-01-00 Section 4.4"
            ::= { zhoneAtmAAl2 2 }

        
        -- 1.3.6.1.4.1.5504.4.2.1.2.1
        aal2CidEntry OBJECT-TYPE
            SYNTAX Aal2CidEntry
            MAX-ACCESS not-accessible
            STATUS current
            DESCRIPTION
                "An entry in the Channel Identifier (CID) table.  
                Indexed by ifIndex, atmVclVpi from atmVclTable, 
                atmVclVci from atmVclTable, and aal2Cid."
            REFERENCE
                "STR-VMOA-LES-01-00 Section 4.4"
            INDEX { ifIndex, atmVclVpi, atmVclVci, aal2Cid }
            ::= { aal2CidTable 1 }

        
        Aal2CidEntry ::=
            SEQUENCE { 
                aal2Cid
                    Integer32,
                aal2CidAdminStatus
                    AtmVorXAdminStatus,
                aal2CidOperStatus
                    AtmVorXOperStatus,
                aal2CidLastChange
                    AtmVorXLastChange,
                aal2CidSscsType
                    INTEGER,
                aal2CidAudioService
                    INTEGER,
                aal2CidCircuitModeData
                    INTEGER,
                aal2CidFrameModeData
                    INTEGER,
                aal2CidFaxDemoRemo
                    INTEGER,
                aal2CidCAS
                    INTEGER,
                aal2CidDTMFDialedDigits
                    INTEGER,
                aal2CidMfR1DialedDigits
                    INTEGER,
                aal2CidMfR2DialedDigits
                    INTEGER,
                aal2CidPCMEncoding
                    INTEGER,
                aal2CidMaxLengthFrame
                    Integer32,
                aal2CidMaxSDULength
                    Integer32,
                aal2CidRasTimer
                    Integer32,
                aal2CidPreferredApIndex
                    Integer32,
                aal2CidCellsReceived
                    Gauge32,
                aal2CidCellsSent
                    Gauge32,
                aal2CidStatsTimeElapsed
                    Integer32,
                aal2CidRowStatus
                    ZhoneRowStatus,
                aal2CidCompletedCalls
                    Counter32,
                aal2CidBlockedCallsNoBandwidth
                    Counter32
             }

-- The Channel Table Index
-- 
        -- 1.3.6.1.4.1.5504.4.2.1.2.1.1
        aal2Cid OBJECT-TYPE
            SYNTAX Integer32 (1..255)
            MAX-ACCESS not-accessible
            STATUS current
            DESCRIPTION
                "The Channel Identifier is one of the indices for
                the CID table.
                
                The maximum number of connections allowed per ATM
                VCL is 255. Note that there are restrictions in 
                the use of CID and in order to be LES compliant.
                
                The following assignments of AAL2 Channels and CID 
                Allocation are specified in STR-VMOA-LES-01-00, 
                Section 4.4.
                  0       Not used
                  1-7     Reserved for I.363.2 layer management
                  8       Some CPE manufactures use this CID for CCS 
                          and/or Emulated Loop Control protocol
                  9       If LES-EOC is supported, else not used.
                  10-15   for future revisions of STR-VMOA-LES-01-00
                  16-223  Bearer channels and ISDN D-channels
                  224-255 set aside for vendor-specific usage
                
                See STR-VMOA-LES-01-00 4.4 for allocation of CIDs
                when ELCP is not used, allocation of CIDs when ELCP
                is used, and implementation options for AAL2 CPS.
                If the ELCP is not used, the default assignment of
                CIDs to bearer channels and ISDN D-channels shall 
                be as specified in this section.  These default
                assignments may be overridden by provisioning or 
                by management action.
                
                POTS ports at the CP-IWF shall be numbered from 1 
                to N, where N is the number of POTS ports that 
                exist at the CP-IWF.  CID = 16 shall be assigned
                to POTS port number 1, CID = 17 shall be assigned
                to POTS port number 2, and so on up to POTS port 
                number N.
                
                For Jetstream applications, CID refers to port
                number and the valid range is 1 to 255.
                
                For non-Jetstream applications, the valid range
                is 16 to 255."
            REFERENCE
                "STR-VMOA-LES-01-00 Section 4.4"
            ::= { aal2CidEntry 1 }

        
-- The AAL2 Channel Table Status Group 
-- 
        -- 1.3.6.1.4.1.5504.4.2.1.2.1.2
        aal2CidAdminStatus OBJECT-TYPE
            SYNTAX AtmVorXAdminStatus
            MAX-ACCESS read-create
            STATUS current
            DESCRIPTION
                "This object is instantiated only for a VCL 
                which terminates a VCC (i.e., one which is NOT
                cross-connected to other VCLs). Its value
                specifies the desired administrative state of
                the CID.
                
                Valid values are up and down.  The default is 
                down."
            DEFVAL { down }
            ::= { aal2CidEntry 2 }

        
-- 
        -- 1.3.6.1.4.1.5504.4.2.1.2.1.3
        aal2CidOperStatus OBJECT-TYPE
            SYNTAX AtmVorXOperStatus
            MAX-ACCESS read-only
            STATUS current
            DESCRIPTION
                "The current operational status of the CID.
                
                Valid values are up, down, and unknown."
            ::= { aal2CidEntry 3 }

        
-- 
        -- 1.3.6.1.4.1.5504.4.2.1.2.1.4
        aal2CidLastChange OBJECT-TYPE
            SYNTAX AtmVorXLastChange
            MAX-ACCESS read-only
            STATUS current
            DESCRIPTION
                "The value of sysUpTime at the time this CID
                entered its current operational state, 
                indicated by aal2CidOperStatus."
            ::= { aal2CidEntry 4 }

        
-- The default for FCS is I.366.2.
-- 
-- 
        -- 1.3.6.1.4.1.5504.4.2.1.2.1.5
        aal2CidSscsType OBJECT-TYPE
            SYNTAX INTEGER
                {
                i3661(1),
                i3662(2),
                jetstreamvoice(3)
                }
            MAX-ACCESS read-create
            STATUS current
            DESCRIPTION
                "The SSCS type that applies to each channel of 
                an AAL2 VCC will vary according to the usage 
                of that channel.  Channels that are used to 
                carry media streams (POTS or ISDN B-channels) 
                shall use the SSCS defined in I.366.2.  
                Channels that are used to carry control and 
                management plane traffic (CCS, ELCP, ISDN 
                D-channels and LES-EOC) shall use the SSCS 
                defined in I.366.1.
                
                Channels that are used to carry Jetstream Voice
                shall use SSCS value of jetstreamvoice.
                
                Valid values are i3661 (I.366.1) and i3662 
                (I.366.2), jetstreamvoice.
                
                If this value is not set by CLI or ZMS, the
                agent will use the AAL2 VCL entry default."
            REFERENCE
                "STR-VMOA-LES-01-00 Section 4.1.4"
            DEFVAL { i3662 }
            ::= { aal2CidEntry 5 }

        
-- SSCS Default Parameters. Please refer to I.366.2
-- and STR-VMOA-LES-01-00 Appendix E
-- 
-- I.366.2 SSCS parameters.This parameter can be 
-- taken from the Default VCL values in the absence 
-- of signaling or provisioning on a per channel 
-- basis, either explicit or implicit, the default 
-- SSCS parameters values shall apply to each AAL2 
-- channel within the ATM AAL2 VCC.
-- 
-- Refer to section 4.1.5 in STR-VMOA-LES-01-00.
-- 
-- 
        -- 1.3.6.1.4.1.5504.4.2.1.2.1.6
        aal2CidAudioService OBJECT-TYPE
            SYNTAX INTEGER
                {
                enabled(1),
                disabled(2),
                enabledEchoCancelOff(3),
                enabledDynamic(4)
                }
            MAX-ACCESS read-create
            STATUS current
            DESCRIPTION
                "Audio Service.
                
                Refer to the corresponding object in the VCL
                table.
                
                Valid values are:
                - enabled.
                - disabled.
                - enabledEchoCancelOff: audio service enabled with echo 
                  cancellation and silence supression off.
                - enabledDynamic: audio service enabled with ability to
                  dynamically disable silence supression, silence detection,
                  echo cancellation and compression algorithms on a per-call
                  basis.
                
                If this value is not set by CLI or ZMS, the agent will 
                use the AAL2 VCL entry default."
            REFERENCE
                "I.366.2, STR-VMOA-LES-01-00 Appendix E"
            DEFVAL { enabled }
            ::= { aal2CidEntry 6 }

        
-- Not currently supported.
-- 
-- 
        -- 1.3.6.1.4.1.5504.4.2.1.2.1.7
        aal2CidCircuitModeData OBJECT-TYPE
            SYNTAX INTEGER
                {
                enabled(1),
                disabled(2)
                }
            MAX-ACCESS read-create
            STATUS current
            DESCRIPTION
                "Circuit Mode Data.
                
                Refer to the corresponding object in the VCL
                table.
                
                Valid values are enabled and disabled. If 
                this value is not set by CLI or ZMS, the 
                agent will use the AAL2 VCL entry default."
            REFERENCE
                "I.366.2, STR-VMOA-LES-01-00 Appendix E"
            DEFVAL { disabled }
            ::= { aal2CidEntry 7 }

        
-- 
        -- 1.3.6.1.4.1.5504.4.2.1.2.1.8
        aal2CidFrameModeData OBJECT-TYPE
            SYNTAX INTEGER
                {
                enabled(1),
                disabled(2)
                }
            MAX-ACCESS read-create
            STATUS current
            DESCRIPTION
                "Frame Mode Data. 
                
                Refer to the corresponding object in the VCL
                table.
                
                Valid values are enabled and disabled. If 
                this value is not set by CLI or ZMS, the 
                agent will use the AAL2 VCL entry default."
            REFERENCE
                "I.366.2, STR-VMOA-LES-01-00 Appendix E"
            DEFVAL { disabled }
            ::= { aal2CidEntry 8 }

        
-- Not currently supported
-- 
-- 
        -- 1.3.6.1.4.1.5504.4.2.1.2.1.9
        aal2CidFaxDemoRemo OBJECT-TYPE
            SYNTAX INTEGER
                {
                enabled(1),
                disabled(2)
                }
            MAX-ACCESS read-create
            STATUS current
            DESCRIPTION
                "Fax Demodulation/Remodulation.
                
                Refer to the corresponding object in the VCL
                table.
                
                Valid values are enabled and disabled. If 
                this value is not set by CLI or ZMS, the 
                agent will use the AAL2 VCL entry default."
            REFERENCE
                "I.366.2, STR-VMOA-LES-01-00 Appendix E"
            DEFVAL { disabled }
            ::= { aal2CidEntry 9 }

        
-- 
        -- 1.3.6.1.4.1.5504.4.2.1.2.1.10
        aal2CidCAS OBJECT-TYPE
            SYNTAX INTEGER
                {
                enabled(1),
                disabled(2)
                }
            MAX-ACCESS read-create
            STATUS current
            DESCRIPTION
                "CAS (Channel Associated Signaling). 
                
                Refer to the corresponding object in the VCL
                table.
                
                Valid values are enabled and disabled. If 
                this value is not set by CLI or ZMS, the 
                agent will use the AAL2 VCL entry default.
                
                For jetstream atmVccAal2AppId the only valid value is disabled."
            REFERENCE
                "I.366.2, STR-VMOA-LES-01-00 Appendix E"
            DEFVAL { enabled }
            ::= { aal2CidEntry 10 }

        
-- Not currently supported.
-- 
        -- 1.3.6.1.4.1.5504.4.2.1.2.1.11
        aal2CidDTMFDialedDigits OBJECT-TYPE
            SYNTAX INTEGER
                {
                enabled(1),
                disabled(2)
                }
            MAX-ACCESS read-create
            STATUS current
            DESCRIPTION
                "DTMF Dialed Digits.
                
                Refer to the corresponding object in the VCL
                table.
                
                Valid values are enabled and disabled. If 
                this value is not set by CLI or ZMS, the 
                agent will use the AAL2 VCL entry default."
            REFERENCE
                "I.366.2, STR-VMOA-LES-01-00 Appendix E"
            DEFVAL { disabled }
            ::= { aal2CidEntry 11 }

        
-- Not currently supported.
-- 
        -- 1.3.6.1.4.1.5504.4.2.1.2.1.12
        aal2CidMfR1DialedDigits OBJECT-TYPE
            SYNTAX INTEGER
                {
                enabled(1),
                disabled(2)
                }
            MAX-ACCESS read-create
            STATUS current
            DESCRIPTION
                "MF-R1 Dialed Digits.
                
                Refer to the corresponding object in the VCL
                table.
                
                Valid values are enabled and disabled. If 
                this value is not set by CLI or ZMS, the 
                agent will use the AAL2 VCL entry default."
            REFERENCE
                "I.366.2, STR-VMOA-LES-01-00 Appendix E"
            DEFVAL { disabled }
            ::= { aal2CidEntry 12 }

        
-- Not currently supported.
-- 
        -- 1.3.6.1.4.1.5504.4.2.1.2.1.13
        aal2CidMfR2DialedDigits OBJECT-TYPE
            SYNTAX INTEGER
                {
                enabled(1),
                disabled(2)
                }
            MAX-ACCESS read-create
            STATUS current
            DESCRIPTION
                "MF-R2 Dialed Digits.
                
                Refer to the corresponding object in the VCL
                table.
                
                Valid values are enabled and disabled. If 
                this value is not set by CLI or ZMS, the 
                agent will use the AAL2 VCL entry default."
            REFERENCE
                "I.366.2, STR-VMOA-LES-01-00 Appendix E"
            DEFVAL { disabled }
            ::= { aal2CidEntry 13 }

        
-- 
        -- 1.3.6.1.4.1.5504.4.2.1.2.1.14
        aal2CidPCMEncoding OBJECT-TYPE
            SYNTAX INTEGER
                {
                muLaw(1),
                aLaw(2)
                }
            MAX-ACCESS read-create
            STATUS current
            DESCRIPTION
                "PCM Encoding.
                
                Refer to the corresponding object in the VCL
                table.
                
                Valid values are muLaw and aLaw. If this 
                value is not set by CLI or ZMS, the agent 
                will use the AAL2 VCL entry default."
            REFERENCE
                "I.366.2, STR-VMOA-LES-01-00 Appendix E"
            DEFVAL { muLaw }
            ::= { aal2CidEntry 14 }

        
-- 
        -- 1.3.6.1.4.1.5504.4.2.1.2.1.15
        aal2CidMaxLengthFrame OBJECT-TYPE
            SYNTAX Integer32 (1..65535)
            UNITS "octets"
            MAX-ACCESS read-create
            STATUS current
            DESCRIPTION
                "Max length frame mode data. 
                
                Refer to the corresponding object in the VCL
                table.
                
                Valid values are 1..65535.  If this value is 
                not set by CLI or ZMS, the agent will use 
                the AAL2 VCL entry default."
            REFERENCE
                "I.366.2, STR-VMOA-LES-01-00 Appendix E"
            DEFVAL { 65535 }
            ::= { aal2CidEntry 15 }

        
-- SSCS Default Parameters. Please refer to I.366.1
-- See 7.7.1 for description.
-- 
-- 
        -- 1.3.6.1.4.1.5504.4.2.1.2.1.16
        aal2CidMaxSDULength OBJECT-TYPE
            SYNTAX Integer32 (1..65568)
            UNITS "octets"
            MAX-ACCESS read-create
            STATUS current
            DESCRIPTION
                "Max_SDU_Length	
                
                Refer to the corresponding object in the VCL
                table.
                
                Valid values are 1..65568. If this value is 
                not set by CLI or ZMS, the agent will use 
                the AAL2 VCL entry default."
            REFERENCE
                "I.366.1 Section 7.7.1"
            DEFVAL { 1536 }
            ::= { aal2CidEntry 16 }

        
-- 
        -- 1.3.6.1.4.1.5504.4.2.1.2.1.17
        aal2CidRasTimer OBJECT-TYPE
            SYNTAX Integer32
            UNITS "milliseconds"
            MAX-ACCESS read-create
            STATUS current
            DESCRIPTION
                "Reassembly timer (RAS_Timer). 
                
                Refer to the corresponding object in the VCL
                table.
                
                If this value is not set by CLI or ZMS, the 
                agent will use the AAL2 VCL entry default."
            REFERENCE
                "I.366.1 7.7.1"
            DEFVAL { 0 }
            ::= { aal2CidEntry 17 }

        
-- This field points to the default Encoding index for an 
-- Audio Profile Identifier. 
-- 
-- 
        -- 1.3.6.1.4.1.5504.4.2.1.2.1.18
        aal2CidPreferredApIndex OBJECT-TYPE
            SYNTAX Integer32 (1..512)
            MAX-ACCESS read-create
            STATUS current
            DESCRIPTION
                "Index for the preferred audio encoding format within
                the Audio Profile. The Index must be an agreed
                operating parameter between the transmitter and
                receiver for both directions. An aal2CidPreferredApIndex
                identifies an audio profile row of the selected audio 
                profile at the aal2 Vcl."
            DEFVAL { 1 }
            ::= { aal2CidEntry 18 }

        
-- 
        -- 1.3.6.1.4.1.5504.4.2.1.2.1.19
        aal2CidCellsReceived OBJECT-TYPE
            SYNTAX Gauge32
            MAX-ACCESS read-only
            STATUS current
            DESCRIPTION
                "Total cells received"
            ::= { aal2CidEntry 19 }

        
-- 
        -- 1.3.6.1.4.1.5504.4.2.1.2.1.20
        aal2CidCellsSent OBJECT-TYPE
            SYNTAX Gauge32
            MAX-ACCESS read-only
            STATUS current
            DESCRIPTION
                "Total cells sent"
            ::= { aal2CidEntry 20 }

        
-- 
        -- 1.3.6.1.4.1.5504.4.2.1.2.1.21
        aal2CidStatsTimeElapsed OBJECT-TYPE
            SYNTAX Integer32
            MAX-ACCESS read-only
            STATUS current
            DESCRIPTION
                "The number of seconds that have elapsed since 
                the beginning of the current collection
                period.  If, for some reason, such as an
                adjustment in the system's time-of-day clock, 
                the current interval exceeds the maximum value,
                the agent will return the maximum value."
            ::= { aal2CidEntry 21 }

        
        -- 1.3.6.1.4.1.5504.4.2.1.2.1.22
        aal2CidRowStatus OBJECT-TYPE
            SYNTAX ZhoneRowStatus
            MAX-ACCESS read-create
            STATUS current
            DESCRIPTION
                "Used to control row creation and deletion. 
                
                A row in this table is created using a 
                single SNMP SET request with varbinds for:
                a) aal2CidRowStatus set to'CreateAndGo'
                b) the following READ-CREATE objects with a
                   DEFVAL but whose defined default value is 
                   inappropriate: 
                   * aal2CidAdminStatus
                
                If 'createAndGo' successfully created a new
                row, the RowStatus will be 'active'.  
                Subsequent to successful row creation, 
                the RowStatus can be retrieved via an 
                SNMP GET and the returned RowStatus value 
                is active.  If the 'createAndGo' was 
                unsuccessful an SNMP error will be 
                returned and a subsequent GET on the 
                non-existent row will also return an 
                SNMP error of noSuchInstance. An SNMP SET 
                with the RowStatus value of 'destroy' 
                indicates that the agent should remove 
                the row from service and then delete it."
            ::= { aal2CidEntry 22 }

        
-- 
        -- 1.3.6.1.4.1.5504.4.2.1.2.1.23
        aal2CidCompletedCalls OBJECT-TYPE
            SYNTAX Counter32
            MAX-ACCESS read-only
            STATUS current
            DESCRIPTION
                "Total number of completed calls made on the CID."
            ::= { aal2CidEntry 23 }

        
-- 
        -- 1.3.6.1.4.1.5504.4.2.1.2.1.24
        aal2CidBlockedCallsNoBandwidth OBJECT-TYPE
            SYNTAX Counter32
            MAX-ACCESS read-only
            STATUS current
            DESCRIPTION
                "Total number of calls blocked on the CID because there
                was not enough bandwidth to support the call."
            ::= { aal2CidEntry 24 }

        
-- The AAL2 User-defined Audio Profile Next Index Table 
-- 
        -- 1.3.6.1.4.1.5504.4.2.1.3
        aal2UserDefinedAudioProfileNextIndexTable OBJECT-TYPE
            SYNTAX SEQUENCE OF Aal2UserDefinedAudioProfileNextIndexEntry
            MAX-ACCESS not-accessible
            STATUS current
            DESCRIPTION
                "The AAL2 User-defined Audio Profile Next Index Table 
                consists of a single READ-ONLY object maintained by
                the agent.  For a given aal2VclAudioProfileIdentifier,
                the entry indicates the next available index 
                to be used for aal2ApIndex when creating user-defined
                entries in the AAL2 Audio Profile Table.  
                
                User-defined audio profile entries have audio profile
                identifiers in the 256..512 range."
            REFERENCE
                "STR-VMOA-LES-01-00 Annex A"
            ::= { zhoneAtmAAl2 3 }

        
        -- 1.3.6.1.4.1.5504.4.2.1.3.1
        aal2UserDefinedAudioProfileNextIndexEntry OBJECT-TYPE
            SYNTAX Aal2UserDefinedAudioProfileNextIndexEntry
            MAX-ACCESS not-accessible
            STATUS current
            DESCRIPTION
                "An entry in the AAL2 Audio Profile Next Index Table. 
                Indexed by aal2VclAudioProfileIdentifier from 
                aal2VclTable.  Each Identifier is associated with 
                an object whose value is used for aal2UdApIndex when
                creating entries in the AAL2 User-defined Audio Profile
                Table."
            REFERENCE
                "STR-VMOA-LES-01-00 Annex A"
            INDEX { aal2VclAudioProfileIdentifier }
            ::= { aal2UserDefinedAudioProfileNextIndexTable 1 }

        
        Aal2UserDefinedAudioProfileNextIndexEntry ::=
            SEQUENCE { 
                aal2UdApNextIndex
                    Integer32
             }

-- 
        -- 1.3.6.1.4.1.5504.4.2.1.3.1.1
        aal2UdApNextIndex OBJECT-TYPE
            SYNTAX Integer32 (0..255)
            MAX-ACCESS read-only
            STATUS current
            DESCRIPTION
                "This object indicates the next available index, for the
                aal2VclAudioProfileIdentifier index, to be used for 
                aal2ApIndex when creating user-defined Audio Profile 
                entries in the AAL2 Audio Profile Table.
                
                The value 0 indicates that no unassigned entries are
                available. To obtain the aal2ApIndex value for a 
                new entry, the manager issues a management protocol 
                retrieval operation to obtain the current value of 
                this object.  After each retrieval, the agent should 
                modify the value to the next unassigned index.  After 
                a manager retrieves a value the agent will determine 
                through its local policy when this index value will 
                be made available for reuse.
                
                Valid values are 0..255"
            ::= { aal2UserDefinedAudioProfileNextIndexEntry 1 }

        
-- The AAL2 Audio Profile Table consists of pre-defined 
-- and user-defined audio profile entries.  Pre-defined
-- audio profiles are instantiated by the agent and are
-- defined by STR-VMOA-LES-01-00 Annex A.  User-defined
-- profiles entries are created via the CLI or ZMS.
-- Refer to the description for the VCL Audio Profile 
-- Identifier, aal2VclAudioProfileIdentifier, in the
-- AAL2 VCL Table.
-- 
-- Each Audio Profile entry is indexed by an Audio 
-- Profile Identifier, whose value is well-defined by 
-- STR-VMOA-LES-01-00 Annex A.  Pre-defined audio 
-- profile identifiers are in the range 1..255. 
-- User-defined audio profile identifiers are in the
-- range 256..512.  
-- 
-- The agent and ZMS are responsible for managing
-- identifier values.  
-- 
-- Each identifier is associated with one or more 
-- audio profiles, indexed by the audio profile index, 
-- aal2ApIndex.  See the tables in Annex A,
-- 
-- Although MAX-ACCESS for objects within audio profile 
-- entries is READ-CREATE, pre-defined and user-defined 
-- audio profile entry columns are processed differently.
-- User-defined Audio Profile entries are treated as 
-- READ-CREATE objects created using the RowStatus 
-- object, unlike pre-defined Audio Profile entry 
-- columns which are treated as if READ-ONLY and where
-- any any row creation requests are ignored.
-- 
-- Audio Profile Tables have 2 indices:
-- * aal2VclAudioProfileIdentifier from aal2VclEntry
-- * aal2ApIndex from aal2AudioProfileEntry
-- 
-- For each Audio Profile Identifier, there is
-- one or more audio profile entries (rows). Each
-- row is indexed by an ApIndex from the 
-- AudioProfileEntry and includes the following 
-- columns:
-- * UUI codepoint range
-- * number of SDUs or multiples in a packet
-- * algorithm
-- * packet time
-- * sequence number interval
-- * silence supression
-- * packet length
-- 
-- These tables contain the audio profile attributes 
-- needed by the I.366.2 service specific convergence 
-- sublayer.
-- 
-- FCS will only support pre-defined profiles. These Audio Profiles are 
-- listed in STR-VMOA-LES-01.00 Annex A
        -- 1.3.6.1.4.1.5504.4.2.1.4
        aal2AudioProfileTable OBJECT-TYPE
            SYNTAX SEQUENCE OF Aal2AudioProfileEntry
            MAX-ACCESS not-accessible
            STATUS current
            DESCRIPTION
                "AAL2 Audio Profile Table
                
                A profile is a set of entries, where each 
                entry specifies an encoding format (see 
                STR-VMOA-LES-01-00 Annex A) with a UUI range
                and length. This set defines a mapping that 
                informs the receiver of a type 1 packet how 
                to interpret the packet contents, i.e. which 
                encoding format in the profile is being used. 
                Once a profile is adopted between a transmitter 
                and a receiver, the transmitter can select 
                any entry of the adopted profile and the 
                receiver shall accept any entry selected by 
                the transmitter.
                
                Unlike the Pre-defined Audio Profile entries, 
                which are created by the agent, the User-defined 
                Audio Profile entries consists of READ-CREATE 
                objects created via CLI or ZMS."
            REFERENCE
                "STR-VMOA-LES-01-00 Annex A"
            ::= { zhoneAtmAAl2 4 }

        
        -- 1.3.6.1.4.1.5504.4.2.1.4.1
        aal2AudioProfileEntry OBJECT-TYPE
            SYNTAX Aal2AudioProfileEntry
            MAX-ACCESS not-accessible
            STATUS current
            DESCRIPTION
                "An entry in the AAL2 Audio Profile Table. 
                Indexed by aal2VclAudioProfileIdentifier from 
                aal2VclEntry and aal2ApIndex.  Each Identifier 
                can be associated with multiple audio profiles, 
                each indexed by aal2ApIndex."
            REFERENCE
                "STR-VMOA-LES-01-00 Annex A"
            INDEX { aal2VclAudioProfileIdentifier, aal2ApIndex }
            ::= { aal2AudioProfileTable 1 }

        
        Aal2AudioProfileEntry ::=
            SEQUENCE { 
                aal2ApIndex
                    Integer32,
                aal2ApMinUUI
                    Integer32,
                aal2ApMaxUUI
                    Integer32,
                aal2ApSduMultiples
                    Integer32,
                aal2ApAlgorithm
                    INTEGER,
                aal2ApPktTime
                    Integer32,
                aal2ApSequence
                    Integer32,
                aal2ApRowStatus
                    ZhoneRowStatus,
                aal2ApSilenceSupression
                    INTEGER,
                aal2ApPacketLength
                    Integer32
             }

        -- 1.3.6.1.4.1.5504.4.2.1.4.1.1
        aal2ApIndex OBJECT-TYPE
            SYNTAX Integer32 (1..512)
            MAX-ACCESS not-accessible
            STATUS current
            DESCRIPTION
                "Index for the AAL2 Audio Profiles within an Audio 
                Profile entry, for a given aal2VclAudioProfileIdentifier.
                
                Valid values are 1..512.  Pre-defined audio profile
                entries are in the 1..255 range.  User-defined audio
                profile entries are in the 256..512 range."
            ::= { aal2AudioProfileEntry 1 }

        
-- 
        -- 1.3.6.1.4.1.5504.4.2.1.4.1.2
        aal2ApMinUUI OBJECT-TYPE
            SYNTAX Integer32 (0..15)
            MAX-ACCESS read-create
            STATUS current
            DESCRIPTION
                "Minimum user to user indicator. 0 for encoding
                of audio.
                
                Valid values are 0..15.  The default is 0 octets."
            REFERENCE
                "STR-VMOA-LES-01-00 Annex A"
            DEFVAL { 0 }
            ::= { aal2AudioProfileEntry 2 }

        
-- 
        -- 1.3.6.1.4.1.5504.4.2.1.4.1.3
        aal2ApMaxUUI OBJECT-TYPE
            SYNTAX Integer32 (0..15)
            MAX-ACCESS read-create
            STATUS current
            DESCRIPTION
                "Maximum user to user indicator  15 for endcoding 
                of audio.
                
                Valid values are 0..15.  The default is 15 octets."
            REFERENCE
                "STR-VMOA-LES-01-00 Annex A, I.366.1 7.7.1"
            DEFVAL { 15 }
            ::= { aal2AudioProfileEntry 3 }

        
-- 
        -- 1.3.6.1.4.1.5504.4.2.1.4.1.4
        aal2ApSduMultiples OBJECT-TYPE
            SYNTAX Integer32 (1..8)
            MAX-ACCESS read-create
            STATUS current
            DESCRIPTION
                "Indicates the multiples of the SDU for each 
                algorithm that occur.
                
                Service data units (SDUs) for audio are defined 
                in relation to the profile of encoding formats 
                adopted on a given AAL type 2 connection. Each 
                algorithm that occurs in a given profile may 
                appear in multiple entries corresponding to 
                packets of different lengths. These packet 
                lengths shall align in a simple sequence, 
                whereby each is an integral multiple of the 
                smallest packet length that occurs for the 
                algorithm (at a given bit rate). The smallest 
                packet length is the SDU of the algorithm, in 
                relation to the given profile.
                
                Valid values are 1..8.  The default is 1 octets."
            REFERENCE
                "STR-VMOA-LES-01-00 Annex A, I.366.1 7.7.1, 
                I.366.2 Section 13.2"
            DEFVAL { 1 }
            ::= { aal2AudioProfileEntry 4 }

        
-- 
        -- 1.3.6.1.4.1.5504.4.2.1.4.1.5
        aal2ApAlgorithm OBJECT-TYPE
            SYNTAX INTEGER
                {
                g711(1),
                g722(2),
                g723(3),
                g72632(4),
                g727(5),
                g728(6),
                g729Edu(7),
                g729Sid(8),
                g72964(9),
                g72912(10),
                genericSid(11)
                }
            MAX-ACCESS read-create
            STATUS current
            DESCRIPTION
                "By I.366.2 Annex B through I, the valid values
                are:
                
                * G.711 Pulse Code Modulation (PCM). Two 
                  encoding laws are recommended, referred 
                  to as A-law and m-law.
                * G.722 Sub-Band Adaptive Pulse Code Modulation 
                  (SB-ADPCM). Note: This codec is not currently supported.
                * G.723.1 Note: This codec is not currently supported.
                * G.726-32 Adaptive Pulse Code Modulation (ADPCM) 
                * G.727 Embedded Adaptive Pulse Code Modulation 
                  (EADPCM). Note: This codec is not currently supported.
                * G.728 Low Delay Code Excited Linear Prediction 
                  (LD-CELP). Note: This codec is not currently supported.
                * G.729-8 EDU format.Note: This codec is not currently supported.
                * G.729 SID packet format.Note: This codec is not currently 
                  supported.
                * G.729-6.4 encoding data unit format. Note: This codec is not 
                  currently supported.
                * G.729-12 encoding data unit format for the 
                  forward adaptive mode. Note: This codec is not currently 
                  supported.
                * Generic SID packet format. Note: This codec is not currently
                  supported.
                
                The default is g711 (G.711)."
            REFERENCE
                "STR-VMOA-LES-01-00 Annex A, I.366.1 7.7.1, 
                I.366.2 Annex B through I"
            DEFVAL { g711 }
            ::= { aal2AudioProfileEntry 5 }

        
-- 
        -- 1.3.6.1.4.1.5504.4.2.1.4.1.6
        aal2ApPktTime OBJECT-TYPE
            SYNTAX Integer32 (50..110)
            UNITS "tenths of milliseconds"
            MAX-ACCESS read-create
            STATUS current
            DESCRIPTION
                "Packet time in tenths of milliseconds.
                
                Valid values are 50..110.  The default 
                is 55 tenths of milliseconds."
            REFERENCE
                "STR-VMOA-LES-01-00 Annex A, I.366.1 7.7.1"
            DEFVAL { 55 }
            ::= { aal2AudioProfileEntry 6 }

        
-- 
        -- 1.3.6.1.4.1.5504.4.2.1.4.1.7
        aal2ApSequence OBJECT-TYPE
            SYNTAX Integer32 (50..110)
            UNITS "tenths of milliseconds"
            MAX-ACCESS read-create
            STATUS current
            DESCRIPTION
                "Audio encoding packets are accompanied by a 
                sequence number field that is embedded within 
                the UUI codepoint range 0-15 for type 1 packets. 
                It is mandatory for a transmitter to increment 
                the designated bits at the frequency corresponding 
                to the sequence number interval specified in 
                the profile entry that defines the last packet 
                transmitted.
                
                The sequence number interval is the time interval 
                for incrementing sequence numbers in the packets 
                that convey an audio stream. This interval is 
                specified as part of the definition of each entry 
                in a profile.
                
                Valid values are 50..110.  The default is 
                55 tenths of milliseconds."
            REFERENCE
                "STR-VMOA-LES-01-00 Annex A, I.366.1 7.7.1"
            DEFVAL { 55 }
            ::= { aal2AudioProfileEntry 7 }

        
        -- 1.3.6.1.4.1.5504.4.2.1.4.1.8
        aal2ApRowStatus OBJECT-TYPE
            SYNTAX ZhoneRowStatus
            MAX-ACCESS read-create
            STATUS current
            DESCRIPTION
                "Used to control row creation and deletion. 
                
                A row in this table is created using a 
                single SNMP SET request with varbinds for:
                a) aal2UdApRowStatus set to'CreateAndGo'
                b) the following READ-CREATE objects with a
                   DEFVAL but whose defined default value is 
                   inappropriate: 
                   * aal2UdApMinUUI
                   * aal2UdApMaxUUI
                   * aal2UdApSduMultiples
                   * aal2UdApAlgorithm
                   * aal2UdApPktTime
                   * aal2UdApSequence
                
                If 'createAndGo' successfully created a new
                row, the RowStatus will be 'active'.  
                Subsequent to successful row creation, 
                the RowStatus can be retrieved via an 
                SNMP GET and the returned RowStatus value 
                is active.  If the 'createAndGo' was 
                unsuccessful an SNMP error will be 
                returned and a subsequent GET on the 
                non-existent row will also return an 
                SNMP error of noSuchInstance. An SNMP SET 
                with the RowStatus value of 'destroy' 
                indicates that the agent should remove 
                the row from service and then delete it."
            ::= { aal2AudioProfileEntry 8 }

        
-- 
        -- 1.3.6.1.4.1.5504.4.2.1.4.1.9
        aal2ApSilenceSupression OBJECT-TYPE
            SYNTAX INTEGER
                {
                enabled(1),
                disabled(2)
                }
            MAX-ACCESS read-create
            STATUS current
            DESCRIPTION
                "Used to control the transmission of cells during periods of
                silence. 
                The default value is enabled.
                
                
                "
            REFERENCE
                "I.366.2, STR-VMOA-LES-01-00 Appendix E"
            DEFVAL { enabled }
            ::= { aal2AudioProfileEntry 9 }

        
-- 
        -- 1.3.6.1.4.1.5504.4.2.1.4.1.10
        aal2ApPacketLength OBJECT-TYPE
            SYNTAX Integer32 (1..64)
            UNITS "octets"
            MAX-ACCESS read-create
            STATUS current
            DESCRIPTION
                "Indicates the length of a packet in octets. The packet length with 
                the MinUUI and MaxUUI are used to correctly decode the encoding format.
                
                Valid values are 1..64. The default is 44 octets
                "
            REFERENCE
                "I.366.2, STR-VMOA-LES-01-00 Appendix E"
            DEFVAL { 44 }
            ::= { aal2AudioProfileEntry 10 }

        
-- This table contains performance metrics for
-- the AAL2 Common Part Sublayer (CPS).  
-- aal2CpsPerformanceTable augments the base table,
-- aal2VclTable.  For definitions of counters, see 
-- I.363.2 Table 6.
-- 
-- The AAL2 Common Part Sublayer (CPS) Performance 
-- Table
-- 
        -- 1.3.6.1.4.1.5504.4.2.1.5
        aal2CpsPerformanceTable OBJECT-TYPE
            SYNTAX SEQUENCE OF Aal2CpsPerformanceEntry
            MAX-ACCESS not-accessible
            STATUS current
            DESCRIPTION
                "The AAL2 Common Part Sublayer (CPS) Performance
                table.  Augments the base table, aal2VclTable.
                
                The error indications to Layer Management are 
                summarized in this table."
            REFERENCE
                "I.363.2 Table 6"
            ::= { zhoneAtmAAl2 5 }

        
        -- 1.3.6.1.4.1.5504.4.2.1.5.1
        aal2CpsPerformanceEntry OBJECT-TYPE
            SYNTAX Aal2CpsPerformanceEntry
            MAX-ACCESS not-accessible
            STATUS current
            DESCRIPTION
                "An entry in the AAL2 Common Part Sublayer (CPS)
                Performance Table.  Augments aal2VclEntry.  Each
                row in the aal2VclTable has a corresponding row 
                in the aal2CpsPerformanceTable."
            AUGMENTS { aal2VclEntry }
            ::= { aal2CpsPerformanceTable 1 }

        
        Aal2CpsPerformanceEntry ::=
            SEQUENCE { 
                aal2CpsPerfSTFParity
                    Counter32,
                aal2CpsPerfSTFBadSeq
                    Counter32,
                aal2CpsPerfBadCPSLength
                    Counter32,
                aal2CpsPerfBadPayloadLength
                    Counter32,
                aal2CpsPerfHEC
                    Counter32,
                aal2CpsPerfPayloadTooLong
                    Counter32,
                aal2CpsPerfRessError
                    Counter32,
                aal2CpsPerfTransError
                    Counter32,
                aal2CpsPerfIllegalUUI
                    Counter32,
                aal2CpsPerfIllegalCID
                    Counter32,
                aal2CpsPerfCongestion
                    Counter32
             }

-- 
        -- 1.3.6.1.4.1.5504.4.2.1.5.1.1
        aal2CpsPerfSTFParity OBJECT-TYPE
            SYNTAX Counter32
            MAX-ACCESS read-only
            STATUS current
            DESCRIPTION
                "The parity of the STF indicates transmission 
                errors; the complete CPS-PDU was discarded."
            REFERENCE
                "I.363.2 Table 6"
            ::= { aal2CpsPerformanceEntry 1 }

        
-- 
        -- 1.3.6.1.4.1.5504.4.2.1.5.1.2
        aal2CpsPerfSTFBadSeq OBJECT-TYPE
            SYNTAX Counter32
            MAX-ACCESS read-only
            STATUS current
            DESCRIPTION
                "The sequence number of the STF is wrong; if the 
                OSF is less than 47, processing starts at the 
                octet pointed to by the OSF, otherwise the 
                complete CPS-PDU is discarded."
            REFERENCE
                "I.363.2 Table 6"
            ::= { aal2CpsPerformanceEntry 2 }

        
-- 
        -- 1.3.6.1.4.1.5504.4.2.1.5.1.3
        aal2CpsPerfBadCPSLength OBJECT-TYPE
            SYNTAX Counter32
            MAX-ACCESS read-only
            STATUS current
            DESCRIPTION
                "The number of octets expected for a CPS-Packet 
                overlapping into this CPS-PDU does not match 
                the information contained in the STF; if the 
                value of the OSF is less than 47, processing 
                starts at the octet pointed to by the OSF."
            REFERENCE
                "I.363.2 Table 6"
            ::= { aal2CpsPerformanceEntry 3 }

        
-- 
        -- 1.3.6.1.4.1.5504.4.2.1.5.1.4
        aal2CpsPerfBadPayloadLength OBJECT-TYPE
            SYNTAX Counter32
            MAX-ACCESS read-only
            STATUS current
            DESCRIPTION
                "The OSF of the STF contains a value 48 or 
                greater; the complete CPS-PDU is discarded."
            REFERENCE
                "I.363.2 Table 6"
            ::= { aal2CpsPerformanceEntry 4 }

        
-- 
        -- 1.3.6.1.4.1.5504.4.2.1.5.1.5
        aal2CpsPerfHEC OBJECT-TYPE
            SYNTAX Counter32
            MAX-ACCESS read-only
            STATUS current
            DESCRIPTION
                "The Header Error Control (HEC) Code of a 
                CPS-Packet header indicates transmission errors 
                in the CPS-Packet header; the unprocessed 
                information in the CPS-PDU is discarded."
            REFERENCE
                "I.363.2 Table 6"
            ::= { aal2CpsPerformanceEntry 5 }

        
-- 
        -- 1.3.6.1.4.1.5504.4.2.1.5.1.6
        aal2CpsPerfPayloadTooLong OBJECT-TYPE
            SYNTAX Counter32
            MAX-ACCESS read-only
            STATUS current
            DESCRIPTION
                "The length of the received CPS-Packet Payload 
                (CPS-SDU) exceeds the maximum length indicated 
                in 'Max_SDU_Deliver_Length'."
            REFERENCE
                "I.363.2 Table 6"
            ::= { aal2CpsPerformanceEntry 6 }

        
-- 
        -- 1.3.6.1.4.1.5504.4.2.1.5.1.7
        aal2CpsPerfRessError OBJECT-TYPE
            SYNTAX Counter32
            MAX-ACCESS read-only
            STATUS current
            DESCRIPTION
                "A partial CPS-Packet has been received previously 
                and must be discarded due to errors detected 
                before the reassembly of the CPS-Packet could 
                be completed."
            REFERENCE
                "I.363.2 Table 6"
            ::= { aal2CpsPerformanceEntry 7 }

        
-- 
        -- 1.3.6.1.4.1.5504.4.2.1.5.1.8
        aal2CpsPerfTransError OBJECT-TYPE
            SYNTAX Counter32
            MAX-ACCESS read-only
            STATUS current
            DESCRIPTION
                "The Header Error Control (HEC) Code of a 
                CPS-Packet header that was overlapping a 
                CPS-PDU boundary indicates transmission errors 
                in the CPS-Packet header; if the value of the 
                OSF is less than 47, processing starts at the 
                octet pointed to by the OSF."
            REFERENCE
                "I.363.2 Table 6"
            ::= { aal2CpsPerformanceEntry 8 }

        
-- 
        -- 1.3.6.1.4.1.5504.4.2.1.5.1.9
        aal2CpsPerfIllegalUUI OBJECT-TYPE
            SYNTAX Counter32
            MAX-ACCESS read-only
            STATUS current
            DESCRIPTION
                "The UUI field in the received CPS-Packet header 
                contains a value ('28' or '29') that is reserved 
                for future standardization."
            REFERENCE
                "I.363.2 Table 6"
            ::= { aal2CpsPerformanceEntry 9 }

        
-- 
        -- 1.3.6.1.4.1.5504.4.2.1.5.1.10
        aal2CpsPerfIllegalCID OBJECT-TYPE
            SYNTAX Counter32
            MAX-ACCESS read-only
            STATUS current
            DESCRIPTION
                "The CID value in the received CPS-Packet header 
                is not associated with a SAP."
            REFERENCE
                "I.363.2 Table 6"
            ::= { aal2CpsPerformanceEntry 10 }

        
-- 
        -- 1.3.6.1.4.1.5504.4.2.1.5.1.11
        aal2CpsPerfCongestion OBJECT-TYPE
            SYNTAX Counter32
            MAX-ACCESS read-only
            STATUS current
            DESCRIPTION
                "The congestion happens when the aal2 receiver is ready 
                to receive cells but there is no buffer ready. The receiver  
                starts dropping cells. The receiver tries to open new buffers
                for cell reception only after the last cell of the discarded
                frame arrives.
                
                This variable represents the number of times the receiver
                verified the receive queue for cell reception but the queue 
                was busy. This is called congestion event."
            ::= { aal2CpsPerformanceEntry 11 }

        
-- This table contains performance metrics for
-- the AAL2 I.366.2 Service Specific Convergence 
-- Sublayer (SSCS).  aal2SscsI3662PerfTable 
-- should only have entries for I.366.2 type CID's
-- as provisioned in aal2CidTable.
-- 
-- For definitions of counters, see I.363.2 Table 6.
-- 
-- The AAL2 I.366.2 Service Specific Convergence 
-- Sublayer (SSCS) Performance Table
-- 
        -- 1.3.6.1.4.1.5504.4.2.1.6
        aal2SscsI3662PerfTable OBJECT-TYPE
            SYNTAX SEQUENCE OF Aal2SscsI3662PerfEntry
            MAX-ACCESS not-accessible
            STATUS current
            DESCRIPTION
                "The AAL2 I.366.2 Service Specific Convergence 
                Sublayer (SSCS) Performance table."
            REFERENCE
                "I.363.2 Table 6"
            ::= { zhoneAtmAAl2 6 }

        
        -- 1.3.6.1.4.1.5504.4.2.1.6.1
        aal2SscsI3662PerfEntry OBJECT-TYPE
            SYNTAX Aal2SscsI3662PerfEntry
            MAX-ACCESS not-accessible
            STATUS current
            DESCRIPTION
                "An entry in the AAL2 I.366.2 Service Specific
                Convergence Sublayer (SSCS) Performance Table.  
                Each row in the aal2CidTable whose SSCS type
                is I.366.2 has a corresponding row in the
                aal2SscsI3662PerfTable."
            REFERENCE
                "I.363.2 Table 6"
            INDEX { ifIndex, atmVclVpi, atmVclVci, aal2Cid }
            ::= { aal2SscsI3662PerfTable 1 }

        
        Aal2SscsI3662PerfEntry ::=
            SEQUENCE { 
                aal2SscsI3662IllegalUUI
                    Counter32,
                aal2SscsI3662Type3CRC
                    Counter32,
                aal2SscsI3662ProfileError
                    Counter32
             }

-- 
        -- 1.3.6.1.4.1.5504.4.2.1.6.1.1
        aal2SscsI3662IllegalUUI OBJECT-TYPE
            SYNTAX Counter32
            MAX-ACCESS read-only
            STATUS current
            DESCRIPTION
                "The UUI field in the received CPS-Packet header 
                contains a value in the reserved ranges (16..22, 
                28..30).  See I.366.2, Table 12."
            REFERENCE
                "I.363.2 Table 12"
            ::= { aal2SscsI3662PerfEntry 1 }

        
-- 
        -- 1.3.6.1.4.1.5504.4.2.1.6.1.2
        aal2SscsI3662Type3CRC OBJECT-TYPE
            SYNTAX Counter32
            MAX-ACCESS read-only
            STATUS current
            DESCRIPTION
                "A Type 3 packet using CRC-10 validation with
                a checksum error will increase this counter."
            REFERENCE
                "I.363.2 Table 6"
            ::= { aal2SscsI3662PerfEntry 2 }

        
-- 
        -- 1.3.6.1.4.1.5504.4.2.1.6.1.3
        aal2SscsI3662ProfileError OBJECT-TYPE
            SYNTAX Counter32
            MAX-ACCESS read-only
            STATUS current
            DESCRIPTION
                "Invalid UUI codepoint and UUI length columns.
                Does not match any Audio Profile entry, based on
                the VCL entry's audio profile index."
            REFERENCE
                "I.363.2 Table 6"
            ::= { aal2SscsI3662PerfEntry 3 }

        
-- This table contains performance metrics for
-- the AAL2 I.366.1 Service Specific Convergence 
-- Sublayer (SSCS).  aal2SscsI3661PerfTable 
-- should only have entries for I.366.1 type CID's
-- as provisioned in aal2CidTable.
-- 
-- 
-- For definitions of counters, see I.366.1.
-- 
-- The AAL2 I.366.1 Service Specific Convergence 
-- Sublayer (SSCS) Performance Table
-- 
        -- 1.3.6.1.4.1.5504.4.2.1.7
        aal2SscsI3661PerfTable OBJECT-TYPE
            SYNTAX SEQUENCE OF Aal2SscsI3661PerfEntry
            MAX-ACCESS not-accessible
            STATUS current
            DESCRIPTION
                "The AAL2 I.366.1 Service Specific Convergence 
                Sublayer (SSCS) Performance table."
            REFERENCE
                "I.366.1"
            ::= { zhoneAtmAAl2 7 }

        
        -- 1.3.6.1.4.1.5504.4.2.1.7.1
        aal2SscsI3661PerfEntry OBJECT-TYPE
            SYNTAX Aal2SscsI3661PerfEntry
            MAX-ACCESS not-accessible
            STATUS current
            DESCRIPTION
                "An entry in the AAL2 I.366.1 Service Specific
                Convergence Sublayer (SSCS) Performance Table.  
                Each row in the aal2CidTable whose SSCS type
                is I.366.1 has a corresponding row in the
                aal2SscsI3661PerfTable."
            REFERENCE
                "I.366.1"
            INDEX { ifIndex, atmVclVpi, atmVclVci, aal2Cid }
            ::= { aal2SscsI3661PerfTable 1 }

        
        Aal2SscsI3661PerfEntry ::=
            SEQUENCE { 
                aal2SscsI3661MsgTooLong
                    Counter32,
                aal2SscsI3661RasTimerExpired
                    Counter32,
                aal2SscsI3661MsgTooShort
                    Counter32,
                aal2SscsI3661BadLength
                    Counter32,
                aal2SscsI3661CRC
                    Counter32
             }

-- 
        -- 1.3.6.1.4.1.5504.4.2.1.7.1.1
        aal2SscsI3661MsgTooLong OBJECT-TYPE
            SYNTAX Counter32
            MAX-ACCESS read-only
            STATUS current
            DESCRIPTION
                "The maximum permissible size for a reassembled 
                SSSAR-SDU ('Max_SDU_Length') has been exceeded."
            REFERENCE
                "I.366.1"
            ::= { aal2SscsI3661PerfEntry 1 }

        
-- 
        -- 1.3.6.1.4.1.5504.4.2.1.7.1.2
        aal2SscsI3661RasTimerExpired OBJECT-TYPE
            SYNTAX Counter32
            MAX-ACCESS read-only
            STATUS current
            DESCRIPTION
                "The reassembly timer RAS_Timer has expired."
            REFERENCE
                "I.366.1"
            ::= { aal2SscsI3661PerfEntry 2 }

        
-- 
        -- 1.3.6.1.4.1.5504.4.2.1.7.1.3
        aal2SscsI3661MsgTooShort OBJECT-TYPE
            SYNTAX Counter32
            MAX-ACCESS read-only
            STATUS current
            DESCRIPTION
                "An SSTED-PDU of length 8 or less has been 
                received."
            REFERENCE
                "I.366.1"
            ::= { aal2SscsI3661PerfEntry 3 }

        
-- 
        -- 1.3.6.1.4.1.5504.4.2.1.7.1.4
        aal2SscsI3661BadLength OBJECT-TYPE
            SYNTAX Counter32
            MAX-ACCESS read-only
            STATUS current
            DESCRIPTION
                "The value of the Length field in the SSTED-PDU 
                does not match the length of the received 
                SSTED-PDU."
            REFERENCE
                "I.366.1"
            ::= { aal2SscsI3661PerfEntry 4 }

        
-- 
        -- 1.3.6.1.4.1.5504.4.2.1.7.1.5
        aal2SscsI3661CRC OBJECT-TYPE
            SYNTAX Counter32
            MAX-ACCESS read-only
            STATUS current
            DESCRIPTION
                "The value of the CRC field is not equal to the 
                CRC calculated over the received information."
            REFERENCE
                "I.366.1"
            ::= { aal2SscsI3661PerfEntry 5 }

        
        -- 1.3.6.1.4.1.5504.4.2.1.8
        aal2vpi OBJECT-TYPE
            SYNTAX AtmVpIdentifier
            MAX-ACCESS accessible-for-notify
            STATUS current
            DESCRIPTION
                "VPI used for traps defined under aal2Traps."
            ::= { zhoneAtmAAl2 8 }

        
        -- 1.3.6.1.4.1.5504.4.2.1.9
        aal2Vci OBJECT-TYPE
            SYNTAX AtmVcIdentifier
            MAX-ACCESS accessible-for-notify
            STATUS current
            DESCRIPTION
                "VCI used for traps defined under aal2Traps."
            ::= { zhoneAtmAAl2 9 }

        
        -- 1.3.6.1.4.1.5504.4.2.1.10
        aal2AlarmConfigTable OBJECT-TYPE
            SYNTAX SEQUENCE OF Aal2AlarmConfigEntry
            MAX-ACCESS not-accessible
            STATUS current
            DESCRIPTION
                "This table contains thresholds that are used to control trap
                generation. aal2AlarmConfigTable augments the base table,
                aal2VclTable.
                
                All the parameters defined in this table are supported
                on the s100."
            ::= { zhoneAtmAAl2 10 }

        
        -- 1.3.6.1.4.1.5504.4.2.1.10.1
        aal2AlarmConfigEntry OBJECT-TYPE
            SYNTAX Aal2AlarmConfigEntry
            MAX-ACCESS not-accessible
            STATUS current
            DESCRIPTION
                "Each entry consists of a list of parameters that
                represents tresholds for the error indications defined
                in aal2CpsPerformanceTable. Each row in the aal2VclTable 
                has a corresponding row in the aal2AlarmConfigTable.
                "
            AUGMENTS { aal2VclEntry }
            ::= { aal2AlarmConfigTable 1 }

        
        Aal2AlarmConfigEntry ::=
            SEQUENCE { 
                aal2AlarmConfigThreshCellLoss
                    Integer32,
                aal2AlarmConfigThreshCongestion
                    Integer32
             }

        -- 1.3.6.1.4.1.5504.4.2.1.10.1.1
        aal2AlarmConfigThreshCellLoss OBJECT-TYPE
            SYNTAX Integer32 (0..900)
            MAX-ACCESS read-create
            STATUS current
            DESCRIPTION
                "The number of bad sequence number of the STF within 
                any given 15 minutes performance data collection period, 
                which causes the SNMP agent to send an
                aal2PerfCellLossThreshTrap.
                One trap will be sent per interval per interface.
                A value of `0' will disable the trap."
            DEFVAL { 0 }
            ::= { aal2AlarmConfigEntry 1 }

        
        -- 1.3.6.1.4.1.5504.4.2.1.10.1.2
        aal2AlarmConfigThreshCongestion OBJECT-TYPE
            SYNTAX Integer32 (0..900)
            MAX-ACCESS read-create
            STATUS current
            DESCRIPTION
                "The number of congestion events within any given 15 
                minutes performance data collection period, 
                which causes the SNMP agent to send an
                aal2PerfCongestionThreshTrap. 
                
                One trap will be sent per interval per interface.
                A value of `0' will disable the trap."
            DEFVAL { 0 }
            ::= { aal2AlarmConfigEntry 2 }

        
        -- 1.3.6.1.4.1.5504.4.2.1.11
        aal2ElcpPortTable OBJECT-TYPE
            SYNTAX SEQUENCE OF Aal2ElcpPortEntry
            MAX-ACCESS not-accessible
            STATUS current
            DESCRIPTION
                "The AAL2 ELCP Port Table.
                
                The AAL2 ELCP Port Table contains entries of 
                IAD ports associated with the ELCP enabled
                ATM VCC. The provisioned values in the AAL2
                ELCP Port Table supercede the defaults values
                specified in the AAL2 VCL entry.
                "
            ::= { zhoneAtmAAl2 11 }

        
        -- 1.3.6.1.4.1.5504.4.2.1.11.1
        aal2ElcpPortEntry OBJECT-TYPE
            SYNTAX Aal2ElcpPortEntry
            MAX-ACCESS not-accessible
            STATUS current
            DESCRIPTION
                "An entry in the aal2ElcpPortTable."
            INDEX { ifIndex, atmVclVpi, atmVclVci, aal2ElcpPortId, aal2ElcpPortType
                 }
            ::= { aal2ElcpPortTable 1 }

        
        Aal2ElcpPortEntry ::=
            SEQUENCE { 
                aal2ElcpPortId
                    Integer32,
                aal2ElcpPortType
                    INTEGER,
                aal2ElcpPortAudioService
                    INTEGER,
                aal2ElcpPortPCMEncoding
                    INTEGER,
                aal2ElcpPortMaxLengthFrame
                    Integer32,
                aal2ElcpPortMaxSDULength
                    Integer32,
                aal2ElcpPortPreferredApIndex
                    Integer32,
                aal2ElcpPortRowStatus
                    ZhoneRowStatus
             }

        -- 1.3.6.1.4.1.5504.4.2.1.11.1.1
        aal2ElcpPortId OBJECT-TYPE
            SYNTAX Integer32 (0..32767)
            MAX-ACCESS not-accessible
            STATUS current
            DESCRIPTION
                "The port address to identify an individual PSTN or ISDN port.
                This address must agree with the provisioned port number on
                the CPE side.
                
                PSTN and ISDN user ports have their own indenpendent
                numbering space.
                "
            REFERENCE
                "AF-VMOA-0145.000, 5.4.2"
            ::= { aal2ElcpPortEntry 1 }

        
        -- 1.3.6.1.4.1.5504.4.2.1.11.1.2
        aal2ElcpPortType OBJECT-TYPE
            SYNTAX INTEGER
                {
                pstn(1),
                isdnBra(2)
                }
            MAX-ACCESS not-accessible
            STATUS current
            DESCRIPTION
                "The port type for a provisioned IAD port for an ELCP
                enabled ATM VCC. Valid types are pstn and isdnBra."
            REFERENCE
                "AF-VMOA-0145.000, 5.4.2"
            ::= { aal2ElcpPortEntry 2 }

        
-- SSCS Default Parameters. Please refer to I.366.2
-- and STR-VMOA-LES-01-00 Appendix E
-- 
-- I.366.2 SSCS parameters.This parameter can be 
-- taken from the Default VCL values in the absence 
-- of signaling or provisioning on a per channel 
-- basis, either explicit or implicit, the default 
-- SSCS parameters values shall apply to each AAL2 
-- channel within the ATM AAL2 VCC.
-- 
-- Refer to section 4.1.5 in STR-VMOA-LES-01-00.
-- 
-- 
        -- 1.3.6.1.4.1.5504.4.2.1.11.1.3
        aal2ElcpPortAudioService OBJECT-TYPE
            SYNTAX INTEGER
                {
                enabled(1),
                disabled(2),
                enabledEchoCancelOff(3),
                enabledDynamic(4)
                }
            MAX-ACCESS read-create
            STATUS current
            DESCRIPTION
                "Audio Service.
                
                Refer to the corresponding object in the VCL
                table.
                
                Valid values are:
                - enabled.
                - disabled.
                - enabledEchoCancelOff: audio service enabled with echo 
                  cancellation and silence supression off.
                - enabledDynamic: audio service enabled with ability to
                  dynamically disable silence supression, silence detection,
                  echo cancellation and compression algorithms on a per-call
                  basis.
                
                If this value is not set by CLI or ZMS, the agent will 
                use the AAL2 VCL entry default."
            REFERENCE
                "I.366.2, STR-VMOA-LES-01-00 Appendix E"
            DEFVAL { enabled }
            ::= { aal2ElcpPortEntry 3 }

        
-- 
        -- 1.3.6.1.4.1.5504.4.2.1.11.1.4
        aal2ElcpPortPCMEncoding OBJECT-TYPE
            SYNTAX INTEGER
                {
                muLaw(1),
                aLaw(2)
                }
            MAX-ACCESS read-create
            STATUS current
            DESCRIPTION
                "PCM Encoding.
                
                Refer to the corresponding object in the VCL
                table.
                
                Valid values are muLaw and aLaw. If this 
                value is not set by CLI or ZMS, the agent 
                will use the AAL2 VCL entry default."
            REFERENCE
                "I.366.2, STR-VMOA-LES-01-00 Appendix E"
            DEFVAL { aLaw }
            ::= { aal2ElcpPortEntry 4 }

        
-- 
        -- 1.3.6.1.4.1.5504.4.2.1.11.1.5
        aal2ElcpPortMaxLengthFrame OBJECT-TYPE
            SYNTAX Integer32 (1..65535)
            UNITS "octets"
            MAX-ACCESS read-create
            STATUS current
            DESCRIPTION
                "Max length frame mode data. 
                
                Refer to the corresponding object in the VCL
                table.
                
                Valid values are 1..65535.  If this value is 
                not set by CLI or ZMS, the agent will use 
                the AAL2 VCL entry default."
            REFERENCE
                "I.366.2, STR-VMOA-LES-01-00 Appendix E"
            DEFVAL { 65535 }
            ::= { aal2ElcpPortEntry 5 }

        
-- SSCS Default Parameters. Please refer to I.366.1
-- See 7.7.1 for description.
-- 
-- 
        -- 1.3.6.1.4.1.5504.4.2.1.11.1.6
        aal2ElcpPortMaxSDULength OBJECT-TYPE
            SYNTAX Integer32 (1..65568)
            UNITS "octets"
            MAX-ACCESS read-create
            STATUS current
            DESCRIPTION
                "Max_SDU_Length	
                
                Refer to the corresponding object in the VCL
                table.
                
                Valid values are 1..65568. If this value is 
                not set by CLI or ZMS, the agent will use 
                the AAL2 VCL entry default."
            REFERENCE
                "I.366.1 Section 7.7.1"
            DEFVAL { 1536 }
            ::= { aal2ElcpPortEntry 6 }

        
-- This field points to the default Encoding index for an 
-- Audio Profile Identifier. 
-- 
-- 
        -- 1.3.6.1.4.1.5504.4.2.1.11.1.7
        aal2ElcpPortPreferredApIndex OBJECT-TYPE
            SYNTAX Integer32 (1..512)
            MAX-ACCESS read-create
            STATUS current
            DESCRIPTION
                "Index for the preferred audio encoding format within
                the Audio Profile. The Index must be an agreed
                operating parameter between the transmitter and
                receiver for both directions. An aal2CidPreferredApIndex
                identifies an audio profile row of the selected audio 
                profile at the aal2 Vcl."
            DEFVAL { 1 }
            ::= { aal2ElcpPortEntry 7 }

        
        -- 1.3.6.1.4.1.5504.4.2.1.11.1.8
        aal2ElcpPortRowStatus OBJECT-TYPE
            SYNTAX ZhoneRowStatus
            MAX-ACCESS read-create
            STATUS current
            DESCRIPTION
                "Used to control row creation and deletion. The valid enums
                are active(1), createAndGo(4) and destroy(6). Refer to 
                Zhone-TC.mib for more details."
            ::= { aal2ElcpPortEntry 8 }

        
        -- 1.3.6.1.4.1.5504.4.2.1.12
        aal2ElcpIgTable OBJECT-TYPE
            SYNTAX SEQUENCE OF Aal2ElcpIgEntry
            MAX-ACCESS not-accessible
            STATUS current
            DESCRIPTION
                "This table provides additional information about an ELCP
                interface group. This table only exists for AAL2 VCL
                entries that are running ELCP protocol. For each AAL2 VCL
                running ELCP, there will be one entry in the aal2ElcpIgTable.
                "
            ::= { zhoneAtmAAl2 12 }

        
        -- 1.3.6.1.4.1.5504.4.2.1.12.1
        aal2ElcpIgEntry OBJECT-TYPE
            SYNTAX Aal2ElcpIgEntry
            MAX-ACCESS not-accessible
            STATUS current
            DESCRIPTION
                "An entry in the aal2ElcpIgTable."
            INDEX { ifIndex, atmVclVpi, atmVclVci }
            ::= { aal2ElcpIgTable 1 }

        
        Aal2ElcpIgEntry ::=
            SEQUENCE { 
                aal2ElcpIgOperStatus
                    AtmVorXOperStatus,
                aal2ElcpIgOperStatusChangeCount
                    Counter32,
                aal2ElcpIgLapvReceived
                    Counter32,
                aal2ElcpIgLapvSent
                    Counter32
             }

-- 
        -- 1.3.6.1.4.1.5504.4.2.1.12.1.1
        aal2ElcpIgOperStatus OBJECT-TYPE
            SYNTAX AtmVorXOperStatus
            MAX-ACCESS read-only
            STATUS current
            DESCRIPTION
                "The operational status of an ELCP interface group."
            ::= { aal2ElcpIgEntry 1 }

        
-- 
        -- 1.3.6.1.4.1.5504.4.2.1.12.1.2
        aal2ElcpIgOperStatusChangeCount OBJECT-TYPE
            SYNTAX Counter32
            MAX-ACCESS read-only
            STATUS current
            DESCRIPTION
                "Number of times the aal2ElcpIgOperStatus has changed."
            ::= { aal2ElcpIgEntry 2 }

        
-- 
        -- 1.3.6.1.4.1.5504.4.2.1.12.1.3
        aal2ElcpIgLapvReceived OBJECT-TYPE
            SYNTAX Counter32
            MAX-ACCESS read-only
            STATUS current
            DESCRIPTION
                "Number of LAPV frames received by this interface group."
            ::= { aal2ElcpIgEntry 3 }

        
-- 
        -- 1.3.6.1.4.1.5504.4.2.1.12.1.4
        aal2ElcpIgLapvSent OBJECT-TYPE
            SYNTAX Counter32
            MAX-ACCESS read-only
            STATUS current
            DESCRIPTION
                "Number of LAPV frames sent from this interface group."
            ::= { aal2ElcpIgEntry 4 }

        
    
    END

--
-- comAtmAal2.mib
--
