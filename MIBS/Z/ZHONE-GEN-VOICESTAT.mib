--
-- genVoiceStatMib.mib
-- MIB generated by MG-SOFT Visual MIB Builder Version 3.0 Build 285
-- Tuesday, September 06, 2005 at 16:19:07
--

    ZHONE-GEN-VOICESTAT DEFINITIONS ::= BEGIN
 
        IMPORTS
            InterfaceIndex            
                FROM IF-MIB            
            OBJECT-GROUP            
                FROM SNMPv2-CONF            
            mib-2, Integer32, OBJECT-TYPE, MODULE-IDENTITY, OBJECT-IDENTITY            
                FROM SNMPv2-SMI            
            zhoneGeneric, zhoneShelfIndex, zhoneSlotIndex, zhoneShelfIndex, zhoneSlotIndex            
                FROM Zhone            
            ZhoneRowStatus            
                FROM Zhone-TC;
    
    
-- 
-- 
-- profile/record definition for 'Voice_Card_Stats' dynamic attributes
-- 
-- profile/record definition for 'Voice_Sub_EP_Stats' dynamic attributes
        -- 1.3.6.1.4.1.5504.3.11.1
        zhoneVoiceStatsRecords MODULE-IDENTITY 
            LAST-UPDATED "200306271737Z"		-- June 27, 2003 at 17:37 GMT
            ORGANIZATION 
                "Zhone Technologies, Inc."
            CONTACT-INFO 
                "Postal: 
                Zhone Technologies, Inc.
                @ Zhone Way
                7001 Oakport Street
                Oakland, CA  94621
                USA
                Toll-Free: +1 877-ZHONE20 (+1 877-946-6320)
                Tel: +1-510-777-7000
                Fax: +1-510-777-7001
                E-mail: support@zhone.com"
            DESCRIPTION 
                "The MIB module to describe objects for voice call statistics.
                
                This MIB record contains tables that define voice calls
                statistics at the system, card, and subscriber end-point
                level for incoming, outgoing, and active calls.
                "
            REVISION "200509061530Z"		-- September 06, 2005 at 15:30 GMT
            DESCRIPTION 
                "Add zhoneVoiceRingTable"
            REVISION "200306271218Z"		-- June 27, 2003 at 12:18 GMT
            DESCRIPTION 
                "V01.00.00 - Initial version"
            ::= { zhoneVoiceStats 1 }

        
    
    
--
-- Node definitions
--
    
        -- 1.3.6.1.4.1.5504.3.11
        zhoneVoiceStats OBJECT-IDENTITY
            STATUS current
            DESCRIPTION 
                "Voice Call Statistics.
                
                This Object contains all instances associated with voice calls
                statistics. In revision 0, Completed, Blocked, and Active calls
                Statistics are implemented for System, card, and subscriber
                end-points.
                
                 "
            ::= { zhoneGeneric 11 }

        
        -- 1.3.6.1.4.1.5504.3.11.1.1
        zhoneSystemStats OBJECT-IDENTITY
            STATUS current
            DESCRIPTION 
                "The System voice statistics object is used to collect voice
                statistics at a system-wide level. These include statistics
                for incoming, outgoing, and active calls. The entry in this
                object is referenced using a static index of zero. 
                 "
            ::= { zhoneVoiceStatsRecords 1 }

        
-- 
        -- 1.3.6.1.4.1.5504.3.11.1.1.1
        systemIncomingCallsCompleted OBJECT-TYPE
            SYNTAX Integer32
            MAX-ACCESS read-only
            STATUS current
            DESCRIPTION
                "The number of completed incoming calls in the system."
            ::= { zhoneSystemStats 1 }

        
-- 
        -- 1.3.6.1.4.1.5504.3.11.1.1.2
        systemIncomingCallsBlocked OBJECT-TYPE
            SYNTAX Integer32
            MAX-ACCESS read-only
            STATUS current
            DESCRIPTION
                "The number of blocked incoming calls in the system."
            ::= { zhoneSystemStats 2 }

        
-- 
        -- 1.3.6.1.4.1.5504.3.11.1.1.3
        systemOutgoingCallsCompleted OBJECT-TYPE
            SYNTAX Integer32
            MAX-ACCESS read-only
            STATUS current
            DESCRIPTION
                "The number of completed outgoing calls in the system."
            ::= { zhoneSystemStats 3 }

        
-- 
        -- 1.3.6.1.4.1.5504.3.11.1.1.4
        systemOutgoingCallsBlocked OBJECT-TYPE
            SYNTAX Integer32
            MAX-ACCESS read-only
            STATUS current
            DESCRIPTION
                "The number of blocked outgoing calls in the system."
            ::= { zhoneSystemStats 4 }

        
-- 
        -- 1.3.6.1.4.1.5504.3.11.1.1.5
        systemActiveCalls OBJECT-TYPE
            SYNTAX Integer32
            MAX-ACCESS read-only
            STATUS current
            DESCRIPTION
                "The number of currently active calls in the system."
            ::= { zhoneSystemStats 5 }

        
        -- 1.3.6.1.4.1.5504.3.11.1.2
        zhoneCardStatsTable OBJECT-TYPE
            SYNTAX SEQUENCE OF ZhoneCardStatsEntry
            MAX-ACCESS not-accessible
            STATUS current
            DESCRIPTION
                "The card voice statistics table is used to collect voice calls
                statistics on any card configured to carry voice traffic.
                Statistics are currently supported for cards with AAL2, GR303,
                V52 and POTS subscribers. This table collects statistics for
                incoming calls, outgoing calls, and active calls. The entry in
                this table is referenced using shelf/slot indices.
                
                "
            ::= { zhoneVoiceStatsRecords 2 }

        
        -- 1.3.6.1.4.1.5504.3.11.1.2.1
        zhoneCardStatsEntry OBJECT-TYPE
            SYNTAX ZhoneCardStatsEntry
            MAX-ACCESS not-accessible
            STATUS current
            DESCRIPTION
                "An entry in the zhoneCardStatsTable"
            INDEX { zhoneShelfIndex, zhoneSlotIndex }
            ::= { zhoneCardStatsTable 1 }

        
        ZhoneCardStatsEntry ::=
            SEQUENCE { 
                cardIncomingCallsCompleted
                    Integer32,
                cardIncomingCallsBlocked
                    Integer32,
                cardOutgoingCallsCompleted
                    Integer32,
                cardOutgoingCallsBlocked
                    Integer32,
                cardActiveCalls
                    Integer32
             }

-- 
        -- 1.3.6.1.4.1.5504.3.11.1.2.1.1
        cardIncomingCallsCompleted OBJECT-TYPE
            SYNTAX Integer32
            MAX-ACCESS read-only
            STATUS current
            DESCRIPTION
                "The number of completed incoming calls on the card."
            ::= { zhoneCardStatsEntry 1 }

        
-- 
        -- 1.3.6.1.4.1.5504.3.11.1.2.1.2
        cardIncomingCallsBlocked OBJECT-TYPE
            SYNTAX Integer32
            MAX-ACCESS read-only
            STATUS current
            DESCRIPTION
                "The number of blocked incoming calls on the card."
            ::= { zhoneCardStatsEntry 2 }

        
-- 
        -- 1.3.6.1.4.1.5504.3.11.1.2.1.3
        cardOutgoingCallsCompleted OBJECT-TYPE
            SYNTAX Integer32
            MAX-ACCESS read-only
            STATUS current
            DESCRIPTION
                "The number of completed outgoing calls on the card."
            ::= { zhoneCardStatsEntry 3 }

        
-- 
        -- 1.3.6.1.4.1.5504.3.11.1.2.1.4
        cardOutgoingCallsBlocked OBJECT-TYPE
            SYNTAX Integer32
            MAX-ACCESS read-only
            STATUS current
            DESCRIPTION
                "The number of blocked outgoing calls on the card."
            ::= { zhoneCardStatsEntry 4 }

        
-- 
        -- 1.3.6.1.4.1.5504.3.11.1.2.1.5
        cardActiveCalls OBJECT-TYPE
            SYNTAX Integer32
            MAX-ACCESS read-only
            STATUS current
            DESCRIPTION
                "The number of currently active calls on the card."
            ::= { zhoneCardStatsEntry 5 }

        
        -- 1.3.6.1.4.1.5504.3.11.1.3
        zhoneSubscriberEPStatsTable OBJECT-TYPE
            SYNTAX SEQUENCE OF ZhoneSubscriberEPStatsEntry
            MAX-ACCESS not-accessible
            STATUS current
            DESCRIPTION
                "The subscriber voice end-point statistics table is used to
                collect incoming, outgoing, and active voice calls
                statistics for any subscriber end point.The entry in this
                table is referenced using end-point index.
                 "
            ::= { zhoneVoiceStatsRecords 3 }

        
        -- 1.3.6.1.4.1.5504.3.11.1.3.1
        zhoneSubscriberEPStatsEntry OBJECT-TYPE
            SYNTAX ZhoneSubscriberEPStatsEntry
            MAX-ACCESS not-accessible
            STATUS current
            DESCRIPTION
                "An entry in the zhoneSubscriberEPStatsTable"
            INDEX { subVoiceEndPointIndex }
            ::= { zhoneSubscriberEPStatsTable 1 }

        
        ZhoneSubscriberEPStatsEntry ::=
            SEQUENCE { 
                subVoiceEndPointIndex
                    Integer32,
                subEPIncomingCallsCompleted
                    Integer32,
                subEPIncomingCallsBlocked
                    Integer32,
                subEPOutgoingCallsCompleted
                    Integer32,
                subEPOutgoingCallsBlocked
                    Integer32,
                subEPActiveCalls
                    Integer32
             }

        -- 1.3.6.1.4.1.5504.3.11.1.3.1.2
        subVoiceEndPointIndex OBJECT-TYPE
            SYNTAX Integer32 (1..2147483647)
            MAX-ACCESS not-accessible
            STATUS current
            DESCRIPTION
                "This index is equal to the end-point indices defined for the
                subscriber voice end-point tables in the zhoneSubscriberRecords.
                These end-points include AAL2, GR303, V52, POTS, etc. For all
                the end point types, the end-point index is unique to the sytem. "
            ::= { zhoneSubscriberEPStatsEntry 2 }

        
-- 
        -- 1.3.6.1.4.1.5504.3.11.1.3.1.3
        subEPIncomingCallsCompleted OBJECT-TYPE
            SYNTAX Integer32
            MAX-ACCESS read-only
            STATUS current
            DESCRIPTION
                "The number of completed incoming calls at the subscriber voice
                end point."
            ::= { zhoneSubscriberEPStatsEntry 3 }

        
-- 
        -- 1.3.6.1.4.1.5504.3.11.1.3.1.4
        subEPIncomingCallsBlocked OBJECT-TYPE
            SYNTAX Integer32
            MAX-ACCESS read-only
            STATUS current
            DESCRIPTION
                "The number of blocked incoming calls at the subscriber voice
                end point."
            ::= { zhoneSubscriberEPStatsEntry 4 }

        
-- 
        -- 1.3.6.1.4.1.5504.3.11.1.3.1.5
        subEPOutgoingCallsCompleted OBJECT-TYPE
            SYNTAX Integer32
            MAX-ACCESS read-only
            STATUS current
            DESCRIPTION
                "The number of completed outgoing calls at the subscriber voice
                end point."
            ::= { zhoneSubscriberEPStatsEntry 5 }

        
-- 
        -- 1.3.6.1.4.1.5504.3.11.1.3.1.6
        subEPOutgoingCallsBlocked OBJECT-TYPE
            SYNTAX Integer32
            MAX-ACCESS read-only
            STATUS current
            DESCRIPTION
                "The number of blocked outgoing calls at the subscriber voice
                end point."
            ::= { zhoneSubscriberEPStatsEntry 6 }

        
-- 
        -- 1.3.6.1.4.1.5504.3.11.1.3.1.7
        subEPActiveCalls OBJECT-TYPE
            SYNTAX Integer32
            MAX-ACCESS read-only
            STATUS current
            DESCRIPTION
                "The number of currently active calls at the subscriber voice
                end point."
            ::= { zhoneSubscriberEPStatsEntry 7 }

        
        -- 1.3.6.1.4.1.5504.3.11.1.7
        zhoneVoiceStatsObjectsGroup OBJECT-GROUP
            OBJECTS { systemIncomingCallsCompleted, systemIncomingCallsBlocked, systemOutgoingCallsCompleted, systemOutgoingCallsBlocked, systemActiveCalls, 
                cardIncomingCallsCompleted, cardIncomingCallsBlocked, cardOutgoingCallsCompleted, cardOutgoingCallsBlocked, cardActiveCalls, 
                subEPIncomingCallsCompleted, subEPIncomingCallsBlocked, subEPOutgoingCallsCompleted, subEPOutgoingCallsBlocked, subEPActiveCalls
                 }
            STATUS current
            DESCRIPTION 
                "This group contains objects associated with voice statistics."
            ::= { zhoneVoiceStatsRecords 7 }

        
        -- 1.3.6.1.4.1.5504.3.11.1.8
        zhoneVoiceRingTable OBJECT-TYPE
            SYNTAX SEQUENCE OF ZhoneVoiceRingEntry
            MAX-ACCESS not-accessible
            STATUS current
            DESCRIPTION
                "Table used to generate ring on a port."
            ::= { zhoneVoiceStatsRecords 8 }

        
        -- 1.3.6.1.4.1.5504.3.11.1.8.1
        zhoneVoiceRingEntry OBJECT-TYPE
            SYNTAX ZhoneVoiceRingEntry
            MAX-ACCESS not-accessible
            STATUS current
            DESCRIPTION
                "Row in the zhoneVoiceRing table - corresponds to a port on which ring can be generated.
                "
            INDEX { zhoneVoiceRingIfIndex }
            ::= { zhoneVoiceRingTable 1 }

        
        ZhoneVoiceRingEntry ::=
            SEQUENCE { 
                zhoneVoiceRingIfIndex
                    InterfaceIndex,
                zhoneVoiceRingRingingCadence
                    INTEGER,
                zhoneVoiceRingTimer
                    Integer32,
                zhoneVoiceRingRowStatus
                    ZhoneRowStatus
             }

        -- 1.3.6.1.4.1.5504.3.11.1.8.1.1
        zhoneVoiceRingIfIndex OBJECT-TYPE
            SYNTAX InterfaceIndex
            MAX-ACCESS not-accessible
            STATUS current
            DESCRIPTION
                "physical interface"
            ::= { zhoneVoiceRingEntry 1 }

        
        -- 1.3.6.1.4.1.5504.3.11.1.8.1.2
        zhoneVoiceRingRingingCadence OBJECT-TYPE
            SYNTAX INTEGER
                {
                ringCadenceR0(1),
                ringCadenceR1(2),
                ringCadenceR2(3),
                ringCadenceR3(4),
                ringCadenceR4(5),
                ringCadenceR5(6),
                ringCadenceR6(7),
                ringCadenceR7(8),
                ringCadenceCommon(9),
                ringCadenceSplash(10)
                }
            MAX-ACCESS read-create
            STATUS current
            DESCRIPTION
                "Ringing cadence to use in test."
            ::= { zhoneVoiceRingEntry 2 }

        
        -- 1.3.6.1.4.1.5504.3.11.1.8.1.3
        zhoneVoiceRingTimer OBJECT-TYPE
            SYNTAX Integer32 (0..999)
            MAX-ACCESS read-create
            STATUS current
            DESCRIPTION
                "Time in seconds to continue ringing."
            ::= { zhoneVoiceRingEntry 3 }

        
        -- 1.3.6.1.4.1.5504.3.11.1.8.1.4
        zhoneVoiceRingRowStatus OBJECT-TYPE
            SYNTAX ZhoneRowStatus
            MAX-ACCESS read-create
            STATUS current
            DESCRIPTION
                "Row status."
            ::= { zhoneVoiceRingEntry 4 }

        
    
    END

--
-- genVoiceStatMib.mib
--
