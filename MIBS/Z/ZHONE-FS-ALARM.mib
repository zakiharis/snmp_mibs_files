--
-- zmsAlarm.mib
-- MIB generated by MG-SOFT Visual MIB Builder Version 3.0 Build 285
-- Sunday, April 21, 2013 at 16:31:12
--

	ZHONE-FS-ALARM DEFINITIONS ::= BEGIN
 
		IMPORTS
			OBJECT-GROUP, NOTIFICATION-GROUP			
				FROM SNMPv2-CONF			
			IpAddress, Integer32, OBJECT-TYPE, MODULE-IDENTITY, OBJECT-IDENTITY, 
			NOTIFICATION-TYPE			
				FROM SNMPv2-SMI			
			TruthValue			
				FROM SNMPv2-TC			
			zhoneTrapVersion, zhoneTrapsSequenceNumber, zhoneTrapsSeverity			
				FROM ZHONE-SYSTEM-MIB			
			zhoneZmsProduct			
				FROM Zhone;
	
	
		-- 1.3.6.1.4.1.5504.2.7.1
		faultServiceAlarm MODULE-IDENTITY 
			LAST-UPDATED "201304211711Z"		-- April 21, 2013 at 17:11 GMT
			ORGANIZATION 
				"Zhone Technologies, Inc."
			CONTACT-INFO 
				"  Postal:
				Zhone Technologies, Inc.
				@ Zhone Way
				7001 Oakport Street
				Oakland, CA  94621
				USA
				Toll-Free: +1 877-ZHONE20 (+1 877-946-6320)
				Tel: +1-510-777-7000
				Fax: +1-510-777-7001
				E-mail: support@zhone.com"
			DESCRIPTION 
				"MIB module to define a trap, that will be used to forward alarms generated Fault Service."
			REVISION "201304211629Z"		-- April 21, 2013 at 16:29 GMT
			DESCRIPTION 
				"Correct binding order in alarmReceived and alarmCleared"
			REVISION "200904291347Z"		-- April 29, 2009 at 13:47 GMT
			DESCRIPTION 
				"Add bindings to notifications."
			REVISION "200107271655Z"		-- July 27, 2001 at 16:55 GMT
			DESCRIPTION 
				"01.00.00 - Initial version"
			::= { zhoneZmsProduct 1 }

		
	
	
--
-- Node definitions
--
	
		-- 1.3.6.1.4.1.5504.2.7.1.1
		faultServiceDefinitions OBJECT-IDENTITY
			STATUS current
			DESCRIPTION 
				"Variable bindings contained in a Fault Service trap are defined here."
			::= { faultServiceAlarm 1 }

		
		-- 1.3.6.1.4.1.5504.2.7.1.1.1
		alarmName OBJECT-TYPE
			SYNTAX OCTET STRING (SIZE (1..45))
			MAX-ACCESS accessible-for-notify
			STATUS current
			DESCRIPTION
				"Alarm name."
			::= { faultServiceDefinitions 1 }

		
		-- 1.3.6.1.4.1.5504.2.7.1.1.2
		alarmDescription OBJECT-TYPE
			SYNTAX OCTET STRING (SIZE (0..128))
			MAX-ACCESS accessible-for-notify
			STATUS current
			DESCRIPTION
				"Alarm description."
			::= { faultServiceDefinitions 2 }

		
		-- 1.3.6.1.4.1.5504.2.7.1.1.3
		alarmType OBJECT-TYPE
			SYNTAX OCTET STRING (SIZE (0..64))
			MAX-ACCESS accessible-for-notify
			STATUS current
			DESCRIPTION
				"Entity type on which the alarm was generated."
			::= { faultServiceDefinitions 3 }

		
		-- 1.3.6.1.4.1.5504.2.7.1.1.4
		alarmSeverity OBJECT-TYPE
			SYNTAX INTEGER
				{
				critical(1),
				major(2),
				minor(3),
				warning(4),
				informational(5)
				}
			MAX-ACCESS accessible-for-notify
			STATUS current
			DESCRIPTION
				"Severity of alarm."
			::= { faultServiceDefinitions 4 }

		
		-- 1.3.6.1.4.1.5504.2.7.1.1.5
		alarmTimestamp OBJECT-TYPE
			SYNTAX OCTET STRING
			MAX-ACCESS accessible-for-notify
			STATUS current
			DESCRIPTION
				"Date and Time when the alarm was received or cleared."
			::= { faultServiceDefinitions 5 }

		
		-- 1.3.6.1.4.1.5504.2.7.1.1.6
		alarmDevice OBJECT-TYPE
			SYNTAX IpAddress
			MAX-ACCESS accessible-for-notify
			STATUS current
			DESCRIPTION
				"IP address of the device on which alarm was generated."
			::= { faultServiceDefinitions 6 }

		
		-- 1.3.6.1.4.1.5504.2.7.1.1.7
		alarmShelf OBJECT-TYPE
			SYNTAX Integer32 (1..32768)
			MAX-ACCESS accessible-for-notify
			STATUS current
			DESCRIPTION
				"Shelf number on which the alarm was generated."
			::= { faultServiceDefinitions 7 }

		
		-- 1.3.6.1.4.1.5504.2.7.1.1.8
		alarmSlot OBJECT-TYPE
			SYNTAX Integer32 (1..30)
			MAX-ACCESS accessible-for-notify
			STATUS current
			DESCRIPTION
				"Slot number on which the alarm was generated."
			::= { faultServiceDefinitions 8 }

		
		-- 1.3.6.1.4.1.5504.2.7.1.1.9
		alarmPort OBJECT-TYPE
			SYNTAX Integer32
			MAX-ACCESS accessible-for-notify
			STATUS current
			DESCRIPTION
				"Port number on which the alarm was generated."
			::= { faultServiceDefinitions 9 }

		
		-- 1.3.6.1.4.1.5504.2.7.1.1.10
		alarmSubPort OBJECT-TYPE
			SYNTAX Integer32
			MAX-ACCESS accessible-for-notify
			STATUS current
			DESCRIPTION
				"SubPort number on which the alarm was generated."
			::= { faultServiceDefinitions 10 }

		
		-- 1.3.6.1.4.1.5504.2.7.1.1.11
		alarmDeviceName OBJECT-TYPE
			SYNTAX OCTET STRING (SIZE (0..255))
			MAX-ACCESS accessible-for-notify
			STATUS current
			DESCRIPTION
				"Device name on which the alarm was generated."
			::= { faultServiceDefinitions 11 }

		
		-- 1.3.6.1.4.1.5504.2.7.1.1.12
		alarmCpeInternal OBJECT-TYPE
			SYNTAX TruthValue
			MAX-ACCESS accessible-for-notify
			STATUS current
			DESCRIPTION
				"For alarms on CPEs. True if alarm was reported by the CPE
				itself in response to a physical condition on the CPE or
				on one of its ports."
			::= { faultServiceDefinitions 12 }

		
		-- 1.3.6.1.4.1.5504.2.7.1.1.13
		alarmCpePortType OBJECT-TYPE
			SYNTAX Integer32
			MAX-ACCESS accessible-for-notify
			STATUS current
			DESCRIPTION
				"For alarms on CPE ports. This is the type of port for which 
				the alarm is being reported. For OMCI ONTs, the is the ME id."
			::= { faultServiceDefinitions 13 }

		
		-- 1.3.6.1.4.1.5504.2.7.1.1.14
		alarmCpePortId OBJECT-TYPE
			SYNTAX Integer32
			MAX-ACCESS accessible-for-notify
			STATUS current
			DESCRIPTION
				"For alarms on CPE ports. This is the identifier of the
				CPE port for which the alarm is being generated."
			::= { faultServiceDefinitions 14 }

		
		-- 1.3.6.1.4.1.5504.2.7.1.2
		faultServiceTraps OBJECT-IDENTITY
			STATUS current
			DESCRIPTION 
				"Traps that will be generated by Fault Service are defined here."
			::= { faultServiceAlarm 2 }

		
		-- 1.3.6.1.4.1.5504.2.7.1.2.0
		faultServiceV2Traps OBJECT-IDENTITY
			STATUS current
			DESCRIPTION 
				"Definition for specification of v2 traps."
			::= { faultServiceTraps 0 }

		
		-- 1.3.6.1.4.1.5504.2.7.1.2.0.1
		alarmReceived NOTIFICATION-TYPE
			OBJECTS { zhoneTrapVersion, zhoneTrapsSequenceNumber, zhoneTrapsSeverity, alarmName, alarmDescription, 
				alarmType, alarmSeverity, alarmTimestamp, alarmDevice, alarmShelf, 
				alarmSlot, alarmPort, alarmSubPort, alarmDeviceName, alarmCpeInternal, 
				alarmCpePortType, alarmCpePortId }
			STATUS current
			DESCRIPTION 
				"Alarm received definition"
			::= { faultServiceV2Traps 1 }

		
		-- 1.3.6.1.4.1.5504.2.7.1.2.0.2
		alarmCleared NOTIFICATION-TYPE
			OBJECTS { zhoneTrapVersion, zhoneTrapsSequenceNumber, zhoneTrapsSeverity, alarmName, alarmDescription, 
				alarmType, alarmSeverity, alarmTimestamp, alarmDevice, alarmShelf, 
				alarmSlot, alarmPort, alarmSubPort, alarmDeviceName, alarmCpeInternal, 
				alarmCpePortType, alarmCpePortId }
			STATUS current
			DESCRIPTION 
				"Alarm clearing trap."
			::= { faultServiceV2Traps 2 }

		
		-- 1.3.6.1.4.1.5504.2.7.1.3
		faultServiceCompliances OBJECT-IDENTITY
			STATUS current
			DESCRIPTION 
				"Group definition for V2 compliance."
			::= { faultServiceAlarm 3 }

		
		-- 1.3.6.1.4.1.5504.2.7.1.3.1
		faultServiceGroups OBJECT-IDENTITY
			STATUS current
			DESCRIPTION 
				"Group specifications for fault service."
			::= { faultServiceCompliances 1 }

		
		-- 1.3.6.1.4.1.5504.2.7.1.3.1.1
		faultServiceAlarmGroup OBJECT-GROUP
			OBJECTS { alarmName, alarmDescription, alarmType, alarmSeverity, alarmTimestamp, 
				alarmDevice, alarmShelf, alarmSlot, alarmPort, alarmSubPort, 
				alarmDeviceName, alarmCpeInternal, alarmCpePortType, alarmCpePortId }
			STATUS current
			DESCRIPTION 
				"Fault Service Group."
			::= { faultServiceGroups 1 }

		
		-- 1.3.6.1.4.1.5504.2.7.1.3.1.2
		faultServiceTrapGroup NOTIFICATION-GROUP
			NOTIFICATIONS { alarmReceived, alarmCleared }
			STATUS current
			DESCRIPTION 
				"Description."
			::= { faultServiceGroups 2 }

		
		-- 1.3.6.1.4.1.5504.2.7.1.4
		faultServiceImports OBJECT-IDENTITY
			STATUS current
			DESCRIPTION 
				"Objects imported from other mibs to serve as bindings 
				in the ZMS traps"
			::= { faultServiceAlarm 4 }

		
	
	END

--
-- zmsAlarm.mib
--
