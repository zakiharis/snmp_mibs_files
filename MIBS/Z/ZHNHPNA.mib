-- Copyright (C) 2012 by Zhone Technologies.  All Rights Reserved.

-- ======================================================================
-- ==                                                                  ==
-- ==                    ZHNHPNA MIB                                   ==
-- ==                                                                  ==
-- ==  Copyright (C) 2012 Zhone Technologies, Inc.                     ==
-- ==  Confidential, Unpublished Property of Zhone Technologies.       ==
-- ==  Rights Reserved Under the Copyright Laws of the United States.  ==
-- ==                                                                  ==
-- ======================================================================

ZHNHPNA DEFINITIONS ::= BEGIN

IMPORTS
    MODULE-IDENTITY , OBJECT-TYPE , enterprises,
    Integer32, Unsigned32, IpAddress, Gauge32
        FROM SNMPv2-SMI
    MODULE-COMPLIANCE, OBJECT-GROUP
        FROM SNMPv2-CONF
    TEXTUAL-CONVENTION, MacAddress, RowStatus, TruthValue
        FROM SNMPv2-TC
    zhoneWtn
        FROM Zhone;

-- 1.3.6.1.4.1.5504.2.5.47
zhnHpna MODULE-IDENTITY
    LAST-UPDATED  "201204251200Z" -- Apr 25, 2012
    ORGANIZATION
        "Zhone Technologies, Inc."
    CONTACT-INFO 
        "Zhone Technologies, Inc.
         Florida Design Center
         8545 126th Avenue North
         Largo, FL 33773

	 Toll-Free: +1 877-ZHONE20 (+1 877-946-6320)
	 Tel: +1-510-777-7000
	 Fax: +1-510-777-7001
	 E-mail: support@zhone.com"


    DESCRIPTION
        "This file defines the private Enterprise MIB extensions
         that define the HCNA/HPNA interfaces supported by the Zhone 
	 CPEs."


    REVISION "201204251200Z" -- Apr 25, 2012
    DESCRIPTION "Added https to FirewallMgmtAccessServiceValues
                 StationRxPower to Integer32"

    REVISION "201201301200Z"  -- Jan 30, 2012
    DESCRIPTION "First Draft"

::= { zhoneWtn 47 }



-- 1.3.6.1.4.1.5504.2.5.47.1
-- InternetGatewayDevice.X_ZHONE_HPNA.
--
zhnHpnaObjects           OBJECT IDENTIFIER ::= { zhnHpna 1 }



--
-- 1.3.6.1.4.1.5504.2.5.47.1.1
--
hpnaDeviceTable OBJECT-TYPE
  SYNTAX        SEQUENCE OF HPNADeviceEntry
  MAX-ACCESS    not-accessible
  STATUS        current
  DESCRIPTION
    "Table of HPNA Phoneline information for the integral HPNA devices."
  ::= { zhnHpnaObjects 1}

hpnaDeviceEntry OBJECT-TYPE
  SYNTAX        HPNADeviceEntry
  MAX-ACCESS    not-accessible
  STATUS        current
  DESCRIPTION
    "This table includes an entry for each integral HPNA device
     supported by the CPE."
  INDEX        { hpnaDeviceIndex }
  ::= { hpnaDeviceTable 1}

HPNADeviceEntry ::=
  SEQUENCE {
      hpnaDeviceIndex                Unsigned32,
      hpnaDeviceMAC                  MacAddress,
      hpnaDeviceHWVersion            OCTET STRING,
      hpnaDeviceFWVersion            OCTET STRING
  }

hpnaDeviceIndex OBJECT-TYPE
  SYNTAX        Unsigned32
  MAX-ACCESS    not-accessible
  STATUS        current
  DESCRIPTION
    "HPNA Device Table index"
  ::= { hpnaDeviceEntry 1 }

hpnaDeviceMAC OBJECT-TYPE
  SYNTAX        MacAddress
  MAX-ACCESS    read-only
  STATUS        current
  DESCRIPTION
    "The Source MAC address of the integral HPNA device."
  ::= { hpnaDeviceEntry 2 }

hpnaDeviceHWVersion OBJECT-TYPE
  SYNTAX        OCTET STRING
  MAX-ACCESS    read-only
  STATUS        current
  DESCRIPTION
    "Version of the on-board, hardware chipset."
  ::= { hpnaDeviceEntry 3 }

hpnaDeviceFWVersion OBJECT-TYPE
  SYNTAX        OCTET STRING
  MAX-ACCESS    read-only
  STATUS        current
  DESCRIPTION
    "Firmware version of the code running on the HPNA device."
  ::= { hpnaDeviceEntry 4 }


--
-- 1.3.6.1.4.1.5504.2.5.47.1.2
--
hcnaDeviceTable OBJECT-TYPE
  SYNTAX        SEQUENCE OF HCNADeviceEntry
  MAX-ACCESS    not-accessible
  STATUS        current
  DESCRIPTION
    "Table of HPNA Coax information for the integral HCNA devices."
  ::= { zhnHpnaObjects 2 }

hcnaDeviceEntry OBJECT-TYPE
  SYNTAX        HCNADeviceEntry
  MAX-ACCESS    not-accessible
  STATUS        current
  DESCRIPTION
    "This table includes an entry for each integral HCNA device
     supported by the CPE."
  INDEX        { hcnaDeviceIndex }
  ::= { hcnaDeviceTable 1 }

HCNADeviceEntry ::=
  SEQUENCE {
      hcnaDeviceIndex                Unsigned32,
      hcnaDeviceMAC                  MacAddress,
      hcnaDeviceHWVersion            OCTET STRING,
      hcnaDeviceFWVersion            OCTET STRING
  }

hcnaDeviceIndex OBJECT-TYPE
  SYNTAX        Unsigned32
  MAX-ACCESS    not-accessible
  STATUS        current
  DESCRIPTION
    "HCNA Device Table index"
  ::= { hcnaDeviceEntry 1 }

hcnaDeviceMAC OBJECT-TYPE
  SYNTAX        MacAddress
  MAX-ACCESS    read-only
  STATUS        current
  DESCRIPTION
    "The Source MAC address of the integral HCNA device."
  ::= { hcnaDeviceEntry 2 }

hcnaDeviceHWVersion OBJECT-TYPE
  SYNTAX        OCTET STRING
  MAX-ACCESS    read-only
  STATUS        current
  DESCRIPTION
    "Version of the on-board, hardware chipset."
  ::= { hcnaDeviceEntry 3 }

hcnaDeviceFWVersion OBJECT-TYPE
  SYNTAX        OCTET STRING
  MAX-ACCESS    read-only
  STATUS        current
  DESCRIPTION
    "Firmware version of the code running on the HCNA device."
  ::= { hcnaDeviceEntry 4 }


--
-- 1.3.6.1.4.1.5504.2.5.47.1.3
--
hpnaStationsTable OBJECT-TYPE
  SYNTAX        SEQUENCE OF HPNAStationsEntry
  MAX-ACCESS    not-accessible
  STATUS        current
  DESCRIPTION
    "Table of HPNA station information."
  ::= { zhnHpnaObjects 3 }

hpnaStationsEntry OBJECT-TYPE
  SYNTAX        HPNAStationsEntry
  MAX-ACCESS    not-accessible
  STATUS        current
  DESCRIPTION
    "Each HPNA interface maintains a list of known HPNA
     devices on the network. This table includes an entry for
     each HPNA device detected."
  INDEX        { hpnaStationIndex }
  ::= { hpnaStationsTable 1 }

HPNAStationsEntry ::=
  SEQUENCE {
      hpnaStationIndex                      Unsigned32,
      hpnaStationSource                     MacAddress,
      hpnaStationDestination                MacAddress,
      hpnaStationRate                       Unsigned32,
      hpnaStationSymbolRate                 Unsigned32,
      hpnaStationBitsPerSymbol              Unsigned32,
      hpnaStationRxPower                    Integer32
  }

hpnaStationIndex OBJECT-TYPE
  SYNTAX        Unsigned32
  MAX-ACCESS    not-accessible
  STATUS        current
  DESCRIPTION
    "HPNA Stations Table index"
  ::= { hpnaStationsEntry 1 }

hpnaStationSource OBJECT-TYPE
  SYNTAX        MacAddress
  MAX-ACCESS    read-only
  STATUS        current
  DESCRIPTION
    "The MAC address of the source HPNA station."
  ::= { hpnaStationsEntry 2 }

hpnaStationDestination OBJECT-TYPE
  SYNTAX        MacAddress
  MAX-ACCESS    read-only
  STATUS        current
  DESCRIPTION
    "The MAC address of the destination HPNA station."
  ::= { hpnaStationsEntry 3 }

hpnaStationRate  OBJECT-TYPE
  SYNTAX        Unsigned32
  MAX-ACCESS    read-only
  STATUS        current
  DESCRIPTION
    "HPNA transmission rate, in Mbps."
  ::= { hpnaStationsEntry 4 }

hpnaStationSymbolRate OBJECT-TYPE
  SYNTAX        Unsigned32
  MAX-ACCESS    read-only
  STATUS        current
  DESCRIPTION
    "HPNA symbol rate, in Mhz."
  ::= { hpnaStationsEntry 5 }

hpnaStationBitsPerSymbol OBJECT-TYPE
  SYNTAX        Unsigned32
  MAX-ACCESS    read-only
  STATUS        current
  DESCRIPTION
    "HPNA rate divided by the symbol rate, in Mhz."
  ::= { hpnaStationsEntry 6 }

hpnaStationRxPower OBJECT-TYPE
  SYNTAX        Integer32
  MAX-ACCESS    read-only
  STATUS        current
  DESCRIPTION
    "HPNA receive power, in dBm."
  ::= { hpnaStationsEntry 7 }


--
-- 1.3.6.1.4.1.5504.2.5.47.1.4
--
hcnaStationsTable OBJECT-TYPE
  SYNTAX        SEQUENCE OF HCNAStationsEntry
  MAX-ACCESS    not-accessible
  STATUS        current
  DESCRIPTION
    "Table of HPNA Coax (HCNA) station information."
  ::= { zhnHpnaObjects 4 }

hcnaStationsEntry OBJECT-TYPE
  SYNTAX        HCNAStationsEntry
  MAX-ACCESS    not-accessible
  STATUS        current
  DESCRIPTION
    "Each HCNA interface maintains a list of known HPNA Coax
     devices on the network. This table includes an entry for
     each HCNA device detected."
  INDEX        { hcnaStationIndex }
  ::= { hcnaStationsTable 1 }

HCNAStationsEntry ::=
  SEQUENCE {
      hcnaStationIndex               Unsigned32,
      hcnaStationSource              MacAddress,
      hcnaStationDestination         MacAddress,
      hcnaStationRate                Unsigned32,
      hcnaStationSymbolRate          Unsigned32,
      hcnaStationBitsPerSymbol       Unsigned32,
      hcnaStationRxPower             Integer32
  }

hcnaStationIndex OBJECT-TYPE
  SYNTAX        Unsigned32
  MAX-ACCESS    not-accessible
  STATUS        current
  DESCRIPTION
    "HCNA Stations Table index"
  ::= { hcnaStationsEntry 1 }

hcnaStationSource OBJECT-TYPE
  SYNTAX        MacAddress
  MAX-ACCESS    read-only
  STATUS        current
  DESCRIPTION
    "The MAC address of the source HCNA station."
  ::= { hcnaStationsEntry 2 }

hcnaStationDestination OBJECT-TYPE
  SYNTAX        MacAddress
  MAX-ACCESS    read-only
  STATUS        current
  DESCRIPTION
    "The MAC address of the destination HCNA station."
  ::= { hcnaStationsEntry 3 }

hcnaStationRate  OBJECT-TYPE
  SYNTAX        Unsigned32
  MAX-ACCESS    read-only
  STATUS        current
  DESCRIPTION
    "HCNA transmission rate, in Mbps."
  ::= { hcnaStationsEntry 4 }

hcnaStationSymbolRate OBJECT-TYPE
  SYNTAX        Unsigned32
  MAX-ACCESS    read-only
  STATUS        current
  DESCRIPTION
    "HCNA symbol rate, in Mhz."
  ::= { hcnaStationsEntry 5 }

hcnaStationBitsPerSymbol OBJECT-TYPE
  SYNTAX        Unsigned32
  MAX-ACCESS    read-only
  STATUS        current
  DESCRIPTION
    "HCNA rate divided by the symbol rate, in Mhz."
  ::= { hcnaStationsEntry 6 }

hcnaStationRxPower OBJECT-TYPE
  SYNTAX        Integer32
  MAX-ACCESS    read-only
  STATUS        current
  DESCRIPTION
    "HCNA receive power, in dBm."
  ::= { hcnaStationsEntry 7 }


-- ****************************************************************************
--
-- Conformance Information
--

zhnHpnaConformance OBJECT IDENTIFIER ::= { zhnHpna 2 }

zhnHpnaGroups OBJECT IDENTIFIER ::= { zhnHpnaConformance 1 }
zhnHpnaCompliances OBJECT IDENTIFIER ::= { zhnHpnaConformance 2 }
 
--
-- Compliance Statements
--

zhnHpnaCompliance  MODULE-COMPLIANCE
  STATUS        current
  DESCRIPTION
        "The Compliance statement for SNMP entities which
         manage the Zhone CPE HPNA/HCNA Station Information"
  MODULE  -- this module
  MANDATORY-GROUPS {
      zhnHpnaDeviceGroup,
      zhnHcnaDeviceGroup
  }
  ::= {zhnHpnaCompliances 1 }


--
-- Units of Conformance
--

zhnHpnaDeviceGroup OBJECT-GROUP
   OBJECTS {
      hpnaDeviceMAC,
      hpnaDeviceHWVersion,
      hpnaDeviceFWVersion
   }
   STATUS current
   DESCRIPTION
      "A collection of Zhone IP objects that describe the 
       HPNA station information. This group is only supported
       by CPEs that have one or more HPNA Phone lines."
   ::= { zhnHpnaGroups 1 }

zhnHcnaDeviceGroup OBJECT-GROUP
   OBJECTS {
      hcnaDeviceMAC,
      hcnaDeviceHWVersion,
      hcnaDeviceFWVersion
   }
   STATUS current
   DESCRIPTION
      "A collection of Zhone IP objects that describe the 
       HPNA station information. This group is only supported
       by CPEs that have one or more HPNA Coax line."
   ::= { zhnHpnaGroups 2 }

zhnHpnaStationsGroup OBJECT-GROUP
   OBJECTS {
      hpnaStationSource,
      hpnaStationDestination,
      hpnaStationRate,
      hpnaStationSymbolRate,
      hpnaStationBitsPerSymbol,
      hpnaStationRxPower
   }
   STATUS current
   DESCRIPTION
      "A collection of Zhone IP objects that describe the 
       HPNA station information. This group is only supported
       by CPEs that have one or more HPNA Phone line."
   ::= { zhnHpnaGroups 3 }

zhnHcnaStationsGroup OBJECT-GROUP
   OBJECTS {
      hcnaStationSource,
      hcnaStationDestination,
      hcnaStationRate,
      hcnaStationSymbolRate,
      hcnaStationBitsPerSymbol,
      hcnaStationRxPower
   }
   STATUS current
   DESCRIPTION
      "A collection of Zhone IP objects that describe the 
       HCNA station information. This group is only supported
       by CPEs that have one or more HPNA Coax line."
   ::= { zhnHpnaGroups 4 }


END
