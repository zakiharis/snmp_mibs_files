--
-- zhoneSFF.mib
-- MIB generated by MG-SOFT Visual MIB Builder Version 3.0 Build 285
-- Monday, April 07, 2014 at 17:39:00
--

	ZHONE-SFF DEFINITIONS ::= BEGIN
 
		IMPORTS
			ifIndex			
				FROM IF-MIB			
			Integer32, Unsigned32, OBJECT-TYPE, MODULE-IDENTITY, OBJECT-IDENTITY			
				FROM SNMPv2-SMI			
			TruthValue			
				FROM SNMPv2-TC			
			zhoneSFF, zhoneModules			
				FROM Zhone			
			ZhoneAdminString			
				FROM Zhone-TC;
	
	
-- 
-- 
-- 
-- 
-- pahrser command:
--  /vob/zhonetools/bin/pahrser.pl Zhone.mib Zhone-TC.mib zhoneSFF.mib
-- 
-- mibcomp command:
-- /vob/EPILOGUE/binaries/emissary/solaris/mibcomp rfc1213.mib rfc1907.mib iftype.mib Zhone.mib Zhone-TC.mib rfc2233.mib rfc2571.mib -stub -o sffHdlrs.c zhoneSFF.mib
		-- 1.3.6.1.4.1.5504.6.114
		zhoneSFFModule MODULE-IDENTITY 
			LAST-UPDATED "201404071205Z"		-- April 07, 2014 at 12:05 GMT
			ORGANIZATION 
				"Zhone Technologies, Inc."
			CONTACT-INFO 
				"Contact-info."
			DESCRIPTION 
				"Zhone MIB support for SFF module (SFP, SFF and XFP)."
			REVISION "201404071213Z"		-- April 07, 2014 at 12:13 GMT
			DESCRIPTION 
				"Add DDM status"
			REVISION "200904271652Z"		-- April 27, 2009 at 16:52 GMT
			DESCRIPTION 
				"Add some values for XFP"
			REVISION "200805211247Z"		-- May 21, 2008 at 12:47 GMT
			DESCRIPTION 
				"allow zero values for enum fields."
			REVISION "200802131049Z"		-- February 13, 2008 at 10:49 GMT
			DESCRIPTION 
				"Add/modify some fields."
			REVISION "200711071907Z"		-- November 07, 2007 at 19:07 GMT
			DESCRIPTION 
				"Version 1.0.0 - initial creation of
				Zhone SFF MIB."
			::= { zhoneModules 114 }

		
	
	
--
-- Node definitions
--
	
		-- 1.3.6.1.4.1.5504.3.12.1
		zhoneSFFObjects OBJECT-IDENTITY
			STATUS current
			DESCRIPTION 
				"Zhone small form factor devices"
			::= { zhoneSFF 1 }

		
		-- 1.3.6.1.4.1.5504.3.12.1.1
		zhoneSFPTable OBJECT-TYPE
			SYNTAX SEQUENCE OF ZhoneSFPEntry
			MAX-ACCESS not-accessible
			STATUS current
			DESCRIPTION
				"Small form pluggable table"
			::= { zhoneSFFObjects 1 }

		
		-- 1.3.6.1.4.1.5504.3.12.1.1.1
		zhoneSFPEntry OBJECT-TYPE
			SYNTAX ZhoneSFPEntry
			MAX-ACCESS not-accessible
			STATUS current
			DESCRIPTION
				"Row in SFP table."
			INDEX { ifIndex }
			::= { zhoneSFPTable 1 }

		
		ZhoneSFPEntry ::=
			SEQUENCE { 
				zhoneSFPVendorName
					ZhoneAdminString,
				zhoneSFPVendorOUI
					ZhoneAdminString,
				zhoneSFPVendorPartNumber
					ZhoneAdminString,
				zhoneSFPVendorRevisionLevel
					ZhoneAdminString,
				zhoneSFPSerialNumber
					ZhoneAdminString,
				zhoneSFPManufacturingDateCode
					ZhoneAdminString,
				zhoneSFPGigeComplianceCode
					BITS,
				zhoneSFPConnectorType
					INTEGER,
				zhoneSFPIdTransceiverType
					INTEGER,
				zhoneSFPExtendedIdentifier
					Unsigned32,
				zhoneSFPSerialEncodingAlgorithm
					INTEGER,
				zhoneSFPFiberChannelLinkLength
					BITS,
				zhoneSFPFiberChannelTransmitterTechnology
					BITS,
				zhoneSFPFiberChannelTransmissionMedia
					BITS,
				zhoneSFPFiberChannelSpeed
					BITS,
				zhoneSFP9To125mmFiberLinkLengthKm
					Unsigned32,
				zhoneSFP9To125mmFiberLinkLength100m
					Unsigned32,
				zhoneSFP50To125mmFiberLinkLength10m
					Unsigned32,
				zhoneSFP62Dot5To125FiberLinkLength10m
					Unsigned32,
				zhoneSFPNominalBitRate
					Unsigned32,
				zhoneSFPUpperBitRateMarginPercentage
					Unsigned32,
				zhoneSFPLowerBitRatePercentage
					Unsigned32,
				zhoneSFPCopperLinkLength
					Unsigned32,
				zhoneSFPIsPresent
					TruthValue
			 }

		-- 1.3.6.1.4.1.5504.3.12.1.1.1.1
		zhoneSFPVendorName OBJECT-TYPE
			SYNTAX ZhoneAdminString
			MAX-ACCESS read-only
			STATUS current
			DESCRIPTION
				"SFP transceiver vendor name (ASCII)"
			::= { zhoneSFPEntry 1 }

		
		-- 1.3.6.1.4.1.5504.3.12.1.1.1.2
		zhoneSFPVendorOUI OBJECT-TYPE
			SYNTAX ZhoneAdminString
			MAX-ACCESS read-only
			STATUS current
			DESCRIPTION
				"SFP transceiver vendor IEEE company ID"
			::= { zhoneSFPEntry 2 }

		
		-- 1.3.6.1.4.1.5504.3.12.1.1.1.3
		zhoneSFPVendorPartNumber OBJECT-TYPE
			SYNTAX ZhoneAdminString
			MAX-ACCESS read-only
			STATUS current
			DESCRIPTION
				"Part number provided by SFP transceiver vendor (ASCII)"
			::= { zhoneSFPEntry 3 }

		
		-- 1.3.6.1.4.1.5504.3.12.1.1.1.4
		zhoneSFPVendorRevisionLevel OBJECT-TYPE
			SYNTAX ZhoneAdminString
			MAX-ACCESS read-only
			STATUS current
			DESCRIPTION
				"Revision level for part number provided by vendor (ASCII)"
			::= { zhoneSFPEntry 4 }

		
		-- 1.3.6.1.4.1.5504.3.12.1.1.1.5
		zhoneSFPSerialNumber OBJECT-TYPE
			SYNTAX ZhoneAdminString
			MAX-ACCESS read-only
			STATUS current
			DESCRIPTION
				"Serial number provided by vendor (ASCII)"
			::= { zhoneSFPEntry 5 }

		
		-- 1.3.6.1.4.1.5504.3.12.1.1.1.6
		zhoneSFPManufacturingDateCode OBJECT-TYPE
			SYNTAX ZhoneAdminString
			MAX-ACCESS read-only
			STATUS current
			DESCRIPTION
				"YYMMDD ASCII"
			::= { zhoneSFPEntry 6 }

		
		-- 1.3.6.1.4.1.5504.3.12.1.1.1.7
		zhoneSFPGigeComplianceCode OBJECT-TYPE
			SYNTAX BITS
				{
				base-1000-SX(0),
				base-1000-LX(1),
				base-1000-CX(2),
				base-1000-T(3),
				base-100-LX(4),
				base-100-FX(5),
				base-100-BX(6),
				base-PX(7)
				}
			MAX-ACCESS read-only
			STATUS current
			DESCRIPTION
				"gigabit ethernet compliance codes"
			::= { zhoneSFPEntry 7 }

		
		-- 1.3.6.1.4.1.5504.3.12.1.1.1.8
		zhoneSFPConnectorType OBJECT-TYPE
			SYNTAX INTEGER
				{
				unknownOrUnspecified(0),
				sc(1),
				fibreStyle1Copper(2),
				fibreStyle2Copper(3),
				bnc-tnc(4),
				fibreCoaxialHeaders(5),
				fiberJack(6),
				lc(7),
				mt-rj(8),
				mu(9),
				sg(10),
				opticalPigtail(11),
				hssdc-II(32),
				copperPigtail(33)
				}
			MAX-ACCESS read-only
			STATUS current
			DESCRIPTION
				"code for connector type."
			::= { zhoneSFPEntry 8 }

		
		-- 1.3.6.1.4.1.5504.3.12.1.1.1.9
		zhoneSFPIdTransceiverType OBJECT-TYPE
			SYNTAX INTEGER
				{
				unknownOrUnspecified(0),
				gbic(1),
				connector(2),
				sfp(3)
				}
			MAX-ACCESS read-only
			STATUS current
			DESCRIPTION
				"Code for electronic compatibility or optical compatibility."
			::= { zhoneSFPEntry 9 }

		
		-- 1.3.6.1.4.1.5504.3.12.1.1.1.10
		zhoneSFPExtendedIdentifier OBJECT-TYPE
			SYNTAX Unsigned32
			MAX-ACCESS read-only
			STATUS current
			DESCRIPTION
				"Extended ID fields"
			::= { zhoneSFPEntry 10 }

		
		-- 1.3.6.1.4.1.5504.3.12.1.1.1.11
		zhoneSFPSerialEncodingAlgorithm OBJECT-TYPE
			SYNTAX INTEGER
				{
				unspecified(0),
				eightB10B(1),
				fourB5B(2),
				nrz(3),
				manchester(4)
				}
			MAX-ACCESS read-only
			STATUS current
			DESCRIPTION
				"Code for serial encoding algorithm"
			::= { zhoneSFPEntry 11 }

		
		-- 1.3.6.1.4.1.5504.3.12.1.1.1.12
		zhoneSFPFiberChannelLinkLength OBJECT-TYPE
			SYNTAX BITS
				{
				unused0(0),
				unused1(1),
				unused2(2),
				unused3(3),
				longDistance(4),
				intermediateDistance(5),
				shortDistance(6),
				veryLongDistance(7)
				}
			MAX-ACCESS read-only
			STATUS current
			DESCRIPTION
				"Code for fiber channel link length."
			::= { zhoneSFPEntry 12 }

		
		-- 1.3.6.1.4.1.5504.3.12.1.1.1.13
		zhoneSFPFiberChannelTransmitterTechnology OBJECT-TYPE
			SYNTAX BITS
				{
				unused0(0),
				unused1(1),
				unused2(2),
				unused3(3),
				longwaveLaserLL(4),
				shortwaveLaserWithOFC(5),
				shortwaveLaserWithoutOFC(6),
				electrical-Intra-Enclosure(7),
				electrical-Inter-Enclosure(8),
				longwabeLaserLC(9)
				}
			MAX-ACCESS read-only
			STATUS current
			DESCRIPTION
				"Fiber channel transmitter technology"
			::= { zhoneSFPEntry 13 }

		
		-- 1.3.6.1.4.1.5504.3.12.1.1.1.14
		zhoneSFPFiberChannelTransmissionMedia OBJECT-TYPE
			SYNTAX BITS
				{
				singleMode(0),
				unused1(1),
				multiMode-50m(2),
				multiMode-62dot5m(3),
				videoCoax(4),
				miniatureCoax(5),
				shieldedTwistedPair(6),
				twinAxialPair(7)
				}
			MAX-ACCESS read-only
			STATUS current
			DESCRIPTION
				"Fiber channel transmission media"
			::= { zhoneSFPEntry 14 }

		
		-- 1.3.6.1.4.1.5504.3.12.1.1.1.15
		zhoneSFPFiberChannelSpeed OBJECT-TYPE
			SYNTAX BITS
				{
				oneHundredMbytesperSec(0),
				unused1(1),
				twoHundredMbytesperSec(2),
				fourHundredMbytesperSec(3)
				}
			MAX-ACCESS read-only
			STATUS current
			DESCRIPTION
				"Fiber channel speed"
			::= { zhoneSFPEntry 15 }

		
		-- 1.3.6.1.4.1.5504.3.12.1.1.1.16
		zhoneSFP9To125mmFiberLinkLengthKm OBJECT-TYPE
			SYNTAX Unsigned32
			UNITS "Km"
			MAX-ACCESS read-only
			STATUS current
			DESCRIPTION
				"Link length supported for 9/125 mm fiber, units of km"
			::= { zhoneSFPEntry 16 }

		
		-- 1.3.6.1.4.1.5504.3.12.1.1.1.17
		zhoneSFP9To125mmFiberLinkLength100m OBJECT-TYPE
			SYNTAX Unsigned32
			UNITS "100m"
			MAX-ACCESS read-only
			STATUS current
			DESCRIPTION
				"Link length supported for 9/125 mm fiber, units of 100 m"
			::= { zhoneSFPEntry 17 }

		
		-- 1.3.6.1.4.1.5504.3.12.1.1.1.18
		zhoneSFP50To125mmFiberLinkLength10m OBJECT-TYPE
			SYNTAX Unsigned32
			UNITS "10m"
			MAX-ACCESS read-only
			STATUS current
			DESCRIPTION
				"Link length supported for 50/125 mm fiber, units of 10 m"
			::= { zhoneSFPEntry 18 }

		
		-- 1.3.6.1.4.1.5504.3.12.1.1.1.19
		zhoneSFP62Dot5To125FiberLinkLength10m OBJECT-TYPE
			SYNTAX Unsigned32
			UNITS "10m"
			MAX-ACCESS read-only
			STATUS current
			DESCRIPTION
				"Link length supported for 62.5/125 mm fiber, units of 10 m"
			::= { zhoneSFPEntry 19 }

		
		-- 1.3.6.1.4.1.5504.3.12.1.1.1.20
		zhoneSFPNominalBitRate OBJECT-TYPE
			SYNTAX Unsigned32
			UNITS "100 Mbits/sec"
			MAX-ACCESS read-only
			STATUS current
			DESCRIPTION
				"Nominal bit rate, units of 100 MBits/sec"
			::= { zhoneSFPEntry 20 }

		
		-- 1.3.6.1.4.1.5504.3.12.1.1.1.21
		zhoneSFPUpperBitRateMarginPercentage OBJECT-TYPE
			SYNTAX Unsigned32
			UNITS "Percentage"
			MAX-ACCESS read-only
			STATUS current
			DESCRIPTION
				"Upper bit rate margin, units of %"
			::= { zhoneSFPEntry 21 }

		
		-- 1.3.6.1.4.1.5504.3.12.1.1.1.22
		zhoneSFPLowerBitRatePercentage OBJECT-TYPE
			SYNTAX Unsigned32
			UNITS "Percentage"
			MAX-ACCESS read-only
			STATUS current
			DESCRIPTION
				"Lower bit rate margin, units of %"
			::= { zhoneSFPEntry 22 }

		
		-- 1.3.6.1.4.1.5504.3.12.1.1.1.23
		zhoneSFPCopperLinkLength OBJECT-TYPE
			SYNTAX Unsigned32
			MAX-ACCESS read-only
			STATUS current
			DESCRIPTION
				"Link length supported for copper, units of meters"
			::= { zhoneSFPEntry 23 }

		
		-- 1.3.6.1.4.1.5504.3.12.1.1.1.24
		zhoneSFPIsPresent OBJECT-TYPE
			SYNTAX TruthValue
			MAX-ACCESS read-only
			STATUS current
			DESCRIPTION
				"TRUE if SFP transceiver is present, otherwise other values in this 
				entry are not meaningful."
			::= { zhoneSFPEntry 24 }

		
		-- 1.3.6.1.4.1.5504.3.12.1.2
		zhoneXFPTable OBJECT-TYPE
			SYNTAX SEQUENCE OF ZhoneXFPEntry
			MAX-ACCESS not-accessible
			STATUS current
			DESCRIPTION
				"10 Gigabit small form factor pluggable table."
			::= { zhoneSFFObjects 2 }

		
		-- 1.3.6.1.4.1.5504.3.12.1.2.1
		zhoneXFPEntry OBJECT-TYPE
			SYNTAX ZhoneXFPEntry
			MAX-ACCESS not-accessible
			STATUS current
			DESCRIPTION
				"Row in zhoneXFP table."
			INDEX { ifIndex }
			::= { zhoneXFPTable 1 }

		
		ZhoneXFPEntry ::=
			SEQUENCE { 
				zhoneXFPVendorName
					ZhoneAdminString,
				zhoneXFPVendorOUI
					ZhoneAdminString,
				zhoneXFPManufacturingDateCode
					ZhoneAdminString,
				zhoneXFPComplianceCode10GbEthernet
					BITS,
				zhoneXFPComplianceCode10GbFiber
					BITS,
				zhoneXFPLowerSpeed
					BITS,
				zhoneXFPConnectorType
					INTEGER,
				zhoneXFPIdTransceiverType
					INTEGER,
				zhoneXFPExtendedIdentifier
					Unsigned32,
				zhoneXFPEncodingSupport
					BITS,
				zhoneXFPDeviceTechnology
					Unsigned32,
				zhoneXFPSMFiberLinkLength1Km
					Unsigned32,
				zhoneXFPMMExtendedFiberLinkLength
					Unsigned32,
				zhoneXFPMM50umFiberLinkLength1m
					Unsigned32,
				zhoneXFPMM62Dot5umFiberLinkLength1m
					Unsigned32,
				zhoneXFPMinimumBitRate
					Unsigned32,
				zhoneXFPMaximumBitRate
					Unsigned32,
				zhoneXFPEnhancedOptions
					BITS,
				zhoneXFPVendorPartNumber
					ZhoneAdminString,
				zhoneXFPVendorRevisionLevel
					ZhoneAdminString,
				zhoneXFPSerialNumber
					ZhoneAdminString,
				zhoneXFPIsPresent
					TruthValue
			 }

		-- 1.3.6.1.4.1.5504.3.12.1.2.1.1
		zhoneXFPVendorName OBJECT-TYPE
			SYNTAX ZhoneAdminString
			MAX-ACCESS read-only
			STATUS current
			DESCRIPTION
				"SFP transceiver vendor name (ASCII)"
			::= { zhoneXFPEntry 1 }

		
		-- 1.3.6.1.4.1.5504.3.12.1.2.1.2
		zhoneXFPVendorOUI OBJECT-TYPE
			SYNTAX ZhoneAdminString
			MAX-ACCESS read-only
			STATUS current
			DESCRIPTION
				"SFP transceiver vendor IEEE company ID"
			::= { zhoneXFPEntry 2 }

		
		-- 1.3.6.1.4.1.5504.3.12.1.2.1.3
		zhoneXFPManufacturingDateCode OBJECT-TYPE
			SYNTAX ZhoneAdminString
			MAX-ACCESS read-only
			STATUS current
			DESCRIPTION
				"YYMMDD ASCII"
			::= { zhoneXFPEntry 3 }

		
		-- 1.3.6.1.4.1.5504.3.12.1.2.1.4
		zhoneXFPComplianceCode10GbEthernet OBJECT-TYPE
			SYNTAX BITS
				{
				unused(0),
				ew(1),
				lw(2),
				sw(3),
				lrm(4),
				er(5),
				lr(6),
				sr(7)
				}
			UNITS "10Gb"
			MAX-ACCESS read-only
			STATUS current
			DESCRIPTION
				"Compliance code for 10 gigabit ethernet"
			::= { zhoneXFPEntry 4 }

		
		-- 1.3.6.1.4.1.5504.3.12.1.2.1.5
		zhoneXFPComplianceCode10GbFiber OBJECT-TYPE
			SYNTAX BITS
				{
				unused0(0),
				unused1(1),
				unused2(2),
				unused3(3),
				intReach100nmFp(4),
				extReach1550nm(5),
				sM-LL-L-1200(6),
				mX-SN-I-1200(7)
				}
			UNITS "10Gb"
			MAX-ACCESS read-only
			STATUS current
			DESCRIPTION
				"Compliance code for 10 gigabit fiber"
			::= { zhoneXFPEntry 5 }

		
		-- 1.3.6.1.4.1.5504.3.12.1.2.1.6
		zhoneXFPLowerSpeed OBJECT-TYPE
			SYNTAX BITS
				{
				unused0(0),
				oC-48-LR(1),
				oC-48-IR(2),
				oC-48-SR(3),
				sMF-2xFC(4),
				sMFM-2xFC(5),
				base100Lx-1xFcSmf(6),
				base100Sx-1xFcMmf(7)
				}
			MAX-ACCESS read-only
			STATUS current
			DESCRIPTION
				"Description."
			::= { zhoneXFPEntry 6 }

		
		-- 1.3.6.1.4.1.5504.3.12.1.2.1.7
		zhoneXFPConnectorType OBJECT-TYPE
			SYNTAX INTEGER
				{
				unknownOrUnspecified(0),
				sc(1),
				fibreStyle1Copper(2),
				fibreStyle2Copper(3),
				bnc-tnc(4),
				fibreCoaxialHeaders(5),
				fiberJack(6),
				lc(7),
				mt-rj(8),
				mu(9),
				sg(10),
				opticalPigtail(11),
				hssdc-ii(32),
				copperPigtail(33)
				}
			MAX-ACCESS read-only
			STATUS current
			DESCRIPTION
				"Description."
			::= { zhoneXFPEntry 7 }

		
		-- 1.3.6.1.4.1.5504.3.12.1.2.1.8
		zhoneXFPIdTransceiverType OBJECT-TYPE
			SYNTAX INTEGER
				{
				unknownOrUnspecified(0),
				gbic(1),
				connector(2),
				sfp(3),
				xpi300Pin(4),
				xenpak(5),
				xfp(6),
				xff(7),
				xfpE(8),
				xpak(9),
				x2(10)
				}
			MAX-ACCESS read-only
			STATUS current
			DESCRIPTION
				"Description."
			::= { zhoneXFPEntry 8 }

		
		-- 1.3.6.1.4.1.5504.3.12.1.2.1.9
		zhoneXFPExtendedIdentifier OBJECT-TYPE
			SYNTAX Unsigned32
			MAX-ACCESS read-only
			STATUS current
			DESCRIPTION
				"Description."
			::= { zhoneXFPEntry 9 }

		
		-- 1.3.6.1.4.1.5504.3.12.1.2.1.10
		zhoneXFPEncodingSupport OBJECT-TYPE
			SYNTAX BITS
				{
				unused0(0),
				unused1(1),
				unused2(2),
				rz(3),
				nrz(4),
				sonetScrambled(5),
				eightB10B(6),
				sixtyFourBper66B(7)
				}
			MAX-ACCESS read-only
			STATUS current
			DESCRIPTION
				"Description."
			::= { zhoneXFPEntry 10 }

		
		-- 1.3.6.1.4.1.5504.3.12.1.2.1.11
		zhoneXFPDeviceTechnology OBJECT-TYPE
			SYNTAX Unsigned32
			MAX-ACCESS read-only
			STATUS current
			DESCRIPTION
				"Description."
			::= { zhoneXFPEntry 11 }

		
		-- 1.3.6.1.4.1.5504.3.12.1.2.1.12
		zhoneXFPSMFiberLinkLength1Km OBJECT-TYPE
			SYNTAX Unsigned32
			UNITS "Km"
			MAX-ACCESS read-only
			STATUS current
			DESCRIPTION
				"Description."
			::= { zhoneXFPEntry 12 }

		
		-- 1.3.6.1.4.1.5504.3.12.1.2.1.13
		zhoneXFPMMExtendedFiberLinkLength OBJECT-TYPE
			SYNTAX Unsigned32
			UNITS "2m"
			MAX-ACCESS read-only
			STATUS current
			DESCRIPTION
				"Description."
			::= { zhoneXFPEntry 13 }

		
		-- 1.3.6.1.4.1.5504.3.12.1.2.1.14
		zhoneXFPMM50umFiberLinkLength1m OBJECT-TYPE
			SYNTAX Unsigned32
			UNITS "1m"
			MAX-ACCESS read-only
			STATUS current
			DESCRIPTION
				"Description."
			::= { zhoneXFPEntry 14 }

		
		-- 1.3.6.1.4.1.5504.3.12.1.2.1.15
		zhoneXFPMM62Dot5umFiberLinkLength1m OBJECT-TYPE
			SYNTAX Unsigned32
			UNITS "1m"
			MAX-ACCESS read-only
			STATUS current
			DESCRIPTION
				"Description."
			::= { zhoneXFPEntry 15 }

		
		-- 1.3.6.1.4.1.5504.3.12.1.2.1.16
		zhoneXFPMinimumBitRate OBJECT-TYPE
			SYNTAX Unsigned32
			UNITS "100Mbits/sec"
			MAX-ACCESS read-only
			STATUS current
			DESCRIPTION
				"Description."
			::= { zhoneXFPEntry 16 }

		
		-- 1.3.6.1.4.1.5504.3.12.1.2.1.17
		zhoneXFPMaximumBitRate OBJECT-TYPE
			SYNTAX Unsigned32
			UNITS "100Mbits/sec"
			MAX-ACCESS read-only
			STATUS current
			DESCRIPTION
				"Description."
			::= { zhoneXFPEntry 17 }

		
		-- 1.3.6.1.4.1.5504.3.12.1.2.1.18
		zhoneXFPEnhancedOptions OBJECT-TYPE
			SYNTAX BITS
				{
				cMU-Support(0),
				wavelengthTurnability(1),
				activeFEC-Control(2),
				vPS-BypassedRegulator(3),
				vPS-LVRegulator(4),
				soft-P-Down(5),
				soft-Tx-Disable(6),
				vps(7)
				}
			MAX-ACCESS read-only
			STATUS current
			DESCRIPTION
				"Description."
			::= { zhoneXFPEntry 18 }

		
		-- 1.3.6.1.4.1.5504.3.12.1.2.1.19
		zhoneXFPVendorPartNumber OBJECT-TYPE
			SYNTAX ZhoneAdminString
			MAX-ACCESS read-only
			STATUS current
			DESCRIPTION
				"Description."
			::= { zhoneXFPEntry 19 }

		
		-- 1.3.6.1.4.1.5504.3.12.1.2.1.20
		zhoneXFPVendorRevisionLevel OBJECT-TYPE
			SYNTAX ZhoneAdminString
			MAX-ACCESS read-only
			STATUS current
			DESCRIPTION
				"Description."
			::= { zhoneXFPEntry 20 }

		
		-- 1.3.6.1.4.1.5504.3.12.1.2.1.21
		zhoneXFPSerialNumber OBJECT-TYPE
			SYNTAX ZhoneAdminString
			MAX-ACCESS read-only
			STATUS current
			DESCRIPTION
				"Description."
			::= { zhoneXFPEntry 21 }

		
		-- 1.3.6.1.4.1.5504.3.12.1.2.1.22
		zhoneXFPIsPresent OBJECT-TYPE
			SYNTAX TruthValue
			MAX-ACCESS read-only
			STATUS current
			DESCRIPTION
				"TRUE if XFP transceiver is present. Otherwise, the values in this row
				are not meaningful."
			::= { zhoneXFPEntry 22 }

		
		-- 1.3.6.1.4.1.5504.3.12.1.3
		zhoneDDMStatusTable OBJECT-TYPE
			SYNTAX SEQUENCE OF ZhoneDDMStatusEntry
			MAX-ACCESS not-accessible
			STATUS current
			DESCRIPTION
				"Digital diagnostic monitoring status from the SFPs."
			::= { zhoneSFFObjects 3 }

		
		-- 1.3.6.1.4.1.5504.3.12.1.3.1
		zhoneDDMStatusEntry OBJECT-TYPE
			SYNTAX ZhoneDDMStatusEntry
			MAX-ACCESS not-accessible
			STATUS current
			DESCRIPTION
				"A row in the DDM table"
			INDEX { ifIndex }
			::= { zhoneDDMStatusTable 1 }

		
		ZhoneDDMStatusEntry ::=
			SEQUENCE { 
				zhoneDDMTemperature
					Integer32,
				zhoneDDMVoltage
					Unsigned32,
				zhoneDDMTxBiasCurrent
					Integer32,
				zhoneDDMTxPower
					Integer32,
				zhoneDDMRxPower
					Integer32,
				zhoneDDMStatusWord
					INTEGER,
				zhoneDDMAlarms
					BITS
			 }

-- 
		-- 1.3.6.1.4.1.5504.3.12.1.3.1.1
		zhoneDDMTemperature OBJECT-TYPE
			SYNTAX Integer32 (-128..128)
			UNITS "Degrees celcius"
			MAX-ACCESS read-only
			STATUS current
			DESCRIPTION
				"Internally measured transceiver temperature. "
			::= { zhoneDDMStatusEntry 1 }

		
-- 
		-- 1.3.6.1.4.1.5504.3.12.1.3.1.2
		zhoneDDMVoltage OBJECT-TYPE
			SYNTAX Unsigned32 (0..655)
			UNITS "Hundredths of volts"
			MAX-ACCESS read-only
			STATUS current
			DESCRIPTION
				"Internally measured tranceiver supply voltage."
			::= { zhoneDDMStatusEntry 2 }

		
-- 
		-- 1.3.6.1.4.1.5504.3.12.1.3.1.3
		zhoneDDMTxBiasCurrent OBJECT-TYPE
			SYNTAX Integer32 (0..131)
			UNITS "milliamperes"
			MAX-ACCESS read-only
			STATUS current
			DESCRIPTION
				"Measured Tx Bias current."
			::= { zhoneDDMStatusEntry 3 }

		
-- 
		-- 1.3.6.1.4.1.5504.3.12.1.3.1.4
		zhoneDDMTxPower OBJECT-TYPE
			SYNTAX Integer32 (-600..200)
			UNITS "tenths of dB"
			MAX-ACCESS read-only
			STATUS current
			DESCRIPTION
				"Measured Tx output power."
			::= { zhoneDDMStatusEntry 4 }

		
		-- 1.3.6.1.4.1.5504.3.12.1.3.1.5
		zhoneDDMRxPower OBJECT-TYPE
			SYNTAX Integer32 (-600..200)
			UNITS "tenths of dB"
			MAX-ACCESS read-only
			STATUS current
			DESCRIPTION
				"Measured received power."
			::= { zhoneDDMStatusEntry 5 }

		
		-- 1.3.6.1.4.1.5504.3.12.1.3.1.6
		zhoneDDMStatusWord OBJECT-TYPE
			SYNTAX INTEGER
				{
				ok(1),
				warning(2),
				alarm(4),
				sfpnotpresent(8),
				ddmnotsupported(16)
				}
			MAX-ACCESS read-only
			STATUS current
			DESCRIPTION
				"Indicates current status of line with respect to DDM."
			::= { zhoneDDMStatusEntry 6 }

		
		-- 1.3.6.1.4.1.5504.3.12.1.3.1.7
		zhoneDDMAlarms OBJECT-TYPE
			SYNTAX BITS
				{
				tempHigh(0),
				tempLow(1),
				vccHigh(2),
				vccLow(3),
				txBiasHigh(4),
				txBiasLow(5),
				txPwrHigh(6),
				txPwrLow(7),
				rxPwrHigh(8),
				rxPwrLow(9)
				}
			MAX-ACCESS read-only
			STATUS current
			DESCRIPTION
				"Bitmap of alarm conditions present, as reported by the SFP."
			::= { zhoneDDMStatusEntry 7 }

		
	
	END

--
-- zhoneSFF.mib
--
