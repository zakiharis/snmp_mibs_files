ZENOSS-MIB DEFINITIONS ::= BEGIN

IMPORTS
    enterprises, OBJECT-TYPE, MODULE-IDENTITY, NOTIFICATION-TYPE, Unsigned32
        FROM SNMPv2-SMI

    MODULE-COMPLIANCE, OBJECT-GROUP, NOTIFICATION-GROUP
        FROM SNMPv2-CONF;

zenMIB MODULE-IDENTITY
    LAST-UPDATED    "200711230000Z"
    ORGANIZATION    "Zenoss, Inc."
    CONTACT-INFO    "support@zenoss.com"
    DESCRIPTION
        "Defines structure of traps sent by Zenoss."
    REVISION        "200711230000Z"
    DESCRIPTION
        "First revision."
    ::= { enterprises 14296 1 }


zen OBJECT IDENTIFIER ::= { enterprises 14296 }

zenTrapDef OBJECT IDENTIFIER ::= { zenMIB 100 }

evtId OBJECT-TYPE
    SYNTAX      OCTET STRING (SIZE (0..255))
    MAX-ACCESS  read-only
    STATUS      current
    DESCRIPTION
        "Unique identifier ID of the event."
    ::= { zenTrapDef 1 }

evtDedupid OBJECT-TYPE
    SYNTAX      OCTET STRING (SIZE (0..255))
    MAX-ACCESS  read-only
    STATUS      current
    DESCRIPTION
        "De-duplication ID of the event."
    ::= { zenTrapDef 2 }

evtDevice OBJECT-TYPE
    SYNTAX      OCTET STRING (SIZE (0..255))
    MAX-ACCESS  read-only
    STATUS      current
    DESCRIPTION
        "Device associated with event."
    ::= { zenTrapDef 3 }

evtComponent OBJECT-TYPE
    SYNTAX      OCTET STRING (SIZE (0..255))
    MAX-ACCESS  read-only
    STATUS      current
    DESCRIPTION
        "Device component associated with event."
    ::= { zenTrapDef 4 }

evtClass OBJECT-TYPE
    SYNTAX      OCTET STRING (SIZE (0..255))
    MAX-ACCESS  read-only
    STATUS      current
    DESCRIPTION
        "Event classification."
    ::= { zenTrapDef 5 }

evtKey OBJECT-TYPE
    SYNTAX      OCTET STRING (SIZE (0..255))
    MAX-ACCESS  read-only
    STATUS      current
    DESCRIPTION
        "Event key used for refining event granularity beyond device and
        component. Used in de-duplication, auto-clearing."
    ::= { zenTrapDef 6 }

evtSummary OBJECT-TYPE
    SYNTAX      OCTET STRING (SIZE (0..255))
    MAX-ACCESS  read-only
    STATUS      current
    DESCRIPTION
        "Event message truncated to 128 characters."
    ::= { zenTrapDef 7 }

evtSeverity OBJECT-TYPE
    SYNTAX      Unsigned32
    MAX-ACCESS  read-only
    STATUS      current
    DESCRIPTION
        "Event severity number: 0=clear(normal), 1=debug, 2=info, 3=warning,
        4=error, 5=critical"
    ::= { zenTrapDef 9 }

evtState OBJECT-TYPE
    SYNTAX      Unsigned32
    MAX-ACCESS  read-only
    STATUS      current
    DESCRIPTION
        "Event state number: 0=new, 1=acknowledged, 2=suppressed"
    ::= { zenTrapDef 10 }

evtClassKey OBJECT-TYPE
    SYNTAX      OCTET STRING (SIZE (0..255))
    MAX-ACCESS  read-only
    STATUS      current
    DESCRIPTION
        "Event class key for rule processing often matches component."
    ::= { zenTrapDef 11 }

evtGroup OBJECT-TYPE
    SYNTAX      OCTET STRING (SIZE (0..255))
    MAX-ACCESS  read-only
    STATUS      current
    DESCRIPTION
        "Logical grouping of event sources."
    ::= { zenTrapDef 12 }

evtStateChange OBJECT-TYPE
    SYNTAX      OCTET STRING (SIZE (0..255))
    MAX-ACCESS  read-only
    STATUS      current
    DESCRIPTION
        "Last time event changed through administrative activity."
    ::= { zenTrapDef 13 }

evtFirstTime OBJECT-TYPE
    SYNTAX      OCTET STRING (SIZE (0..255))
    MAX-ACCESS  read-only
    STATUS      current
    DESCRIPTION
        "First time an event was received."
    ::= { zenTrapDef 14 }

evtLastTime OBJECT-TYPE
    SYNTAX      OCTET STRING (SIZE (0..255))
    MAX-ACCESS  read-only
    STATUS      current
    DESCRIPTION
        "Last time an event was received."
    ::= { zenTrapDef 15 }

evtCount OBJECT-TYPE
    SYNTAX      OCTET STRING (SIZE (0..255))
    MAX-ACCESS  read-only
    STATUS      current
    DESCRIPTION
        "Number of times this event has been seen."
    ::= { zenTrapDef 16 }

evtProdState OBJECT-TYPE
    SYNTAX      OCTET STRING (SIZE (0..255))
    MAX-ACCESS  read-only
    STATUS      current
    DESCRIPTION
        "Production state of the device or component associated with this
        event."
    ::= { zenTrapDef 17 }

evtSuppId OBJECT-TYPE
    SYNTAX      OCTET STRING (SIZE (0..255))
    MAX-ACCESS  read-only
    STATUS      current
    DESCRIPTION
        "evtId of the event that suppressed this event."
    ::= { zenTrapDef 18 }

evtManager OBJECT-TYPE
    SYNTAX      OCTET STRING (SIZE (0..255))
    MAX-ACCESS  read-only
    STATUS      current
    DESCRIPTION
        "FQDN of Zenoss system that processed this event."
    ::= { zenTrapDef 19 }

evtAgent OBJECT-TYPE
    SYNTAX      OCTET STRING (SIZE (0..255))
    MAX-ACCESS  read-only
    STATUS      current
    DESCRIPTION
        "Collector process that received or created this event."
    ::= { zenTrapDef 20 }

evtDeviceClass OBJECT-TYPE
    SYNTAX      OCTET STRING (SIZE (0..255))
    MAX-ACCESS  read-only
    STATUS      current
    DESCRIPTION
        "Class of device that this event is associated with."
    ::= { zenTrapDef 21 }

evtLocation OBJECT-TYPE
    SYNTAX      OCTET STRING (SIZE (0..255))
    MAX-ACCESS  read-only
    STATUS      current
    DESCRIPTION
        "Location of device that this event is associated with."
    ::= { zenTrapDef 22 }

evtSystems OBJECT-TYPE
    SYNTAX      OCTET STRING (SIZE (0..255))
    MAX-ACCESS  read-only
    STATUS      current
    DESCRIPTION
        "Systems containing the device that this event is associated with."
    ::= { zenTrapDef 23 }

evtDeviceGroups OBJECT-TYPE
    SYNTAX      OCTET STRING (SIZE (0..255))
    MAX-ACCESS  read-only
    STATUS      current
    DESCRIPTION
        "Groups containing the device that this event is associated with."
    ::= { zenTrapDef 24 }

evtIpAddress OBJECT-TYPE
    SYNTAX      OCTET STRING (SIZE (0..255))
    MAX-ACCESS  read-only
    STATUS      current
    DESCRIPTION
        "IP address that this event was generated or sent from."
    ::= { zenTrapDef 25 }

evtFacility OBJECT-TYPE
    SYNTAX      Unsigned32
    MAX-ACCESS  read-only
    STATUS      current
    DESCRIPTION
        "Syslog facility if the event was initially sent as a syslog."
    ::= { zenTrapDef 26 }

evtPriority OBJECT-TYPE
    SYNTAX      Unsigned32
    MAX-ACCESS  read-only
    STATUS      current
    DESCRIPTION
        "Syslog priority if the event was initially sent as a syslog."
    ::= { zenTrapDef 27 }

evtNtEvId OBJECT-TYPE
    SYNTAX      OCTET STRING (SIZE (0..255))
    MAX-ACCESS  read-only
    STATUS      current
    DESCRIPTION
        "Windows NT_EVENT_ID if the event was initially received from Windows
        event log."
    ::= { zenTrapDef 28 }

evtOwnerId OBJECT-TYPE
    SYNTAX      OCTET STRING (SIZE (0..255))
    MAX-ACCESS  read-only
    STATUS      current
    DESCRIPTION
        "User that acknowledged this event."
    ::= { zenTrapDef 29 }

evtDeletedTime OBJECT-TYPE
    SYNTAX      OCTET STRING (SIZE (0..255))
    MAX-ACCESS  read-only
    STATUS      current
    DESCRIPTION
        "Time that this event was deleted or archived by a user."
    ::= { zenTrapDef 30 }

evtClearId OBJECT-TYPE
    SYNTAX      OCTET STRING (SIZE (0..255))
    MAX-ACCESS  read-only
    STATUS      current
    DESCRIPTION
        "evtId that cleared this event."
    ::= { zenTrapDef 31 }

evtDevicePriority OBJECT-TYPE
    SYNTAX      OCTET STRING (SIZE (0..255))
    MAX-ACCESS  read-only
    STATUS      current
    DESCRIPTION
        "Priority of the device that this event is associated with."
    ::= { zenTrapDef 32 }

evtClassMapping OBJECT-TYPE
    SYNTAX      OCTET STRING (SIZE (0..255))
    MAX-ACCESS  read-only
    STATUS      current
    DESCRIPTION
        "Name of the event class mapping that matched this event."
    ::= { zenTrapDef 33 }


zenNotifications    OBJECT IDENTIFIER ::= { zenTrapDef 0 }
zenTraps            OBJECT IDENTIFIER ::= { zenNotifications 0 }


zenGenTrap NOTIFICATION-TYPE
    OBJECTS {
        evtId,
        evtDedupid,
        evtDevice,
        evtComponent,
        evtClass,
        evtKey,
        evtSummary,
        evtSeverity,
        evtState,
        evtClassKey,
        evtGroup,
        evtStateChange,
        evtFirstTime,
        evtLastTime
    }
    STATUS current
    DESCRIPTION
        "The trap notifying of when an event is received by the Zen server."
    ::= { zenTraps 1 }

--
-- conformance information
--

zenMIBConformance   OBJECT IDENTIFIER ::= { zenMIB 2 }

zenMIBCompliances   OBJECT IDENTIFIER ::= { zenMIBConformance 1 }
zenMIBGroups        OBJECT IDENTIFIER ::= { zenMIBConformance 2 }

-- compliance statements

zenMIBCompliance MODULE-COMPLIANCE
    STATUS current
    DESCRIPTION
        "The compliance statement for SNMPv2 entities which
        implement UDP over IPv6."
    MODULE
        MANDATORY-GROUPS {
            zenMIBObjectGroup,
            zenMIBTrapGroup
        }
   ::= { zenMIBCompliances 1 }

zenMIBObjectGroup OBJECT-GROUP
    OBJECTS {
        evtId,
        evtDedupid,
        evtDevice,
        evtComponent,
        evtClass,
        evtKey,
        evtSummary,
        evtSeverity,
        evtState,
        evtClassKey,
        evtGroup,
        evtStateChange,
        evtFirstTime,
        evtLastTime
    }
    STATUS current
    DESCRIPTION
        "The group of objects providing trap contents."
    ::= { zenMIBGroups 1 }

zenMIBTrapGroup NOTIFICATION-GROUP
    NOTIFICATIONS {
        zenGenTrap
    }
    STATUS current
    DESCRIPTION
        "The group of objects providing traps."
    ::= { zenMIBGroups 2 }

END
