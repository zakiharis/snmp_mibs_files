--
-- phyZhoneLineTypes.mib
-- MIB generated by MG-SOFT Visual MIB Builder Version 3.0 Build 271
-- Tuesday, May 27, 2003 at 12:08:08
--

-- The ZHONE profile definition for DS3_Profile used here can be found 
-- in rfc2496.mib. We use this profile here to include the
-- values from the dsx3ConfigExtTable 

        ZHONE-PHY-LINE-TYPES DEFINITIONS ::= BEGIN
 
                IMPORTS
                        transmission, Integer32, OBJECT-TYPE, MODULE-IDENTITY, OBJECT-IDENTITY                        
                                FROM SNMPv2-SMI                        
                        zhonePhysical, zhoneShelfIndex, zhoneSlotIndex, zhoneModules, zhoneShelfIndex, 
                        zhoneSlotIndex                        
                                FROM Zhone;
        
        
-- 
                phyZhoneLineTypes MODULE-IDENTITY 
                        LAST-UPDATED "200305271116Z"		-- May 27, 2003 at 11:16 GMT
                        ORGANIZATION 
                                "Organization."
                        CONTACT-INFO 
                                "Contact-info."
                        DESCRIPTION 
                                "Description."
                        REVISION "200305271155Z"		-- May 27, 2003 at 11:55 GMT
                        DESCRIPTION
                                "1.0.1 - Add trap-enable to ulc-config."
                        REVISION "200302111123Z"		-- February 11, 2003 at 11:23 GMT
                        DESCRIPTION
                                "1.0 - Initial version."
                        ::= { zhoneModules 1 }
                
        
        
--
-- Node definitions
--
        
                -- 1.3.6.1.4.1.5504.5.11
                zhoneLineTypes OBJECT-IDENTITY
                        STATUS current
                        DESCRIPTION 
                                "Definitions for custom Zhone line types."
                        ::= { zhonePhysical 11 }
                
                -- 1.3.6.1.4.1.5504.5.11.1
                ulcTable OBJECT-TYPE
                        SYNTAX SEQUENCE OF UlcEntry
                        MAX-ACCESS not-accessible
                        STATUS current
                        DESCRIPTION
                                "Universal Line Card (ULC) line type definitions."
                        ::= { zhoneLineTypes 1 }
                
                -- 1.3.6.1.4.1.5504.5.11.1.1
                ulcEntry OBJECT-TYPE
                        SYNTAX UlcEntry
                        MAX-ACCESS not-accessible
                        STATUS current
                        DESCRIPTION
                                "ULC Entry line type definitions.  There is one entry
                                per ULC port."
                        INDEX { zhoneShelfIndex, zhoneSlotIndex, ulcPortIndex }
                        ::= { ulcTable 1 }
                
                UlcEntry ::=
                        SEQUENCE { 
                                ulcPortIndex
                                        Integer32,
                                ulcPortType
                                        INTEGER,
                                ulcTrapEnable
                                        INTEGER
                         }

                -- 1.3.6.1.4.1.5504.5.11.1.1.1
                ulcPortIndex OBJECT-TYPE
                        SYNTAX Integer32 (0..12)
                        MAX-ACCESS not-accessible
                        STATUS current
                        DESCRIPTION
                                "This object is used as part of the indexing of this table,
                                along with zhoneShelfIndex and zhoneSlotIndex.  This object
                                specifies the port number."
                        ::= { ulcEntry 1 }
                
                -- 1.3.6.1.4.1.5504.5.11.1.1.2
                ulcPortType OBJECT-TYPE
                        SYNTAX INTEGER
                                {
                                pots(1),
                                isdn(2),
                                ebs(3)
                                }
                        MAX-ACCESS read-write
                        STATUS current
                        DESCRIPTION
                                "Each port on a ULC can be provisioned in many different
                                ways.  This object identifies the port provisioning.  There
                                is one entry per ULC port."
                        ::= { ulcEntry 2 }
                
                -- 1.3.6.1.4.1.5504.5.11.1.1.3
                ulcTrapEnable OBJECT-TYPE
                        SYNTAX INTEGER
                                {
                                enabled(1),
                                disabled(2)
                                }
                        MAX-ACCESS read-write
                        STATUS current
                        DESCRIPTION
                                "Allows snmp user to disable or enable the sending
                                of line level traps from the device to the NMS.
                                
                                Defaults to disabled."
                        DEFVAL { disabled }
                        ::= { ulcEntry 3 }
                
        
        END

--
-- phyZhoneLineTypes.mib
--
