-- ZyXEL Communications Corporation
-- Private Enterprise MIB definition

-- $Log: zyxel-IES5000.mib $
-- Revision 1.157  2013/12/13 03:39:26  DavidLiu
-- Revision 1.156  2013/12/13 03:39:04  DavidLiu
-- Revision 1.155  2013/12/13 03:35:36  DavidLiu
-- Revision 1.154  2013/11/27 02:29:06  alan
-- add description for alarmConfId
-- Revision 1.153  2013/11/14 10:40:05  alan
-- 1. remove Xdsl2TransmissionType
-- 2. change syntex for vdsl2LineProfTransmissionType
-- 3. change description for macDisplayTarget, vlanMacDisplayTarget
-- Revision 1.152  2013/10/29 10:02:16  alan
-- add igmpHistoryTable
-- Revision 1.151  2013/10/28 03:18:32  alan
-- 1. add vdsl2LineProfTransmissionType
-- 2. change eqptSptPortRoleOrig, eqptSptPortRoleNew
-- Revision 1.150  2013/10/25 06:22:57  alan
-- add mvlanNonmemberPort object
-- Revision 1.149  2013/10/21 07:26:58  alan
-- add vdsl2Paepvc
-- Revision 1.148  2013/08/29 07:55:48  alan
-- change value of eqptSptPortStateOrig, eqptSptPortStateNew
-- Revision 1.147  2013/08/28 07:22:21  alan
-- 1. add MIB object eqptSptMstiInstanceId, eqptSptPortStateOrig, eqptSptPortStateNew, eqptSptPortRoleOrig, eqptSptPortRoleNew
-- 2. add trap  eqptSptPortStateChange, eqptSptPortRoleChange
-- Revision 1.146  2013/08/14 07:31:39  alan
-- add vop1372G_61_SIP(127) in slotModuleType
-- Revision 1.145  2013/07/31 08:52:33  alan
-- Add mib object enetLineConfSpeed
-- Revision 1.144  2013/06/27 02:55:15  alan
-- change description of voipNumberPlanPattern, voipNumberPlanRule
-- Revision 1.143  2013/06/27 02:04:45  alan
-- add BIT9: Disable Nitro mode for adslLineConfOptionMask
-- Revision 1.142  2013/06/18 08:39:57  alan
-- add voipSipLineConfDataProfile
-- Revision 1.141  2013/05/28 09:52:52  Alan
-- change voipNumberPlanRule MIB object's description
-- Revision 1.140  2013/05/20 01:47:57  Alan
-- add vdsl2LineProfDpboType, vdsl2LineProfDpboEselMin, vdsl2LineProfCompatible for vlc1424g56
-- Revision 1.139  2013/05/17 01:22:02  Alan
-- Modify/add following two object:
-- 1.	macFilterPerPVCMacCount is only for ALC1372G-51
-- 2.	value 2 of macFilterPerPVCEnable is only for ALC1372G-51
-- Revision 1.138  2013/05/14 08:06:08  Alan
-- change description of portOps
-- Revision 1.137  2013/04/22 02:47:50  Alan
-- there are three more mib objects added: pvcAcName, pvcServiceName, pvcHelloTime. And pvcEncap is modified.
-- Revision 1.136  2013/02/20 09:23:47  Alan
-- modify the mib description "0~1488096 pkt/s, -1 means no limit" to support GLC1320G_55 for usStormBcastThresh,  usStormMcastThresh, usStormUcastThresh
-- Revision 1.135  2013/02/05 07:15:11  Alan
-- add 3010:enetSFPTxEnable and 3011:enetSFPTxDisable of the description in alarmConfId
-- Revision 1.134  2013/01/30 04:35:18  Alan
-- add glc1320G_55 in slotModuleType
-- Revision 1.133  2013/01/09 05:36:58  Alan
-- 1. add enetPortConfDtEnable, enetPortConfDtSvid, enetPortConfDtSpriority, enetPortConfDtCvid in enetPortConfTable
-- 2. add enetPortPvlanTable, enetPortXvlanTable
-- Revision 1.132  2013/01/08 08:27:18  Alan
-- add enetSfpTxEnable, enetSfpTxDisable
-- Revision 1.131  2013/01/03 06:26:37  Alan
-- add dspProfileCodecPriority MIB object
-- Revision 1.130  2012/12/27 01:46:32  Alan
-- 1. remove xdslTCAEQINP descr from alarmConfId
-- 2. add mvlanExtTable
-- 3. add vdslLineConfDpboParamType, vdslLineConfDpboParamEselMin, vdslLineConfHsTxA43Psd, vdslLineConfHsTxB43Psd, vdslLineConfHsTxA43cB43cPsd, vdslLineConfHsTxV43Carrier257Psd, vdslLineConfHsTxV43Carrier383Psd, vdslLineConfHsTxV43Carrier511Psd
-- Revision 1.129  2012/12/18 01:38:53  Alan
-- add dhcpRelayOption82CheckEnable MIB OID
-- Revision 1.128  2012/12/03 01:54:37  Alan
-- add msc1024GC(125) for slotModuleType
-- Revision 1.127  2012/11/27 09:59:13  Alan
-- add trap dslLineVturInfoReady, dslLineVturLpr
-- Revision 1.126  2012/11/21 10:30:16  Alan
-- change binding for trap vopRingerFail and vopRingerNormal
-- Revision 1.125  2012/11/21 09:05:29  Alan
-- change binding for trap vopTermNameDup
-- Revision 1.124  2012/11/12 01:18:03  Alan
-- Revision 1.123  2012/11/06 12:26:37  Alan
-- add pvcAllFilter and pvcAllTable
-- Revision 1.122  2012/10/29 03:03:12  Alan
-- Revision 1.121  2012/10/24 08:27:37  Alan
-- chang binding of trap for vopBatteryFail, vopBatteryNormal, vopRingerFail, vopRingerNormal
-- Revision 1.120  2012/06/27 09:29:46  Alan
-- 1. change SYNTAX from INTEGER to Counter64 for voipRtpStatTxPktCnt, voipRtpStatRxPktCnt, voipRtpStatTxJitter, voipRtpStatRxJitter, voipRtpStatTxAvgDelay, voipRtpStatRxAvgDelay
-- 2. change SYNTAX from INTEGER to Counter64 for voipCdrStatResultTxPktCnt, voipCdrStatResultRxPktCnt, voipCdrStatResultTxJitter, voipCdrStatResultRxJitter, voipCdrStatResultTxAvgDelay, voipCdrStatResultRxAvgDelay
-- Revision 1.119  2012/06/22 06:11:21  Alan
-- 1. add mltErrorMsg MIB object
-- Revision 1.118  2012/05/29 02:34:37  Alan
-- 1. add MIB object xdsl2PMLSinceInitLofs, xdsl2PMLSinceInitLols, xdsl2PMLSinceInitLol, xdsl2PMLSinceInitLprs, xdsl2PMLSinceInitLpr, xdsl2PMLSinceInitInits
-- Revision 1.117  2012/05/16 01:27:49  Alan
-- 1. add voipCdrStatFilterErrCodeEnable, voipCdrStatResultErrCode MIB objects
-- Revision 1.116  2012/04/27 01:38:11  Alan
-- Revision 1.115  2012/04/19 05:40:50  Alan
-- 1. change description of voipClearOps 
-- Revision 1.114  2012/04/19 03:12:42  Alan
-- 1. change description of voipCdrStatFilterPort
-- 2. add voipClearOps, voipClearH248TargetInterface MIB object
-- Revision 1.113  2012/04/18 05:52:47  Alan
-- 1. add voipCdrStatFilterInterface in the head of voipCdrStatFilter and shift OID of all object under table voipCdrStatFilter 
-- 2. add voipH248StatisticsInterface in the head of voipH248Statistics and move all object under table voipProtocolStatTable and change prefix from voipProtocolStatXXX to voipH248StatisticsXXX
-- Revision 1.112  2012/04/11 06:46:24  Alan
-- 1. remove voipCdrStatFilterSlot 
-- 2. move voipCdrStatFilterIndexEnable from (1.3.6.1.4.1.890.1.5.13.5.13.12.10.1.2) to (1.3.6.1.4.1.890.1.5.13.5.13.12.10.1.1)
-- 3. move voipCdrStatFilterIndex from (1.3.6.1.4.1.890.1.5.13.5.13.12.10.1.3)  to (1.3.6.1.4.1.890.1.5.13.5.13.12.10.1.2)
-- 4. move voipCdrStatFilterPortEnable from (1.3.6.1.4.1.890.1.5.13.5.13.12.10.1.4) to (1.3.6.1.4.1.890.1.5.13.5.13.12.10.1.3) and change object name from  voipCdrStatFilterPortEnable  to voipCdrStatFilterSlotPortEnable and change description of voipCdrStatFilterSlotPortEnable 
-- 5. insert voipCdrStatFilterSlot at OID(1.3.6.1.4.1.890.1.5.13.5.13.12.10.1.4)
-- 6. Insert voipCdrStatResultSlot after voipCdrStatResultIndex, and shift OID of all object below it
-- Revision 1.111  2012/04/09 09:45:34  Alan
-- 1. change MAXaccess of macFilterPerPVCMACAddr from read-write to read-only
-- 2. change description of alarmConfId
-- Revision 1.110  2012/04/05 03:50:28  Alan
-- 1. add MIB objects voipLineInfoLastCidMode, voipLineInfoPlaySignalTel, voipLineInfoPlaySignalNet
-- 2. add range for voipH248LocalcallEnterTime, voipH248LocalcallExistTime, voipPotsRingVoltage
-- Revision 1.109  2012/04/03 06:01:34  Alan
-- 1. add voipProtocolStatTable
-- Revision 1.108  2012/03/28 07:58:49  Alan
-- 1. change OBJECTS of vopTermNameDup
-- Revision 1.107  2012/03/28 07:36:17  Alan
-- 1. add vopMgcIP MIB object
-- 2. change description of mltCount
-- 3. change OBJECTS of vopMgcMissing, vopMgcNormal, vopPortMissing, vopPortNormal
-- Revision 1.106  2012/03/22 09:33:37  Alan
-- 1. add voipH248Localcall subtree
-- 2. add voipH248LocalcallEnterTime, voipH248LocalcallExistTime, voipPotsRingVoltage MIB objects
-- Revision 1.105  2012/03/22 07:27:17  Alan
-- 1. add h248ProfileLocalcall, h248ProfileCallthrough MIB object
-- Revision 1.104  2012/03/16 06:51:38  Alan
-- 1. add mltDetectedDtmfDigit MIB object
-- Revision 1.103  2012/03/16 05:46:06  Alan
-- 1. add mltCount MIB object
-- Revision 1.102  2012/03/12 10:31:02  Alan
-- 1. change MAX-access of imaMgmtPvcEncap, imaMgmtPvcPriority, imaMgmtPvcProfile from read-create to read-write
-- 2. change MAX-access of imaMgmtPvcManagedIp, imaMgmtPvcGatewayIp from read-create to read-only
-- Revision 1.101  2012/03/12 06:56:41  Alan
-- 1. remove sipDialPlanProfileDefaultSipServer MIB object
-- 2. change description of sipDialPlanProfileIndex and sipDialPlanProfileDialPlanTableName
-- Revision 1.100  2012/03/09 07:25:11  Alan
-- 1. add sipDialPlanProfileDefaultSipServer MIB object
-- 2. change MAX-access of sipDialPlanProfileDialPlanTableName form "read-create" to "read-write"
-- Revision 1.99  2012/03/06 02:12:10  Alan
-- 1. recovery description of configOps to original
-- 2. remove configReloadStatus MIB object
-- Revision 1.98  2012/03/05 07:29:59  Alan
-- 1. add mltType MIB object
-- 2. add voipPotsCidConfTable
-- Revision 1.97  2012/03/05 01:54:18  Alan
-- 1. change description of mltVacTip, mltVacRing, mltVacDiff, mltVdcTip, mltVdcRing, mltVdcDiff, mltRLoop, mltRtg, mltRrg, mltRtr, mltCtg, mltCrg, mltCtr, mltRen, mltVRing, mltVMetering, mltDialToneDetected, mltDetectedDtmfCount, mltDialToneDelay, mltReceiverState
-- 2. change description of configOps
-- 3. add MIB object configReloadStatus
-- Revision 1.96  2012/02/29 07:23:53  Alan
-- 1. add cfmMIPMacAddress MIB OID
-- 2. modify description of dhcpv6RelayOptionFormat
-- Revision 1.95  2012/01/05 07:08:35  Alan
-- change valuelist of h248ProfileSoftswitch
-- Revision 1.94  2012/01/02 09:29:28  Alan
-- 1. add description for voipCdrStatFilter and voipCdrStatResultEntry's objects
-- 2. change MAX-access of voipCdrStatFilterSlot, voipCdrStatFilterIndexEnable, voipCdrStatFilterPortEnable, voipCdrStatFilterTalktimeEnable, voipCdrStatFilterTelEnable, voipCdrStatFilterOffhookEnable, voipCdrStatFilterCodeEnable from read-only to read-write
-- Revision 1.93  2011/12/23 08:34:37  Alan
-- 1. add a value(loopguardOccurence) of slotModuleAlarmStatus
-- 2. change loopguardStatsPortStatus's value
-- Revision 1.92  2011/12/23 06:15:36  Alan
-- 1. add voipRtpStatTable
-- 2. add description for mltRtg, mltRrg, and mltRtr
-- Revision 1.91  2011/12/22 10:27:54  Alan
-- add a value(not_measured(5)) for mltReceiverState MIB oid
-- Revision 1.90  2011/12/22 05:49:56  Alan
-- 1. remove voipRtpStatTable
-- Revision 1.89  2011/12/21 01:46:13  Alan
-- 1. add voipRtpStatRxAvgDelay MIB OID
-- 2. add voipCdrStat subtree
-- Revision 1.88  2011/12/12 02:20:46  Alan
-- change type of vdsl2LineProfDynamicDepthEnableDs, vdsl2LineProfDynamicDepthEnableUs, vdsl2LineProfRocEnableDs, and vdsl2LineProfRocEnableUs from Unsigned32 to INTEGER
-- Revision 1.87  2011/11/23 04:32:29  Alan
-- remove igmpGroupNumOfActiveUsers OID
-- Revision 1.86  2011/11/23 01:05:59  Alan
-- add vlaue and description of staticIpOps
-- Revision 1.85  2011/11/22 02:29:20  Alan
-- 1. change description of macFFDynamicIndex from The macFF static entry index 1 ~ 24 to The macFF entry index 1 ~ 24
-- 2. add index for macFFArpStatusUplinkTable and macFFArpStatusSlotTable
-- Revision 1.84  2011/11/16 10:05:56  Alan
-- 1. remove macFFDynamicRowStatus
-- 2. change MAX-ACCESS of macFFDynamicSrcIP, macFFDynamicMask, macFFDynamicArasIP, macFFDynamicVid from read-write to read-only
-- Revision 1.83  2011/11/15 10:03:41  Alan
-- add staticIp table
-- Revision 1.82  2011/11/11 08:28:02  Alan
-- change vlaue of macFilterPerPVCEnable, macFilterPerPVCMode, vdsl2LineProfDynamicDepthEnableDs, vdsl2LineProfDynamicDepthEnableUs, vdsl2LineProfRocEnableDs, vdsl2LineProfRocEnableUs
-- Revision 1.81  2011/11/11 06:06:29  Alan
-- 1. change description of macFFArpCntPortRpyRxDrop from "mac force arp reply rx drop counter from subscrib port" to "macFF reply rx drop counter from subscrib port"
-- 2. add value of counterClearOps: BIT14: clear macFF arp counters
-- Revision 1.80  2011/11/11 05:27:53  Alan
-- 1. change table name from macForceFwdTable to macFFStaticTable
-- 2. change table name from macForceFwdVlanTable to macFFVlanTable
-- 3. add table macFFDynamicTable
-- 4. change table name from macForceArpInfoTable to macFFArpStatusUplinkTable
-- 5. add table macFFArpStatusSlotTable
-- 6. change table name from macForceArpCntTable to macFFArpCntUplinkTable
-- 7. add table macFFArpCntPortTable
-- Revision 1.79  2011/11/09 02:35:23  Alan
-- add e10M_fullduplex(5), e10M_halfduplex(6), e10G_fullduplex(7) for enetPortSpeed
-- Revision 1.78  2011/11/08 09:50:36  Alan
-- to change description of extAlarmStatus
-- Revision 1.77  2011/11/03 10:43:07  Alan
-- 1. change vdslLineConfRocEnableDs's object type from Unsigned32 to INTEGER 
-- 2. change vdslLineConfRocEnableUs's object type from Unsigned32 to INTEGER 
-- 3. add vdslLineConfSosEnableDs, vdslLineConfSosEnableUs, vdslLineConfDynamicDepthDs, vdslLineConfDynamicDepthUs Object OIDs
-- Revision 1.76  2011/11/01 07:13:05  Alan
-- add vopPortNormal trap
-- Revision 1.75  2011/11/01 06:04:38  Alan
-- Add vopPortMissing trap
-- Revision 1.74  2011/10/31 08:54:36  Alan
-- 1. change MIB Object name from vdsl2LConfProfProileName to vdsl2LConfProfProfileName
-- 2. add https(7) in accessCtrlService MIB OID
-- Revision 1.73  2011/10/19 01:43:13  Alan
-- Add Inm, Sos, G.inp in zyxel-ies5000.mib
-- Revision 1.72  2011/10/17 01:08:14  Alan
-- Revision 1.71  2011/10/14 06:06:14  Alan
-- Revision 1.70  2011/10/14 05:43:39  Alan
-- add enetPortConfQueueRateLimitProfile, enetQScheduleTable, enetQueueWeightTable MIB OIDs
-- Revision 1.69  2011/10/13 08:08:36  Alan
-- add igmpGroupNumOfActiveUsers, mldGroupNumOfActiveUsers, vdslPortConfTlsPrioCopyEnable MIB OIDs
-- Revision 1.68  2011/10/13 06:27:42  Alan
-- Revision 1.67  2011/10/13 05:57:52  Alan
-- Revision 1.66  2011/10/12 08:55:07  Alan
-- add new objects for OBM 4.00 feature enhancement in our private MIB
-- Revision 1.65  2011/10/05 01:39:01  Alan
-- 1. add voipRtpStatTable
-- 2. add vdsl2LineConfTempTemplatePortMap, vdsl2LineProfDynamicDepthEnableDs, vdsl2LineProfDynamicDepthEnableUs, vdslLineStatsVtucRxPower, vdslLineStatsVturRxPower MIB OID
-- Revision 1.64  2011/09/20 01:58:04  Alan
-- add alarmConfId for vopMgcMissing, vopMgEnable and vopMgDisable
-- add trap object id vopMgcMissing, vopMgcNormal, vopMgEnable and vopMgDisable 
-- Revision 1.63  2011/09/08 09:49:01  Alan
--  change the range of ACL rate limit and rate limit profile to be 100032
-- 1. aclProfileActionRate
-- 2.rateLimitProfileIngressRate
-- 3.rateLimitProfileEgressRate
-- Revision 1.62  2011/09/06 01:08:50  Alan
-- add extAlarmStatus MIB OID
-- Revision 1.61  2011/08/23 01:32:01  Alan
-- add vdsl2QSchedule MIB OID
-- Revision 1.60  2011/08/22 08:16:40  Alan
-- add IMPLIED key word for queueRateLimitProfileTable
-- Revision 1.59  2011/08/17 10:04:33  Alan
-- Add queueRateLimitProfileTable, vdsl2LineConfQueueRateLimitProfile MIB objects
-- Revision 1.58  2011/08/16 03:22:48  Alan
-- Change description of vopBatteryFail, vopBatteryNormal, vopClockFail, vopClockNormal, vopRingerFail, vopRingerNormal traps
-- Revision 1.57  2011/08/15 08:58:41  Alan
-- Add vopBatteryFail, vopBatteryNormal, vopClockFail, vopClockNormal, vopRingerFail, vopRingerNormal traps
-- Add description for voip traps
-- Revision 1.56  2011/08/03 01:18:27  Alan
-- add xdsl2ExtSCStatusTable and xdsl2ExtSCStatusBandTable
-- Revision 1.55  2011/07/29 03:39:22  Alan
-- add xdsl2LineAlarmConfProfileXtucThresh15MinLols MIB OID
-- Revision 1.54  2011/06/17 02:58:38  Alan
-- modify the SYNTAX/INDEX from Counter32 to OCTETSTRING
-- xdsl2PMLSinceLinkInmEqInp, xdsl2PMLSinceLinkInmIAT, xdsl2PMLCurr15MInmEqInp,
-- xdsl2PMLCurr15MInmIAT, xdsl2PMLCurr1DayInmEqInp, xdsl2PMLCurr1DayInmIAT,
-- xdsl2PMLHist15MInmEqInp, xdsl2PMLHist15MInmIAT, xdsl2PMLHist1DInmEqInp,
-- xdsl2PMLHist1DInmIAT
-- Revision 1.53  2011/06/16 09:29:32  Alan
-- add MIB trap object sysUserLoginInetAddrType, sysUserLoginInetAddr, sysLoginInet, sysLoginFailureInet
-- Revision 1.52  2011/06/16 03:04:45  Alan
-- add MIB object mltReceiverState
-- Revision 1.51  2011/06/14 10:20:45  Alan
-- add MIB object mcastBwInetTable
-- Revision 1.50  2011/06/14 09:34:40  Alan
-- add subnetvlanInetTable, mcastInetGroupTable, mcastBwInetAddrType, mcastBwInetAddrStart,
-- add MIB object mcastBwInetAddrStart, vdsl2Pvc, aclProfileRuleSrcIp6, aclProfileRuleDstIp6, aclProfileRuleSip6, aclProfileRuleDip6,
-- enetPortStatusLinkSpeed, enetPortStatusLinkDuplex, enetPortStatusDataRateTx, enetPortStatusDataRateRx,
-- enetPortStatusDataUtilTx, enetPortStatusDataUtilRx
-- Revision 1.49  2011/06/10 07:13:55  Alan
-- Add mirror MIBs, DDMI alarm MIBs and Traps, mldStats
-- Remove G.INP, SOS, INM MIBs
-- Revision 1.48  2011/06/03 07:10:02  Alan
-- Add MIB object cfmMode, cfmMIPRespondMcastLbm, cfmLoopbackTimeout, cfmLbrTable, cfmLbrEntry, cfmLbrSeqNumber, cfmLbrReceiveOrder, cfmLbrSrcMac 
-- Revision 1.47  2011/05/27 03:11:02  Alan
-- Change MIB object name
-- vdslChanReedSolomonCodeWordPerDut -> vdslChanReedSolomonCodeWordPerDtu
-- xxxxRtxCW -> xxxxRtx
-- xxxxRtxCorrectedCW -> xxxxRtxCorrected
-- xxxxRtxUncorrectedCW -> xxxxRtxUncorrected
-- Revision 1.46  2011/05/17 10:05:37  Alan
-- change naming from vopTempNoraml to vopTempNormal
-- Revision 1.45  2011/05/02 06:03:34  Alan
-- add IPv6 support
-- Revision 1.44  2011/04/19 05:49:50  Alan
-- add extended VDSL2 INM, SOS, and G.INP
-- Revision 1.43  2011/04/18 05:42:43  Alan
-- add voip trap
-- Revision 1.42  2011/03/29 09:39:23  Alan
-- Revision 1.41  2011/03/29 08:03:12  Alan
-- add ies5000/statistics/vdsl2Stats/xdsl2LineBandExtTable
-- Revision 1.40  2011/03/28 05:41:05  Alan
-- Revision 1.39  2011/03/18 01:38:54  Alan
-- Revision 1.38  2011/03/15 09:04:43  Alan
-- Add slotModuleType for vop1372G_61_H248
-- Revision 1.37  2011/03/04 09:41:25  Alan
-- add slotModuleType: msc1024GB and msc1224GB
-- Revision 1.36  2011/01/26 01:00:24  Alan
-- Add new alarm id
-- Revision 1.35  2011/01/04 09:28:42  Alan
-- Revision 1.34  2011/01/04 06:57:31  Alan
-- Revision 1.33  2011/01/04 01:46:25  Alan
-- Revision 1.31  2010/12/29 10:07:31  Alan
-- Revision 1.30  2010/12/02 09:11:10  Alan
-- R5.06
-- Revision 1.29  2010/11/10 08:26:49  Alan
-- R5.06
-- Revision 1.28  2010/07/28 09:12:42  12682
-- Revision 1.27  2010/07/20 01:53:07  12682
-- R5.05.01
-- Revision 1.23  2009/08/26 07:00:07  12682
-- Revision 1.22  2009/08/14 02:23:40  12682
-- Revision 1.21  2009/07/15 07:28:35  12682
-- Revision 1.20  2009/05/06 07:35:52  12682    
-- add sys\ledStatus\ledAlarmStatus
-- Revision 1.19  2009/04/30 03:42:26  12682     
-- add description(1: g711mu(0)2: g711a(8)3: g723(4)4: g729(18)5: g726_16(96)6: g726_24(97)7: g728_32(98)8: g728_40(99)) in voipLineInfoRtpTxPt and voipLineInfoRtpRxPt
-- add statistics\ifStats\ifStatusTable\ifStatusEntry\ifCurrentStatus
-- Revision 1.18  2009/04/21 10:39:14  12682
-- change the description of sipCallSvcProfileStateMask(bit4)
-- Revision 1.17  2009/04/20 06:25:10  12682
-- change the description of sipCallSvcProfileStateMask(bit1 and bit4)
-- Revision 1.16  2009/04/13 06:40:39  12682
-- change description in sys->sysState->systemStatus(sysOverHeat changed to sysTemperatureAbnormal, sysFanRpmLow changed to sysFanRpmAbnormal, sysVoltageLow changed to sysVoltageAbnormal)
-- Revision 1.15  2009/04/03 02:00:37  12682
-- insert dialing_out(5) in voipH248TerminationStatCallServiceState mib object of voipH248TerminationStatTable
-- Revision 1.14  2009/04/03 01:57:07  12682
-- Revision 1.13  2009/03/19 06:26:50  Alan
-- Revision 1.12  2009/03/06 03:35:47  Alan
-- Revision 1.11  2009/03/04 01:46:52  Jennifer
-- Revision 1.10  2009/01/08 06:16:46  Jennifer
-- Revision 1.9  2008/12/18 07:10:50  Jennifer
-- Revision 1.8  2008/11/27 05:55:31  Jennifer
-- Revision 1.7  2008/01/22 06:19:36  11766
-- Add VoIP related MIB (R4.01)
-- Revision 1.5  2007/04/19 08:05:55  11766
-- Add card type msc1024G, alc1272G_51, vop1248G_61
-- Revision 1.4  2006/12/01 07:38:00  11766
-- IES-5000/5005/6000 R3.0
-- Revision 1.1  2005/06/09 00:58:26  jennyhsu
-- Initial revision


ZYXEL-IES5000-MIB DEFINITIONS ::= BEGIN

    IMPORTS

	enterprises, IpAddress, TimeTicks
		FROM RFC1155-SMI
	OBJECT-TYPE, Counter64, Counter32, Gauge32, Unsigned32, Integer32, NOTIFICATION-TYPE          
		FROM SNMPv2-SMI
	DisplayString, PhysAddress, ifIndex
		FROM RFC1213-MIB
	RowStatus, TEXTUAL-CONVENTION
		FROM SNMPv2-TC
	VlanIndex, PortList, dot1qVlanIndex	
		FROM Q-BRIDGE-MIB
	dot1dTrafficClass, EnabledStatus
		FROM P-BRIDGE-MIB
	MacAddress, Timeout, BridgeId, dot1dBasePort
		FROM BRIDGE-MIB
	vdslPhysSide, vdslChanCurrTxRate, vdslLineConfProfileName, vdslLineAlarmConfProfileName
		FROM VDSL-LINE-MIB
	dot1agCfmMdIndex, dot1agCfmMaIndex, dot1agCfmMepIdentifier, dot1agCfmMdMdLevel, dot1agCfmVlanPrimaryVid, dot1agCfmMepIdentifier
		FROM IEEE8021-CFM-MIB 
	InetAddressType, InetAddress
        FROM INET-ADDRESS-MIB           -- RFC4001
	xdsl2PMChHist15MUnit, xdsl2PMChHist15MInterval, xdsl2PMLHist1DUnit, xdsl2PMLHist1DInterval, xdsl2PMLHist15MUnit, xdsl2PMLHist15MInterval, 
	xdsl2PMChHist1DUnit, xdsl2PMChHist1DInterval, xdsl2PMLCurrUnit, xdsl2LConfProfProfileName, xdsl2ChConfProfProfileName, xdsl2LineAlarmConfProfileName, 
	xdsl2LineBand, xdsl2LConfTempTemplateName, xdsl2LAlarmConfTempTemplateName, xdsl2ChAlarmConfProfileName, xdsl2SCStatusDirection, xdsl2SCStatusBand 
		FROM VDSL2-LINE-MIB
	InterfaceIndex
		FROM IF-MIB;

	Xdsl2ConfigRtxMode ::= TEXTUAL-CONVENTION
    STATUS current
	DESCRIPTION
	"Forbidden(0) - Support for G998.4 is disabled.
	 Preferred(1) - If G998.4 is supported by the far-end, it is enabled.
	 Forced(2)    - The line will only train if G998.4 can be enabled.
	 Test(3)      - G998.4 is enabled in test mode (refer to G998.4, Clause 10.4)."
	SYNTAX INTEGER {
	    forbidden(0),
	    preferred(1),
	    forced(2),
	    test(3)
	}
	
	Xdsl2StatusActualRaMode ::= TEXTUAL-CONVENTION
    STATUS      current
    DESCRIPTION
       "fixedRateMode(1) - Fixed rate mode
        raInit(2)        - Adaptive rate mode at initialization
        dynamicRa(3)     - Dynamic rate adaptation
        sosEnabled(4)    - SOS enabled"
    SYNTAX      INTEGER {
        none(0),
        fixedRateMode(1),
        raInit(2),
        dynamicRa(3),
        sosEnabled(4)
    }
    
    Xdsl2StatusRtxMode ::= TEXTUAL-CONVENTION
    STATUS      current
    DESCRIPTION
       "rtxInUse(1)            - RTX in use.
        rtxForbidden(2)        - RTX not in use because RTX_MODE = FORBIDDEN.
        rtxNotSupportedXtuC(3) - RTX not in use because it is not supported by the XTU-C.
        rtxNotSupportedXtuR(4) - RTX not in use because it is not supported by the XTU-R.
        rtxNotSupportedBoth(5) - RTX not in use because it is not supported by the XTU-C and XTU-R."
    SYNTAX      INTEGER {
    	none(0),
        rtxInUse(1),
        rtxForbidden(2),
        rtxNotSupportedXtuC(3),
        rtxNotSupportedXtuR(4),
        rtxNotSupportedBoth(5)
    }
    
    Unsigned64 ::= TEXTUAL-CONVENTION
    STATUS current
    DESCRIPTION
    	"A non-negative 64-bit bit integer, without counter
    	semantics."
    SYNTAX Counter64		

	zyxel		OBJECT IDENTIFIER ::= { enterprises 890 }
    	products	OBJECT IDENTIFIER ::= { zyxel 1 }
	accessSwitch  	OBJECT IDENTIFIER ::= { products 5 }	
	iesSeries	OBJECT IDENTIFIER ::= { accessSwitch 13 }
--	ies5000		OBJECT IDENTIFIER ::= { iesSeries 5 }
	
    ies5000 MODULE-IDENTITY

    LAST-UPDATED "0609010000Z" -- 9/1, 2006
    ORGANIZATION "ZyXEL"
    CONTACT-INFO "EMS"
    DESCRIPTION "ZyXEL Private MIB"
    ::= { iesSeries 5 }
    
	ies5005		OBJECT IDENTIFIER ::= { iesSeries 7 }
	ies6000		OBJECT IDENTIFIER ::= { iesSeries 8 }
	
	acl 		OBJECT IDENTIFIER ::= { ies5000 1 }
	alarmconf 	OBJECT IDENTIFIER ::= { ies5000 2 }
	config 		OBJECT IDENTIFIER ::= { ies5000 3 }
	diagnostic 	OBJECT IDENTIFIER ::= { ies5000 4 }
	ipconf 		OBJECT IDENTIFIER ::= { ies5000 5 }
	lcm 		OBJECT IDENTIFIER ::= { ies5000 6 }
	multicast 	OBJECT IDENTIFIER ::= { ies5000 7 }
	port 		OBJECT IDENTIFIER ::= { ies5000 8 }
	profile 	OBJECT IDENTIFIER ::= { ies5000 9 }
	switch 		OBJECT IDENTIFIER ::= { ies5000 10 }
	sys		OBJECT IDENTIFIER ::= { ies5000 11 }
	trap		OBJECT IDENTIFIER ::= { ies5000 12 }
	statistics	OBJECT IDENTIFIER ::= { ies5000 13 }
	clear		OBJECT IDENTIFIER ::= { ies5000 14 }
	cluster		OBJECT IDENTIFIER ::= { ies5000 15 }
	voip		OBJECT IDENTIFIER ::= { ies5000 16 }
	ima			OBJECT IDENTIFIER ::= { ies5000 17 }
    
----------------------------------------
-- acl
----------------------------------------

	dhcp		OBJECT IDENTIFIER ::= { acl 1 }
	dot1x		OBJECT IDENTIFIER ::= { acl 2 }
	macfilter	OBJECT IDENTIFIER ::= { acl 3 }
	pktfilter	OBJECT IDENTIFIER ::= { acl 4 }
	dhcpSnoop	OBJECT IDENTIFIER ::= { acl 5 }
	aclRule		OBJECT IDENTIFIER ::= { acl 6 }
	pppoeAgent	OBJECT IDENTIFIER ::= { acl 7 }
	dsBcast		OBJECT IDENTIFIER ::= { acl 8 }
	usBcast		OBJECT IDENTIFIER ::= { acl 9 }
	dscpMapping	OBJECT IDENTIFIER ::= { acl 10 }

	macAntiSpoofEnable OBJECT-TYPE
        SYNTAX  INTEGER {
			enable(1),
			disable(2)
		}
        MAX-ACCESS read-write
        STATUS current
        DESCRIPTION
		"Enable/disable MAC anti-spoof."
        ::= { acl 13 }   
        
    subnetvlan		OBJECT IDENTIFIER ::= { acl 14 }
	loopguard		OBJECT IDENTIFIER ::= { acl 15 }        	
	usStorm			OBJECT IDENTIFIER ::= { acl 16 }
	arpInspection 	OBJECT IDENTIFIER ::= { acl 17 }
	macFF 			OBJECT IDENTIFIER ::= { acl 18 }
	dhcpv6  		OBJECT IDENTIFIER ::= { acl 19 }
--------------------
-- DHCP Relay
--------------------

        dhcpRelayEnable OBJECT-TYPE
        SYNTAX  INTEGER {
			auto(1),
			both(2),
			disable(3)
		}
        MAX-ACCESS read-write
        STATUS current
        DESCRIPTION
		"Enable/disable DHCP relay Option82 function. Note that this object
		is obsolete in R1.03 and later versions."
        ::= { dhcp 1 }
                
	dhcpRelay82Table OBJECT-TYPE
        SYNTAX SEQUENCE OF DhcpRelay82Entry
        MAX-ACCESS not-accessible
        STATUS current
        DESCRIPTION
                "A table that contains DHCP Relay configuration."
        ::= { dhcp 2 }

        dhcpRelay82Entry OBJECT-TYPE
        SYNTAX DhcpRelay82Entry
        MAX-ACCESS not-accessible
        STATUS current
        DESCRIPTION
        	"The entry of DHCP Relay table."
        INDEX  { dot1qVlanIndex }
        ::= { dhcpRelay82Table 1 }

        DhcpRelay82Entry ::=
        	SEQUENCE {
        		dhcpRelay82PrimaryServer	IpAddress,
        		dhcpRelay82SecondaryServer	IpAddress,
        		dhcpRelay82ActiveServer		INTEGER,
        		dhcpRelay82Enable		INTEGER,
        		dhcpRelay82Info			DisplayString,
        		dhcpRelay82RelayMode		INTEGER,
        		dhcpRelay82RowStatus		RowStatus,
        		dhcpRelay82Suboption2Enable	INTEGER,
        		dhcpRelay82Suboption2Info	DisplayString,
        		dhcpRelay82Option82Mode		INTEGER
           	}
           
        dhcpRelay82PrimaryServer OBJECT-TYPE
        SYNTAX IpAddress
        MAX-ACCESS read-create
        STATUS current
        DESCRIPTION
		"The IP address of the DHCP Relay primary server."
        ::= { dhcpRelay82Entry 1 }

        dhcpRelay82SecondaryServer OBJECT-TYPE
        SYNTAX IpAddress
        MAX-ACCESS read-create
        STATUS current
        DESCRIPTION
		"The IP address of the DHCP Relay secondary server.
		This object is supported by R1.02 and later versions."
        ::= { dhcpRelay82Entry 2 }

        dhcpRelay82ActiveServer OBJECT-TYPE
        SYNTAX	INTEGER {
        		primary(1),
        		secondary(2)
        	}
        MAX-ACCESS read-create
        STATUS current
        DESCRIPTION
		"The current active DHCP Relay server.
		This object is supported by R1.02 and later versions."
        ::= { dhcpRelay82Entry 3 }

	dhcpRelay82Enable OBJECT-TYPE
        SYNTAX  INTEGER {
			relayEnable-option82Enable(1),
			relayDisable-option82Enable(2),
			disable(3)
		}
        MAX-ACCESS read-create
        STATUS current
        DESCRIPTION
		"Enable/disable DHCP relay and Option82 function.
		This object is supported by R1.03 and later versions."
        ::= { dhcpRelay82Entry 4 }
                        
        dhcpRelay82Info OBJECT-TYPE
        SYNTAX DisplayString (SIZE (0..23))
        MAX-ACCESS read-create
        STATUS current
        DESCRIPTION
		"User specific Option82 information.
		This object is supported by R1.03 and later versions."
        ::= { dhcpRelay82Entry 5 }
        
        dhcpRelay82RelayMode OBJECT-TYPE
        SYNTAX  INTEGER {
			auto(1),
			both(2)
		}
        MAX-ACCESS read-create
        STATUS current
        DESCRIPTION
		"DHCP relay mode.
		This object is supported by R1.03 and later versions."
        ::= { dhcpRelay82Entry 6 }
        
        dhcpRelay82RowStatus OBJECT-TYPE
        SYNTAX RowStatus
        MAX-ACCESS read-create
        STATUS current
        DESCRIPTION
		"Row status of the table entry."
        ::= { dhcpRelay82Entry 7 }
        
        dhcpRelay82Suboption2Enable OBJECT-TYPE
        SYNTAX	INTEGER {
        		enable(1),
        		disable(2)
        	}
        MAX-ACCESS read-create
        STATUS current
        DESCRIPTION
		"Enable/disable Option 82 sub-option 2.
		This object is supported by R3.00 and later versions."
        ::= { dhcpRelay82Entry 8 }
        
        dhcpRelay82Suboption2Info OBJECT-TYPE
        SYNTAX DisplayString
        MAX-ACCESS read-create
        STATUS current
        DESCRIPTION
		"User specified information for Option 82 sub-option 2.
		This object is supported by R3.00 and later versions."
        ::= { dhcpRelay82Entry 9 }	

	dhcpRelay82Option82Mode OBJECT-TYPE
        SYNTAX INTEGER {
        		private(1),
        		tr101(2),
        		tr101PlusVlanInfo(3)
        	}
        MAX-ACCESS read-create
        STATUS current
        DESCRIPTION
		""
        ::= { dhcpRelay82Entry 10 }
        
        
	dhcpRelayInfo OBJECT-TYPE
        SYNTAX DisplayString (SIZE (0..23))
        MAX-ACCESS read-write
        STATUS current
        DESCRIPTION
		"User specific Option82 information. Note that this object
		is obsolete in R1.03 and later versions."
        ::= { dhcp 3 }
        
	maxNumOfDhcpRelay82Conf OBJECT-TYPE
	SYNTAX INTEGER
	MAX-ACCESS read-only
	STATUS current
	DESCRIPTION
		"The maximum number of rows that can be created in dhcpRelay82Table."
	::= { dhcp 4 }
	
	dhcpRelay82Delimiter OBJECT-TYPE
	SYNTAX INTEGER
	MAX-ACCESS read-write
	STATUS current
	DESCRIPTION
		"To configure the ASCII value of the delimiter character."
	::= { dhcp 5 }    
	
	dhcpRelayOption82CheckEnable OBJECT-TYPE
	SYNTAX INTEGER{
		enable(1), 
		disable(2)
	}
	MAX-ACCESS read-write
	STATUS current
	DESCRIPTION
		"Enable/disable system to check option82 in DHCP packets from DHCP server."
	::= { dhcp 6 }

	
--------------------
-- 802.1x
--------------------

	dot1xEnable OBJECT-TYPE
	SYNTAX 	INTEGER {
			enable(1),
			disable(2)
		}
        MAX-ACCESS read-write
	STATUS current
	DESCRIPTION
		"Enable/disable the 802.1x function."
	::= { dot1x 1 }
	
-- Radius Server Table
	
	radiusServerTable OBJECT-TYPE
   	SYNTAX SEQUENCE OF RadiusServerEntry
    	MAX-ACCESS not-accessible
    	STATUS current
    	DESCRIPTION
                "A table that contains Radius Server information."
    	::= { dot1x 2 }

    	radiusServerEntry OBJECT-TYPE
        SYNTAX RadiusServerEntry
        MAX-ACCESS not-accessible
        STATUS current
        DESCRIPTION
        	"The entry of Radius Server table."
        INDEX  { radiusServerIndex }
        ::= { radiusServerTable 1 }

   	RadiusServerEntry ::=
        	SEQUENCE {
            		radiusServerIndex	INTEGER,
            		radiusServerIp		IpAddress,
            		radiusServerPort	INTEGER,
            		radiusServerSecret	DisplayString
    		} 
        
        radiusServerIndex OBJECT-TYPE
        SYNTAX INTEGER
        MAX-ACCESS read-only
        STATUS current
        DESCRIPTION
        	"The identity of the RADIUS server."
        ::= { radiusServerEntry 1 }
        
	radiusServerIp OBJECT-TYPE
	SYNTAX IpAddress
	MAX-ACCESS read-write
	STATUS current
	DESCRIPTION
		"The IP address of the Radius Server."
	::= { radiusServerEntry 2 }

	radiusServerPort OBJECT-TYPE
	SYNTAX INTEGER
	MAX-ACCESS read-write
	STATUS current
	DESCRIPTION
		"The UDP port of the Radius Server."
	::= { radiusServerEntry 3 }
	
	radiusServerSecret OBJECT-TYPE
	SYNTAX DisplayString (SIZE (1..31))
	MAX-ACCESS read-write
	STATUS current
	DESCRIPTION
		"The shared secret of the Radius Server."
	::= { radiusServerEntry 4 }         

-- 802.1x Port Table

        dot1xPortTable OBJECT-TYPE
        SYNTAX SEQUENCE OF Dot1xPortEntry
        MAX-ACCESS not-accessible
        STATUS current
        DESCRIPTION
        	"This table includes 802.1x port configuration."
        ::= { dot1x 3 }

	dot1xPortEntry OBJECT-TYPE
        SYNTAX Dot1xPortEntry
        MAX-ACCESS not-accessible
        STATUS current
        DESCRIPTION
		"An entry in dot1xPortTable."
        INDEX { ifIndex }
        ::= { dot1xPortTable 1 }

        Dot1xPortEntry ::=
        	SEQUENCE {
			dot1xPortEnable	  	INTEGER,
			dot1xPortControl	INTEGER,
			dot1xPortReAuthEnable	INTEGER,
			dot1xPortReAuthPeriod	INTEGER
           	}

        dot1xPortEnable OBJECT-TYPE
        SYNTAX  INTEGER {
			enable(1),
			disable(2)
		}
        MAX-ACCESS read-write
        STATUS current
        DESCRIPTION
                "Enable/disable 802.1x for the port."
         ::= { dot1xPortEntry 1 }
         
        dot1xPortControl OBJECT-TYPE
        SYNTAX  INTEGER {
			auto(1),
			forceAuth(2),
			forceUnAuth(3)
		}
        MAX-ACCESS read-write
        STATUS current
        DESCRIPTION
                "The object defines the 802.1x control type for the port."
         ::= { dot1xPortEntry 2 }

	dot1xPortReAuthEnable OBJECT-TYPE
        SYNTAX  INTEGER {
			enable(1),
			disable(2)
		}
        MAX-ACCESS read-write
        STATUS current
        DESCRIPTION
                "Enable/disable 802.1x re-authentication for the port."
         ::= { dot1xPortEntry 3 }
         
        dot1xPortReAuthPeriod OBJECT-TYPE
        SYNTAX INTEGER (60..65535)
        UNITS "second"
        MAX-ACCESS read-write
        STATUS current
        DESCRIPTION
                "The object defines the 802.1x re-authentication period for the port."
         ::= { dot1xPortEntry 4 }

-- Batch Set for 802.1x

	dot1xBatchSet		OBJECT IDENTIFIER ::= { dot1x 4 }
		
        dot1xTarget OBJECT-TYPE
        SYNTAX OCTET STRING
        MAX-ACCESS read-write
        STATUS current
        DESCRIPTION
		"This managed object is used for identify the target on which 
		the port configuration should be performed. The target is encoded as:
		Byte 1:   the octet specifies a set of eight chassis, chassis 0 through 7
		Byte 2~4: each octet specifies a set of eight slots, with the 
			  first octet specifying slots 1 through 8, and the second
		          octet specifying slots 9 through 16, and so on.
		Byte 5~:  each octet specifies a set of eight ports, with the first
		          octet specifying ports 1 through 8, etc."
        ::= { dot1xBatchSet 1 }
        
        dot1xOps OBJECT-TYPE
        SYNTAX INTEGER
        MAX-ACCESS read-write
        STATUS current
        DESCRIPTION
		"The corresponding bit is set to 1 to start the operation.
		The various bit positions are:
		BIT 1: enable dot1x
		BIT 2: disable dot1x
		BIT 3: set dot1x control to be auto
		BIT 4: set dot1x control to be forceAuth
		BIT 5: set dot1x control to be forceUnAuth
		BIT 6: enable dot1x re-authentication
		BIT 7: disable dot1x re-authentication
		BIT 8: set dot1x re-authentication period."
        ::= { dot1xBatchSet 2 }

        dot1xReAuthPeriodForBatchSet OBJECT-TYPE
        SYNTAX INTEGER (60..65535)
        UNITS "second"
        MAX-ACCESS read-write
        STATUS current
        DESCRIPTION
                "The object defines the 802.1x re-authentication period for batch setting."
         ::= { dot1xBatchSet 3 }
                 
--------------------
-- MAC Filter
--------------------

-- MAC Filter Port Table

        macFilterPortTable OBJECT-TYPE
        SYNTAX SEQUENCE OF MacFilterPortEntry
        MAX-ACCESS not-accessible
        STATUS current
        DESCRIPTION
        	"This table includes the status of mac filtering for each port."
        ::= { macfilter 1 }

	macFilterPortEntry OBJECT-TYPE
        SYNTAX MacFilterPortEntry
        MAX-ACCESS not-accessible
        STATUS current
        DESCRIPTION
		"An entry in macFilterPortTable."
        INDEX { ifIndex }
        ::= { macFilterPortTable 1 }

        MacFilterPortEntry ::=
        	SEQUENCE {
			macFilterPortEnable	INTEGER,
			macFilterPortMacCount	INTEGER,
			macFilterPortFilterMode	INTEGER
           	}

        macFilterPortEnable OBJECT-TYPE
        SYNTAX  INTEGER {
			enableMacFilter(1),
			enableMacCount(2),
			enableOuiFilter(3),
			disable(4)
		}
        MAX-ACCESS read-write
        STATUS current
        DESCRIPTION
                "Enable/disable MAC filtering for the port."
         ::= { macFilterPortEntry 1 }

        macFilterPortMacCount OBJECT-TYPE
        SYNTAX INTEGER
        MAX-ACCESS read-write
        STATUS current
        DESCRIPTION
                "The total number of MAC addresses allowed for the port."
         ::= { macFilterPortEntry 2 }
 
        macFilterPortFilterMode OBJECT-TYPE
        SYNTAX	INTEGER {
        		accept(1),
        		deny(2)
        	}
        MAX-ACCESS read-write
        STATUS current
        DESCRIPTION
                "The mac filter mode (accept or deny) for the port.
                This object is supported by R1.02 and later versions."
         ::= { macFilterPortEntry 3 }
                 	
	maxNumOfMacFiltersInSystem OBJECT-TYPE
	SYNTAX INTEGER
	MAX-ACCESS read-only
	STATUS current
	DESCRIPTION
		"The max number of mac filters supported in the system."
	::= { macfilter 2 }

	maxNumOfMacFiltersPerPort OBJECT-TYPE
	SYNTAX INTEGER
	MAX-ACCESS read-only
	STATUS current
	DESCRIPTION
		"The max number of mac filters supported per port."
	::= { macfilter 3 }

	currNumOfMacFiltersInSystem OBJECT-TYPE
	SYNTAX INTEGER
	MAX-ACCESS read-only
	STATUS current
	DESCRIPTION
		"The current number of mac filters in the system."
	::= { macfilter 4 }

-- MAC Table

	macFilterTable OBJECT-TYPE
   	SYNTAX SEQUENCE OF MacFilterEntry
    	MAX-ACCESS not-accessible
    	STATUS current
    	DESCRIPTION
                "A table that contains the mac filter addresses."
    	::= { macfilter 5 }

    	macFilterEntry OBJECT-TYPE
        SYNTAX MacFilterEntry
        MAX-ACCESS not-accessible
        STATUS current
        DESCRIPTION
        	"The entry of macFilterTable."
        INDEX { ifIndex, macFilterAddr }
        ::= { macFilterTable 1 }

   	MacFilterEntry ::=
        	SEQUENCE {
	    		macFilterAddr		PhysAddress,
	    		macFilterRowStatus	RowStatus
    	   	} 
        
        macFilterAddr OBJECT-TYPE
        SYNTAX PhysAddress
        MAX-ACCESS read-only
        STATUS current
        DESCRIPTION
        	"The mac address which can pass through or be rejected from the port."
        ::= { macFilterEntry 1 }
        
	macFilterRowStatus OBJECT-TYPE
	SYNTAX RowStatus
	MAX-ACCESS read-create
	STATUS current
	DESCRIPTION
		"The row status of the entry."
	::= { macFilterEntry 2 }

-- Batch Set for MAC Filter

	macfilterBatchSet		OBJECT IDENTIFIER ::= { macfilter 6 }
		
        macfilterTarget OBJECT-TYPE
        SYNTAX OCTET STRING
        MAX-ACCESS read-write
        STATUS current
        DESCRIPTION
		"This managed object is used for identify the target on which 
		the port configuration should be performed. The target is encoded as:
		Byte 1:   the octet specifies a set of eight chassis, chassis 0 through 7
		Byte 2~4: each octet specifies a set of eight slots, with the 
			  first octet specifying slots 1 through 8, and the second
		          octet specifying slots 9 through 16, and so on.
		Byte 5~:  each octet specifies a set of eight ports, with the first
		          octet specifying ports 1 through 8, etc."
        ::= { macfilterBatchSet 1 }
        
        macfilterOps OBJECT-TYPE
        SYNTAX INTEGER
        MAX-ACCESS read-write
        STATUS current
        DESCRIPTION
		"The corresponding bit is set to 1 to start the operation.
		The various bit positions are:
		BIT 1: enable mac filter
		BIT 2: enable mac count filter
		BIT 3: disable mac filter
		BIT 4: set mac count."
        ::= { macfilterBatchSet 2 }

        macFilterMacCountForBatchSet OBJECT-TYPE
        SYNTAX INTEGER (1..128)
        MAX-ACCESS read-write
        STATUS current
        DESCRIPTION
                "The total number of MAC addresses allowed for a port."
         ::= { macfilterBatchSet 3 }

-- OUI Filter Table

	ouiFilterTable OBJECT-TYPE
   	SYNTAX SEQUENCE OF OuiFilterEntry
    	MAX-ACCESS not-accessible
    	STATUS current
    	DESCRIPTION
                "A table that contains the OUI filter addresses."
    	::= { macfilter 7 }

    	ouiFilterEntry OBJECT-TYPE
        SYNTAX OuiFilterEntry
        MAX-ACCESS not-accessible
        STATUS current
        DESCRIPTION
        	"The entry of ouiFilterTable."
        INDEX { ifIndex, ouiFilterAddr }
        ::= { ouiFilterTable 1 }

   	OuiFilterEntry ::=
        	SEQUENCE {
	    		ouiFilterAddr		OCTET STRING,
	    		ouiFilterRowStatus	RowStatus
    	   	} 
        
        ouiFilterAddr OBJECT-TYPE
        SYNTAX OCTET STRING
        MAX-ACCESS read-only
        STATUS current
        DESCRIPTION
        	"The first three bytes of the mac address which can pass through or be rejected from the port."
        ::= { ouiFilterEntry 1 }
        
	ouiFilterRowStatus OBJECT-TYPE
	SYNTAX RowStatus
	MAX-ACCESS read-create
	STATUS current
	DESCRIPTION
		"The row status of the entry."
	::= { ouiFilterEntry 2 }

	maxNumOfOuiFiltersPerPort OBJECT-TYPE
	SYNTAX INTEGER
	MAX-ACCESS read-only
	STATUS current
	DESCRIPTION
		"The max number of OUI filters supported per port."
	::= { macfilter 8 }

-- macFilterStatusTable

	macFilterStatusTable OBJECT-TYPE
   	SYNTAX SEQUENCE OF MacFilterStatusEntry
    	MAX-ACCESS not-accessible
    	STATUS current
    	DESCRIPTION
                "A table that contains the mac filter addresses."
    	::= { macfilter 9 }

    	macFilterStatusEntry OBJECT-TYPE
        SYNTAX MacFilterStatusEntry
        MAX-ACCESS not-accessible
        STATUS current
        DESCRIPTION
        	"The entry of macFilterStatusTable."
        INDEX { ifIndex, macFilterStatusId }
        ::= { macFilterStatusTable 1 }

   	MacFilterStatusEntry ::=
        	SEQUENCE {
        		macFilterStatusId	INTEGER,
	    		macFilterStatusAddr	PhysAddress
    	   	} 

	macFilterStatusId OBJECT-TYPE
	SYNTAX INTEGER
	MAX-ACCESS read-only
	STATUS current
	DESCRIPTION
		"The index of the entry."
	::= { macFilterStatusEntry 1 }
	       
        macFilterStatusAddr OBJECT-TYPE
        SYNTAX PhysAddress
        MAX-ACCESS read-only
        STATUS current
        DESCRIPTION
        	"The mac address which can pass through or be rejected from the port."
        ::= { macFilterStatusEntry 2 }

-- macFilterPerPVCTable 

	macFilterPerPVCTable  OBJECT-TYPE
   	SYNTAX SEQUENCE OF MacFilterPerPVCEntry
    	MAX-ACCESS not-accessible
    	STATUS current
    	DESCRIPTION
                "A table for per-PVC macfilter configuration."
    	::= { macfilter 10 }

    macFilterPerPVCEntry OBJECT-TYPE
        SYNTAX MacFilterPerPVCEntry
        MAX-ACCESS not-accessible
        STATUS current
        DESCRIPTION
        	"The entry of macFilterPerPVCTable."
        INDEX { ifIndex, macFilterPerPVCVpi, macFilterPerPVCVci }
        ::= { macFilterPerPVCTable 1 }

   	MacFilterPerPVCEntry ::=
        	SEQUENCE {
        		macFilterPerPVCVpi				INTEGER,
        		macFilterPerPVCVci				INTEGER,
        		macFilterPerPVCEnable		INTEGER,
	    		macFilterPerPVCMode				INTEGER,
	    		macFilterPerPVCMacCount				INTEGER
    	   	} 
    macFilterPerPVCVpi OBJECT-TYPE
    SYNTAX INTEGER (0..255)
    MAX-ACCESS read-only
    STATUS current
    DESCRIPTION
          "VPI of the pvc."
    ::= { macFilterPerPVCEntry 1 }

    macFilterPerPVCVci OBJECT-TYPE
    SYNTAX INTEGER (1..65535)
    MAX-ACCESS read-only
    STATUS current
    DESCRIPTION
          "VCI of the pvc."
    ::= { macFilterPerPVCEntry 2 }
    
	macFilterPerPVCEnable OBJECT-TYPE
	SYNTAX INTEGER{
		enablePvcMacFilter(1),
		enablePvcMacCount(2),
		disable(3)
    }
	MAX-ACCESS read-write
	STATUS current
	DESCRIPTION
		"Enable/disable MAC filtering for the port-vpi/vci"
	::= { macFilterPerPVCEntry 3 }
	       
    macFilterPerPVCMode OBJECT-TYPE
	SYNTAX INTEGER{
		accept(1),
       	deny(2)
	}
	MAX-ACCESS read-write
	STATUS current
	DESCRIPTION
		"The mac filter mode (accept or deny) for the port-vpi/vci."
	::= { macFilterPerPVCEntry 4 }
	
    macFilterPerPVCMacCount OBJECT-TYPE
        SYNTAX INTEGER
        MAX-ACCESS read-write
        STATUS current
        DESCRIPTION
                "The total number of MAC addresses allowed for the port-vpi/vci."
         ::= { macFilterPerPVCEntry 5 }
 

	
-- macFilterPerPVCMACTable  

	macFilterPerPVCMACTable  OBJECT-TYPE
   	SYNTAX SEQUENCE OF MacFilterPerPVCMACEntry
    	MAX-ACCESS not-accessible
    	STATUS current
    	DESCRIPTION
                "A table for per-PVC macfilter configuration."
    	::= { macfilter 11 }

    macFilterPerPVCMACEntry OBJECT-TYPE
        SYNTAX MacFilterPerPVCMACEntry
        MAX-ACCESS not-accessible
        STATUS current
        DESCRIPTION
        	"The entry of macFilterPerPVCMACTable."
        INDEX { ifIndex, macFilterPerPVCMACVpi, macFilterPerPVCMACVci, macFilterPerPVCMACAddr  }
        ::= { macFilterPerPVCMACTable 1 }

   	MacFilterPerPVCMACEntry ::=
        	SEQUENCE {
        		macFilterPerPVCMACVpi				INTEGER,
        		macFilterPerPVCMACVci				INTEGER,
        		macFilterPerPVCMACAddr		PhysAddress,
	    		macFilterPerPVCMACRowStatus			RowStatus
    	   	} 
    
    macFilterPerPVCMACVpi OBJECT-TYPE
    SYNTAX INTEGER (0..255)
    MAX-ACCESS read-only
    STATUS current
    DESCRIPTION
          "VPI of the pvc."
    ::= { macFilterPerPVCMACEntry 1 }

    macFilterPerPVCMACVci OBJECT-TYPE
    SYNTAX INTEGER (1..65535)
    MAX-ACCESS read-only
    STATUS current
    DESCRIPTION
          "VCI of the pvc."
    ::= { macFilterPerPVCMACEntry 2 }
         
	macFilterPerPVCMACAddr OBJECT-TYPE
	SYNTAX PhysAddress
	MAX-ACCESS read-only
	STATUS current
	DESCRIPTION
		"The mac address which can pass through or be rejected from the port-vpi/vci"
	::= { macFilterPerPVCMACEntry 3 }
	       
    macFilterPerPVCMACRowStatus OBJECT-TYPE
	SYNTAX RowStatus
	MAX-ACCESS read-write
	STATUS current
	DESCRIPTION
		"The row status of the entry."
	::= { macFilterPerPVCMACEntry 4 }		         
--------------------
-- Packet Filter
--------------------

        pktFilterPortTable OBJECT-TYPE
        SYNTAX SEQUENCE OF PktFilterPortEntry
        MAX-ACCESS not-accessible
        STATUS current
        DESCRIPTION
        	"This table includes packet filtering for each port."
        ::= { pktfilter 1 }

	pktFilterPortEntry OBJECT-TYPE
        SYNTAX PktFilterPortEntry
        MAX-ACCESS not-accessible
        STATUS current
        DESCRIPTION
		"An entry in pktFilterPortTable."
        INDEX { ifIndex }
        ::= { pktFilterPortTable 1 }

        PktFilterPortEntry ::=
        	SEQUENCE {
			pktFilter	INTEGER
           	}

        pktFilter OBJECT-TYPE
        SYNTAX INTEGER
        MAX-ACCESS read-write
        STATUS current
        DESCRIPTION
                "The packet filter. The semantic for each bit is:
                      	BIT 1: accept all
                      	BIT 2: accept PPPoE only
                      	BIT 3: reject ARP
                      	BIT 4: reject DHCP
			BIT 5: reject EAPOL
                      	BIT 6: reject PPPoE
			BIT 7: reject NetBIOS
			BIT 8: reject IGMP
			BIT 9: reject IP"
         ::= { pktFilterPortEntry 1 }

-- Batch Set for Packet Filter

	pktfilterBatchSet		OBJECT IDENTIFIER ::= { pktfilter 2 }
		
        pktfilterTarget OBJECT-TYPE
        SYNTAX OCTET STRING
        MAX-ACCESS read-write
        STATUS current
        DESCRIPTION
		"This managed object is used for identify the target on which 
		the port configuration should be performed. The target is encoded as:
		Byte 1:   the octet specifies a set of eight chassis, chassis 0 through 7
		Byte 2~4: each octet specifies a set of eight slots, with the 
			  first octet specifying slots 1 through 8, and the second
		          octet specifying slots 9 through 16, and so on.
		Byte 5~:  each octet specifies a set of eight ports, with the first
		          octet specifying ports 1 through 8, etc."
        ::= { pktfilterBatchSet 1 }
        
        pktfilterOps OBJECT-TYPE
        SYNTAX INTEGER
        MAX-ACCESS read-write
        STATUS current
        DESCRIPTION
		"The corresponding bit is set to 1 to start the operation.
		The various bit positions are:
		BIT 1: set packet filter."
        ::= { pktfilterBatchSet 2 }

        pktfilterForBatchSet OBJECT-TYPE
        SYNTAX INTEGER
        MAX-ACCESS read-write
        STATUS current
        DESCRIPTION
                "The packet filter for batch setting. The semantic for each bit is identical to the object pktFilter."
         ::= { pktfilterBatchSet 3 }
 
 -- pktFilterPerPVCTable 
 pktFilterPerPVCTable  OBJECT-TYPE
        SYNTAX SEQUENCE OF PktFilterPerPVCEntry
        MAX-ACCESS not-accessible
        STATUS current
        DESCRIPTION
        	"This table includes per-PVC packet filter configuration."
        ::= { pktfilter 3 }

	pktFilterPerPVCEntry OBJECT-TYPE
        SYNTAX PktFilterPerPVCEntry
        MAX-ACCESS not-accessible
        STATUS current
        DESCRIPTION
		"An entry in pktFilterPerPVCTable."
        INDEX { ifIndex, pktFilterPerPVCVpi, pktFilterPerPVCVci }
        ::= { pktFilterPerPVCTable 1 }

        PktFilterPerPVCEntry ::=
        	SEQUENCE {
        	pktFilterPerPVCVpi 			INTEGER,
        	pktFilterPerPVCVci          INTEGER,
			pktFilterPerPVCpktFilter	INTEGER
           	}
           	
        pktFilterPerPVCVpi OBJECT-TYPE
	    SYNTAX INTEGER (0..255)
	    MAX-ACCESS read-only
	    STATUS current
	    DESCRIPTION
	          "VPI of the pvc."
	    ::= { pktFilterPerPVCEntry 1 }
	
	    pktFilterPerPVCVci OBJECT-TYPE
	    SYNTAX INTEGER (1..65535)
	    MAX-ACCESS read-only
	    STATUS current
	    DESCRIPTION
	          "VCI of the pvc."
	    ::= { pktFilterPerPVCEntry 2 }

        pktFilterPerPVCpktFilter OBJECT-TYPE
        SYNTAX INTEGER
        MAX-ACCESS read-write
        STATUS current
        DESCRIPTION
                "The packet filter. The semantic for each bit is:
                BIT 1: accept all
                BIT 2: accept PPPoE only
                BIT 3: reject ARP
                BIT 4: reject DHCP
                BIT 5: reject EAPOL
                BIT 6: reject PPPoE
                BIT 7: reject NetBIOS
                BIT 8: reject IGMP
                BIT 9: reject IP"
         ::= { pktFilterPerPVCEntry 3 }

--------------------
-- DHCP Snoop
--------------------

-- dhcpSnoopPortTable

        dhcpSnoopPortTable OBJECT-TYPE
        SYNTAX SEQUENCE OF DhcpSnoopPortEntry
        MAX-ACCESS not-accessible
        STATUS current
        DESCRIPTION
        	"This table includes DHCP snooping enable/disable for each port.
        	This table is supported by R1.02 and later versions."
        ::= { dhcpSnoop 1 }

	dhcpSnoopPortEntry OBJECT-TYPE
        SYNTAX DhcpSnoopPortEntry
        MAX-ACCESS not-accessible
        STATUS current
        DESCRIPTION
		"An entry of dhcpSnoopPortTable."
        INDEX { ifIndex }
        ::= { dhcpSnoopPortTable 1 }

        DhcpSnoopPortEntry ::=
        	SEQUENCE {
			dhcpSnoopEnable		INTEGER
           	}

        dhcpSnoopEnable OBJECT-TYPE
        SYNTAX  INTEGER {
        		enable(1),
        		disable(2)
        	}
        MAX-ACCESS read-write
        STATUS current
        DESCRIPTION
                "Enable/disable DHCP snooping for a port."
         ::= { dhcpSnoopPortEntry 1 }

-- dhcpSnoopOperation

        dhcpSnoopTarget OBJECT-TYPE
        SYNTAX OCTET STRING
        MAX-ACCESS read-write
        STATUS current
        DESCRIPTION
		"This managed object is used for identify the target on which 
		the operation should be performed. The target is encoded as:
		Byte 1:   the octet specifies a set of eight chassis, chassis 0 through 7
		Byte 2~4: each octet specifies a set of eight slots, with the 
			  first octet specifying slots 1 through 8, and the second
		          octet specifying slots 9 through 16, and so on.
		Byte 5~:  each octet specifies a set of eight ports, with the first
		          octet specifying ports 1 through 8, etc."
        ::= { dhcpSnoop 2 }
        
        dhcpSnoopOps OBJECT-TYPE
        SYNTAX INTEGER
        MAX-ACCESS read-write
        STATUS current
        DESCRIPTION
		"The corresponding bit is set to 1 to start the operation.
		The various bit positions are:
		BIT 1: DHCP snooping table flush."
        ::= { dhcpSnoop 3 }

-- dhcpStaticTable

        dhcpStaticTable OBJECT-TYPE
        SYNTAX SEQUENCE OF DhcpStaticEntry
        MAX-ACCESS not-accessible
        STATUS current
        DESCRIPTION
        	"This table defines DHCP static IP addresses.
        	This table is supported by R1.03 and later versions."
        ::= { dhcpSnoop 4 }

	dhcpStaticEntry OBJECT-TYPE
        SYNTAX DhcpStaticEntry
        MAX-ACCESS not-accessible
        STATUS current
        DESCRIPTION
		"An entry of dhcpStaticTable."
        INDEX { ifIndex, dhcpStaticIpAddr }
        ::= { dhcpStaticTable 1 }

        DhcpStaticEntry ::=
        	SEQUENCE {
			dhcpStaticIpAddr	IpAddress,
			dhcpStaticRowStatus	RowStatus
           	}

        dhcpStaticIpAddr OBJECT-TYPE
        SYNTAX IpAddress
        MAX-ACCESS read-only
        STATUS current
        DESCRIPTION
                "The IP address which can pass through the port."
        ::= { dhcpStaticEntry 1 }
        
        dhcpStaticRowStatus OBJECT-TYPE
        SYNTAX RowStatus
        MAX-ACCESS read-create
        STATUS current
        DESCRIPTION
                "Row status of the table entry."
        ::= { dhcpStaticEntry 2 }
         
        maxNumOfDhcpStaticIp OBJECT-TYPE
        SYNTAX INTEGER
        MAX-ACCESS read-only
        STATUS current
        DESCRIPTION
                "The maximum number of DHCP static IP addresses which can be created for a port.
                This object is supported by R1.03 and later versions."
         ::= { dhcpSnoop 5 }
 
 -- dhcpSnoopLan2lanTable         
		dhcpSnoopLan2lanTable OBJECT-TYPE
        SYNTAX SEQUENCE OF DhcpSnoopLan2lanEntry
        MAX-ACCESS not-accessible
        STATUS current
        DESCRIPTION
                "Support DHCP lan2lan to prevent DHCP service hack 
                if customer installed DHCP server in its subscriber network. 
                This table is supported by R5.05 and later versions."
        ::= { dhcpSnoop 6 }

        dhcpSnoopLan2lanEntry OBJECT-TYPE
        SYNTAX DhcpSnoopLan2lanEntry
        MAX-ACCESS not-accessible
        STATUS current
        DESCRIPTION
        	"The entry of dhcpSnoopLan2lanTable."
        INDEX  { ifIndex }
        ::= { dhcpSnoopLan2lanTable 1 }

        DhcpSnoopLan2lanEntry ::=
        	SEQUENCE {
        		dhcpSnoopLan2lanEnable	INTEGER
           	}

		dhcpSnoopLan2lanEnable OBJECT-TYPE
        SYNTAX  INTEGER {
        		enable(1),
        		disable(2)
        	}
        MAX-ACCESS read-write
        STATUS current
        DESCRIPTION
		"Enable/disable DHCP server on subscriber port"
        ::= { dhcpSnoopLan2lanEntry 1 }          
--------------------
-- aclRule
--------------------

-- aclSetTable

        aclSetTable OBJECT-TYPE
        SYNTAX SEQUENCE OF AclSetEntry
        MAX-ACCESS not-accessible
        STATUS current
        DESCRIPTION
        	"This table is supported by R1.03 and later versions."
        ::= { aclRule 1 }

	aclSetEntry OBJECT-TYPE
        SYNTAX AclSetEntry
        MAX-ACCESS not-accessible
        STATUS current
        DESCRIPTION
		"An entry of aclSetTable."
        INDEX { ifIndex, aclSetVpi, aclSetVci, IMPLIED aclSetProfileName }
        ::= { aclSetTable 1 }

        AclSetEntry ::=
           SEQUENCE {
		aclSetVpi		INTEGER,
		aclSetVci       	INTEGER,
		aclSetProfileName  	DisplayString,
		aclSetRowStatus		RowStatus
           }

	aclSetVpi OBJECT-TYPE
        SYNTAX INTEGER
        MAX-ACCESS read-only
        STATUS current
        DESCRIPTION
        	"VPI value."
        ::= { aclSetEntry 1 }

        aclSetVci OBJECT-TYPE
        SYNTAX INTEGER
        MAX-ACCESS read-only
        STATUS current
        DESCRIPTION
        	"VCI value."
        ::= { aclSetEntry 2 }

        aclSetProfileName OBJECT-TYPE
        SYNTAX DisplayString
        MAX-ACCESS read-only
        STATUS current
        DESCRIPTION
        	"ACL Profile name."
        ::= { aclSetEntry 3 }

        aclSetRowStatus OBJECT-TYPE
        SYNTAX RowStatus
        MAX-ACCESS read-create
        STATUS current
        DESCRIPTION
         	"RowStatus of aclSetEntry."
        ::= { aclSetEntry 4 }

-- aclNoMatchTable

        aclNoMatchTable OBJECT-TYPE
        SYNTAX SEQUENCE OF AclNoMatchEntry
        MAX-ACCESS not-accessible
        STATUS current
        DESCRIPTION
        	"This table is supported by R5.02 and later versions."
        ::= { aclRule 2 }

	aclNoMatchEntry OBJECT-TYPE
        SYNTAX AclNoMatchEntry
        MAX-ACCESS not-accessible
        STATUS current
        DESCRIPTION
		"An entry of aclNoMatchTable."
        INDEX { ifIndex }
        ::= { aclNoMatchTable 1 }

        AclNoMatchEntry ::=
           SEQUENCE {
		aclNoMatchAction	INTEGER
           }

	aclNoMatchAction OBJECT-TYPE
        SYNTAX  INTEGER {
        		accept(1),
        		deny(2)
        	}
        MAX-ACCESS read-write
        STATUS current
        DESCRIPTION
        	"Pass or drop the packet."
        ::= { aclNoMatchEntry 1 }

--------------------
-- PPPoE Agent
--------------------

-- pppoeAgentTable

        pppoeAgentTable OBJECT-TYPE
        SYNTAX SEQUENCE OF PppoeAgentEntry
        MAX-ACCESS not-accessible
        STATUS current
        DESCRIPTION
        	"A table that contains PPPoE DHCP Relay configuration.
        	This table is supported by R1.03 and later versions."
        ::= { pppoeAgent 1 }

	pppoeAgentEntry OBJECT-TYPE
        SYNTAX PppoeAgentEntry
        MAX-ACCESS not-accessible
        STATUS current
        DESCRIPTION
		"An entry of pppoeAgentTable."
        INDEX { dot1qVlanIndex }
        ::= { pppoeAgentTable 1 }

        PppoeAgentEntry ::=
           SEQUENCE {
        		pppoeAgentEnable		INTEGER,
        		pppoeAgentInfo			DisplayString,
        		pppoeAgentRowStatus		RowStatus,
        		pppoeAgentOptionMode		INTEGER
           	}

	pppoeAgentEnable OBJECT-TYPE
        SYNTAX  INTEGER {
			enable(1),
			disable(2)
		}
        MAX-ACCESS read-create
        STATUS current
        DESCRIPTION
		"Enable/disable DHCP relay and Option82 function."
        ::= { pppoeAgentEntry 1 }
                        
        pppoeAgentInfo OBJECT-TYPE
        SYNTAX DisplayString (SIZE (0..23))
        MAX-ACCESS read-create
        STATUS current
        DESCRIPTION
		"User specific Option82 information."
        ::= { pppoeAgentEntry 2 }
        
        pppoeAgentRowStatus OBJECT-TYPE
        SYNTAX RowStatus
        MAX-ACCESS read-create
        STATUS current
        DESCRIPTION
		"Row status of the table entry."
        ::= { pppoeAgentEntry 3 }	

	pppoeAgentOptionMode OBJECT-TYPE
        SYNTAX INTEGER {
        		private(1),
        		tr101(2),
        		tr101PlusVlanInfo(3)
        	}
        MAX-ACCESS read-create
        STATUS current
        DESCRIPTION
		""
        ::= { pppoeAgentEntry 4 }
        
        
	maxNumOfPppoeDhcpRelay82Conf OBJECT-TYPE
	SYNTAX INTEGER
	MAX-ACCESS read-only
	STATUS current
	DESCRIPTION
		"The maximum number of rows that can be created in pppoeAgentTable."
	::= { pppoeAgent 2 } 
	
	pppoeAgentDelimiter OBJECT-TYPE
	SYNTAX INTEGER
	MAX-ACCESS read-write
	STATUS current
	DESCRIPTION
		"To configure the ASCII value of the delimiter character."
	::= { pppoeAgent 3 }
        
--------------------
-- Downstream Broadcast
--------------------

-- dsBcastTable

        dsBcastTable OBJECT-TYPE
        SYNTAX SEQUENCE OF DsBcastEntry
        MAX-ACCESS not-accessible
        STATUS current
        DESCRIPTION
        	"A table that contains downstream broadcast forbidden configuration.
        	This table is supported by R3.00 and later versions."
        ::= { dsBcast 1 }

	dsBcastEntry OBJECT-TYPE
        SYNTAX DsBcastEntry
        MAX-ACCESS not-accessible
        STATUS current
        DESCRIPTION
		"An entry of dsBcastTable."
        INDEX { ifIndex, dot1qVlanIndex }
        ::= { dsBcastTable 1 }

        DsBcastEntry ::=
           SEQUENCE {
        		dsBcastRowStatus	RowStatus
           	}

	dsBcastRowStatus OBJECT-TYPE
        SYNTAX RowStatus
        MAX-ACCESS read-create
        STATUS current
        DESCRIPTION
		"Row status of the table entry."
        ::= { dsBcastEntry 1 }

--------------------
-- Upstream Broadcast
--------------------

	usBcastCtrlEnable OBJECT-TYPE
        SYNTAX INTEGER {
        		enable(1),
        		disable(2)
        	}
        MAX-ACCESS read-write
        STATUS current
        DESCRIPTION
		"Enable/disable upstream broadcast control."
        ::= { usBcast 1 }
        
        usBcastCtrlRate OBJECT-TYPE
        SYNTAX INTEGER
        UNITS "Kbps"
        MAX-ACCESS read-write
        STATUS current
        DESCRIPTION
		""
        ::= { usBcast 2 }

--------------------
-- DSCP
--------------------

-- dscpMappingTable

	dscpMappingTable OBJECT-TYPE
	SYNTAX SEQUENCE OF DscpMappingEntry
	MAX-ACCESS not-accessible
	STATUS current
	DESCRIPTION
		"The table contains DSCP mapping configuration."
	::= { dscpMapping 1 }
			
	dscpMappingEntry OBJECT-TYPE
	SYNTAX DscpMappingEntry
	MAX-ACCESS not-accessible
	STATUS current
	DESCRIPTION
		"An entry of dscpMappingTable."
	INDEX { dscpMappingSrcCodePoint }
	::= { dscpMappingTable 1 }
			
	DscpMappingEntry ::=
		SEQUENCE {
			dscpMappingSrcCodePoint	INTEGER,
			dscpMappingMapPriority	INTEGER
		}
	
	dscpMappingSrcCodePoint OBJECT-TYPE
	SYNTAX INTEGER
	MAX-ACCESS read-only
	STATUS current
	DESCRIPTION
		"The DSCP source code point used for mapping."
	::= { dscpMappingEntry 1 }
	
	dscpMappingMapPriority OBJECT-TYPE
	SYNTAX INTEGER (0..7)
	MAX-ACCESS read-write
	STATUS current
	DESCRIPTION
		"The mapping p bits that will replace the source p bits in the incoming packet."
	::= { dscpMappingEntry 2 }

-- dscpPortTable

	dscpPortTable OBJECT-TYPE
	SYNTAX SEQUENCE OF DscpPortEntry
	MAX-ACCESS not-accessible
	STATUS current
	DESCRIPTION
		"The table contains DSCP port configuration."
	::= { dscpMapping 2 }
			
	dscpPortEntry OBJECT-TYPE
	SYNTAX DscpPortEntry
	MAX-ACCESS not-accessible
	STATUS current
	DESCRIPTION
		"An entry of dscpPortTable."
	INDEX { ifIndex }
	::= { dscpPortTable 1 }
			
	DscpPortEntry ::=
		SEQUENCE {
			dscpPortEnable	INTEGER
		}
	
	dscpPortEnable OBJECT-TYPE
	SYNTAX INTEGER {
			enable(1),
			disable(2)
		}
	MAX-ACCESS read-write
	STATUS current
	DESCRIPTION
		"Enable/disable DSCP."
	::= { dscpPortEntry 1 } 
	
--------------------
-- Subnet VLAN
--------------------

        subnetvlanStatus OBJECT-TYPE
        SYNTAX  INTEGER {
			enable(1),
			disable(2)
		}
        MAX-ACCESS read-write
        STATUS current
        DESCRIPTION
		""
        ::= { subnetvlan 1 }

-- subnetvlanTable                
	subnetvlanTable OBJECT-TYPE
        SYNTAX SEQUENCE OF SubnetvlanEntry
        MAX-ACCESS not-accessible
        STATUS current
        DESCRIPTION
                "A table that contains subnet vlan configuration."
        ::= { subnetvlan 2 }

        subnetvlanEntry OBJECT-TYPE
        SYNTAX SubnetvlanEntry
        MAX-ACCESS not-accessible
        STATUS current
        DESCRIPTION
        	"The entry of subnet vlan table."
        INDEX  { subnetvlanIp, subnetvlanMask, subnetvlanVid, subnetvlanPriority }
        ::= { subnetvlanTable 1 }

        SubnetvlanEntry ::=
        	SEQUENCE {
        		subnetvlanIp	IpAddress,
        		subnetvlanMask	INTEGER,
        		subnetvlanVid		INTEGER,
        		subnetvlanPriority	INTEGER,
        		subnetvlanName		DisplayString,
        		subnetvlanRowStatus	RowStatus
           	}
           
        subnetvlanIp OBJECT-TYPE
        SYNTAX IpAddress
        MAX-ACCESS read-only
        STATUS current
        DESCRIPTION
		""
        ::= { subnetvlanEntry 1 }

        subnetvlanMask OBJECT-TYPE
        SYNTAX INTEGER
        MAX-ACCESS read-only
        STATUS current
        DESCRIPTION
		""
        ::= { subnetvlanEntry 2 }

        subnetvlanVid OBJECT-TYPE
        SYNTAX	INTEGER (1..4094)
        MAX-ACCESS read-only
        STATUS current
        DESCRIPTION
		""
        ::= { subnetvlanEntry 3 }

		subnetvlanPriority OBJECT-TYPE
        SYNTAX  INTEGER (0..7)
        MAX-ACCESS read-only
        STATUS current
        DESCRIPTION
		""
        ::= { subnetvlanEntry 4 }
                        
        subnetvlanName OBJECT-TYPE
        SYNTAX DisplayString (SIZE (0..31))
        MAX-ACCESS read-create
        STATUS current
        DESCRIPTION
		""
        ::= { subnetvlanEntry 5 }
        
        subnetvlanRowStatus OBJECT-TYPE
        SYNTAX RowStatus
        MAX-ACCESS read-create
        STATUS current
        DESCRIPTION
		"Row status of the table entry."
        ::= { subnetvlanEntry 6 }
        
-- subnetvlanInetTable 
		subnetvlanInetTable OBJECT-TYPE
        SYNTAX SEQUENCE OF SubnetvlanInetEntry
        MAX-ACCESS not-accessible
        STATUS current
        DESCRIPTION
                "A table that contains IPv4/IPv6 subnet vlan configuration."
        ::= { subnetvlan 3 }

        subnetvlanInetEntry OBJECT-TYPE
        SYNTAX SubnetvlanInetEntry
        MAX-ACCESS not-accessible
        STATUS current
        DESCRIPTION
        	"The entry of subnet vlan inet table."
        INDEX  { subnetvlanInetAddrType, subnetvlanInetAddr, subnetvlanInetMask, subnetvlanInetVid, subnetvlanInetPriority }
        ::= { subnetvlanInetTable 1 }

        SubnetvlanInetEntry ::=
        	SEQUENCE {
        		subnetvlanInetAddrType		InetAddressType,		
        		subnetvlanInetAddr			InetAddress,
        		subnetvlanInetMask			INTEGER,
        		subnetvlanInetVid			INTEGER,
        		subnetvlanInetPriority		INTEGER,
        		subnetvlanInetName			DisplayString,
        		subnetvlanInetRowStatus		RowStatus
           	}
        subnetvlanInetAddrType OBJECT-TYPE
        SYNTAX InetAddressType
        MAX-ACCESS read-only
        STATUS current
        DESCRIPTION
		""
        ::= { subnetvlanInetEntry 1 }
           
        subnetvlanInetAddr OBJECT-TYPE
        SYNTAX InetAddress
        MAX-ACCESS read-only
        STATUS current
        DESCRIPTION
		""
        ::= { subnetvlanInetEntry 2 }

        subnetvlanInetMask OBJECT-TYPE
        SYNTAX INTEGER
        MAX-ACCESS read-only
        STATUS current
        DESCRIPTION
		""
        ::= { subnetvlanInetEntry 3 }

        subnetvlanInetVid OBJECT-TYPE
        SYNTAX	INTEGER (1..4094)
        MAX-ACCESS read-only
        STATUS current
        DESCRIPTION
		""
        ::= { subnetvlanInetEntry 4 }

		subnetvlanInetPriority OBJECT-TYPE
        SYNTAX  INTEGER (0..7)
        MAX-ACCESS read-only
        STATUS current
        DESCRIPTION
		""
        ::= { subnetvlanInetEntry 5 }
                        
        subnetvlanInetName OBJECT-TYPE
        SYNTAX DisplayString (SIZE (0..31))
        MAX-ACCESS read-create
        STATUS current
        DESCRIPTION
		""
        ::= { subnetvlanInetEntry 6 }
        
        subnetvlanInetRowStatus OBJECT-TYPE
        SYNTAX RowStatus
        MAX-ACCESS read-create
        STATUS current
        DESCRIPTION
		"Row status of the table entry."
        ::= { subnetvlanInetEntry 7 }
	                
--------------------
-- Loopguard
--------------------
                
	loopguardTable OBJECT-TYPE
        SYNTAX SEQUENCE OF LoopguardEntry
        MAX-ACCESS not-accessible
        STATUS current
        DESCRIPTION
                "A table that contains Loopguard configuration."
        ::= { loopguard 1 }

        loopguardEntry OBJECT-TYPE
        SYNTAX LoopguardEntry
        MAX-ACCESS not-accessible
        STATUS current
        DESCRIPTION
        	"The entry of Loopguard table."
        INDEX  { ifIndex }
        ::= { loopguardTable 1 }

        LoopguardEntry ::=
        	SEQUENCE {
              	loopguardStatus 	INTEGER,
        		loopguardMode 		INTEGER,
        		loopguardRecoverTime	INTEGER
           	}
           
        loopguardStatus OBJECT-TYPE
        SYNTAX INTEGER{
			enable(1),
			disable(2)
		}
        MAX-ACCESS read-write
        STATUS current
        DESCRIPTION
		""
        ::= { loopguardEntry 1 }

        loopguardMode OBJECT-TYPE
        SYNTAX	INTEGER{
			fix(0),
			dynamic(1)
		}
        MAX-ACCESS read-write
        STATUS current
        DESCRIPTION
		""
        ::= { loopguardEntry 2 }

		loopguardRecoverTime OBJECT-TYPE
        SYNTAX  INTEGER (60..600)
        MAX-ACCESS read-write
        STATUS current
        DESCRIPTION
		"seconds"
        ::= { loopguardEntry 3 }

--------------------
-- usStorm
--------------------
                
	usStormTable OBJECT-TYPE
        SYNTAX SEQUENCE OF UsStormEntry
        MAX-ACCESS not-accessible
        STATUS current
        DESCRIPTION
                "A table that contains UsStorm configuration."
        ::= { usStorm 1 }

        usStormEntry OBJECT-TYPE
        SYNTAX UsStormEntry
        MAX-ACCESS not-accessible
        STATUS current
        DESCRIPTION
        	"The entry of UsStorm table."
        INDEX  { ifIndex }
        ::= { usStormTable 1 }

        UsStormEntry ::=
        	SEQUENCE {
        		usStormBcastThresh	INTEGER,
				usStormMcastThresh	INTEGER,
				usStormUcastThresh	INTEGER
           	}

		usStormBcastThresh OBJECT-TYPE
        SYNTAX  INTEGER
        MAX-ACCESS read-write
        STATUS current
        DESCRIPTION
		"0~1488096 pkt/s, -1 means no limit"
        ::= { usStormEntry 1 } 
        
        usStormMcastThresh OBJECT-TYPE
        SYNTAX  INTEGER
        MAX-ACCESS read-write
        STATUS current
        DESCRIPTION
		"0~1488096 pkt/s, -1 means no limit"
        ::= { usStormEntry 2 }
        
        usStormUcastThresh OBJECT-TYPE
        SYNTAX  INTEGER
        MAX-ACCESS read-write
        STATUS current
        DESCRIPTION
		"0~1488096 pkt/s, -1 means no limit"
        ::= { usStormEntry 3 }   

--------------------
-- arpInspection 
--------------------
                
	arpInspectionTable OBJECT-TYPE
        SYNTAX SEQUENCE OF ArpInspectionEntry
        MAX-ACCESS not-accessible
        STATUS current
        DESCRIPTION
                "Support ARP inspection to filter unauthorized ARP packets on the network. 
                This can prevent many kinds of man-in-the-middle attacks. 
                This table is supported by R5.05 and later versions."
        ::= { arpInspection 1 }

        arpInspectionEntry OBJECT-TYPE
        SYNTAX ArpInspectionEntry
        MAX-ACCESS not-accessible
        STATUS current
        DESCRIPTION
        	"The entry of arpInspectionTable."
        INDEX  { ifIndex }
        ::= { arpInspectionTable 1 }

        ArpInspectionEntry ::=
        	SEQUENCE {
        		arpInspectionEnable	INTEGER
           	}

		arpInspectionEnable OBJECT-TYPE
        SYNTAX  INTEGER {
        		enable(1),
        		disable(2)
        	}
        MAX-ACCESS read-write
        STATUS current
        DESCRIPTION
		"Enable/disable  arp inspection on the specified subscriber port."
        ::= { arpInspectionEntry 1 } 

--------------------
-- macFF 
--------------------
-- macFFStaticTable                
	macFFStaticTable OBJECT-TYPE
        SYNTAX SEQUENCE OF MacFFStaticEntry
        MAX-ACCESS not-accessible
        STATUS current
        DESCRIPTION
                ""
        ::= { macFF 1 }

        macFFStaticEntry OBJECT-TYPE
        SYNTAX MacFFStaticEntry
        MAX-ACCESS not-accessible
        STATUS current
        DESCRIPTION
        	"The entry of macFFStaticTable."
        INDEX  { slotId, macFFStaticIndex }
        ::= { macFFStaticTable 1 }

        MacFFStaticEntry ::=
        	SEQUENCE {
        		macFFStaticIndex		INTEGER,
        		macFFStaticSrcIP		IpAddress,
        		macFFStaticMask			INTEGER,
        		macFFStaticArasIP		IpAddress,
        		macFFStaticVid			INTEGER,
        		macFFStaticRowStatus	RowStatus
           	}

		macFFStaticIndex OBJECT-TYPE
        SYNTAX  INTEGER
        MAX-ACCESS read-only
        STATUS current
        DESCRIPTION
		"The macFF static entry index 1 ~ 24"
        ::= { macFFStaticEntry 1 }
        
        macFFStaticSrcIP OBJECT-TYPE
        SYNTAX  IpAddress
        MAX-ACCESS read-write
        STATUS current
        DESCRIPTION
		"Matched range for static subscriber's IP in ARP request"
        ::= { macFFStaticEntry 2 }
        
        macFFStaticMask OBJECT-TYPE
        SYNTAX  INTEGER
        MAX-ACCESS read-write
        STATUS current
        DESCRIPTION
		"Matched range for static subscriber's IP in ARP request"
        ::= { macFFStaticEntry 3 }
        
        macFFStaticArasIP OBJECT-TYPE
        SYNTAX  IpAddress
        MAX-ACCESS read-write
        STATUS current
        DESCRIPTION
		"IP of static macFF Access Router/App Server"
        ::= { macFFStaticEntry 4 }
        
        macFFStaticVid OBJECT-TYPE
        SYNTAX  INTEGER(1..4094)
        MAX-ACCESS read-write
        STATUS current
        DESCRIPTION
		"vlan ID of macFF Access Router/App Server"
        ::= { macFFStaticEntry 5 }
                
        macFFStaticRowStatus OBJECT-TYPE
        SYNTAX  RowStatus
        MAX-ACCESS read-create
        STATUS current
        DESCRIPTION
		""
        ::= { macFFStaticEntry 6 }

-- macFFDynamicTable                
	macFFDynamicTable OBJECT-TYPE
        SYNTAX SEQUENCE OF MacFFDynamicEntry
        MAX-ACCESS not-accessible
        STATUS current
        DESCRIPTION
                ""
        ::= { macFF 2 }

        macFFDynamicEntry OBJECT-TYPE
        SYNTAX MacFFDynamicEntry
        MAX-ACCESS not-accessible
        STATUS current
        DESCRIPTION
        	"The entry of macFFDynamicTable."
        INDEX  { slotId, macFFDynamicIndex }
        ::= { macFFDynamicTable 1 }

        MacFFDynamicEntry ::=
        	SEQUENCE {
        		macFFDynamicIndex		INTEGER,
        		macFFDynamicSrcIP		IpAddress,
        		macFFDynamicMask			INTEGER,
        		macFFDynamicArasIP		IpAddress,
        		macFFDynamicVid			INTEGER
           	}

		macFFDynamicIndex OBJECT-TYPE
        SYNTAX  INTEGER
        MAX-ACCESS read-only
        STATUS current
        DESCRIPTION
		"The macFF entry index 1 ~ 24"
        ::= { macFFDynamicEntry 1 }
        
        macFFDynamicSrcIP OBJECT-TYPE
        SYNTAX  IpAddress
        MAX-ACCESS read-only
        STATUS current
        DESCRIPTION
		"Matched range for dynamic subscriber's IP in ARP request"
        ::= { macFFDynamicEntry 2 }
        
        macFFDynamicMask OBJECT-TYPE
        SYNTAX  INTEGER
        MAX-ACCESS read-only
        STATUS current
        DESCRIPTION
		"Matched range for dynamic subscriber's IP in ARP request"
        ::= { macFFDynamicEntry 3 }
        
        macFFDynamicArasIP OBJECT-TYPE
        SYNTAX  IpAddress
        MAX-ACCESS read-only
        STATUS current
        DESCRIPTION
		"IP of dynamic macFF Access Router/App Server"
        ::= { macFFDynamicEntry 4 }
        
        macFFDynamicVid OBJECT-TYPE
        SYNTAX  INTEGER(1..4094)
        MAX-ACCESS read-only
        STATUS current
        DESCRIPTION
		"vlan ID of macFF Access Router/App Server"
        ::= { macFFDynamicEntry 5 }
                        
-- macFFVlanTable                
	macFFVlanTable OBJECT-TYPE
        SYNTAX SEQUENCE OF MacFFVlanEntry
        MAX-ACCESS not-accessible
        STATUS current
        DESCRIPTION
                ""
        ::= { macFF 3 }

        macFFVlanEntry OBJECT-TYPE
        SYNTAX MacFFVlanEntry
        MAX-ACCESS not-accessible
        STATUS current
        DESCRIPTION
        	"The entry of macFFVlanTable."
        INDEX  { slotId, macFFVlanVid  }
        ::= { macFFVlanTable 1 }

        MacFFVlanEntry ::=
        	SEQUENCE {
        		macFFVlanVid 			INTEGER,
        		macFFVlanRowStatus	RowStatus
           	}

		macFFVlanVid OBJECT-TYPE
        SYNTAX  INTEGER(1..4094)
        MAX-ACCESS read-only
        STATUS current
        DESCRIPTION
		"Vlan ID of macFF Access Router/App Server"
        ::= { macFFVlanEntry 1 } 
        
        macFFVlanRowStatus OBJECT-TYPE
        SYNTAX  RowStatus
        MAX-ACCESS read-create
        STATUS current
        DESCRIPTION
		""
        ::= { macFFVlanEntry 2 }   
            
 -- macFFFlush    
 	macFFFlush OBJECT-TYPE
        SYNTAX INTEGER
        MAX-ACCESS read-write
        STATUS current
        DESCRIPTION
        	"Set the object to n to flush the slot n's macff arp table(not include the MSC slot).
        	macFFArpStatusUplinkTable(1.3.6.1.4.1.890.1.5.13.5.13.23.1)
        	macFFArpStatusSlotTable(1.3.6.1.4.1.890.1.5.13.5.13.23.2)"
        ::= { macFF 4 }

--------------------
-- dhcpv6 
--------------------
-- dhcpv6RelayTable                
	dhcpv6RelayTable OBJECT-TYPE
        SYNTAX SEQUENCE OF Dhcpv6RelayEntry
        MAX-ACCESS not-accessible
        STATUS current
        DESCRIPTION
                ""
        ::= { dhcpv6 1 }

        dhcpv6RelayEntry OBJECT-TYPE
        SYNTAX Dhcpv6RelayEntry
        MAX-ACCESS not-accessible
        STATUS current
        DESCRIPTION
        	"The entry of dhcpv6RelayTable."
        INDEX  { dot1qVlanIndex }
        ::= { dhcpv6RelayTable 1 }

        Dhcpv6RelayEntry ::=
        	SEQUENCE {
        		dhcpv6RelayLdraState		INTEGER,
        		dhcpv6RelayRowStatus		RowStatus
           	}

		dhcpv6RelayLdraState OBJECT-TYPE
        SYNTAX  INTEGER{
        		enable(1), 
        		disable(2)
        }
        MAX-ACCESS read-create
        STATUS current
        DESCRIPTION
		"Enable/disable DHCPv6 LDRA function"
        ::= { dhcpv6RelayEntry 1 }
        
        dhcpv6RelayRowStatus OBJECT-TYPE
        SYNTAX  RowStatus
        MAX-ACCESS read-create
        STATUS current
        DESCRIPTION
		""
        ::= { dhcpv6RelayEntry 2 }

-- dhcpv6RelayOptionTable                
	dhcpv6RelayOptionTable OBJECT-TYPE
        SYNTAX SEQUENCE OF Dhcpv6RelayOptionEntry
        MAX-ACCESS not-accessible
        STATUS current
        DESCRIPTION
                ""
        ::= { dhcpv6 2 }

        dhcpv6RelayOptionEntry OBJECT-TYPE
        SYNTAX Dhcpv6RelayOptionEntry
        MAX-ACCESS not-accessible
        STATUS current
        DESCRIPTION
        	"The entry of dhcpv6RelayOptionTable."
        INDEX  { dot1qVlanIndex, dhcpv6RelayOptionId }
        ::= { dhcpv6RelayOptionTable 1 }

        Dhcpv6RelayOptionEntry ::=
        	SEQUENCE {
        		dhcpv6RelayOptionId			INTEGER,
        		dhcpv6RelayOptionState		INTEGER,
        		dhcpv6RelayOptionFormat		OCTET STRING
           	}

		dhcpv6RelayOptionId OBJECT-TYPE
        SYNTAX  INTEGER{
        		interfaceId(18), 
        		remoteId(37)
        }
        MAX-ACCESS read-only
        STATUS current
        DESCRIPTION
		"DHCPv6 option ID" 
        ::= { dhcpv6RelayOptionEntry 1 }
        
        dhcpv6RelayOptionState OBJECT-TYPE
        SYNTAX  INTEGER{
        		enable(1), 
        		disable(2)
        }
        MAX-ACCESS read-write
        STATUS current
        DESCRIPTION
		"Enable/disable DHCPv6 option"
        ::= { dhcpv6RelayOptionEntry 2 }
        
        dhcpv6RelayOptionFormat OBJECT-TYPE
        SYNTAX  OCTET STRING
        MAX-ACCESS read-write
        STATUS current
        DESCRIPTION
		"User specific Option format
		'%' treated as a beginner of predefined runtime variable
		the rule is below:
		%%: equals character %
		%0x00~0xFF: represents byte value
		%pname: configured port name
		%ptel: configured port tel
		%pid: port index
		%chvpi: channel vpi
		%chvci: channel vci
		%slotid: slot index of the logic port
		%svlan: SVLAN ID which DHCP client runs on
		%cvlan: CVLAN ID which DHCP client runs on
		%hname: host device name
		%cmac: MAC address of client, represents as Byte
		%phtype: ATM: 'atm'   Ethernet 'eth'
		%blank: blank character
		"
        ::= { dhcpv6RelayOptionEntry 3 }
                                                                                                               
----------------------------------------
-- alarmconf
----------------------------------------

        alarmOps OBJECT-TYPE
        SYNTAX INTEGER
        MAX-ACCESS read-write
        STATUS current
        DESCRIPTION
        	"The manager sets the corresponding bit value to 1 to start the operation
        	and the agent clears the object to zero when the operation is successfully completed.
        	The various bit positions are:
		BIT 1: clear
		BIT 2: cutoff
		BIT 3: clear alarm history table"
        ::= { alarmconf 1 }

-- Alarm Conf Table
       
        alarmConfTable OBJECT-TYPE
        SYNTAX SEQUENCE OF AlarmConfEntry
        MAX-ACCESS not-accessible
        STATUS current
        DESCRIPTION
        	"This table includes alarm configuration."
        ::= { alarmconf 2 }

	alarmConfEntry OBJECT-TYPE
        SYNTAX AlarmConfEntry
        MAX-ACCESS not-accessible
        STATUS current
        DESCRIPTION
		"An entry in alarmConfTable."
        INDEX { alarmConfId }
        ::= { alarmConfTable 1 }

        AlarmConfEntry ::=
        	SEQUENCE {
			alarmConfId		INTEGER,
			alarmConfFacility	INTEGER,
			alarmConfTarget		INTEGER,
			alarmConfSeverity	INTEGER,
			alarmConfClearable	INTEGER
           	}

        alarmConfId OBJECT-TYPE
        SYNTAX INTEGER
        MAX-ACCESS read-only
        STATUS current
        DESCRIPTION
                "
                 3: dslLineUp
                 4: dslLineDown
                 7: dslLineLdmStart
                 8: dslLineLdmDone
                 9: dslLinePowerDownL2
                 10:dslLinePowerDownL0
                 11:dslLineFailure
                 14:adslPerfLolThresh
                 17:adslPerfLofThresh
                 18:adslPerfLosThresh
                 19:adslPerfLprThresh
                 20:adslPerfESThresh
                 21:adslRateChange
                 22:adslPerfSESThresh
                 23:adslPerfUASThresh
                 24:shdslLoopAttenCrossing
                 25:shdslSNRMarginCrossing
                 26:shdslPerfESThresh
                 27:shdslPerfSESThresh
                 28:shdslPerfCRCAnomaliesThresh
                 29:shdslPerfLOSWSThresh
                 30:shdslPerfUASThresh
                 31:vdslPerfLolThresh
                 32:vdslPerfLofThresh
                 33:vdslPerfLosThresh
                 34:vdslPerfLprThresh
                 35:vdslPerfESThresh
                 36:vdslPerfSESThresh
                 37:vdslPerfUASThresh
                 38:dslMacAntiSpoofing
                 39:vdslPerfCodeViolationThresh
                 40:vdslVturInfoReady
                 41:vdslPerfRateChange
                 42:vdslTCACorrect
                 43:vdslTCAFailinit
                 44:vdslTCAFEC
                 45:vdslStatusChange
                 46:lineLoopGuard
                 
                 1001:eqpt48VPowerFailure
                 1002:eqptVoltageError
                 1003:eqptTempError
                 1004:eqptFanError
                 1005:eqptTempLowFanStop
                 1009:eqptHWMonitorFailre
                 1011:eqptColdStart
                 1012:eqptWarmStart
                 1019:eqptMgmtPortUp
                 1020:eqptMgmtPortDown
                 1021:eqptExternalAlarmInput
                 1022:eqptTopologyChange
                 1023:eqptFWUploadOK
                 1024:eqptFWUploadFailure
                 1025:eqptLTPlugIn
                 1026:eqptLTPullOut
                 1028:eqptLTDslDeviceFailure
                 1029:eqptLTDslDeviceRedownload
                 1031:eqptLTActive
                 1032:eqptLTInactive
                 1038:eqptLTFWUploadOK
                 1039:eqptLTFWUploadFailure                                  
                 1040:eqptLTEnable
                 1041:eqptLTDisable
                 1042:eqptLTReset
                 1043:eqptNTSwitchOK
                 1044:eqptCpuUtilizationHigh
                 1045:eqptVopBatteryFailure
                 1046:eqptVopClockFailure
                 1047:eqptVopRingerFault
                 1048:eqptPacketBufferUsageHigh
                 1049:eqptMemoryUsageHigh
                 1050:eqptStpNewRoot
                 1053:eqptStpPortStateChange
                 1054:eqptStpPortRoleChange
                 
                 2001:sysReboot
                 2002:sysConfigChange
                 2003:sysConfigUploadOK
                 2004:sysConfigUploadFailure
                 2005:sysTimeSyncFailure
                 2006:sysAlarmCutoffEnable
                 2007:sysAlarmClearEnable 
                 2008:sysLoginFailure
                 2009:sysLogin
                 2010:sysAccountAdded
                 2011:sysAccountDeleted
                 2012:sysAccountModified
                 2013:sysSvrSyncProfOk
                 2014:sysSvrSyncProfFail
                 2015:sysCliSyncProfOk
                 2016:sysCliSyncProfFail
                 2017:sysMacAntiSpoofing
                 2018:sysClusterMemberActive
                 2019:sysClusterMemberInactive
                 2020:sysClusterMemeberAdded
                 2021:sysClusterMemeberDeleted
                 2022:pingProbeFailed
                 2023:pingTestFailed
                 2024:pingTestCompleted
                 2025:traceRouteTestFailed
                 2026:traceRouteTestCompleted
		 
                 3006:enetUp
                 3007:enetDown
                 3008:enetLoopGuard
                 3009:enetSFPError
                 3010:enetSFPTxEnable
                 3011:enetSFPTxDisable
                 
                 4001:vopTempError
                 4002:vopDCPowerFailure
                 4003:vopACPowerFailure
                 4004:vopRingTimerFailure
                 4005:vopRingResourceFailure
                 4006:vopRingOhdFailure
                 4007:vopNoFreeDSPChannel
                 4008:vopMCMissing
                 4009:vopSCMissing
                 4010:vopTermNameDup
                 4011:vopNoProtection
                 4012:vopProtectionSwitch
                 4013:vopDropCall
                 4014:vopBatteryFail
                 4015:vopClockFail
                 4016:vopRingerFail
                 4017:vopMgcMissing
                 4018:vopMgEnable
                 4019:vopMgDisable
                 
                 5001:cfmError
                 5003:lldpRemoteChange
                    
				 6001: imaAlarmGroupStartupFe
				 6002: imaAlarmGroupCfgAbort
				 6003: imaAlarmGroupCfgAbortFe
				 6004: imaAlarmGroupInsuffLinks
				 6005: imaAlarmGroupInsuffLinksFe
				 6006: imaAlarmGroupBlockedFe
				 6007: imaAlarmGroupTimingSynch
				 6008: imaAlarmLinkLif
				 6009: imaAlarmLinkLods
				 6010: imaAlarmLinkRfi
				 6011: imaAlarmLinkTxMisConnect
				 6012: imaAlarmLinkRxMisConnect
				 6013: imaAlarmLinkTxFault
				 6014: imaAlarmLinkRxFault
				 6015: imaAlarmLinkTxUnusableFe
				 6016: imaAlarmLinkRxUnusableFe
				 
				 7001: e1AlarmLinkLOS
				 7002: e1AlarmPathLOF
				 7003: e1AlarmPathAIS
				 7004: e1AlarmPathRDI
				 7005: e1AlarmPathOCASMF
				 7006: e1AlarmPathOCRCMF
				 7007: e1AlarmLinkSF
				 7008: e1AlarmLinkSD
				 7009: e1AlarmTCAQuarterES
				 7010: e1AlarmTCAQuarterSES
				 7011: e1AlarmTCAQuarterUAS
				 7012: e1AlarmTCADayES
				 7013: e1AlarmTCADaySES
				 7014: e1AlarmTCADayUAS"
         ::= { alarmConfEntry 1 }

        alarmConfFacility OBJECT-TYPE
        SYNTAX  INTEGER {
        		local1(0),        
        		local1(1),
        		local2(2),
        		local3(3),
        		local4(4),
        		local5(5),
        		local6(6),
        		local7(7)
        	}
        MAX-ACCESS read-write
        STATUS current
        DESCRIPTION
                "Alarm facility."
         ::= { alarmConfEntry 2 }

        alarmConfTarget OBJECT-TYPE
        SYNTAX INTEGER
        MAX-ACCESS read-write
        STATUS current
        DESCRIPTION
                "The destination which alarms are reported to. Set the bit to 1 to enable the target.
                BIT 1: snmp trap
                BIT 2: syslog"
         ::= { alarmConfEntry 3 }
         
        alarmConfSeverity OBJECT-TYPE
        SYNTAX 	INTEGER  {
        		critical(1),
        		major(2),
        		minor(3),
        		info(4)
        	}
        MAX-ACCESS read-write
        STATUS current
        DESCRIPTION
                "Alarm severity"
         ::= { alarmConfEntry 4 }

        alarmConfClearable OBJECT-TYPE
        SYNTAX 	INTEGER  {
        		clearable(1),
        		unclearable(2)
        	}
        MAX-ACCESS read-write
        STATUS current
        DESCRIPTION
                "Setting the object to one indicates that the alarm is to be cleared when user submits alarm clear."
         ::= { alarmConfEntry 5 }
                  
-- Alarm Current Table

        alarmCurrTable OBJECT-TYPE
        SYNTAX SEQUENCE OF AlarmCurrEntry
        MAX-ACCESS not-accessible
        STATUS current
        DESCRIPTION
        	"This table includes current alarm information."
        ::= { alarmconf 3 }

	alarmCurrEntry OBJECT-TYPE
        SYNTAX AlarmCurrEntry
        MAX-ACCESS not-accessible
        STATUS current
        DESCRIPTION
		"An entry in alarmCurrTable."
        INDEX { alarmCurrIndex }
        ::= { alarmCurrTable 1 }

        AlarmCurrEntry ::=
        	SEQUENCE {
			alarmCurrIndex		INTEGER,
			alarmCurrOccurTime	TimeTicks,
			alarmCurrTrapOid	OBJECT IDENTIFIER,
			alarmCurrParam1		INTEGER,
			alarmCurrParam2		INTEGER,
			alarmCurrParam3		INTEGER,
			alarmCurrParam4		INTEGER,
			alarmCurrParam5		INTEGER,
			alarmCurrParam6		INTEGER,
			alarmCurrParam7		INTEGER,
			alarmCurrParam8		INTEGER,
			alarmCurrTimeDescr	DisplayString,
			alarmCurrSeverity	INTEGER,
			alarmCurrDescr		DisplayString
           	}

        alarmCurrIndex OBJECT-TYPE
        SYNTAX INTEGER
        MAX-ACCESS read-only
        STATUS current
        DESCRIPTION
                "Index of the alarm."
        ::= { alarmCurrEntry 1 }
         
        alarmCurrOccurTime OBJECT-TYPE
        SYNTAX TimeTicks
        MAX-ACCESS read-only
        STATUS current
        DESCRIPTION
                "Alarm occurence time (in hundredths of a second) since the system was last re-initialized."
        ::= { alarmCurrEntry 2 }
         
        alarmCurrTrapOid OBJECT-TYPE
        SYNTAX OBJECT IDENTIFIER
        MAX-ACCESS read-only
        STATUS current
        DESCRIPTION
                "Trap OID of the alarm."
        ::= { alarmCurrEntry 3 }
         
        alarmCurrParam1 OBJECT-TYPE
        SYNTAX INTEGER
        MAX-ACCESS read-only
        STATUS current
        DESCRIPTION
                "The 1st parameter of the alarm."
        ::= { alarmCurrEntry 4 }

        alarmCurrParam2 OBJECT-TYPE
        SYNTAX INTEGER
        MAX-ACCESS read-only
        STATUS current
        DESCRIPTION
                "The 2nd parameter of the alarm."
        ::= { alarmCurrEntry 5 }
        
        alarmCurrParam3 OBJECT-TYPE
        SYNTAX INTEGER
        MAX-ACCESS read-only
        STATUS current
        DESCRIPTION
                "The 3rd parameter of the alarm."
        ::= { alarmCurrEntry 6 }         

        alarmCurrParam4 OBJECT-TYPE
        SYNTAX INTEGER
        MAX-ACCESS read-only
        STATUS current
        DESCRIPTION
                "The 4th parameter of the alarm."
        ::= { alarmCurrEntry 7 }
        
        alarmCurrParam5 OBJECT-TYPE
        SYNTAX INTEGER
        MAX-ACCESS read-only
        STATUS current
        DESCRIPTION
                "The 5th parameter of the alarm."
        ::= { alarmCurrEntry 8 }
        
        alarmCurrParam6 OBJECT-TYPE
        SYNTAX INTEGER
        MAX-ACCESS read-only
        STATUS current
        DESCRIPTION
                "The 6th parameter of the alarm."
        ::= { alarmCurrEntry 9 }
        
        alarmCurrParam7 OBJECT-TYPE
        SYNTAX INTEGER
        MAX-ACCESS read-only
        STATUS current
        DESCRIPTION
                "The 7th parameter of the alarm."
        ::= { alarmCurrEntry 10 }
        
        alarmCurrParam8 OBJECT-TYPE
        SYNTAX INTEGER
        MAX-ACCESS read-only
        STATUS current
        DESCRIPTION
                "The 8th parameter of the alarm."
        ::= { alarmCurrEntry 11 }        

        alarmCurrTimeDescr OBJECT-TYPE
        SYNTAX DisplayString
        MAX-ACCESS read-only
        STATUS current
        DESCRIPTION
                "The string representation of occurence time (YYYY/MM/DD HH:MM:SS)."
        ::= { alarmCurrEntry 12 }

        alarmCurrSeverity OBJECT-TYPE
        SYNTAX 	INTEGER {
        		critical(1),
        		major(2),
        		minor(3),
        		info(4)
        	}
        MAX-ACCESS read-only
        STATUS current
        DESCRIPTION
                "The severity of the alarm."
        ::= { alarmCurrEntry 13 }

        alarmCurrDescr OBJECT-TYPE
        SYNTAX DisplayString
        MAX-ACCESS read-only
        STATUS current
        DESCRIPTION
                "The description of the alarm."
        ::= { alarmCurrEntry 14 }                

-- Alarm Severity Port Table
       
        alarmSeverityPortTable OBJECT-TYPE
        SYNTAX SEQUENCE OF AlarmSeverityPortEntry
        MAX-ACCESS not-accessible
        STATUS current
        DESCRIPTION
        	"This table includes the configuration of alarm reporting severity threshold for each port."
        ::= { alarmconf 4 }

	alarmSeverityPortEntry OBJECT-TYPE
        SYNTAX AlarmSeverityPortEntry
        MAX-ACCESS not-accessible
        STATUS current
        DESCRIPTION
		"An entry in alarmSeverityPortTable."
        INDEX { ifIndex }
        ::= { alarmSeverityPortTable 1 }

        AlarmSeverityPortEntry ::=
        	SEQUENCE {
			severityThresh	INTEGER
           	}

        severityThresh OBJECT-TYPE
        SYNTAX 	INTEGER {
        		critical(1),
        		major(2),
        		minor(3),
        		info(4)
        	}
        MAX-ACCESS read-write
        STATUS current
        DESCRIPTION
                "The minimum alarm severity that is reported."
         ::= { alarmSeverityPortEntry 1 }

-- External Alarm Table
       
        externalAlarmTable OBJECT-TYPE
        SYNTAX SEQUENCE OF ExternalAlarmEntry
        MAX-ACCESS not-accessible
        STATUS current
        DESCRIPTION
        	"This table includes the configuration of external alarms."
        ::= { alarmconf 5 }

	externalAlarmEntry OBJECT-TYPE
        SYNTAX ExternalAlarmEntry
        MAX-ACCESS not-accessible
        STATUS current
        DESCRIPTION
		"An entry in externalAlarmTable."
        INDEX { externalAlarmIndex }
        ::= { externalAlarmTable 1 }

        ExternalAlarmEntry ::=
        	SEQUENCE {
			externalAlarmIndex	INTEGER,
			externalAlarmName	DisplayString
           	}

        externalAlarmIndex OBJECT-TYPE
        SYNTAX INTEGER
        MAX-ACCESS read-only
        STATUS current
        DESCRIPTION
                "The external alarm index."
        ::= { externalAlarmEntry 1 }
         
        externalAlarmName OBJECT-TYPE
        SYNTAX DisplayString
        MAX-ACCESS read-write
        STATUS current
        DESCRIPTION
                "The external alarm name."
         ::= { externalAlarmEntry 2 }

--  Alarm Target
alarmTarget OBJECT-TYPE
        SYNTAX INTEGER
        MAX-ACCESS read-write
        STATUS current
        DESCRIPTION
        "The manager sets the corresponding bit value to 1 to start the operation and 
        the agent clears the object to zero when the operation is successfully completed.
        The various bit positions are:
        BIT 1: clear
        BIT 2: cutoff"
        ::= { alarmconf 6 }
         
-- Alarm History Table
       
        alarmHisTable OBJECT-TYPE
        SYNTAX SEQUENCE OF AlarmHisEntry
        MAX-ACCESS not-accessible
        STATUS current
        DESCRIPTION
        	"This table that contains alarm history data.
        	This table is supported by R5.05 and later versions."
        ::= { alarmconf 7 }

	alarmHisEntry OBJECT-TYPE
        SYNTAX AlarmHisEntry
        MAX-ACCESS not-accessible
        STATUS current
        DESCRIPTION
		"An entry in alarmHisTable. "
        INDEX { alarmHisIndex }
        ::= { alarmHisTable 1 }

        AlarmHisEntry ::=
        	SEQUENCE {
			alarmHisIndex		INTEGER,
			alarmHisOccurTime	TimeTicks,
			alarmHisTrapOid		OBJECT IDENTIFIER,
			alarmHisParam1		INTEGER,
			alarmHisParam2		INTEGER,		
			alarmHisParam3		INTEGER,
			alarmHisParam4		INTEGER,
			alarmHisParam5		INTEGER,
			alarmHisParam6		INTEGER,
			alarmHisParam7		INTEGER,
			alarmHisParam8		INTEGER, 
			alarmHisTimeDescr	DisplayString,
			alarmHisSeverity	INTEGER,
			alarmHisDescr		DisplayString
           	}

        alarmHisIndex OBJECT-TYPE
        SYNTAX INTEGER
        MAX-ACCESS read-only
        STATUS current
        DESCRIPTION
                "Index of the alarm."
        ::= { alarmHisEntry 1 }
         
        alarmHisOccurTime OBJECT-TYPE
        SYNTAX TimeTicks
        MAX-ACCESS read-only
        STATUS current
        DESCRIPTION
                "Alarm occurence time (in hundredths of a second) since the system was last re-initialized."
        ::= { alarmHisEntry 2 } 
         
        alarmHisTrapOid OBJECT-TYPE
        SYNTAX OBJECT IDENTIFIER
        MAX-ACCESS read-only
        STATUS current
        DESCRIPTION
                "Trap OID of the alarm."
        ::= { alarmHisEntry 3 }
         
        alarmHisParam1 OBJECT-TYPE
        SYNTAX INTEGER
        MAX-ACCESS read-only
        STATUS current
        DESCRIPTION
                "The 1st parameter of the alarm."
        ::= { alarmHisEntry 4 }
        
        alarmHisParam2 OBJECT-TYPE
        SYNTAX INTEGER
        MAX-ACCESS read-only
        STATUS current
        DESCRIPTION
                "The 2nd parameter of the alarm."
        ::= { alarmHisEntry 5 }
        
        alarmHisParam3 OBJECT-TYPE
        SYNTAX INTEGER
        MAX-ACCESS read-only
        STATUS current
        DESCRIPTION
                "The 3rd parameter of the alarm."
        ::= { alarmHisEntry 6 }
        
        alarmHisParam4 OBJECT-TYPE
        SYNTAX INTEGER
        MAX-ACCESS read-only
        STATUS current
        DESCRIPTION
                "The 4th parameter of the alarm."
        ::= { alarmHisEntry 7 }
        
        alarmHisParam5 OBJECT-TYPE
        SYNTAX INTEGER
        MAX-ACCESS read-only
        STATUS current
        DESCRIPTION
                "The 5th parameter of the alarm."
        ::= { alarmHisEntry 8 }
        
        alarmHisParam6 OBJECT-TYPE
        SYNTAX INTEGER
        MAX-ACCESS read-only
        STATUS current
        DESCRIPTION
                "The 6th parameter of the alarm."
        ::= { alarmHisEntry 9 }
        
        alarmHisParam7 OBJECT-TYPE
        SYNTAX INTEGER
        MAX-ACCESS read-only
        STATUS current
        DESCRIPTION
                "The 7th parameter of the alarm."
        ::= { alarmHisEntry 10 }
        
        alarmHisParam8 OBJECT-TYPE
        SYNTAX INTEGER
        MAX-ACCESS read-only
        STATUS current
        DESCRIPTION
                "The 8th parameter of the alarm."
        ::= { alarmHisEntry 11 }
        
        alarmHisTimeDescr OBJECT-TYPE
        SYNTAX DisplayString
        MAX-ACCESS read-only
        STATUS current
        DESCRIPTION
                "The string representation of occurence time (YYYY/MM/DD HH:MM:SS)."
        ::= { alarmHisEntry 12 }
        
        alarmHisSeverity OBJECT-TYPE
        SYNTAX 	INTEGER {
        		critical(1),
        		major(2),
        		minor(3),
        		info(4)
        	}
        MAX-ACCESS read-only
        STATUS current
        DESCRIPTION
                "The severity of the alarm."
        ::= { alarmHisEntry 13 }
        
        alarmHisDescr OBJECT-TYPE
        SYNTAX DisplayString
        MAX-ACCESS read-only
        STATUS current
        DESCRIPTION
                "The description of the alarm."
        ::= { alarmHisEntry 14 }
                                                                                                           
----------------------------------------
-- Alarm HisFilter 
----------------------------------------

	alarmHisFilter 	OBJECT IDENTIFIER ::= { alarmconf 8 }
        
--  Alarm HisFilter  
         	         
    alarmHisFilterByIfIndex OBJECT-TYPE
    SYNTAX INTEGER
    MAX-ACCESS read-write
    STATUS current
    DESCRIPTION
		"ifIndex Filter for alarmHisTable."
    ::= { alarmHisFilter 1 }
        
                                                                                                           
----------------------------------------
-- config
----------------------------------------

        configOps OBJECT-TYPE
        SYNTAX INTEGER
        MAX-ACCESS read-write
        STATUS current
        DESCRIPTION
        	"The manager sets the corresponding bit value to 1 to start the operation
        	and the agent clears the object to zero when the operation is successfully completed.
        	The various bit positions are:
		BIT 1: config save
		BIT 2: factory default
		"
        ::= { config 1 }
        
----------------------------------------
-- diagnostic
----------------------------------------

	loopback 				OBJECT IDENTIFIER ::= { diagnostic 1 }
	ldm 					OBJECT IDENTIFIER ::= { diagnostic 2 }
	selt					OBJECT IDENTIFIER ::= { diagnostic 3 }
	mlt						OBJECT IDENTIFIER ::= { diagnostic 4 }
	oamloopback				OBJECT IDENTIFIER ::= { diagnostic 5 }
	vdslldm					OBJECT IDENTIFIER ::= { diagnostic 6 }
	imaOamF5Loopback		OBJECT IDENTIFIER ::= { diagnostic 7 } 
	xdsl2ExtStatus			OBJECT IDENTIFIER ::= { diagnostic 8 }


--------------------
-- loopback
--------------------

        loopbackTarget OBJECT-TYPE
        SYNTAX INTEGER
        MAX-ACCESS read-write
        STATUS current
        DESCRIPTION
		"IfIndex of the port which would be performed loopback test."
        ::= { loopback 1 }
        
        loopbackOps OBJECT-TYPE
        SYNTAX INTEGER
        MAX-ACCESS read-write
        STATUS current
        DESCRIPTION
        	"The manager sets the corresponding bit value to 1 to start the loopback test
        	and the agent clears the object to zero when loopback test is successfully completed.
        	The various bit positions are:
		BIT 1: local loopback
		BIT 2: remote F5 loopback."
        ::= { loopback 2 }

	loopbackVpi OBJECT-TYPE
        SYNTAX INTEGER
        MAX-ACCESS read-write
        STATUS current
        DESCRIPTION
		"VPI of the virtual channel which would be performed loopback test."
        ::= { loopback 3 }
        
        loopbackVci OBJECT-TYPE
        SYNTAX INTEGER
        MAX-ACCESS read-write
        STATUS current
        DESCRIPTION
		"VCI of the virtual channel which would be performed loopback test."
        ::= { loopback 4 }

		loopbackStatus OBJECT-TYPE
			SYNTAX DisplayString
			MAX-ACCESS read-only
			STATUS current
			DESCRIPTION
				"Loopback test status message."
				::= { loopback 5 }

                
--------------------
-- ldm
--------------------

	ldmTarget OBJECT-TYPE
	SYNTAX INTEGER
	MAX-ACCESS read-write
	STATUS current
	DESCRIPTION
		"IfIndex of the port which would be performed ldm test."
	::= { ldm 1 }
	
	ldmOps OBJECT-TYPE
	SYNTAX INTEGER
	MAX-ACCESS read-write
	STATUS current
	DESCRIPTION
		"The manager sets the object to 1 to start the ldm test
        	and the agent clears the object to zero when ldm test is successfully completed."
	::= { ldm 2 }

	ldmStatus OBJECT-TYPE
	SYNTAX DisplayString
	MAX-ACCESS read-only
	STATUS current
	DESCRIPTION
		"Status description of ldm test result."
	::= { ldm 3 }
		   
	ldmAtucLoopAttenuation OBJECT-TYPE
	SYNTAX INTEGER
	UNITS "tenth dB"
	MAX-ACCESS read-only
	STATUS current
	DESCRIPTION
		"Loop Attenuation."
	::= { ldm 4 }

	ldmAtucSignalAttenuation OBJECT-TYPE
	SYNTAX INTEGER
	UNITS "tenth dB"
	MAX-ACCESS read-only
	STATUS current
	DESCRIPTION
		"Signal Attenuation."
	::= { ldm 5 }

	ldmAtucSignalMargin OBJECT-TYPE
	SYNTAX INTEGER
	UNITS "tenth dB"
	MAX-ACCESS read-only
	STATUS current
	DESCRIPTION
		"Signal Margin."
	::= { ldm 6 } 

	ldmAtucAggregateTxPower OBJECT-TYPE
	SYNTAX INTEGER
	UNITS "tenth dB"
	MAX-ACCESS read-only
	STATUS current
	DESCRIPTION
		"Actual Aggregate Transmit Power."
	::= { ldm 7 }
	
	ldmAtucAttainableBitRate OBJECT-TYPE
	SYNTAX Unsigned32
	UNITS "bits per second"
	MAX-ACCESS read-only
	STATUS current
	DESCRIPTION
		"Attainable Bit Rate."
	::= { ldm 8 }

	ldmAturLoopAttenuation OBJECT-TYPE
	SYNTAX INTEGER
	UNITS "tenth dB"
	MAX-ACCESS read-only
	STATUS current
	DESCRIPTION
		"Loop Attenuation."
	::= { ldm 9 }

	ldmAturSignalAttenuation OBJECT-TYPE
	SYNTAX INTEGER
	UNITS "tenth dB"
	MAX-ACCESS read-only
	STATUS	current
	DESCRIPTION
		"Signal Attenuation."
	::= { ldm 10 }

	ldmAturSignalMargin OBJECT-TYPE
	SYNTAX INTEGER
	UNITS "tenth dB"
	MAX-ACCESS read-only
	STATUS current
	DESCRIPTION
		"Signal Margin."
	::= { ldm 11 } 

	ldmAturAggregateTxPower OBJECT-TYPE
	SYNTAX INTEGER
	UNITS "tenth dB"
	MAX-ACCESS read-only
	STATUS current
	DESCRIPTION
		"Actual Aggregate Transmit Power."
	::= { ldm 12 }
	
	ldmAturAttainableBitRate OBJECT-TYPE
	SYNTAX Unsigned32
	UNITS "bits per second"
	MAX-ACCESS read-only
	STATUS current
	DESCRIPTION
		"Attainable Bit Rate."
	::= { ldm 13 }

	ldmAtucNumOfSubcarriersPerPort OBJECT-TYPE
	SYNTAX INTEGER
	MAX-ACCESS read-only
	STATUS current
	DESCRIPTION
		"The number of subcarriers per port for ATU-C."
	::= { ldm 14 }

	ldmAturNumOfSubcarriersPerPort OBJECT-TYPE
	SYNTAX INTEGER
	MAX-ACCESS read-only
	STATUS current
	DESCRIPTION
		"The number of subcarriers per port for ATU-R."
	::= { ldm 15 }

	ldmAtucHlinScale OBJECT-TYPE
	SYNTAX INTEGER
	MAX-ACCESS read-only
	STATUS current
	DESCRIPTION
		"Scale of Hlin."
	::= { ldm 16 }
					
	ldmAtucHlinReal1 OBJECT-TYPE
	SYNTAX OCTET STRING
	MAX-ACCESS read-only
	STATUS current
	DESCRIPTION
		"The object provides real part of Hlin for the first 256 subcarriers.
		Each subcarrier takes two octets to store the value."
	::= { ldm 17 }

	ldmAtucHlinReal2 OBJECT-TYPE
	SYNTAX OCTET STRING
	MAX-ACCESS read-only
	STATUS current
	DESCRIPTION
		"The object provides real part of Hlin for the last 256 subcarriers.
		Each subcarrier takes two octets to store the value."
	::= { ldm 18 }

	ldmAtucHlinImage1 OBJECT-TYPE
	SYNTAX OCTET STRING
	MAX-ACCESS read-only
	STATUS current
	DESCRIPTION
		"The object provides image part of Hlin for the first 256 subcarriers.
		Each subcarrier takes two octets to store the value."
	::= { ldm 19 }

	ldmAtucHlinImage2 OBJECT-TYPE
	SYNTAX OCTET STRING
	MAX-ACCESS read-only
	STATUS current
	DESCRIPTION
		"The object provides image part of Hlin for the last 256 subcarriers.
		Each subcarrier takes two octets to store the value."
	::= { ldm 20 }

	ldmAtucHlog1 OBJECT-TYPE
	SYNTAX OCTET STRING
	MAX-ACCESS read-only
	STATUS current
	DESCRIPTION
		"The object provides Hlog for the first 256 subcarriers.
		Each subcarrier takes two octets to store the value.
		A special value -32768 indicates that no measurement could 
		be done for the sub-carrier group."
	::= { ldm 21 }

	ldmAtucHlog2 OBJECT-TYPE
	SYNTAX OCTET STRING
	MAX-ACCESS read-only
	STATUS current
	DESCRIPTION
		"The object provides Hlog for the last 256 subcarriers.
		Each subcarrier takes two octets to store the value.
		A special value -32768 indicates that no measurement could 
		be done for the sub-carrier group."
	::= { ldm 22 }

	ldmAtucQln1 OBJECT-TYPE
	SYNTAX OCTET STRING
	MAX-ACCESS read-only
	STATUS current
	DESCRIPTION
		"The object provides QLN for the first 256 subcarriers.
		Each subcarrier takes two octets to store the value.
		A special value 0 indicates that no measurement could 
		be done for the sub-carrier group."
	::= { ldm 23 }

	ldmAtucQln2 OBJECT-TYPE
	SYNTAX OCTET STRING
	MAX-ACCESS read-only
	STATUS current
	DESCRIPTION
		"The object provides QLN for the last 256 subcarriers.
		Each subcarrier takes two octets to store the value.
		A special value 0 indicates that no measurement could 
		be done for the sub-carrier group."
	::= { ldm 24 }

	ldmAtucSnr1 OBJECT-TYPE
	SYNTAX OCTET STRING
	MAX-ACCESS read-only
	STATUS current
	DESCRIPTION
		"The object provides SNR for the first 256 subcarriers.
		Each subcarrier takes two octets to store the value.
		A special value -32768 indicates that no measurement 
		could be done for the sub-carrier group."
	::= { ldm 25 }

	ldmAtucSnr2 OBJECT-TYPE
	SYNTAX OCTET STRING
	MAX-ACCESS read-only
	STATUS current
	DESCRIPTION
		"The object provides SNR for the last 256 subcarriers.
		Each subcarrier takes two octets to store the value.
		A special value -32768 indicates that no measurement 
		could be done for the sub-carrier group."
	::= { ldm 26 }

	ldmAturHlinScale OBJECT-TYPE
	SYNTAX INTEGER
	MAX-ACCESS read-only
	STATUS current
	DESCRIPTION
		"Scale of Hlin."
	::= { ldm 27 }
					
	ldmAturHlinReal OBJECT-TYPE
	SYNTAX OCTET STRING
	MAX-ACCESS read-only
	STATUS current
	DESCRIPTION
		"Real part of Hlin. Each subcarrier takes two octets to store the value."
	::= { ldm 28 }

	ldmAturHlinImage OBJECT-TYPE
	SYNTAX OCTET STRING
	MAX-ACCESS read-only
	STATUS current
	DESCRIPTION
		"Image part of Hlin. Each subcarrier takes two octets to store the value."
	::= { ldm 29 }

	ldmAturHlog OBJECT-TYPE
	SYNTAX OCTET STRING
	MAX-ACCESS read-only
	STATUS current
	DESCRIPTION
		"Hlog of subcarrier. Each subcarrier takes two octets to store the value.
		A special value -32768 indicates that no measurement could be done for 
		the sub-carrier group."
	::= { ldm 30 }

	ldmAturQln OBJECT-TYPE
	SYNTAX OCTET STRING
	MAX-ACCESS read-only
	STATUS current
	DESCRIPTION
		"QLN of subcarrier. Each subcarrier takes two octets to store the value.
		A special value 0 indicates that no measurement could be done for the 
		sub-carrier group."
	::= { ldm 31 }
	
	ldmAturSnr OBJECT-TYPE
	SYNTAX OCTET STRING
	MAX-ACCESS read-only
	STATUS current
	DESCRIPTION
		"SNR of subcarrier. Each subcarrier takes two octets to store the value.
		A special value -32768 indicates that no measurement could be done for 
		the sub-carrier group."
	::= { ldm 32 }

--------------------
-- selt
--------------------

	seltTarget OBJECT-TYPE
	SYNTAX INTEGER
	MAX-ACCESS read-write
	STATUS current
	DESCRIPTION
		"IfIndex of the port which would be performed single end loopback test."
	::= { selt 1 }
	
	seltOps OBJECT-TYPE
	SYNTAX INTEGER
	MAX-ACCESS read-write
	STATUS current
	DESCRIPTION
		"The manager sets the object to 1 to start the selt
        	and the agent clears the object to zero when selt is successfully completed."
	::= { selt 2 }

	seltStatus OBJECT-TYPE
	SYNTAX DisplayString
	MAX-ACCESS read-only
	STATUS current
	DESCRIPTION
		"Status description of the selt result."
	::= { selt 3 }

	seltCableType OBJECT-TYPE
	SYNTAX 	INTEGER {
			awg24(1),
			awg26(2)
		}
	MAX-ACCESS read-only
	STATUS current
	DESCRIPTION
		"The cable type that selt result indicates."
	::= { selt 4 }

	seltLoopEstimateLengthFt OBJECT-TYPE
	SYNTAX INTEGER
	UNITS "feet"
	MAX-ACCESS read-only
	STATUS current
	DESCRIPTION
		"The estimated loop length that selt result indicates."
	::= { selt 5 }
	
	seltLoopEstimateLengthMeter OBJECT-TYPE
	SYNTAX INTEGER
	UNITS "meter"
	MAX-ACCESS read-only
	STATUS current
	DESCRIPTION
		"The estimated loop length that selt result indicates."
	::= { selt 6 }

--------------------
-- mlt
--------------------

	mltTarget OBJECT-TYPE
	SYNTAX INTEGER
	MAX-ACCESS read-write
	STATUS current
	DESCRIPTION
		"IfIndex of the port which would be performed Metallic Link Test."
	::= { mlt 1 }
	
	mltOps OBJECT-TYPE
	SYNTAX INTEGER
	MAX-ACCESS read-write
	STATUS current
	DESCRIPTION
		"The manager sets the object to 1 to start the mlt
        	and the agent clears the object to zero when mlt is successfully completed."
	::= { mlt 2 }
        
        mltOption OBJECT-TYPE
        SYNTAX INTEGER {
        		all(1),
        		vac(2),
        		vdc(3),
        		rload(4),
        		riso(5),
        		cap(6),
        		ren(7),
        		ring(8),
        		metering(9),
        		dialtone(10),
        		digit(11),
        		roh(12)
        	}
        MAX-ACCESS read-write
        STATUS current
        DESCRIPTION
		"all : test all items
		 vac: test AC voltage
		 vdc: test DC voltage
		 rload: test load resistance
		 riso: test isolation resistance
		 cap: test capacitor
		 ren: test REN value
		 ring: test ring voltage
		 metering: test metering voltage
		 dialtone: test dialtone
		 digit: test digit
		 roh: test roh"
        ::= { mlt 3 }
        
        mltForce OBJECT-TYPE
        SYNTAX INTEGER {
        		force(1),
        		not-force(2)
        	}
        MAX-ACCESS read-write
        STATUS current
        DESCRIPTION
		"Force test even the port is in use."
        ::= { mlt 4 }
        
        mltResult 	OBJECT IDENTIFIER ::= { mlt 5 }
        
	mltVacTip OBJECT-TYPE
	SYNTAX INTEGER
	UNITS "0.1 rms"
	MAX-ACCESS read-only
	STATUS current
	DESCRIPTION
                "[Special value]:
                250000016 : No result.
                250000032 : Test failed.
                250000048 : 'Not Measured' reason # 1: Can't start the test when port is enabled and force not set.
                250000064 : 'Not Measured' reason # 2: Can't start the test when port is off-hook.
                250000080 : 'Not Measured' reason # 3: Can't start the test when port is disabled or on-hook.
                250000096 : 'Not Measured' reason # 4: can't start the test when port is disabled or off-hook or service state is out-of-service.
                250000112 : 'Not Measured' reason # 5: can't start the test when port is disabled or off-hook.
                250000128 : 'Not Measured' reason # 6: The test item will be skipped when testing all items and (vTip > 0.5Vac or vRing > 0.5Vac or abs(vTip) > 0.5Vdc or abs(vRing) > 0.5Vdc).
                250000144 : 'Not Measured' reason # 7: Hardware driver do not measure this item."
	::= { mltResult 1 }
	
	mltVacRing OBJECT-TYPE
	SYNTAX INTEGER
	UNITS "0.1 rms"
	MAX-ACCESS read-only
	STATUS current
	DESCRIPTION
                "[Special value]:
                250000016 : No result.
                250000032 : Test failed.
                250000048 : 'Not Measured' reason # 1: Can't start the test when port is enabled and force not set.
                250000064 : 'Not Measured' reason # 2: Can't start the test when port is off-hook.
                250000080 : 'Not Measured' reason # 3: Can't start the test when port is disabled or on-hook.
                250000096 : 'Not Measured' reason # 4: can't start the test when port is disabled or off-hook or service state is out-of-service.
                250000112 : 'Not Measured' reason # 5: can't start the test when port is disabled or off-hook.
                250000128 : 'Not Measured' reason # 6: The test item will be skipped when testing all items and (vTip > 0.5Vac or vRing > 0.5Vac or abs(vTip) > 0.5Vdc or abs(vRing) > 0.5Vdc).
                250000144 : 'Not Measured' reason # 7: Hardware driver do not measure this item."
	::= { mltResult 2 }
	
	mltVacDiff OBJECT-TYPE
	SYNTAX INTEGER
	UNITS "0.1 rms"
	MAX-ACCESS read-only
	STATUS current
	DESCRIPTION
                "[Special value]:
                250000016 : No result.
                250000032 : Test failed.
                250000048 : 'Not Measured' reason # 1: Can't start the test when port is enabled and force not set.
                250000064 : 'Not Measured' reason # 2: Can't start the test when port is off-hook.
                250000080 : 'Not Measured' reason # 3: Can't start the test when port is disabled or on-hook.
                250000096 : 'Not Measured' reason # 4: can't start the test when port is disabled or off-hook or service state is out-of-service.
                250000112 : 'Not Measured' reason # 5: can't start the test when port is disabled or off-hook.
                250000128 : 'Not Measured' reason # 6: The test item will be skipped when testing all items and (vTip > 0.5Vac or vRing > 0.5Vac or abs(vTip) > 0.5Vdc or abs(vRing) > 0.5Vdc).
                250000144 : 'Not Measured' reason # 7: Hardware driver do not measure this item."
	::= { mltResult 3 }
	
	mltVdcTip OBJECT-TYPE
	SYNTAX INTEGER
	UNITS "0.1 volt"
	MAX-ACCESS read-only
	STATUS current
	DESCRIPTION
                "[Special value]:
                250000016 : No result.
                250000032 : Test failed.
                250000048 : 'Not Measured' reason # 1: Can't start the test when port is enabled and force not set.
                250000064 : 'Not Measured' reason # 2: Can't start the test when port is off-hook.
                250000080 : 'Not Measured' reason # 3: Can't start the test when port is disabled or on-hook.
                250000096 : 'Not Measured' reason # 4: can't start the test when port is disabled or off-hook or service state is out-of-service.
                250000112 : 'Not Measured' reason # 5: can't start the test when port is disabled or off-hook.
                250000128 : 'Not Measured' reason # 6: The test item will be skipped when testing all items and (vTip > 0.5Vac or vRing > 0.5Vac or abs(vTip) > 0.5Vdc or abs(vRing) > 0.5Vdc).
                250000144 : 'Not Measured' reason # 7: Hardware driver do not measure this item."
	::= { mltResult 4 }
	
	mltVdcRing OBJECT-TYPE
	SYNTAX INTEGER
	UNITS "0.1 volt"
	MAX-ACCESS read-only
	STATUS current
	DESCRIPTION
                "[Special value]:
                250000016 : No result.
                250000032 : Test failed.
                250000048 : 'Not Measured' reason # 1: Can't start the test when port is enabled and force not set.
                250000064 : 'Not Measured' reason # 2: Can't start the test when port is off-hook.
                250000080 : 'Not Measured' reason # 3: Can't start the test when port is disabled or on-hook.
                250000096 : 'Not Measured' reason # 4: can't start the test when port is disabled or off-hook or service state is out-of-service.
                250000112 : 'Not Measured' reason # 5: can't start the test when port is disabled or off-hook.
                250000128 : 'Not Measured' reason # 6: The test item will be skipped when testing all items and (vTip > 0.5Vac or vRing > 0.5Vac or abs(vTip) > 0.5Vdc or abs(vRing) > 0.5Vdc).
                250000144 : 'Not Measured' reason # 7: Hardware driver do not measure this item."
	::= { mltResult 5 }
	
	mltVdcDiff OBJECT-TYPE
	SYNTAX INTEGER
	UNITS "0.1 volt"
	MAX-ACCESS read-only
	STATUS current
	DESCRIPTION
                "[Special value]:
                250000016 : No result.
                250000032 : Test failed.
                250000048 : 'Not Measured' reason # 1: Can't start the test when port is enabled and force not set.
                250000064 : 'Not Measured' reason # 2: Can't start the test when port is off-hook.
                250000080 : 'Not Measured' reason # 3: Can't start the test when port is disabled or on-hook.
                250000096 : 'Not Measured' reason # 4: can't start the test when port is disabled or off-hook or service state is out-of-service.
                250000112 : 'Not Measured' reason # 5: can't start the test when port is disabled or off-hook.
                250000128 : 'Not Measured' reason # 6: The test item will be skipped when testing all items and (vTip > 0.5Vac or vRing > 0.5Vac or abs(vTip) > 0.5Vdc or abs(vRing) > 0.5Vdc).
                250000144 : 'Not Measured' reason # 7: Hardware driver do not measure this item."
	::= { mltResult 6 }
	
	mltRLoop OBJECT-TYPE
	SYNTAX INTEGER
	UNITS "0.1 ohm"
	MAX-ACCESS read-only
	STATUS current
	DESCRIPTION
                "[Special value]:
                250000016 : No result.
                250000032 : Test failed.
                250000048 : 'Not Measured' reason # 1: Can't start the test when port is enabled and force not set.
                250000064 : 'Not Measured' reason # 2: Can't start the test when port is off-hook.
                250000080 : 'Not Measured' reason # 3: Can't start the test when port is disabled or on-hook.
                250000096 : 'Not Measured' reason # 4: can't start the test when port is disabled or off-hook or service state is out-of-service.
                250000112 : 'Not Measured' reason # 5: can't start the test when port is disabled or off-hook.
                250000128 : 'Not Measured' reason # 6: The test item will be skipped when testing all items and (vTip > 0.5Vac or vRing > 0.5Vac or abs(vTip) > 0.5Vdc or abs(vRing) > 0.5Vdc).
                250000144 : 'Not Measured' reason # 7: Hardware driver do not measure this item."
	::= { mltResult 7 }
	
	mltRtg OBJECT-TYPE
	SYNTAX INTEGER
	UNITS "0.1 ohm"
	MAX-ACCESS read-only
	STATUS current
	DESCRIPTION
                "[Special value]:
                250000016  : No result.
                250000032  : Test failed.
                250000048  : 'Not Measured' reason # 1: Can't start the test when port is enabled and force not set.
                250000064  : 'Not Measured' reason # 2: Can't start the test when port is off-hook.
                250000080  : 'Not Measured' reason # 3: Can't start the test when port is disabled or on-hook.
                250000096  : 'Not Measured' reason # 4: can't start the test when port is disabled or off-hook or service state is out-of-service.
                250000112  : 'Not Measured' reason # 5: can't start the test when port is disabled or off-hook.
                250000128  : 'Not Measured' reason # 6: The test item will be skipped when testing all items and (vTip > 0.5Vac or vRing > 0.5Vac or abs(vTip) > 0.5Vdc or abs(vRing) > 0.5Vdc).
                250000144  : 'Not Measured' reason # 7: Hardware driver do not measure this item.
                2147483647 : Circuit open.
                0          : Circuit short or fault."
	::= { mltResult 8 }
	
	mltRrg OBJECT-TYPE
	SYNTAX INTEGER
	UNITS "0.1 ohm"
	MAX-ACCESS read-only
	STATUS current
	DESCRIPTION
                "[Special value]:
                250000016  : No result.
                250000032  : Test failed.
                250000048  : 'Not Measured' reason # 1: Can't start the test when port is enabled and force not set.
                250000064  : 'Not Measured' reason # 2: Can't start the test when port is off-hook.
                250000080  : 'Not Measured' reason # 3: Can't start the test when port is disabled or on-hook.
                250000096  : 'Not Measured' reason # 4: can't start the test when port is disabled or off-hook or service state is out-of-service.
                250000112  : 'Not Measured' reason # 5: can't start the test when port is disabled or off-hook.
                250000128  : 'Not Measured' reason # 6: The test item will be skipped when testing all items and (vTip > 0.5Vac or vRing > 0.5Vac or abs(vTip) > 0.5Vdc or abs(vRing) > 0.5Vdc).
                250000144  : 'Not Measured' reason # 7: Hardware driver do not measure this item.           2147483647 : Circuit open.
                0          : Circuit short or fault."
	::= { mltResult 9 }
	
	mltRtr OBJECT-TYPE
	SYNTAX INTEGER
	UNITS "0.1 ohm"
	MAX-ACCESS read-only
	STATUS current
	DESCRIPTION
                "[Special value]:
                250000016  : No result.
                250000032  : Test failed.
                250000048  : 'Not Measured' reason # 1: Can't start the test when port is enabled and force not set.
                250000064  : 'Not Measured' reason # 2: Can't start the test when port is off-hook.
                250000080  : 'Not Measured' reason # 3: Can't start the test when port is disabled or on-hook.
                250000096  : 'Not Measured' reason # 4: can't start the test when port is disabled or off-hook or service state is out-of-service.
                250000112  : 'Not Measured' reason # 5: can't start the test when port is disabled or off-hook.
                250000128  : 'Not Measured' reason # 6: The test item will be skipped when testing all items and (vTip > 0.5Vac or vRing > 0.5Vac or abs(vTip) > 0.5Vdc or abs(vRing) > 0.5Vdc).
                250000144  : 'Not Measured' reason # 7: Hardware driver do not measure this item.           2147483647 : Circuit open.
                0          : Circuit short or fault."
	::= { mltResult 10 }
	
	mltCtg OBJECT-TYPE
	SYNTAX INTEGER
	UNITS "10^-10 F"
	MAX-ACCESS read-only
	STATUS current
	DESCRIPTION
                "[Special value]:
                250000016 : No result.
                250000032 : Test failed.
                250000048 : 'Not Measured' reason # 1: Can't start the test when port is enabled and force not set.
                250000064 : 'Not Measured' reason # 2: Can't start the test when port is off-hook.
                250000080 : 'Not Measured' reason # 3: Can't start the test when port is disabled or on-hook.
                250000096 : 'Not Measured' reason # 4: can't start the test when port is disabled or off-hook or service state is out-of-service.
                250000112 : 'Not Measured' reason # 5: can't start the test when port is disabled or off-hook.
                250000128 : 'Not Measured' reason # 6: The test item will be skipped when testing all items and (vTip > 0.5Vac or vRing > 0.5Vac or abs(vTip) > 0.5Vdc or abs(vRing) > 0.5Vdc).
                250000144 : 'Not Measured' reason # 7: Hardware driver do not measure this item."
	::= { mltResult 11 }
	
	mltCrg OBJECT-TYPE
	SYNTAX INTEGER
	UNITS "10^-10 F"
	MAX-ACCESS read-only
	STATUS current
	DESCRIPTION
                "[Special value]:
                250000016 : No result.
                250000032 : Test failed.
                250000048 : 'Not Measured' reason # 1: Can't start the test when port is enabled and force not set.
                250000064 : 'Not Measured' reason # 2: Can't start the test when port is off-hook.
                250000080 : 'Not Measured' reason # 3: Can't start the test when port is disabled or on-hook.
                250000096 : 'Not Measured' reason # 4: can't start the test when port is disabled or off-hook or service state is out-of-service.
                250000112 : 'Not Measured' reason # 5: can't start the test when port is disabled or off-hook.
                250000128 : 'Not Measured' reason # 6: The test item will be skipped when testing all items and (vTip > 0.5Vac or vRing > 0.5Vac or abs(vTip) > 0.5Vdc or abs(vRing) > 0.5Vdc).
                250000144 : 'Not Measured' reason # 7: Hardware driver do not measure this item."
	::= { mltResult 12 }
	
	mltCtr OBJECT-TYPE
	SYNTAX INTEGER
	UNITS "10^-10 F"
	MAX-ACCESS read-only
	STATUS current
	DESCRIPTION
                "[Special value]:
                250000016 : No result.
                250000032 : Test failed.
                250000048 : 'Not Measured' reason # 1: Can't start the test when port is enabled and force not set.
                250000064 : 'Not Measured' reason # 2: Can't start the test when port is off-hook.
                250000080 : 'Not Measured' reason # 3: Can't start the test when port is disabled or on-hook.
                250000096 : 'Not Measured' reason # 4: can't start the test when port is disabled or off-hook or service state is out-of-service.
                250000112 : 'Not Measured' reason # 5: can't start the test when port is disabled or off-hook.
                250000128 : 'Not Measured' reason # 6: The test item will be skipped when testing all items and (vTip > 0.5Vac or vRing > 0.5Vac or abs(vTip) > 0.5Vdc or abs(vRing) > 0.5Vdc).
                250000144 : 'Not Measured' reason # 7: Hardware driver do not measure this item."
	::= { mltResult 13 }
	
	mltRen OBJECT-TYPE
	SYNTAX INTEGER
	UNITS "0.1 ren"
	MAX-ACCESS read-only
	STATUS current
	DESCRIPTION
                "[Special value]:
                250000016  : No result.
                250000032  : Test failed.
                250000048  : 'Not Measured' reason # 1: Can't start the test when port is enabled and force not set.
                250000064  : 'Not Measured' reason # 2: Can't start the test when port is off-hook.
                250000080  : 'Not Measured' reason # 3: Can't start the test when port is disabled or on-hook.
                250000096  : 'Not Measured' reason # 4: can't start the test when port is disabled or off-hook or service state is out-of-service.
                250000112  : 'Not Measured' reason # 5: can't start the test when port is disabled or off-hook.
                250000128  : 'Not Measured' reason # 6: The test item will be skipped when testing all items and (vTip > 0.5Vac or vRing > 0.5Vac or abs(vTip) > 0.5Vdc or abs(vRing) > 0.5Vdc).
                250000144  : 'Not Measured' reason # 7: Hardware driver do not measure this item.
                2147483647 : Circuit open."
	::= { mltResult 14 }
	
	mltVRing OBJECT-TYPE
	SYNTAX INTEGER
	UNITS "0.1 volt"
	MAX-ACCESS read-only
	STATUS current
	DESCRIPTION
                "[Special value]:
                250000016 : No result.
                250000032 : Test failed.
                250000048 : 'Not Measured' reason # 1: Can't start the test when port is enabled and force not set.
                250000064 : 'Not Measured' reason # 2: Can't start the test when port is off-hook.
                250000080 : 'Not Measured' reason # 3: Can't start the test when port is disabled or on-hook.
                250000096 : 'Not Measured' reason # 4: can't start the test when port is disabled or off-hook or service state is out-of-service.
                250000112 : 'Not Measured' reason # 5: can't start the test when port is disabled or off-hook.
                250000128 : 'Not Measured' reason # 6: The test item will be skipped when testing all items and (vTip > 0.5Vac or vRing > 0.5Vac or abs(vTip) > 0.5Vdc or abs(vRing) > 0.5Vdc).
                250000144 : 'Not Measured' reason # 7: Hardware driver do not measure this item."
	::= { mltResult 15 }
	
	mltVMetering OBJECT-TYPE
	SYNTAX INTEGER
	UNITS "0.1 vpeak"
	MAX-ACCESS read-only
	STATUS current
	DESCRIPTION
                "[Special value]:
                250000016 : No result.
                250000032 : Test failed.
                250000048 : 'Not Measured' reason # 1: Can't start the test when port is enabled and force not set.
                250000064 : 'Not Measured' reason # 2: Can't start the test when port is off-hook.
                250000080 : 'Not Measured' reason # 3: Can't start the test when port is disabled or on-hook.
                250000096 : 'Not Measured' reason # 4: can't start the test when port is disabled or off-hook or service state is out-of-service.
                250000112 : 'Not Measured' reason # 5: can't start the test when port is disabled or off-hook.
                250000128 : 'Not Measured' reason # 6: The test item will be skipped when testing all items and (vTip > 0.5Vac or vRing > 0.5Vac or abs(vTip) > 0.5Vdc or abs(vRing) > 0.5Vdc).
                250000144 : 'Not Measured' reason # 7: Hardware driver do not measure this item."
	::= { mltResult 16 }
	
	mltDialToneDetected OBJECT-TYPE
	SYNTAX INTEGER {
		yes(1),
        no(2),
		test-failed(3),
		no-result(4)
	}
	MAX-ACCESS read-only
	STATUS current
	DESCRIPTION
                "Value List:
                1 : Yes.
                2 : No.
                3 : Test failed
                4 : No result."
	::= { mltResult 17 }
	
	mltDetectedDtmfCount OBJECT-TYPE
	SYNTAX INTEGER
	MAX-ACCESS read-only
	STATUS current
	DESCRIPTION
                "[Special value]:
                250000016 : No result.
                250000032 : Test failed.
                250000048 : 'Not Measured' reason # 1: Can't start the test when port is enabled and force not set.
                250000064 : 'Not Measured' reason # 2: Can't start the test when port is off-hook.
                250000080 : 'Not Measured' reason # 3: Can't start the test when port is disabled or on-hook.
                250000096 : 'Not Measured' reason # 4: can't start the test when port is disabled or off-hook or service state is out-of-service.
                250000112 : 'Not Measured' reason # 5: can't start the test when port is disabled or off-hook.
                250000128 : 'Not Measured' reason # 6: The test item will be skipped when testing all items and (vTip > 0.5Vac or vRing > 0.5Vac or abs(vTip) > 0.5Vdc or abs(vRing) > 0.5Vdc).
                250000144 : 'Not Measured' reason # 7: Hardware driver do not measure this item."
	::= { mltResult 18 }

	mltDialToneDelay OBJECT-TYPE
	SYNTAX INTEGER
	UNITS "0.001 sec"
	MAX-ACCESS read-only
	STATUS current
	DESCRIPTION
                "[Special value]:
                250000016 : No result.
                250000032 : Test failed.
                250000048 : 'Not Measured' reason # 1: Can't start the test when port is enabled and force not set.
                250000064 : 'Not Measured' reason # 2: Can't start the test when port is off-hook.
                250000080 : 'Not Measured' reason # 3: Can't start the test when port is disabled or on-hook.
                250000096 : 'Not Measured' reason # 4: can't start the test when port is disabled or off-hook or service state is out-of-service.
                250000112 : 'Not Measured' reason # 5: can't start the test when port is disabled or off-hook.
                250000128 : 'Not Measured' reason # 6: The test item will be skipped when testing all items and (vTip > 0.5Vac or vRing > 0.5Vac or abs(vTip) > 0.5Vdc or abs(vRing) > 0.5Vdc).
                250000144 : 'Not Measured' reason # 7: Hardware driver do not measure this item."
	::= { mltResult 19 }
	
	mltReceiverState OBJECT-TYPE
	SYNTAX INTEGER{
		on-hook(1),
        off-hook(2),
        short(3),
        open(4),
        not-measured(5)
	}
	MAX-ACCESS read-only
	STATUS current
	DESCRIPTION
                "[Normal Value]:
                1         : On hook.
                2         : Off hook.
                3         : circuit short or fault.
                4         : circuit open.    
                 
                 [Special value]:     
                250000016 : No result.
                250000032 : Test failed.
                250000048 : 'Not Measured' reason # 1: Can't start the test when port is enabled and force not set.
                250000064 : 'Not Measured' reason # 2: Can't start the test when port is off-hook.
                250000080 : 'Not Measured' reason # 3: Can't start the test when port is disabled or on-hook.
                250000096 : 'Not Measured' reason # 4: can't start the test when port is disabled or off-hook or service state is out-of-service.
                250000112 : 'Not Measured' reason # 5: can't start the test when port is disabled or off-hook.
                250000128 : 'Not Measured' reason # 6: The test item will be skipped when testing all items and (vTip > 0.5Vac or vRing > 0.5Vac or abs(vTip) > 0.5Vdc or abs(vRing) > 0.5Vdc).
                250000144 : 'Not Measured' reason # 7: Hardware driver do not measure this item."
	::= { mltResult 20 } 
	
	mltDetectedDtmfDigit OBJECT-TYPE
	SYNTAX DisplayString (SIZE (1..63))
	MAX-ACCESS read-only
	STATUS current
	DESCRIPTION
                "The DTMF digit string be detected in MLT test."
	::= { mltResult 21 }    
	
	mltErrorMsg OBJECT-TYPE
	SYNTAX DisplayString (SIZE (1..128))
	MAX-ACCESS read-only
	STATUS current
	DESCRIPTION
                "The error message when fail to start MLT test."
	::= { mltResult 22 }


-- mlt relay table
	
	mltRelayTable OBJECT-TYPE
        SYNTAX SEQUENCE OF MltRelayEntry
        MAX-ACCESS not-accessible
        STATUS current
        DESCRIPTION
		"Perform specified MLT relay function, or turn off 
		MLT relay function in specified subscriber."
        ::= { mlt 6 }

        mltRelayEntry OBJECT-TYPE
        SYNTAX MltRelayEntry
        MAX-ACCESS not-accessible
        STATUS current
        DESCRIPTION
		"An entry of mltRelayTable."
        INDEX  { ifIndex }
        ::= { mltRelayTable 1 }

        MltRelayEntry ::=
		SEQUENCE {
        		mltRelaySet		INTEGER,
        		mltRelayTimeout		INTEGER,
        		mltRelayForce		INTEGER
           	}

        mltRelaySet OBJECT-TYPE
        SYNTAX INTEGER {
        		in(1),
        		out(2),
        		both(3),
        		off(4)
        	}
        MAX-ACCESS read-write
        STATUS current
        DESCRIPTION
		"By default, relay function is turned off."
        ::= { mltRelayEntry 1 }
        
        mltRelayTimeout OBJECT-TYPE
        SYNTAX INTEGER (1..65535)
        UNITS "minute"
        MAX-ACCESS read-write
        STATUS current
        DESCRIPTION
		"Relays will be turned off automatically while the specified timer is timeout.
		This object is supported by R5.01 and later versions."
        ::= { mltRelayEntry 2 }
        
        mltRelayForce OBJECT-TYPE
        SYNTAX INTEGER
        MAX-ACCESS read-write
        STATUS current
        DESCRIPTION
		"Set to 1 to force to set relays even the port is in use.
		This object is supported by R5.01 and later versions."
        ::= { mltRelayEntry 3 }

		mltType OBJECT-TYPE
        SYNTAX INTEGER 
        MAX-ACCESS read-write
        STATUS current
        DESCRIPTION
		"option(All)       : all(0), test vac, vdc, riso, cap(1)
		option(Ring)    : normal(0), start to ring(1), stop to ring(2)
		option(Digit)    : normal(0), user input dtmf(1)
		"
        ::= { mlt 7 }
        
        mltCount OBJECT-TYPE
        SYNTAX INTEGER 
        MAX-ACCESS read-write
        STATUS current
        DESCRIPTION
		"When test mltOption digit(11) and mltType set to user input dtmf(1), 
		set the number of digit for testing."
        ::= { mlt 8 }
        
        mltAbort OBJECT-TYPE
        SYNTAX INTEGER 
        MAX-ACCESS read-write
        STATUS current
        DESCRIPTION
		"Set the slot id of a VoIP Card to terminate MLT test on it."
        ::= { mlt 9 }          
-- oamloopback

        oamloopbackTarget OBJECT-TYPE
        SYNTAX INTEGER
        MAX-ACCESS read-write
        STATUS current
        DESCRIPTION
		"IfIndex of the port which would be performed oamloopback test."
        ::= { oamloopback 1 }
        
        oamloopbackOps OBJECT-TYPE
        SYNTAX INTEGER
        MAX-ACCESS read-write
        STATUS current
        DESCRIPTION
        	"The manager sets the corresponding bit value to 1 to start the oamloopback test
        	and the agent clears the object to zero when oamloopback test is completed."
        ::= { oamloopback 2 }

	oamloopbackPacketNumber OBJECT-TYPE
        SYNTAX INTEGER
        MAX-ACCESS read-write
        STATUS current
        DESCRIPTION
		"Number of packets to be sent. 1~100000"
        ::= { oamloopback 3 }
        
        oamloopbackPacketSize OBJECT-TYPE
        SYNTAX INTEGER
        MAX-ACCESS read-write
        STATUS current
        DESCRIPTION
		"Size of each packet. 64~1518"
        ::= { oamloopback 4 }              
        
        oamloopbackResult 	OBJECT IDENTIFIER ::= { oamloopback 5 }
     
	oamloopbackRecvCnt OBJECT-TYPE
        SYNTAX INTEGER
        MAX-ACCESS read-only
        STATUS current
        DESCRIPTION
		"Number of packets received."
        ::= { oamloopbackResult 1 }
        
        oamloopbackElapseTime OBJECT-TYPE
        SYNTAX INTEGER
        MAX-ACCESS read-only
        STATUS current
        DESCRIPTION
		"oamloopback test elapsed time."
        ::= { oamloopbackResult 2 }
        
        oamloopbackErrorStatus OBJECT-TYPE
        SYNTAX INTEGER{
        		ok(0),
			alloc-fail(1),
			loopback-command-timeout(2),
			receive-packet-timeout(3),
			receive-packet-error(4),
			remote-state-error(5),
			unknown-result(6)
		}
	MAX-ACCESS read-only
        STATUS current
        DESCRIPTION
		"oamloopback test status."
        ::= { oamloopbackResult 3 }

-- vdslldm

	vdslldmTarget OBJECT-TYPE
	SYNTAX INTEGER
	MAX-ACCESS read-write
	STATUS current
	DESCRIPTION
		"IfIndex of the port which would be performed vdsl ldm test."
	::= { vdslldm 1 }
	
	vdslldmOps OBJECT-TYPE
	SYNTAX INTEGER
	MAX-ACCESS read-write
	STATUS current
	DESCRIPTION
		"The manager sets the object to 1 to start the vdsl ldm test
        	and the agent clears the object to zero when ldm test is successfully completed."
	::= { vdslldm 2 }

	vdslldmStatus OBJECT-TYPE
	SYNTAX DisplayString
	MAX-ACCESS read-only
	STATUS current
	DESCRIPTION
		"Status description of vdsl ldm test result."
	::= { vdslldm 3 }
	
	ldmVtuNeLoopAttenuationUS0 OBJECT-TYPE
	SYNTAX INTEGER
	UNITS "tenth dB"
	MAX-ACCESS read-only
	STATUS current
	DESCRIPTION
		"Loop Attenuation at US0 band.
		A special value -32768 indicates that no measurement could 
		be done for the sub-carrier group."
	::= { vdslldm 4 }
	
	ldmVtuNeLoopAttenuationUS1 OBJECT-TYPE
	SYNTAX INTEGER
	UNITS "tenth dB"
	MAX-ACCESS read-only
	STATUS current
	DESCRIPTION
		"Loop Attenuation at US1 band.
		A special value -32768 indicates that no measurement could 
		be done for the sub-carrier group."
	::= { vdslldm 5 }
	
	ldmVtuNeLoopAttenuationUS2 OBJECT-TYPE
	SYNTAX INTEGER
	UNITS "tenth dB"
	MAX-ACCESS read-only
	STATUS current
	DESCRIPTION
		"Loop Attenuation at US2 band.
		A special value -32768 indicates that no measurement could 
		be done for the sub-carrier group."
	::= { vdslldm 6 }
	
	ldmVtuNeLoopAttenuationUS3 OBJECT-TYPE
	SYNTAX INTEGER
	UNITS "tenth dB"
	MAX-ACCESS read-only
	STATUS current
	DESCRIPTION
		"Loop Attenuation at US3 band.
		A special value -32768 indicates that no measurement could 
		be done for the sub-carrier group."
	::= { vdslldm 7 }

	ldmVtuNeSignalAttenuationUS0 OBJECT-TYPE
	SYNTAX INTEGER
	UNITS "tenth dB"
	MAX-ACCESS read-only
	STATUS current
	DESCRIPTION
		"Signal Attenuation at US0 band.
		A special value -32768 indicates that no measurement could 
		be done for the sub-carrier group."
	::= { vdslldm 8 }

	ldmVtuNeSignalAttenuationUS1 OBJECT-TYPE
	SYNTAX INTEGER
	UNITS "tenth dB"
	MAX-ACCESS read-only
	STATUS current
	DESCRIPTION
		"Signal Attenuation at US1 band.
		A special value -32768 indicates that no measurement could 
		be done for the sub-carrier group."
	::= { vdslldm 9 }

	ldmVtuNeSignalAttenuationUS2 OBJECT-TYPE
	SYNTAX INTEGER
	UNITS "tenth dB"
	MAX-ACCESS read-only
	STATUS current
	DESCRIPTION
		"Signal Attenuation at US2 band.
		A special value -32768 indicates that no measurement could 
		be done for the sub-carrier group."
	::= { vdslldm 10 }

	ldmVtuNeSignalAttenuationUS3 OBJECT-TYPE
	SYNTAX INTEGER
	UNITS "tenth dB"
	MAX-ACCESS read-only
	STATUS current
	DESCRIPTION
		"Signal Attenuation at US3 band.
		A special value -32768 indicates that no measurement could 
		be done for the sub-carrier group."
	::= { vdslldm 11 }

	ldmVtuNeSignalMarginUS0 OBJECT-TYPE
	SYNTAX INTEGER
	UNITS "tenth dB"
	MAX-ACCESS read-only
	STATUS current
	DESCRIPTION
		"Signal Margin at US0 band.
		A special value -32768 indicates that no measurement could 
		be done for the sub-carrier group."
	::= { vdslldm 12 }

	ldmVtuNeSignalMarginUS1 OBJECT-TYPE
	SYNTAX INTEGER
	UNITS "tenth dB"
	MAX-ACCESS read-only
	STATUS current
	DESCRIPTION
		"Signal Margin at US1 band.
		A special value -32768 indicates that no measurement could 
		be done for the sub-carrier group."
	::= { vdslldm 13 }

	ldmVtuNeSignalMarginUS2 OBJECT-TYPE
	SYNTAX INTEGER
	UNITS "tenth dB"
	MAX-ACCESS read-only
	STATUS current
	DESCRIPTION
		"Signal Margin at US2 band.
		A special value -32768 indicates that no measurement could 
		be done for the sub-carrier group."
	::= { vdslldm 14 }

	ldmVtuNeSignalMarginUS3 OBJECT-TYPE
	SYNTAX INTEGER
	UNITS "tenth dB"
	MAX-ACCESS read-only
	STATUS current
	DESCRIPTION
		"Signal Margin at US3 band.
		A special value -32768 indicates that no measurement could 
		be done for the sub-carrier group."
	::= { vdslldm 15 } 

	ldmVtuNeAggregateTxPower OBJECT-TYPE
	SYNTAX INTEGER
	UNITS "tenth dB"
	MAX-ACCESS read-only
	STATUS current
	DESCRIPTION
		"Actual Aggregate Transmit Power.
		A special value -32768 indicates that no measurement could 
		be done for the sub-carrier group."
	::= { vdslldm 16 }
	
	ldmVtuNeAttainableBitRate OBJECT-TYPE
	SYNTAX Unsigned32
	UNITS "bits per second"
	MAX-ACCESS read-only
	STATUS current
	DESCRIPTION
		"Attainable Bit Rate."
	::= { vdslldm 17 }

	ldmVtuFeLoopAttenuationDS1 OBJECT-TYPE
	SYNTAX INTEGER
	UNITS "tenth dB"
	MAX-ACCESS read-only
	STATUS current
	DESCRIPTION
		"Loop Attenuation at DS1 band.
		A special value -32768 indicates that no measurement could 
		be done for the sub-carrier group."
	::= { vdslldm 18 }

	ldmVtuFeLoopAttenuationDS2 OBJECT-TYPE
	SYNTAX INTEGER
	UNITS "tenth dB"
	MAX-ACCESS read-only
	STATUS current
	DESCRIPTION
		"Loop Attenuation at DS2 band.
		A special value -32768 indicates that no measurement could 
		be done for the sub-carrier group."
	::= { vdslldm 19 }

	ldmVtuFeLoopAttenuationDS3 OBJECT-TYPE
	SYNTAX INTEGER
	UNITS "tenth dB"
	MAX-ACCESS read-only
	STATUS current
	DESCRIPTION
		"Loop Attenuation at DS3 band.
		A special value -32768 indicates that no measurement could 
		be done for the sub-carrier group."
	::= { vdslldm 20 }

	ldmVtuFeSignalAttenuationDS1 OBJECT-TYPE
	SYNTAX INTEGER
	UNITS "tenth dB"
	MAX-ACCESS read-only
	STATUS	current
	DESCRIPTION
		"Signal Attenuation at DS1 band.
		A special value -32768 indicates that no measurement could 
		be done for the sub-carrier group."
	::= { vdslldm 21 }

	ldmVtuFeSignalAttenuationDS2 OBJECT-TYPE
	SYNTAX INTEGER
	UNITS "tenth dB"
	MAX-ACCESS read-only
	STATUS	current
	DESCRIPTION
		"Signal Attenuation at DS2 band.
		A special value -32768 indicates that no measurement could 
		be done for the sub-carrier group."
	::= { vdslldm 22 }

	ldmVtuFeSignalAttenuationDS3 OBJECT-TYPE
	SYNTAX INTEGER
	UNITS "tenth dB"
	MAX-ACCESS read-only
	STATUS	current
	DESCRIPTION
		"Signal Attenuation at DS3 band.
		A special value -32768 indicates that no measurement could 
		be done for the sub-carrier group."
	::= { vdslldm 23 }

	ldmVtuFeSignalMarginDS1 OBJECT-TYPE
	SYNTAX INTEGER
	UNITS "tenth dB"
	MAX-ACCESS read-only
	STATUS current
	DESCRIPTION
		"Signal Margin at DS1 band.
		A special value -32768 indicates that no measurement could 
		be done for the sub-carrier group."
	::= { vdslldm 24 }

	ldmVtuFeSignalMarginDS2 OBJECT-TYPE
	SYNTAX INTEGER
	UNITS "tenth dB"
	MAX-ACCESS read-only
	STATUS current
	DESCRIPTION
		"Signal Margin at DS2 band.
		A special value -32768 indicates that no measurement could 
		be done for the sub-carrier group."
	::= { vdslldm 25 }

	ldmVtuFeSignalMarginDS3 OBJECT-TYPE
	SYNTAX INTEGER
	UNITS "tenth dB"
	MAX-ACCESS read-only
	STATUS current
	DESCRIPTION
		"Signal Margin at DS3 band.
		A special value -32768 indicates that no measurement could 
		be done for the sub-carrier group."
	::= { vdslldm 26 }

	ldmVtuFeAggregateTxPower OBJECT-TYPE
	SYNTAX INTEGER
	UNITS "tenth dB"
	MAX-ACCESS read-only
	STATUS current
	DESCRIPTION
		"Actual Aggregate Transmit Power.
		A special value -32768 indicates that no measurement could 
		be done for the sub-carrier group."
	::= { vdslldm 27 }
	
	ldmVtuFeAttainableBitRate OBJECT-TYPE
	SYNTAX Unsigned32
	UNITS "bits per second"
	MAX-ACCESS read-only
	STATUS current
	DESCRIPTION
		"Attainable Bit Rate."
	::= { vdslldm 28 }

	ldmVtuNeHlinScale OBJECT-TYPE
	SYNTAX INTEGER
	MAX-ACCESS read-only
	STATUS current
	DESCRIPTION
		"Scale of Hlin."
	::= { vdslldm 29 }
					
	ldmVtuNeHlinReal OBJECT-TYPE
	SYNTAX OCTET STRING
	MAX-ACCESS read-only
	STATUS current
	DESCRIPTION
		"The object provides real part of Hlin for the subcarriers.
		Each subcarrier takes two octets to store the value."
	::= { vdslldm 30 }

	ldmVtuNeHlinImage OBJECT-TYPE
	SYNTAX OCTET STRING
	MAX-ACCESS read-only
	STATUS current
	DESCRIPTION
		"The object provides image part of Hlin for the subcarriers.
		Each subcarrier takes two octets to store the value."
	::= { vdslldm 31 }

	ldmVtuNeHlog OBJECT-TYPE
	SYNTAX OCTET STRING
	MAX-ACCESS read-only
	STATUS current
	DESCRIPTION
		"The object provides Hlog for the subcarriers.
		Each subcarrier takes two octets to store the value.
		A special value -32768 indicates that no measurement could 
		be done for the sub-carrier group."
	::= { vdslldm 32 }

	ldmVtuNeQln OBJECT-TYPE
	SYNTAX OCTET STRING
	MAX-ACCESS read-only
	STATUS current
	DESCRIPTION
		"The object provides QLN for the subcarriers.
		Each subcarrier takes two octets to store the value."
	::= { vdslldm 33 }

	ldmVtuNeSnr OBJECT-TYPE
	SYNTAX OCTET STRING
	MAX-ACCESS read-only
	STATUS current
	DESCRIPTION
		"The object provides SNR for the subcarriers.
		Each subcarrier takes two octets to store the value.
		A special value -32768 indicates that no measurement 
		could be done for the sub-carrier group."
	::= { vdslldm 34 }

	ldmVtuFeHlinScale OBJECT-TYPE
	SYNTAX INTEGER
	MAX-ACCESS read-only
	STATUS current
	DESCRIPTION
		"Scale of Hlin."
	::= { vdslldm 35 }
					
	ldmVtuFeHlinReal OBJECT-TYPE
	SYNTAX OCTET STRING
	MAX-ACCESS read-only
	STATUS current
	DESCRIPTION
		"Real part of Hlin. Each subcarrier takes two octets to store the value."
	::= { vdslldm 36 }

	ldmVtuFeHlinImage OBJECT-TYPE
	SYNTAX OCTET STRING
	MAX-ACCESS read-only
	STATUS current
	DESCRIPTION
		"Image part of Hlin. Each subcarrier takes two octets to store the value."
	::= { vdslldm 37 }

	ldmVtuFeHlog OBJECT-TYPE
	SYNTAX OCTET STRING
	MAX-ACCESS read-only
	STATUS current
	DESCRIPTION
		"Hlog of subcarrier. Each subcarrier takes two octets to store the value.
		A special value -32768 indicates that no measurement could be done for 
		the sub-carrier group."
	::= { vdslldm 38 }

	ldmVtuFeQln OBJECT-TYPE
	SYNTAX OCTET STRING
	MAX-ACCESS read-only
	STATUS current
	DESCRIPTION
		"QLN of subcarrier. Each subcarrier takes two octets to store the value."
	::= { vdslldm 39 }
	
	ldmVtuFeSnr OBJECT-TYPE
	SYNTAX OCTET STRING
	MAX-ACCESS read-only
	STATUS current
	DESCRIPTION
		"SNR of subcarrier. Each subcarrier takes two octets to store the value.
		A special value -32768 indicates that no measurement could be done for 
		the sub-carrier group."
	::= { vdslldm 40 }
	
	ldmVtuNeHlinGroupSize OBJECT-TYPE
	SYNTAX INTEGER
	MAX-ACCESS read-only
	STATUS current
	DESCRIPTION
		"Number of sub-carriers per group used to report the H(f) linear representation values for the 
		respective transmission direction. The valid values are 1, 2, 4 and 8. 
		This object is supported by R5.02 and later versions."
	::= { vdslldm 41 }

	ldmVtuFeHlinGroupSize OBJECT-TYPE
	SYNTAX INTEGER
	MAX-ACCESS read-only
	STATUS current
	DESCRIPTION
		"Number of sub-carriers per group used to report the H(f) linear representation values for the 
		respective transmission direction. The valid values are 1, 2, 4 and 8. 
		This object is supported by R5.02 and later versions."
	::= { vdslldm 42 }
	
	ldmVtuNeHlogGroupSize OBJECT-TYPE
	SYNTAX INTEGER
	MAX-ACCESS read-only
	STATUS current
	DESCRIPTION
		"Number of sub-carriers per group used to report the H(f) linear representation values for the 
		respective transmission direction. The valid values are 1, 2, 4 and 8. 
		This object is supported by R5.02 and later versions."
	::= { vdslldm 43 }

	ldmVtuFeHlogGroupSize OBJECT-TYPE
	SYNTAX INTEGER
	MAX-ACCESS read-only
	STATUS current
	DESCRIPTION
		"Number of sub-carriers per group used to report the H(f) linear representation values for the 
		respective transmission direction. The valid values are 1, 2, 4 and 8. 
		This object is supported by R5.02 and later versions."
	::= { vdslldm 44 }

	ldmVtuNeQlnGroupSize OBJECT-TYPE
	SYNTAX INTEGER
	MAX-ACCESS read-only
	STATUS current
	DESCRIPTION
		"Number of sub-carriers per group used to report the Quiet Line Noise values for the 
		respective transmission direction. The valid values are 1, 2, 4 and 8. 
		This object is supported by R5.02 and later versions."
	::= { vdslldm 45 }

	ldmVtuFeQlnGroupSize OBJECT-TYPE
	SYNTAX INTEGER
	MAX-ACCESS read-only
	STATUS current
	DESCRIPTION
		"Number of sub-carriers per group used to report the Quiet Line Noise values for the 
		respective transmission direction. The valid values are 1, 2, 4 and 8. 
		This object is supported by R5.02 and later versions."
	::= { vdslldm 46 }

	ldmVtuNeSnrGroupSize OBJECT-TYPE
	SYNTAX INTEGER
	MAX-ACCESS read-only
	STATUS current
	DESCRIPTION
		"Number of sub-carriers per group used to report the SNR values on the 
		respective transmission direction. The valid values are 1, 2, 4 and 8. 
		This object is supported by R5.02 and later versions."
	::= { vdslldm 47 }

	ldmVtuFeSnrGroupSize OBJECT-TYPE
	SYNTAX INTEGER
	MAX-ACCESS read-only
	STATUS current
	DESCRIPTION
		"Number of sub-carriers per group used to report the SNR values on the 
		respective transmission direction. The valid values are 1, 2, 4 and 8. 
		This object is supported by R5.02 and later versions."
	::= { vdslldm 48 }

--------------------
-- imaOamF5Loopback
--------------------
        
        imaOamF5LoopbackTargetGroupIndex OBJECT-TYPE
        SYNTAX INTEGER
        MAX-ACCESS read-write
        STATUS current
        DESCRIPTION
		""
        ::= { imaOamF5Loopback 1 }
        
        imaOamF5LoopbackTargetVpi OBJECT-TYPE
        SYNTAX INTEGER
        MAX-ACCESS read-write
        STATUS current
        DESCRIPTION
		"VPI of the virtual channel which would be performed imaOamF5Loopback test."
        ::= { imaOamF5Loopback 2 }
        
        imaOamF5LoopbackTargetVci OBJECT-TYPE
        SYNTAX INTEGER
        MAX-ACCESS read-write
        STATUS current
        DESCRIPTION
		"VCI of the virtual channel which would be performed imaOamF5Loopback test."
        ::= { imaOamF5Loopback 3 }
        
        imaOamF5LoopbackType OBJECT-TYPE
		SYNTAX 	INTEGER {
			end-to-end(1),
			segment(2)
		}
		MAX-ACCESS read-write
		STATUS current
		DESCRIPTION
		""
		::= { imaOamF5Loopback 4 }
		
		imaOamF5LoopbackOps OBJECT-TYPE
        SYNTAX INTEGER
        MAX-ACCESS read-write
        STATUS current
        DESCRIPTION
        	"The manager sets the corresponding bit value to 1 to start the imaOamF5Loopback test
        	and the agent clears the object to zero when loopback test is successfully completed."
        ::= { imaOamF5Loopback 5 }   
		
		imaOamF5LoopbackSegmentId OBJECT-TYPE
		SYNTAX DisplayString
		MAX-ACCESS read-write
		STATUS current
		DESCRIPTION
		"16 bytes segment id."
		::= { imaOamF5Loopback 6 }
        
        imaOamF5LoopbackStatus OBJECT-TYPE
		SYNTAX DisplayString
		MAX-ACCESS read-only
		STATUS current
		DESCRIPTION
		"Status description of IMA OAM F5 Loopback test result."
		::= { imaOamF5Loopback 7 }
 
 
--------------------
-- xdsl2ExtSCStatusTable
--------------------
    xdsl2ExtSCStatusTable  OBJECT-TYPE
    SYNTAX      SEQUENCE  OF  Xdsl2ExtSCStatusEntry
    MAX-ACCESS  not-accessible
    STATUS      current
    DESCRIPTION
       "The table xdsl2ExtSCStatusTable extends xdsl2SCStatusTable for 
         ZyXEL product."
    ::= { xdsl2ExtStatus 1 }

    xdsl2ExtSCStatusEntry  OBJECT-TYPE
    SYNTAX      Xdsl2ExtSCStatusEntry
    MAX-ACCESS  not-accessible
    STATUS      current
    DESCRIPTION
       "The table xdsl2ExtSCStatusTable contains extra subcarrier  
        status parameters besides those in xdsl2LineSegmentTable."
    INDEX  { ifIndex, xdsl2SCStatusDirection }
    ::= { xdsl2ExtSCStatusTable 1 }

    Xdsl2ExtSCStatusEntry  ::=
    SEQUENCE {
       xdsl2SCStatusActAtp    Integer32
    }
    
    xdsl2SCStatusActAtp  OBJECT-TYPE
    SYNTAX      Integer32 (-310..310 | 2147483647)
    UNITS       "0.1 dBm"
    MAX-ACCESS  read-only
    STATUS      current
    DESCRIPTION
       "Actual Aggregate Transmit Power Downstream. 
        The total amount of transmit power delivered by the xTU-C at
        the U-C reference point, at the instant of measurement.  It
        ranges from -310 to 310 units of 0.1 dBm (Physical values are -31
        to 31 dBm).
        A value of 0x7FFFFFFF (2147483647) indicates the measurement is
        out of range to be represented.
        This object reflects the value of the parameter following the
        most recent DELT performed on the associated line.  Once the DELT
        process is over, the parameter no longer changes until the row is
        deleted or a new DELT process is initiated.
        "
    DEFVAL       { 2147483647 }
    ::= { xdsl2ExtSCStatusEntry 1 }  

--------------------
-- xdsl2ExtSCStatusBandTable
--------------------
    xdsl2ExtSCStatusBandTable  OBJECT-TYPE
    SYNTAX      SEQUENCE  OF  Xdsl2ExtSCStatusBandEntry
    MAX-ACCESS  not-accessible
    STATUS      current
    DESCRIPTION
       "The table xdsl2ExtSCStatusBandTable extends xdsl2SCStatusBandTable for 
         ZyXEL product."
    ::= { xdsl2ExtStatus 2 }

    xdsl2ExtSCStatusBandEntry  OBJECT-TYPE
    SYNTAX      Xdsl2ExtSCStatusBandEntry
    MAX-ACCESS  not-accessible
    STATUS      current
    DESCRIPTION
       "The table xdsl2ExtSCStatusBandTable contains extra subcarrier  
        status parameters that are grouped per-band besides those in 
        xdsl2SCStatusBandTable."
    INDEX  { ifIndex, xdsl2SCStatusBand }
    ::= { xdsl2ExtSCStatusBandTable 1 }

    Xdsl2ExtSCStatusBandEntry  ::=
    SEQUENCE {
       xdsl2SCStatusBandSnrMargin          Integer32
    }    

    xdsl2SCStatusBandSnrMargin  OBJECT-TYPE
    SYNTAX      Integer32 (-640..630 | 2147483646 | 2147483647)
    UNITS       "0.1 dB"
    MAX-ACCESS  read-only
    STATUS      current
    DESCRIPTION
       "SNR Margin is the maximum increase in dB of the noise power
        received at the xTU (xTU-R for a band in the downstream direction
        and xTU-C for a band in the upstream direction), such that the
        BER requirements are met for all bearer channels received at the
        xTU. Values range from -640 to 630 in units of 0.1 dB (Physical
        values are -64 to 63 dB).
        A special value of 0x7FFFFFFF (2147483647) indicates the SNR
        Margin is out of range to be represented.
        A special value of 0x7FFFFFFE (2147483646) indicates the SNR
        Margin measurement is currently unavailable.
        This object reflects the value of the parameter following the
        most recent DELT performed on the associated line.  Once the DELT
        process is over, the parameter no longer changes until the row is
        deleted or a new DELT process is initiated."
    DEFVAL       { 2147483646 }
    ::= { xdsl2ExtSCStatusBandEntry 1 }              	
----------------------------------------
-- ipconf 
----------------------------------------
--------------------
-- staticRoute
--------------------

	staticRoute 	OBJECT IDENTIFIER ::= { ipconf 1 }

        maxNumOfStaticRoutes OBJECT-TYPE
        SYNTAX INTEGER
        MAX-ACCESS read-only
        STATUS current
        DESCRIPTION
		"The maximum number of static routes supported by the system."
        ::= { staticRoute 1 }

        staticRouteTable OBJECT-TYPE
        SYNTAX SEQUENCE OF StaticRouteEntry
        MAX-ACCESS not-accessible
        STATUS current
        DESCRIPTION
		"A table that contains information about static routes."
        ::= { staticRoute 2 }

        staticRouteEntry OBJECT-TYPE
        SYNTAX StaticRouteEntry
        MAX-ACCESS not-accessible
        STATUS current
        DESCRIPTION
		"A list of static route entry."
        INDEX  { IMPLIED staticRouteName }
        ::= { staticRouteTable 1 }

        StaticRouteEntry ::=
		SEQUENCE {
        		staticRouteName		DisplayString,
			staticRouteDest		IpAddress,
			staticRouteMask		IpAddress,
			staticRouteGateway	IpAddress,
			staticRouteMetric	INTEGER,
			staticRouteRowStatus	RowStatus
           	}

        staticRouteName OBJECT-TYPE
        SYNTAX DisplayString (SIZE (1..31))
        MAX-ACCESS read-only
        STATUS current
        DESCRIPTION
		"The name of the static route."
        ::= { staticRouteEntry 1 }

        staticRouteDest OBJECT-TYPE
        SYNTAX IpAddress
        MAX-ACCESS read-create
        STATUS current
        DESCRIPTION
		"The destination IP address of the static route."
        ::= { staticRouteEntry 2 }

        staticRouteMask OBJECT-TYPE
        SYNTAX IpAddress
        MAX-ACCESS read-create
        STATUS current
        DESCRIPTION
		"The subnet mask of the static route."
        ::= { staticRouteEntry 3 }

        staticRouteGateway OBJECT-TYPE
        SYNTAX IpAddress
        MAX-ACCESS read-create
        STATUS current
        DESCRIPTION
		"The gateway IP address of the static route."
        ::= { staticRouteEntry 4 }

        staticRouteMetric OBJECT-TYPE
        SYNTAX INTEGER
        MAX-ACCESS read-create
        STATUS current
        DESCRIPTION
		"The routing metric of the static route."
        ::= { staticRouteEntry 5 }

        staticRouteRowStatus OBJECT-TYPE
        SYNTAX RowStatus
        MAX-ACCESS read-create
        STATUS current
        DESCRIPTION
        	"This object is used to create a new row or modify or delete an existing row
        	in this table. A row is activated by setting this object to `active', , and is
        	deactivated by setting it to 'notInService'."
        ::= { staticRouteEntry 6 }

--------------------
-- staticIp
--------------------

	staticIp 	OBJECT IDENTIFIER ::= { ipconf 2 }

    staticIpInbandIp OBJECT-TYPE
    SYNTAX IpAddress
    MAX-ACCESS read-write
    STATUS current
    DESCRIPTION
	"Inband IP Address. Not immediately apply. Use staticIpOps to apply the object setting on device."
    ::= { staticIp 1 }
    
    staticIpInbandMask OBJECT-TYPE
    SYNTAX IpAddress
    MAX-ACCESS read-write
    STATUS current
    DESCRIPTION
	"Inband IP Mask. Not immediately apply. Use staticIpOps to apply the object setting on device."
    ::= { staticIp 2 }
    
    staticIpInbandVlan OBJECT-TYPE
    SYNTAX INTEGER
    MAX-ACCESS read-write
    STATUS current
    DESCRIPTION
	"Inband IP Vlan. Not immediately apply. Use staticIpOps to apply the object setting on device."
    ::= { staticIp 3 }
    
    staticIpOutbandIp OBJECT-TYPE
    SYNTAX IpAddress
    MAX-ACCESS read-write
    STATUS current
    DESCRIPTION
	"Outband IP Address. Not immediately apply. Use staticIpOps to apply the object setting on device."
    ::= { staticIp 4 }
    
    staticIpOutbandMask OBJECT-TYPE
    SYNTAX IpAddress
    MAX-ACCESS read-write
    STATUS current
    DESCRIPTION
	"Outband IP Mask. Not immediately apply. Use staticIpOps to apply the object setting on device."
    ::= { staticIp 5 }
    
    staticIpGatewayIP OBJECT-TYPE
    SYNTAX IpAddress
    MAX-ACCESS read-write
    STATUS current
    DESCRIPTION
	"Gateway IP Address. Not immediately apply. Use staticIpOps to apply the object setting on device."
    ::= { staticIp 6 } 
    
    staticIpOps OBJECT-TYPE
    SYNTAX INTEGER{
    	set(1),
  		reload(2)  		
    }
    MAX-ACCESS read-write
    STATUS current
    DESCRIPTION
	"The manager setting will temporary saved but not set into Device.
	Set value of staticIpOps to 1 to apply the setting of IpTable on device.
	Set value of staticIpOps to 2 to reload the real setting of IpTable on device now.
	"
    ::= { staticIp 7 }       			        	
----------------------------------------
-- lcm
----------------------------------------

	numOfChassis OBJECT-TYPE
	SYNTAX INTEGER
	MAX-ACCESS read-only
	STATUS current
	DESCRIPTION
		"The number of chassis in the system."
	::= { lcm 1 }

-- Chassis Table
	
	chassisTable OBJECT-TYPE
	SYNTAX SEQUENCE OF ChassisEntry
	MAX-ACCESS not-accessible
	STATUS current
	DESCRIPTION
		"The table which contains the chassis information in the system."
	::= { lcm 2 }
			
	chassisEntry OBJECT-TYPE
	SYNTAX ChassisEntry
	MAX-ACCESS not-accessible
	STATUS current
	DESCRIPTION
		""
	INDEX { chassisId }
	::= { chassisTable 1 }
			
	ChassisEntry ::=
		SEQUENCE {
			chassisId		INTEGER,
			chassisFrameNumber	INTEGER,
			chassisSerialNumber  	DisplayString,
			chassisNumber		INTEGER,
			chassisStatus  		INTEGER
		}
	
	chassisId OBJECT-TYPE
	SYNTAX INTEGER
	MAX-ACCESS read-only
	STATUS current
	DESCRIPTION
		"The Chassis ID."
	::= { chassisEntry 1 }
	
	chassisFrameNumber OBJECT-TYPE
	SYNTAX INTEGER
	MAX-ACCESS read-write
	STATUS current
	DESCRIPTION
		"The Frame ID."
	::= { chassisEntry 2 }
	
	chassisSerialNumber OBJECT-TYPE
	SYNTAX DisplayString
	MAX-ACCESS read-only
	STATUS current
	DESCRIPTION
		"The Chassis Serial Number."
	::= { chassisEntry 3 }

	chassisNumber OBJECT-TYPE
	SYNTAX INTEGER (1..64)
	MAX-ACCESS read-write
	STATUS current
	DESCRIPTION
		"The Chassis Number which is defined by the system administrator
		for management purpose."
	::= { chassisEntry 4 }
	
	chassisStatus OBJECT-TYPE
	SYNTAX	INTEGER {
			empty(1),
			up(2),
			down(3),
			testing(4)
		}
	MAX-ACCESS read-only
	STATUS current
	DESCRIPTION
		"The current status of the chassis."
	::= { chassisEntry 5 }

-- Slot Table
		
	slotTable OBJECT-TYPE
	SYNTAX SEQUENCE OF SlotEntry
	MAX-ACCESS not-accessible
	STATUS current
	DESCRIPTION
		"The table which contains the slot information in a chassis."
	::= { lcm 3 }
			
	slotEntry OBJECT-TYPE
	SYNTAX SlotEntry
	MAX-ACCESS not-accessible
	STATUS current
	DESCRIPTION
		""
	INDEX { chassisId, slotId }
	::= { slotTable 1 }
			
	SlotEntry ::=
		SEQUENCE {
			slotId				INTEGER,
			slotModuleType			INTEGER,
			slotModuleDescr			DisplayString,
			slotModuleFWVersion  		DisplayString,
			slotModuleDriverVersion 	DisplayString,
			slotModuleModemCodeVersion 	DisplayString,
			slotModuleStatus		INTEGER,
			slotModuleAlarmStatus 		INTEGER,
			slotModuleSerialNumber		DisplayString,
			slotModuleHWVersion		DisplayString,
			slotModuleUpTime		INTEGER,
			slotModuleMacAddress MacAddress,
			slotModuleMacAddress2 MacAddress
		}
			
	slotId OBJECT-TYPE
	SYNTAX INTEGER
	MAX-ACCESS read-only
	STATUS current
	DESCRIPTION
		"Identity of the slot."
	::= { slotEntry 1 }

	slotModuleType OBJECT-TYPE
	SYNTAX	INTEGER {
			unknown(1),
			msc1000G(101),
			alc1248G-51(102),
			alc1248G-53(103),
			slc1248G-22(104),
			vlc1224G-41(105),
			msc1024G(106),
			alc1272G-51(107),
			vop1248G-61-SIP(108),
			msc1000GA(109),
			vlc1324G-51(110),
			msc1224G(111),
			vop1248G-61-H248(112),
			vlc1348G-51(113),
			elc1220G-55(114),
			msc1024GA(115),
			vlc1324G-53(116),
			ima1408G-81(117),
			vlc1424G-56(118),
			slc1348G-22(119),
			vlc1348G-53(120),
			alc1372G-51(121),
			msc1024GB(122), 
			msc1224GB(123),
			vop1372G-61-H248(124),
			msc1024GC(125),
			glc1320G-55(126),
			vop1372G-61-SIP(127),
			alc1348G-51C(128),
			alc1348G-51C-H248(129)
		}
	MAX-ACCESS read-only
	STATUS current
	DESCRIPTION
		"Card type of the plug-in card."
	::= { slotEntry 2 }
	
	slotModuleDescr OBJECT-TYPE
	SYNTAX DisplayString
	MAX-ACCESS read-only
	STATUS current
	DESCRIPTION
		"The descriptions of the plug-in card."
	::= { slotEntry 3 }
	
	slotModuleFWVersion OBJECT-TYPE
	SYNTAX DisplayString
	MAX-ACCESS read-only
	STATUS current
	DESCRIPTION
		"The firmware version of the plug-in card."
	::= { slotEntry 4 }
	
	slotModuleDriverVersion	OBJECT-TYPE
	SYNTAX DisplayString
	MAX-ACCESS read-only
	STATUS current
	DESCRIPTION
		"The DSL driver of the plug-in card."
	::= { slotEntry 5 }
	
	slotModuleModemCodeVersion OBJECT-TYPE
	SYNTAX DisplayString
	MAX-ACCESS read-only
	STATUS current
	DESCRIPTION
		"The DSL modem code version of the plug-in card."
	::= { slotEntry 6 }
	
	slotModuleStatus OBJECT-TYPE
	SYNTAX	INTEGER {
			empty(1),
			up(2),
			down(3),
			testing(4),
			standby(5)
		}
	MAX-ACCESS read-only
	STATUS current
	DESCRIPTION
		"The module state of the plug-in card."
	::= { slotEntry 7 }
	
	slotModuleAlarmStatus OBJECT-TYPE
	SYNTAX INTEGER
	MAX-ACCESS read-only
	STATUS current
	DESCRIPTION
		"This variable indicates the alarm status of the module.
		It is a bit map represented a sum, therefore, it can represent 
		multiple defects simultaneously. The moduleNoDefect should be set 
		if and only if no other flag is set.
		
		The various bit positions are:
             1   moduleNoDefect
             2   moduleOverHeat
		     3	 moduleFanRpmLow
		     4	 moduleVoltageLow
		     5   moduleThermalSensorFailure
		     6   modulePullOut
		     7   powerDC48VAFailure
		     8   powerDC48VBFailure
		     9   extAlarmInputTrigger
		    10   moduleDown
		    11 	 mscSwitchOverOK
		    12	 networkTopologyChange
		    13	 macSpoof
		    14   cpuHigh
		    15   memoryUsageHigh
		    16   packetBufferUsageHigh
		    17	 loopguardOccurence"
	::= { slotEntry 8 }
	
	slotModuleSerialNumber OBJECT-TYPE
	SYNTAX DisplayString
	MAX-ACCESS read-only
	STATUS current
	DESCRIPTION
		"The serial number of the plug-in card."
	::= { slotEntry 9 }
	
	slotModuleHWVersion OBJECT-TYPE
	SYNTAX DisplayString
	MAX-ACCESS read-only
	STATUS current
	DESCRIPTION
		"The hardware version of the plug-in card."
	::= { slotEntry 10 }
	
	slotModuleUpTime OBJECT-TYPE
	SYNTAX INTEGER
	UNITS "second"
	MAX-ACCESS read-only
	STATUS current
	DESCRIPTION
		"The time (in seconds) since the plug-in card was last re-initialized."
	::= { slotEntry 11 }
	
	slotModuleMacAddress OBJECT-TYPE
	SYNTAX MacAddress
	MAX-ACCESS read-only
	STATUS current
	DESCRIPTION
		"The MAC Address of the plug-in card."
	::= { slotEntry 12 }
	
	slotModuleMacAddress2 OBJECT-TYPE
	SYNTAX MacAddress
	MAX-ACCESS read-only
	STATUS current
	DESCRIPTION
		"The MAC Address of the plug-in card."
	::= { slotEntry 13 }
	
-- MSC Port Table

	mscPortTable OBJECT-TYPE
	SYNTAX SEQUENCE OF MscPortEntry
	MAX-ACCESS not-accessible
	STATUS current
	DESCRIPTION
		"The table contains MSC port status."
	::= { lcm 4 }
			
	mscPortEntry OBJECT-TYPE
	SYNTAX MscPortEntry
	MAX-ACCESS not-accessible
	STATUS current
	DESCRIPTION
		""
	INDEX { chassisId, slotId, mscPortId }
	::= { mscPortTable 1 }
			
	MscPortEntry ::=
		SEQUENCE {
			mscPortId		INTEGER,
			mscPortType		INTEGER
		}
	
	mscPortId OBJECT-TYPE
	SYNTAX INTEGER
	MAX-ACCESS read-only
	STATUS current
	DESCRIPTION
		"Identity of the MSC port."
	::= { mscPortEntry 1 }

	mscPortType OBJECT-TYPE
	SYNTAX	INTEGER {
			unknown(1),
			e1000BaseT(2),
			e1000BaseLX(3),
			e1000BaseSX(4),
			e100BaseFX(5), 
			e100BaseTX(6),
			e1000BaseGBIC(7),
			e10000BaseGBIC(8)			
		}
	MAX-ACCESS read-only
	STATUS current
	DESCRIPTION
		"Type of the MSC port."
	::= { mscPortEntry 2 }

----------------------------------------
-- multicast 
----------------------------------------

	staticMulticast		OBJECT IDENTIFIER ::= { multicast 2 }
	igmpFilter		OBJECT IDENTIFIER ::= { multicast 3 }
	mcastBandwidth		OBJECT IDENTIFIER ::= { multicast 4 }
	igmpCount		OBJECT IDENTIFIER ::= { multicast 5 }
	mvlan			OBJECT IDENTIFIER ::= { multicast 6 }
	queryVid		OBJECT IDENTIFIER ::= { multicast 7 }

	igmpEnable OBJECT-TYPE
	SYNTAX	INTEGER {
			enableProxy(1),
			enableSnooping(2),
			disable(3)
		}
	MAX-ACCESS read-write
	STATUS current
	DESCRIPTION
		"Enable/disable IGMP protocol."
	::= { multicast 1 }

	igmpMode OBJECT-TYPE
	SYNTAX	INTEGER {
			aggresive(1),
			normal(2)
		}
	MAX-ACCESS read-write
	STATUS current
	DESCRIPTION
		"Setting IGMP with aggresive mode will issue an IGMP report from new active port 
		when topology change occurs, while normal mode won't."
	::= { multicast 8 }

	igmpVersion OBJECT-TYPE
	SYNTAX	INTEGER {
			v2(1),
			v3(2),
			mldv1(3),
			mldv2(4)
		}
	MAX-ACCESS read-write
	STATUS current
	DESCRIPTION
		"Setting IGMP version. This object is supported by R3.00 and later versions."
	::= { multicast 9 }

	igmpFastLeaveEnable OBJECT-TYPE
	SYNTAX	INTEGER {
			enable(1),
			disable(2)
		}
	MAX-ACCESS read-write
	STATUS current
	DESCRIPTION
		""
	::= { multicast 10 }
	
	igmpFastLeaveTimer OBJECT-TYPE
	SYNTAX INTEGER
	UNITS "second"
	MAX-ACCESS read-write
	STATUS current
	DESCRIPTION
		""
	::= { multicast 11 }   
	
	unknownMulticast OBJECT-TYPE
	SYNTAX	INTEGER {
			drop(1),
			flood(2)
		}
	MAX-ACCESS read-write
	STATUS current
	DESCRIPTION
		""
	::= { multicast 12 }

	ipv6PassThrough OBJECT-TYPE
	SYNTAX	INTEGER {
			drop(1),
			flood(2),
			disable(3)
		}
	MAX-ACCESS read-write
	STATUS current
	DESCRIPTION
		"Set IPv6 packet transparent passthrough."
	::= { multicast 13 }

	reservedGroup OBJECT-TYPE
	SYNTAX	INTEGER {
			drop(1),
			flood(2)
		}
	MAX-ACCESS read-write
	STATUS current
	DESCRIPTION
		"Set reserved packets transparent passthrougth"
	::= { multicast 14 } 
	
	igmpHistoryTable OBJECT-TYPE
        SYNTAX SEQUENCE OF IgmpHistoryEntry
        MAX-ACCESS not-accessible
        STATUS current
        DESCRIPTION
                "This table contains multicast IGMP/MLD history configuration."
        ::= { multicast 15 }

        igmpHistoryEntry OBJECT-TYPE
        SYNTAX IgmpHistoryEntry
        MAX-ACCESS not-accessible
        STATUS current
        DESCRIPTION
        	"The entry of multicast igmp history table."
        INDEX { slotId }
        ::= { igmpHistoryTable 1 }

        IgmpHistoryEntry ::=
        	SEQUENCE {
        		igmphistoryenable			INTEGER
           	}
	
	igmphistoryenable OBJECT-TYPE
	SYNTAX INTEGER{
			enable(1),
			disable(2)	
	}
	MAX-ACCESS read-write
	STATUS current
	DESCRIPTION
		"Enable/disable IGMP/MLD multicast group join/leave history logging."
	::= { igmpHistoryEntry 1 }
			
--------------------
--  staticMulticast
--------------------

-- mcastGroupTable
        		
	maxNumberOfMcastGroups OBJECT-TYPE
	SYNTAX INTEGER
	MAX-ACCESS read-only
	STATUS current
	DESCRIPTION
		"The max number of static multicast groups supported by the system."
	::= { staticMulticast 1 }

	mcastGroupTable OBJECT-TYPE
        SYNTAX SEQUENCE OF McastGroupEntry
        MAX-ACCESS not-accessible
        STATUS current
        DESCRIPTION
                "A table that contains static multicast group information."
        ::= { staticMulticast 2 }

        mcastGroupEntry OBJECT-TYPE
        SYNTAX McastGroupEntry
        MAX-ACCESS not-accessible
        STATUS current
        DESCRIPTION
        	"The entry of multicast group table."
        INDEX { dot1qVlanIndex, mcastGroupIp }
        ::= { mcastGroupTable 1 }

        McastGroupEntry ::=
        	SEQUENCE {
        		mcastGroupIp				IpAddress,        		
        		mcastGroupFixedPorts		PortList,
        		mcastGroupForbiddenPorts	PortList,
				mcastGroupRowStatus			RowStatus
           	}
	
	mcastGroupIp OBJECT-TYPE
	SYNTAX IpAddress
	MAX-ACCESS read-only
	STATUS current
	DESCRIPTION
		"The multicast IP address of the group."
	::= { mcastGroupEntry 1 }

	mcastGroupFixedPorts OBJECT-TYPE
	SYNTAX PortList
	MAX-ACCESS read-create
	STATUS current
	DESCRIPTION
		"The port list which specify the ports joining the multicast group."
	::= { mcastGroupEntry 2 }

	mcastGroupForbiddenPorts OBJECT-TYPE
	SYNTAX PortList
	MAX-ACCESS read-create
	STATUS current
	DESCRIPTION
		"The port list which specify the ports prohibited by the multicast group."
	::= { mcastGroupEntry 3 }
		
	mcastGroupRowStatus OBJECT-TYPE
	SYNTAX RowStatus
	MAX-ACCESS read-create
	STATUS current
	DESCRIPTION
		"The row status of the multicast group entry."
	::= { mcastGroupEntry 4 } 

-- macMcastGroupTable

	maxNumberOfMacMcastGroups OBJECT-TYPE
	SYNTAX INTEGER
	MAX-ACCESS read-only
	STATUS current
	DESCRIPTION
		"The maximum number of row entries that user can create in macMcastGroupTable.
		This object is supported by R5.02 and later versions."
	::= { staticMulticast 3 }

        macMcastGroupTable OBJECT-TYPE
        SYNTAX SEQUENCE OF MacMcastGroupEntry
        MAX-ACCESS not-accessible
        STATUS current
        DESCRIPTION
		"This table specify the static multicast group with MAC address.
		This table is supported by R5.02 and later versions."
        ::= { staticMulticast 4 }

	macMcastGroupEntry OBJECT-TYPE
        SYNTAX MacMcastGroupEntry
        MAX-ACCESS not-accessible
        STATUS current
        DESCRIPTION
        	"An entry of macMcastGroupTable."
        INDEX { dot1qVlanIndex, macMcastGroupMac }
        ::= { macMcastGroupTable 1 }

        MacMcastGroupEntry ::=
        	SEQUENCE {
			macMcastGroupMac		PhysAddress,
			macMcastGroupFixedPorts		PortList,
			macMcastGroupRowStatus		RowStatus
           	}
           
        macMcastGroupMac OBJECT-TYPE
        SYNTAX  PhysAddress
        MAX-ACCESS read-only
        STATUS current
        DESCRIPTION
		"The multicast MAC address of the group."
        ::= { macMcastGroupEntry 1 }
 
        macMcastGroupFixedPorts OBJECT-TYPE
        SYNTAX PortList
        MAX-ACCESS read-create
        STATUS current
        DESCRIPTION
		"The port list which specify the ports joining the multicast group."
        ::= { macMcastGroupEntry 2 }

        macMcastGroupRowStatus OBJECT-TYPE
        SYNTAX RowStatus
        MAX-ACCESS read-create
        STATUS current
        DESCRIPTION
		"The row status of the MAC multicast group entry."
        ::= { macMcastGroupEntry 3 }

-- mcastInetGroupTable
	mcastInetGroupTable OBJECT-TYPE
        SYNTAX SEQUENCE OF McastInetGroupEntry
        MAX-ACCESS not-accessible
        STATUS current
        DESCRIPTION
                "A table that contains static multicast group information."
        ::= { staticMulticast 5 }

        mcastInetGroupEntry OBJECT-TYPE
        SYNTAX McastInetGroupEntry
        MAX-ACCESS not-accessible
        STATUS current
        DESCRIPTION
        	"The entry of multicast group table."
        INDEX { dot1qVlanIndex, mcastGroupInetAddrType, mcastGroupInetAddr }
        ::= { mcastInetGroupTable 1 }

        McastInetGroupEntry ::=
        	SEQUENCE {
        		mcastGroupInetAddrType      	InetAddressType,
        		mcastGroupInetAddr				InetAddress,        		
        		mcastGroupInetFixedPorts		PortList,
        		mcastGroupInetForbiddenPorts	PortList,
				mcastGroupInetRowStatus			RowStatus
           	}
    mcastGroupInetAddrType OBJECT-TYPE
	SYNTAX InetAddressType
	MAX-ACCESS read-only
	STATUS current
	DESCRIPTION
		"The multicast IP address type of the group."
	::= { mcastInetGroupEntry 1 }
	
	mcastGroupInetAddr OBJECT-TYPE
	SYNTAX InetAddress
	MAX-ACCESS read-only
	STATUS current
	DESCRIPTION
		"The multicast IP address of the group."
	::= { mcastInetGroupEntry 2 }

	mcastGroupInetFixedPorts OBJECT-TYPE
	SYNTAX PortList
	MAX-ACCESS read-create
	STATUS current
	DESCRIPTION
		"The port list which specify the ports joining the multicast group."
	::= { mcastInetGroupEntry 3 }

	mcastGroupInetForbiddenPorts OBJECT-TYPE
	SYNTAX PortList
	MAX-ACCESS read-create
	STATUS current
	DESCRIPTION
		"The port list which specify the ports prohibited by the multicast group."
	::= { mcastInetGroupEntry 4 }
		
	mcastGroupInetRowStatus OBJECT-TYPE
	SYNTAX RowStatus
	MAX-ACCESS read-create
	STATUS current
	DESCRIPTION
		"The row status of the multicast group entry."
	::= { mcastInetGroupEntry 5 }
	
--------------------
--  igmpFilter
--------------------

	maxNumOfIgmpFilters OBJECT-TYPE
	SYNTAX INTEGER
	MAX-ACCESS read-only
	STATUS current
	DESCRIPTION
		"The max number of IGMP filters supported by the system."
	::= { igmpFilter 1 }

-- IGMP Filter Table

	igmpFilterTable OBJECT-TYPE
        SYNTAX SEQUENCE OF IgmpFilterEntry
        MAX-ACCESS not-accessible
        STATUS current
        DESCRIPTION
                "A table that contains IGMP filters."
        ::= { igmpFilter 2 }

        igmpFilterEntry OBJECT-TYPE
        SYNTAX IgmpFilterEntry
        MAX-ACCESS not-accessible
        STATUS current
        DESCRIPTION
        	"The entry of IGMP filter table."
        INDEX { igmpFilterName, igmpFilterIndex }
        ::= { igmpFilterTable 1 }

        IgmpFilterEntry ::=
        	SEQUENCE {
        		igmpFilterName		DisplayString,
        		igmpFilterIndex		INTEGER,
        		igmpFilterStartIp	IpAddress,
        		igmpFilterEndIp		IpAddress,
				igmpFilterRowStatus	RowStatus,
				igmpFilterInetAddrType	InetAddressType,
				igmpFilterInetAddrStart InetAddress,
				igmpFilterInetAddrEnd	InetAddress				
           	}
	
	igmpFilterName OBJECT-TYPE
	SYNTAX DisplayString (SIZE (1..31))
	MAX-ACCESS read-only
	STATUS current
	DESCRIPTION
		"The IGMP filter name."
	::= { igmpFilterEntry 1 }

	igmpFilterIndex OBJECT-TYPE
	SYNTAX INTEGER
	MAX-ACCESS read-only
	STATUS current
	DESCRIPTION
		"The index which specif the filter rule."
	::= { igmpFilterEntry 2 }

	igmpFilterStartIp OBJECT-TYPE
	SYNTAX IpAddress
	MAX-ACCESS read-create
	STATUS current
	DESCRIPTION
		"The start IP of the filter rule."
	::= { igmpFilterEntry 3 }
	
	igmpFilterEndIp OBJECT-TYPE
	SYNTAX IpAddress
	MAX-ACCESS read-create
	STATUS current
	DESCRIPTION
		"The end IP of the filter rule."
	::= { igmpFilterEntry 4 }
		
	igmpFilterRowStatus OBJECT-TYPE
	SYNTAX RowStatus
	MAX-ACCESS read-create
	STATUS current
	DESCRIPTION
		"The row status of the IGMP filter entry."
	::= { igmpFilterEntry 5 } 
	
	igmpFilterInetAddrType OBJECT-TYPE
	SYNTAX InetAddressType
	MAX-ACCESS read-create
	STATUS current
	DESCRIPTION
		"The IP Address type."
	::= { igmpFilterEntry 6 }
	
	igmpFilterInetAddrStart OBJECT-TYPE
	SYNTAX InetAddress
	MAX-ACCESS read-create
	STATUS current
	DESCRIPTION
		"The start IP of the filter rule."
	::= { igmpFilterEntry 7 }
	
	igmpFilterInetAddrEnd OBJECT-TYPE
	SYNTAX InetAddress
	MAX-ACCESS read-create
	STATUS current
	DESCRIPTION
		"The end IP of the filter rule."
	::= { igmpFilterEntry 8 }


-- IGMP Filter Port Table
	
        igmpFilterPortTable OBJECT-TYPE
        SYNTAX SEQUENCE OF IgmpFilterPortEntry
        MAX-ACCESS not-accessible
        STATUS current
        DESCRIPTION
		"This table specif the IGMP filter of the port."
        ::= { igmpFilter 3 }

	igmpFilterPortEntry OBJECT-TYPE
        SYNTAX IgmpFilterPortEntry
        MAX-ACCESS not-accessible
        STATUS current
        DESCRIPTION
        	"An entry in igmpFilterPortTable."
        INDEX { ifIndex }
        ::= { igmpFilterPortTable 1 }

        IgmpFilterPortEntry ::=
        	SEQUENCE {
			igmpFilterPortFilterName	DisplayString
           	}
           
        igmpFilterPortFilterName OBJECT-TYPE
        SYNTAX DisplayString (SIZE (1..31))
        MAX-ACCESS read-write
        STATUS current
        DESCRIPTION
		"The IGMP filter name of the port."
        ::= { igmpFilterPortEntry 1 }

-- Batch Set for IGMP Filter

	igmpfilterBatchSet		OBJECT IDENTIFIER ::= { igmpFilter 4 }
		
        igmpfilterTarget OBJECT-TYPE
        SYNTAX OCTET STRING
        MAX-ACCESS read-write
        STATUS current
        DESCRIPTION
		"This managed object is used for identify the target on which 
		the port configuration should be performed. The target is encoded as:
		Byte 1:   the octet specifies a set of eight chassis, chassis 0 through 7
		Byte 2~4: each octet specifies a set of eight slots, with the 
			  first octet specifying slots 1 through 8, and the second
		          octet specifying slots 9 through 16, and so on.
		Byte 5~:  each octet specifies a set of eight ports, with the first
		          octet specifying ports 1 through 8, etc."
        ::= { igmpfilterBatchSet 1 }
        
        igmpfilterOps OBJECT-TYPE
        SYNTAX INTEGER
        MAX-ACCESS read-write
        STATUS current
        DESCRIPTION
		"The corresponding bit is set to 1 to start the operation.
		The various bit positions are:
		BIT 1: set IGMP filter."
        ::= { igmpfilterBatchSet 2 }

        igmpfilterForBatchSet OBJECT-TYPE
        SYNTAX DisplayString (SIZE (1..31))
        MAX-ACCESS read-write
        STATUS current
        DESCRIPTION
                "The IGMP filter name."
         ::= { igmpfilterBatchSet 3 }

--------------------
--  bandwidth
--------------------

	mcastDefaultBandwidth OBJECT-TYPE
	SYNTAX INTEGER (1..100000)
	UNITS "Kbps"
	MAX-ACCESS read-write
	STATUS current
	DESCRIPTION
		"Default bandwidth requirement for a multicast channel.
		This object is supported by R1.02 and later versions."
	::= { mcastBandwidth 1 }

	maxNumOfMcastBw OBJECT-TYPE
	SYNTAX INTEGER
	MAX-ACCESS read-only
	STATUS current
	DESCRIPTION
		"The maximum number of row entries that user can create in mcastBwTable.
		This object is supported by R1.02 and later versions."
	::= { mcastBandwidth 2 }
	
-- mcastBwTable

	mcastBwTable OBJECT-TYPE
        SYNTAX SEQUENCE OF McastBwEntry
        MAX-ACCESS not-accessible
        STATUS current
        DESCRIPTION
                "This table defines bandwidth budget for a range of multicast IP channels.
                This table is supported by R1.02 and later versions."
        ::= { mcastBandwidth 3 }

        mcastBwEntry OBJECT-TYPE
        SYNTAX McastBwEntry
        MAX-ACCESS not-accessible
        STATUS current
        DESCRIPTION
        	"An entry of mcastBwTable."
        INDEX { mcastBwIndex, mcastBwStartIp, mcastBwEndIp }
        ::= { mcastBwTable 1 }

        McastBwEntry ::=
        	SEQUENCE {
        		mcastBwIndex			INTEGER,
        		mcastBwStartIp			IpAddress,
        		mcastBwEndIp			IpAddress,
        		mcastBwBandwidth		INTEGER,
				mcastBwRowStatus		RowStatus
           	}

	mcastBwIndex OBJECT-TYPE
	SYNTAX INTEGER
	MAX-ACCESS read-only
	STATUS current
	DESCRIPTION
		"The index which specify the entry."
	::= { mcastBwEntry 1 }

	mcastBwStartIp OBJECT-TYPE
	SYNTAX IpAddress
	MAX-ACCESS read-only
	STATUS current
	DESCRIPTION
		"The start multicast IP of the bandwidth control range."
	::= { mcastBwEntry 2 }
	
	mcastBwEndIp OBJECT-TYPE
	SYNTAX IpAddress
	MAX-ACCESS read-only
	STATUS current
	DESCRIPTION
		"The end multicast IP of the bandwidth control range."
	::= { mcastBwEntry 3 }

	mcastBwBandwidth OBJECT-TYPE
	SYNTAX INTEGER
	UNITS "Kbps"
	MAX-ACCESS read-create
	STATUS current
	DESCRIPTION
		"The bandwidth budget for the multicast IP channels."
	::= { mcastBwEntry 4 }
			
	mcastBwRowStatus OBJECT-TYPE
	SYNTAX RowStatus
	MAX-ACCESS read-create
	STATUS current
	DESCRIPTION
		"The row status of the entry."
	::= { mcastBwEntry 5 }

-- mcastBwPortTable
	
        mcastBwPortTable OBJECT-TYPE
        SYNTAX SEQUENCE OF McastBwPortEntry
        MAX-ACCESS not-accessible
        STATUS current
        DESCRIPTION
		"This table specify the multicast bandwidth control of the port.
		This table is supported by R1.02 and later versions."
        ::= { mcastBandwidth 4 }

	mcastBwPortEntry OBJECT-TYPE
        SYNTAX McastBwPortEntry
        MAX-ACCESS not-accessible
        STATUS current
        DESCRIPTION
        	"An entry of mcastBwPortTable."
        INDEX { ifIndex }
        ::= { mcastBwPortTable 1 }

        McastBwPortEntry ::=
        	SEQUENCE {
			mcastBwPortEnable	INTEGER,
			mcastBwPortBandwidth	INTEGER
           	}
           
        mcastBwPortEnable OBJECT-TYPE
        SYNTAX  INTEGER {
        		enable(1),
        		disable(2)
        	}
        MAX-ACCESS read-write
        STATUS current
        DESCRIPTION
		"Enable/disable multicast bandwidth control for a port."
        ::= { mcastBwPortEntry 1 }
 
        mcastBwPortBandwidth OBJECT-TYPE
        SYNTAX INTEGER
        UNITS "Kbps"
        MAX-ACCESS read-write
        STATUS current
        DESCRIPTION
		"Set bandwidth threshold for a port."
        ::= { mcastBwPortEntry 2 }

-- mcastBwInetTable

	mcastBwInetTable OBJECT-TYPE
        SYNTAX SEQUENCE OF McastBwInetEntry
        MAX-ACCESS not-accessible
        STATUS current
        DESCRIPTION
                "This table defines bandwidth budget for a range of multicast IP channels for IPv6.
                This table is supported by R5.06 and later versions."
        ::= { mcastBandwidth 5 }

        mcastBwInetEntry OBJECT-TYPE
        SYNTAX McastBwInetEntry
        MAX-ACCESS not-accessible
        STATUS current
        DESCRIPTION
        	"An entry of mcastBwInetTable."
        INDEX { mcastBwInetIndex, mcastBwInetAddrType, mcastBwInetAddrStart, mcastBwInetAddrEnd }
        ::= { mcastBwInetTable 1 }

        McastBwInetEntry ::=
        	SEQUENCE {
        		mcastBwInetIndex			INTEGER,
        		mcastBwInetAddrType		InetAddressType,
        		mcastBwInetAddrStart	InetAddress,
        		mcastBwInetAddrEnd		InetAddress,
        		mcastBwInetBandwidth	INTEGER,
				mcastBwInetRowStatus	RowStatus
           	}

	mcastBwInetIndex OBJECT-TYPE
	SYNTAX INTEGER
	MAX-ACCESS read-only
	STATUS current
	DESCRIPTION
		"The index which specify the entry."
	::= { mcastBwInetEntry 1 }
	
	mcastBwInetAddrType OBJECT-TYPE
	SYNTAX InetAddressType
	MAX-ACCESS read-only
	STATUS current
	DESCRIPTION
		"The ip address type of multicast IP."
	::= { mcastBwInetEntry 2 }

	mcastBwInetAddrStart OBJECT-TYPE
	SYNTAX InetAddress
	MAX-ACCESS read-only
	STATUS current
	DESCRIPTION
		"The start multicast IP of the bandwidth control range."
	::= { mcastBwInetEntry 3 }
	
	mcastBwInetAddrEnd OBJECT-TYPE
	SYNTAX InetAddress
	MAX-ACCESS read-only
	STATUS current
	DESCRIPTION
		"The end multicast IP of the bandwidth control range."
	::= { mcastBwInetEntry 4 }

	mcastBwInetBandwidth OBJECT-TYPE
	SYNTAX INTEGER
	UNITS "Kbps"
	MAX-ACCESS read-create
	STATUS current
	DESCRIPTION
		"The bandwidth budget for the multicast IP channels."
	::= { mcastBwInetEntry 5 }
			
	mcastBwInetRowStatus OBJECT-TYPE
	SYNTAX RowStatus
	MAX-ACCESS read-create
	STATUS current
	DESCRIPTION
		"The row status of the entry."
	::= { mcastBwInetEntry 6 }
	
--------------------
--  igmpCount
--------------------

-- igmpCountPortTable

        igmpCountPortTable OBJECT-TYPE
        SYNTAX SEQUENCE OF IgmpCountPortEntry
        MAX-ACCESS not-accessible
        STATUS current
        DESCRIPTION
		"This table specify the IGMP count limiting of the port.
		This table is supported by R1.02 and later versions."
        ::= { igmpCount 1 }

	igmpCountPortEntry OBJECT-TYPE
        SYNTAX IgmpCountPortEntry
        MAX-ACCESS not-accessible
        STATUS current
        DESCRIPTION
        	"An entry of igmpCountPortTable."
        INDEX { ifIndex }
        ::= { igmpCountPortTable 1 }

        IgmpCountPortEntry ::=
        	SEQUENCE {
			igmpCountPortEnable	INTEGER,
			igmpCountPortLimit	INTEGER
           	}
           
        igmpCountPortEnable OBJECT-TYPE
        SYNTAX  INTEGER {
        		enable(1),
        		disable(2)
        	}
        MAX-ACCESS read-write
        STATUS current
        DESCRIPTION
		"Enable/disable IGMP count limiting for a port."
        ::= { igmpCountPortEntry 1 }
 
        igmpCountPortLimit OBJECT-TYPE
        SYNTAX INTEGER
        MAX-ACCESS read-write
        STATUS current
        DESCRIPTION
		"The maximum allowed IGMP report count for a port."
        ::= { igmpCountPortEntry 2 }

-- igmpMessageCountPortTable
	
	igmpMessageCountPortTable OBJECT-TYPE
        SYNTAX SEQUENCE OF IgmpMessageCountPortEntry
        MAX-ACCESS not-accessible
        STATUS current
        DESCRIPTION
		"This table specify the IGMP message count limiting of the port."
        ::= { igmpCount 2 }

	igmpMessageCountPortEntry OBJECT-TYPE
        SYNTAX IgmpMessageCountPortEntry
        MAX-ACCESS not-accessible
        STATUS current
        DESCRIPTION
        	"An entry of igmpMessageCountPortTable."
        INDEX { ifIndex }
        ::= { igmpMessageCountPortTable 1 }

        IgmpMessageCountPortEntry ::=
        	SEQUENCE {
			igmpMessageCountPortEnable	INTEGER,
			igmpMessageCountPortLimit	INTEGER
           	}
           
        igmpMessageCountPortEnable OBJECT-TYPE
        SYNTAX  INTEGER {
        		enable(1),
        		disable(2)
        	}
        MAX-ACCESS read-write
        STATUS current
        DESCRIPTION
		"Enable/disable IGMP message count limiting for a port."
        ::= { igmpMessageCountPortEntry 1 }
 
        igmpMessageCountPortLimit OBJECT-TYPE
        SYNTAX INTEGER
        MAX-ACCESS read-write
        STATUS current
        DESCRIPTION
		"The maximum allowed IGMP message count for a port."
        ::= { igmpMessageCountPortEntry 2 }
        	
--------------------
--  mvlan
--------------------

	maxNumOfMvlan OBJECT-TYPE
	SYNTAX INTEGER
	MAX-ACCESS read-only
	STATUS current
	DESCRIPTION
		"The maximum number of row entries that user can create in mvlanTable."
	::= { mvlan 1 }
	
-- mvlanTable

	mvlanTable OBJECT-TYPE
   	SYNTAX SEQUENCE OF MvlanEntry
    	MAX-ACCESS not-accessible
    	STATUS current
    	DESCRIPTION
        	"A table containing static configuration information for
        	each multicast VLAN configured into the device."
    	::= { mvlan 2 }

	mvlanEntry OBJECT-TYPE
    	SYNTAX MvlanEntry
    	MAX-ACCESS not-accessible
    	STATUS current
    	DESCRIPTION
        	"An entry of mvlanTable."
    	INDEX { mvlanIndex }
    	::= { mvlanTable 1 }

	MvlanEntry ::=
    		SEQUENCE {
    			mvlanIndex		VlanIndex,
        		mvlanName		DisplayString,     		
        		mvlanEgressPorts	PortList,
       			mvlanRowStatus		RowStatus,
       			mvlan8021pPriority	INTEGER
    		}

	mvlanIndex OBJECT-TYPE
    	SYNTAX VlanIndex
    	MAX-ACCESS read-only
    	STATUS current
    	DESCRIPTION
        	"The VLAN-ID refering to this VLAN."
    	::= { mvlanEntry 1 }
    	
	mvlanName OBJECT-TYPE
    	SYNTAX DisplayString (SIZE (0..31))
    	MAX-ACCESS read-create
    	STATUS current
    	DESCRIPTION
        	"An administratively assigned string, which may be used to identify the VLAN."
    	::= { mvlanEntry 2 }

	mvlanEgressPorts OBJECT-TYPE
    	SYNTAX PortList
    	MAX-ACCESS read-create
    	STATUS current
    	DESCRIPTION
        	"The set of ports which are permanently assigned to the
        	egress list for this multicast VLAN."
    	::= { mvlanEntry 3 }

	mvlanRowStatus OBJECT-TYPE
    	SYNTAX RowStatus
    	MAX-ACCESS read-create
    	STATUS current
    	DESCRIPTION
        	"This object indicates the status of this entry."
    	::= { mvlanEntry 4 }
    
    	mvlan8021pPriority OBJECT-TYPE
    	SYNTAX INTEGER (0..7)
    	MAX-ACCESS read-create
    	STATUS current
    	DESCRIPTION
        	""
    	::= { mvlanEntry 5 }
    	
-- mvlanTranslateTable

	mvlanTranslateTable OBJECT-TYPE
        SYNTAX SEQUENCE OF MvlanTranslateEntry
        MAX-ACCESS not-accessible
        STATUS current
        DESCRIPTION
                "A table that contains multicast to VLAN translation."
        ::= { mvlan 3 }

        mvlanTranslateEntry OBJECT-TYPE
        SYNTAX MvlanTranslateEntry
        MAX-ACCESS not-accessible
        STATUS current
        DESCRIPTION
        	"An entry of mvlanTranslateTable."
        INDEX { dot1qVlanIndex, mvlanTranslateIndex }
        ::= { mvlanTranslateTable 1 }

        MvlanTranslateEntry ::=
        	SEQUENCE {
        		mvlanTranslateIndex		INTEGER,
        		mvlanTranslateStartIp		IpAddress,
        		mvlanTranslateEndIp		IpAddress,
        		mvlanTranslateInetAddrType	InetAddressType,
        		mvlanTranslateInetAddrStart	InetAddress,
        		mvlanTranslateInetAddrEnd	InetAddress
           	}
	
	mvlanTranslateIndex OBJECT-TYPE
	SYNTAX INTEGER
	MAX-ACCESS read-only
	STATUS current
	DESCRIPTION
		"The index which specif the entry."
	::= { mvlanTranslateEntry 1 }

	mvlanTranslateStartIp OBJECT-TYPE
	SYNTAX IpAddress
	MAX-ACCESS read-write
	STATUS current
	DESCRIPTION
		"The start IP of the multicast VLAN translation."
	::= { mvlanTranslateEntry 2 }
	
	mvlanTranslateEndIp OBJECT-TYPE
	SYNTAX IpAddress
	MAX-ACCESS read-write
	STATUS current
	DESCRIPTION
		"The end IP of the multicast VLAN translation."
	::= { mvlanTranslateEntry 3 } 
	
	mvlanTranslateInetAddrType OBJECT-TYPE
	SYNTAX InetAddressType
	MAX-ACCESS read-write
	STATUS current
	DESCRIPTION
		"The IP Address type."
	::= { mvlanTranslateEntry 4 }
	
	mvlanTranslateInetAddrStart OBJECT-TYPE
	SYNTAX InetAddress
	MAX-ACCESS read-write
	STATUS current
	DESCRIPTION
		"The start IP of the multicast VLAN translation."
	::= { mvlanTranslateEntry 5 }
	
	mvlanTranslateInetAddrEnd OBJECT-TYPE
	SYNTAX InetAddress
	MAX-ACCESS read-write
	STATUS current
	DESCRIPTION
		"The end IP of the multicast VLAN translation."
	::= { mvlanTranslateEntry 6 }

-- mvlanExtTable

	mvlanExtTable OBJECT-TYPE
        SYNTAX SEQUENCE OF MvlanExtEntry
        MAX-ACCESS not-accessible
        STATUS current
        DESCRIPTION
                "A table that contains MVLAN."
        ::= { mvlan 4 }

        mvlanExtEntry OBJECT-TYPE
        SYNTAX MvlanExtEntry
        MAX-ACCESS not-accessible
        STATUS current
        DESCRIPTION
        	"An entry of mvlanExtTable."
        INDEX { mvlanIndex, ifIndex }
        ::= { mvlanExtTable 1 }

        MvlanExtEntry ::=
        	SEQUENCE {
        		mvlanExtReg		INTEGER,
        		mvlanExtCvid	INTEGER
           	}
	
	mvlanExtReg OBJECT-TYPE
	SYNTAX INTEGER{
        		fix(1),
        		forbid(2)
        	}
	MAX-ACCESS read-write
	STATUS current
	DESCRIPTION
		"Egress or forbid to the Multicast VLAN."
	::= { mvlanExtEntry 1 }

	mvlanExtCvid OBJECT-TYPE
	SYNTAX INTEGER
	MAX-ACCESS read-write
	STATUS current
	DESCRIPTION
		"Customer VLAN"
	::= { mvlanExtEntry 2 }    

--mvlanNonmemberPort
	mvlanNonmemberPort OBJECT-TYPE
	SYNTAX INTEGER{
        		discard(1),
        		pass(2)
        	}
	MAX-ACCESS read-write
	STATUS current
	DESCRIPTION
		"set this object to 'discard' so that the system discards IGMP/MLD reports 
		if the subscriber port is not a member of the MVLAN which the group address belong to. 
		Set to 'pass' so that the system accepts such IGMP/MLD reports and process them with the original VLAN."
	::= { mvlan 5 }
	
	
--------------------
--  queryVid
--------------------

	maxNumOfQryVid OBJECT-TYPE
	SYNTAX INTEGER
	MAX-ACCESS read-only
	STATUS current
	DESCRIPTION
		"The maximum number of row entries that user can create in qryVidConfTable.
		This object is supported by R1.02 and later versions."
	::= { queryVid 1 }

-- qryVidConfTable

        qryVidConfTable OBJECT-TYPE
        SYNTAX SEQUENCE OF QryVidConfEntry
        MAX-ACCESS not-accessible
        STATUS current
        DESCRIPTION
		"This table defines statically set VLANs used for response IGMP report.
		This table is supported by R1.02 and later versions."
        ::= { queryVid 2 }

	qryVidConfEntry OBJECT-TYPE
        SYNTAX QryVidConfEntry
        MAX-ACCESS not-accessible
        STATUS current
        DESCRIPTION
        	"An entry in qryVidConfTable."
        INDEX { qryVid }
        ::= { qryVidConfTable 1 }

        QryVidConfEntry ::=
        	SEQUENCE {
			qryVid			INTEGER,
			qryVidRowStatus 	RowStatus
           	}

	qryVid OBJECT-TYPE
	SYNTAX INTEGER
	MAX-ACCESS read-only
	STATUS current
	DESCRIPTION
		"VLAN ID."
	::= { qryVidConfEntry 1 }

        qryVidRowStatus OBJECT-TYPE
        SYNTAX RowStatus
        MAX-ACCESS read-create
        STATUS current
        DESCRIPTION
        	"This object indicates the status of this entry."
        ::= { qryVidConfEntry 2 }

-- qryVidStatusTable
	
        qryVidStatusTable OBJECT-TYPE
        SYNTAX SEQUENCE OF QryVidStatusEntry
        MAX-ACCESS not-accessible
        STATUS current
        DESCRIPTION
		"This table shows statically set or dynamically learned VLANs used for response IGMP report."
        ::= { queryVid 3 }

	qryVidStatusEntry OBJECT-TYPE
        SYNTAX QryVidStatusEntry
        MAX-ACCESS not-accessible
        STATUS current
        DESCRIPTION
        	"An entry in qryVidStatusTable."
        INDEX { qryVid }
        ::= { qryVidStatusTable 1 }

        QryVidStatusEntry ::=
        	SEQUENCE {
			qryVidType		INTEGER
           	}

	qryVidType OBJECT-TYPE
	SYNTAX  INTEGER {
			static(1),
			dynamic(2)
		}
	MAX-ACCESS read-only
	STATUS current
	DESCRIPTION
		"VLAN type."
	::= { qryVidStatusEntry 1 }

	        							                                	
----------------------------------------
-- port
----------------------------------------
	
	adslPort		OBJECT IDENTIFIER ::= { port 2 }
	shdslPort		OBJECT IDENTIFIER ::= { port 3 }
	pvc			OBJECT IDENTIFIER ::= { port 4 }
	ppvc			OBJECT IDENTIFIER ::= { port 5 }
	portOperation		OBJECT IDENTIFIER ::= { port 6 }
	pvcStats		OBJECT IDENTIFIER ::= { port 7 }
	paepvc			OBJECT IDENTIFIER ::= { port 8 }
	tlspvc			OBJECT IDENTIFIER ::= { port 9 }
	vdslPort		OBJECT IDENTIFIER ::= { port 10 }
	ipbpvc			OBJECT IDENTIFIER ::= { port 11 }
	voipPort		OBJECT IDENTIFIER ::= { port 12 }
	enetPort		OBJECT IDENTIFIER ::= { port 13 }
	dtpvc			OBJECT IDENTIFIER ::= { port 15 }
	e1Port			OBJECT IDENTIFIER ::= { port 16 }
	xvlan			OBJECT IDENTIFIER ::= { port 17 }
	vdsl2Port			OBJECT IDENTIFIER ::= { port 18 }


-- Subscriber Port Table

        subrPortTable OBJECT-TYPE
        SYNTAX SEQUENCE OF SubrPortEntry
        MAX-ACCESS not-accessible
        STATUS current
        DESCRIPTION
		"This table includes subscriber attributes for the port."
        ::= { port 1 }

	subrPortEntry OBJECT-TYPE
        SYNTAX SubrPortEntry
        MAX-ACCESS not-accessible
        STATUS current
        DESCRIPTION
        	"An entry in subrPortTable."
        INDEX { ifIndex }
        ::= { subrPortTable 1 }

        SubrPortEntry ::=
        	SEQUENCE {
			subrPortName	DisplayString,
			subrPortTel	DisplayString,
			subrPortMdf	DisplayString
		}

        subrPortName OBJECT-TYPE
        SYNTAX DisplayString (SIZE (0..47))
        MAX-ACCESS read-write
        STATUS current
        DESCRIPTION
		"Name of the subscriber."
        ::= { subrPortEntry 1 }

        subrPortTel OBJECT-TYPE
        SYNTAX DisplayString (SIZE (0..31))
        MAX-ACCESS read-write
        STATUS current
        DESCRIPTION
		"Telephone number of the subscriber."
        ::= { subrPortEntry 2 }

        subrPortMdf OBJECT-TYPE
        SYNTAX DisplayString (SIZE (0..47))
        MAX-ACCESS read-write
        STATUS current
        DESCRIPTION
		"MDF information of this subscriber port"
        ::= { subrPortEntry 3 }

                          
--------------------
--  adslPort
--------------------

-- ADSL Line Table

        adslLineConfTable OBJECT-TYPE
        SYNTAX SEQUENCE OF AdslLineConfEntry
        MAX-ACCESS not-accessible
        STATUS current
        DESCRIPTION
		"This table includes common attributes describing the ADSL line."
        ::= { adslPort 1 }

	adslLineConfEntry OBJECT-TYPE
        SYNTAX AdslLineConfEntry
        MAX-ACCESS not-accessible
        STATUS current
        DESCRIPTION
        	"An entry in adslLineConfTable."
        INDEX { ifIndex }
        ::= { adslLineConfTable 1 }

        AdslLineConfEntry ::=
           SEQUENCE {
		adslLineConfAdslMode		INTEGER,
		adslLineConfAnnexL		INTEGER,
		adslLineConfAnnexM		INTEGER,
		adslLineConfAnnexI		INTEGER,
		adslLineConfOptionMask		INTEGER,
		adslLineConfPowerMgmt		INTEGER,
		adslLineConfPowerMode		INTEGER,
		adslLineConfAturMaxTxPower	INTEGER,
		adslLineConfAtucMaxTxPower	INTEGER,
		adslLineConfMaxRxPower		INTEGER,
		adslLineConfAturCarrierMask	OCTET STRING,
		adslLineConfAtucCarrierMask0	OCTET STRING,
		adslLineConfAtucCarrierMask1	OCTET STRING,
		adslLineConfAturInp		INTEGER,
		adslLineConfAtucInp		INTEGER
           }

        adslLineConfAdslMode OBJECT-TYPE
        SYNTAX 	INTEGER {
			gDotLite(1),
			gDotDmt(2),
			t1Dot413(3),
			auto(4),
			etsi(5),
			adsl2(6),
			adsl2Plus(7)
		}
        MAX-ACCESS read-write
        STATUS current
        DESCRIPTION
		"G.lite and T1.413 are only applicable to annex A board.
		ETSI is only applicable to annex B board."
        ::= { adslLineConfEntry 1 }
			
        adslLineConfAnnexL OBJECT-TYPE
        SYNTAX  INTEGER {
        		enableNarrowMode(1),
        		enableWideMode(2),
        		disable(3)
        	}
        MAX-ACCESS read-write
        STATUS current
        DESCRIPTION
		"Enable/disable annex L for the port."
        ::= { adslLineConfEntry 2 }
        
        adslLineConfAnnexM OBJECT-TYPE
        SYNTAX  INTEGER {
        		enable(1),
        		disable(2)
        	}
        MAX-ACCESS read-write
        STATUS current
        DESCRIPTION
		"Enable/disable annex M for the port."
        ::= { adslLineConfEntry 3 }
        
        adslLineConfAnnexI OBJECT-TYPE
        SYNTAX  INTEGER {
        		enable(1),
        		disable(2)
        	}
        MAX-ACCESS read-write
        STATUS current
        DESCRIPTION
		"Enable/disable annex I for the port."
        ::= { adslLineConfEntry 4 }
        
        adslLineConfOptionMask OBJECT-TYPE
        SYNTAX INTEGER
        MAX-ACCESS read-write
        STATUS current
        DESCRIPTION
		"The semantic for each bit is:
		BIT 1 : Disable Trellis
		BIT 2 : Disable Reed-Solomon
		BIT 3 : Disable upstream bitswap
		BIT 4 : Disable downstream bitswap
		BIT 5 : Disable 1-bit constellation
		BIT 6 : Disable transmit windowing
		BIT 7 : Disable s=0.5 support (ADSL1 only)
		BIT 8 : Disable G.lite rate limit (ADSL1 only)
		BIT 9 : Disable Nitro mode"
        ::= { adslLineConfEntry 5 }
        
        adslLineConfPowerMgmt OBJECT-TYPE
        SYNTAX  INTEGER {
        		enableL2(1),
        		enableL2andL3(2),
        		disable(3)
        	}
        MAX-ACCESS read-write
        STATUS current
        DESCRIPTION
		"Enable/disable power management for the port."
        ::= { adslLineConfEntry 6 }
                
        adslLineConfPowerMode OBJECT-TYPE
        SYNTAX  INTEGER {
        		fix(1),
        		priorityToPower(2),
        		priorityToRate(3)
        	}
        MAX-ACCESS read-write
        STATUS current
        DESCRIPTION
		"The power mode of the ADSL line."
        ::= { adslLineConfEntry 7 }
        
        adslLineConfAturMaxTxPower OBJECT-TYPE
        SYNTAX INTEGER (-130..200)
        UNITS "tenth dBm"
        MAX-ACCESS read-write
        STATUS current
        DESCRIPTION
		"The maximum allowed transmit power of ATU-R."
        ::= { adslLineConfEntry 8 }

        adslLineConfAtucMaxTxPower OBJECT-TYPE
        SYNTAX INTEGER (-50..200)
        UNITS "tenth dBm"
        MAX-ACCESS read-write
        STATUS current
        DESCRIPTION
		"The maximum allowed transmit power of ATU-C."
        ::= { adslLineConfEntry 9 }
                        
        adslLineConfMaxRxPower OBJECT-TYPE
        SYNTAX INTEGER (-255..255)
        UNITS "tenth dBm"
        MAX-ACCESS read-write
        STATUS current
        DESCRIPTION
		"The maximum aggregate received power."
        ::= { adslLineConfEntry 10 }
        
        adslLineConfAturCarrierMask OBJECT-TYPE
        SYNTAX OCTET STRING
        MAX-ACCESS read-write
        STATUS current
        DESCRIPTION
		"The upstream carrier mask from bin 0 to 63. Bit set to 1 indicates
		the bin is masked off."
        ::= { adslLineConfEntry 11 }

        adslLineConfAtucCarrierMask0 OBJECT-TYPE
        SYNTAX OCTET STRING
        MAX-ACCESS read-write
        STATUS current
        DESCRIPTION
		"The downstream carrier mask from bin 32 to 255. Bit set to 1 indicates
		the bin is masked off."
        ::= { adslLineConfEntry 12 }
        
        adslLineConfAtucCarrierMask1 OBJECT-TYPE
        SYNTAX OCTET STRING
        MAX-ACCESS read-write
        STATUS current
        DESCRIPTION
		"The downstream carrier mask from bin 256 to 511. Bit set to 1 indicates
		the bin is masked off."
        ::= { adslLineConfEntry 13 }
        
        adslLineConfAturInp OBJECT-TYPE
        SYNTAX  INTEGER {
        		zero(1),
        		zero-point-five(2),
        		one(3),
        		two(4),
        		four(5),
        		eight(6),
        		sixteen(7)
        	}
        MAX-ACCESS read-write
        STATUS current
        DESCRIPTION
        	"The upstream Impulse Noise Protection minimum setting in unit of DMT symbol."
        ::= { adslLineConfEntry 14 }

        adslLineConfAtucInp OBJECT-TYPE
        SYNTAX  INTEGER {
        		zero(1),
        		zero-point-five(2),
        		one(3),
        		two(4),
        		four(5),
        		eight(6),
        		sixteen(7)
        	}
        MAX-ACCESS read-write
        STATUS current
        DESCRIPTION
		"The downstream Impulse Noise Protection minimum setting in unit of DMT symbol."
        ::= { adslLineConfEntry 15 }

-- Bit Loading

	bitLoad		OBJECT IDENTIFIER ::= { adslPort 2 }

        bitLoadTable OBJECT-TYPE
        SYNTAX SEQUENCE OF BitLoadEntry
        MAX-ACCESS not-accessible
        STATUS current
        DESCRIPTION
        	"This table provides the number of bits per carrier for each ADSL port."
        ::= { bitLoad 1 }

	bitLoadEntry OBJECT-TYPE
        SYNTAX BitLoadEntry
        MAX-ACCESS not-accessible
        STATUS current
        DESCRIPTION
        	"An entry in bitLoadTable."
        INDEX { ifIndex }
        ::= { bitLoadTable 1 }

        BitLoadEntry ::=
        	SEQUENCE {
        		bitLoadBits			OCTET STRING,
        		bitLoadAtucNumOfCarriers 	INTEGER,
        		bitLoadAturNumOfCarriers	INTEGER
           	}

        bitLoadBits OBJECT-TYPE
        SYNTAX OCTET STRING
        MAX-ACCESS read-only
        STATUS current
        DESCRIPTION
        	"This object provides the number of bits for all carriers in the port. 
        	The first octet specify the number of bits for carrier 1, and the second 
        	octet specify the number of bits for carrier 2, and so on.
		The object provides the number of bits for carrier 1 to 512."
        ::= { bitLoadEntry 1 }

	bitLoadAtucNumOfCarriers OBJECT-TYPE
	SYNTAX INTEGER
	MAX-ACCESS read-only
	STATUS current
	DESCRIPTION
		"The number of carriers for ATU-C."
	::= { bitLoadEntry 2 }

	bitLoadAturNumOfCarriers OBJECT-TYPE
	SYNTAX INTEGER
	MAX-ACCESS read-only
	STATUS current
	DESCRIPTION
		"The number of carriers for ATU-R."
	::= { bitLoadEntry 3 }	                        
	                        
-- ADSL Port Batch Set

	adslPortBatchSet		OBJECT IDENTIFIER ::= { adslPort 3 }
	
        adslPortTarget OBJECT-TYPE
        SYNTAX OCTET STRING
        MAX-ACCESS read-write
        STATUS current
        DESCRIPTION
		"The managed object is used for identify the target on which 
		the port configuration should be performed. The target is encoded as:
		Byte 1:   the octet specifies a set of eight chassis, chassis 0 through 7
		Byte 2~4: each octet specifies a set of eight slots, with the 
			  first octet specifying slots 1 through 8, and the second
		          octet specifying slots 9 through 16, and so on.
		Byte 5~:  each octet specifies a set of eight ports, with the first
		          octet specifying ports 1 through 8, etc."
        ::= { adslPortBatchSet 1 }
        
        adslPortOps OBJECT-TYPE
        SYNTAX INTEGER
        MAX-ACCESS read-write
        STATUS current
        DESCRIPTION
		"The managed object is for ADSL line configuration. When the EMS
		wants to issue the desired operation, the EMS shall send SNMP-SET message to set 
		the corresponding bit value to be 1. The various bit positions are:
		BIT  1: enable port
		BIT  2: disable port
		BIT  3: set ADSL mode			 
		BIT  4: set line profile
		BIT  5: set alarm profile
		BIT  6: enable Annex L to be narrow mode
		BIT  7: enable Annex L to be wide mode
		BIT  8: disable Annex L
		BIT  9: enable Annex M
		BIT 10: disable Annex M
		BIT 11: enable Annex I
		BIT 12: disable Annex I
		BIT 13: set option mask
		BIT 14: enable power management mode to be L2
		BIT 15: enable power management mode to be L3
		BIT 16: disable power management mode
		BIT 17: set power mode to be fixed
		BIT 18: set power mode to be priority to power
		BIT 19: set power mode to be priority to rate
		BIT 20: set ATU-R max Tx power
		BIT 21: set ATU-C max Tx power
		BIT 22: set max Rx power
		BIT 23: set ATU-R carrier mask
		BIT 24: set ATU-C carrier mask
		BIT 25: set ATU-R INP minimum setting
		BIT 26: set ATU-C INP minimum setting"
        ::= { adslPortBatchSet 2 }

        adslModeForBatchSet OBJECT-TYPE
        SYNTAX 	INTEGER {
			gDotLite(1),
			gDotDmt(2),
			t1Dot413(3),
			auto(4),
			etsi(5),
			adsl2(6),
			adsl2Plus(7)
		}
        MAX-ACCESS read-write
        STATUS current
        DESCRIPTION
		"G.lite and T1.413 are only applicable to annex A board.
		ETSI is only applicable to annex B board."
        ::= { adslPortBatchSet 3 }

        adslLineProfileForBatchSet OBJECT-TYPE
        SYNTAX DisplayString (SIZE (1..31))
        MAX-ACCESS read-write
        STATUS current
        DESCRIPTION
		"The ADSL line profile."
        ::= { adslPortBatchSet 4 }

        adslAlarmProfileForBatchSet OBJECT-TYPE
        SYNTAX DisplayString (SIZE (1..31))
        MAX-ACCESS read-write
        STATUS current
        DESCRIPTION
		"The ADSL alarm profile."
        ::= { adslPortBatchSet 5 }
                        
        adslOptionMaskForBatchSet OBJECT-TYPE
        SYNTAX INTEGER
        MAX-ACCESS read-write
        STATUS current
        DESCRIPTION
		"The semantic for each bit is identical to the object adslLineConfOptionMask."
        ::= { adslPortBatchSet 6 }

        adslAturMaxTxPowerForBatchSet OBJECT-TYPE
        SYNTAX INTEGER (-130..200)
        UNITS "tenth dBm"
        MAX-ACCESS read-write
        STATUS current
        DESCRIPTION
		"The maximum allowed transmit power of ATU-R."
        ::= { adslPortBatchSet 7 }

        adslAtucMaxTxPowerForBatchSet OBJECT-TYPE
        SYNTAX INTEGER (-50..200)
        UNITS "tenth dBm"
        MAX-ACCESS read-write
        STATUS current
        DESCRIPTION
		"The maximum allowed transmit power of ATU-C."
        ::= { adslPortBatchSet 8 }
                        
        adslMaxRxPowerForBatchSet OBJECT-TYPE
        SYNTAX INTEGER (-255..255)
        UNITS "tenth dBm"
        MAX-ACCESS read-write
        STATUS current
        DESCRIPTION
		"The maximum aggregate received power."
        ::= { adslPortBatchSet 9 }
        
        adslAturCarrierMaskForBatchSet OBJECT-TYPE
        SYNTAX OCTET STRING
        MAX-ACCESS read-write
        STATUS current
        DESCRIPTION
		"The upstream carrier mask from bin 0 to 63. Bit set to 1 indicates
		the bin is masked off."
        ::= { adslPortBatchSet 10 }

        adslAtucCarrierMask0ForBatchSet OBJECT-TYPE
        SYNTAX OCTET STRING
        MAX-ACCESS read-write
        STATUS current
        DESCRIPTION
		"The downstream carrier mask from bin 32 to 255. Bit set to 1 indicates
		the bin is masked off."
        ::= { adslPortBatchSet 11 }
        
        adslAtucCarrierMask1ForBatchSet OBJECT-TYPE
        SYNTAX OCTET STRING
        MAX-ACCESS read-write
        STATUS current
        DESCRIPTION
		"The downstream carrier mask from bin 256 to 511. Bit set to 1 indicates
		the bin is masked off."
        ::= { adslPortBatchSet 12 }
        
        adslAturInpForBatchSet OBJECT-TYPE
        SYNTAX  INTEGER {
        		zero(1),
        		zero-point-five(2),
        		one(3),
        		two(4),
        		four(5),
        		eight(6),
        		sixteen(7)
        	}
        MAX-ACCESS read-write
        STATUS current
        DESCRIPTION
        	"The upstream Impulse Noise Protection minimum setting in unit of DMT symbol."
        ::= { adslPortBatchSet 13 }

        adslAtucInpForBatchSet OBJECT-TYPE
        SYNTAX  INTEGER {
        		zero(1),
        		zero-point-five(2),
        		one(3),
        		two(4),
        		four(5),
        		eight(6),
        		sixteen(7)
        	}
        MAX-ACCESS read-write
        STATUS current
        DESCRIPTION
		"The downstream Impulse Noise Protection minimum setting in unit of DMT symbol."
        ::= { adslPortBatchSet 14 }

-- Line Status

        adslLineStatusTable OBJECT-TYPE
        SYNTAX SEQUENCE OF AdslLineStatusEntry
        MAX-ACCESS not-accessible
        STATUS current
        DESCRIPTION
        	"This table includes the ADSL line status."
        ::= { adslPort 4 }

	adslLineStatusEntry OBJECT-TYPE
        SYNTAX AdslLineStatusEntry
        MAX-ACCESS not-accessible
        STATUS current
        DESCRIPTION 
        	"An entry in adslLineStatusTable."
        INDEX { ifIndex }
        ::= { adslLineStatusTable 1 }

        AdslLineStatusEntry ::=
           SEQUENCE {
        	adslLineStatusMode	INTEGER,
        	adslLineStatusUpTime	Unsigned32,
        	adslLineStatusAturInp	INTEGER,
        	adslLineStatusAtucInp	INTEGER
           }

        adslLineStatusMode OBJECT-TYPE
        SYNTAX  INTEGER {
			gDotLite(1),
			gDotDmt(2),
			t1Dot413(3),
			etsi(4),
			adsl2(5),
			adsl2Plus(6),
			none(7),
			adsl2Annexi(8),
			adsl2Annexl(9),
			adsl2AnnexlNarrow(10),
			adsl2Annexm(11),
			adsl2PlusAnnexi(12),
			adsl2PlusAnnexm(13)
		}
        MAX-ACCESS read-only
        STATUS current
        DESCRIPTION
        	"The link up mode of the ADSL line.
        	The following items is added from R5.05
        	8: adsl2Annexi(8)
 			9: adsl2Annexl(9)
 			10: adsl2AnnexlNarrow(10)
 			11: adsl2Annexm(11)
 			12: adsl2PlusAnnexi(12)
 			13: adsl2PlusAnnexm(13)"
        ::= { adslLineStatusEntry 1 }
        
        adslLineStatusUpTime OBJECT-TYPE
        SYNTAX Unsigned32
        UNITS "second"
        MAX-ACCESS read-only
        STATUS current
        DESCRIPTION
        	"The time since the ADSL line link up."
        ::= { adslLineStatusEntry 2 }

	adslLineStatusAturInp OBJECT-TYPE
        SYNTAX INTEGER
        UNITS "0.1 DMT symbol"
        MAX-ACCESS read-only
        STATUS current
        DESCRIPTION
        	"The upstream Impulse Noise Protection in unit of 0.1 DMT symbol."
        ::= { adslLineStatusEntry 3 }

        adslLineStatusAtucInp OBJECT-TYPE
        SYNTAX INTEGER
        UNITS "0.1 DMT symbol"
        MAX-ACCESS read-only
        STATUS current
        DESCRIPTION
		"The downstream Impulse Noise Protection in unit of 0.1 DMT symbol."
        ::= { adslLineStatusEntry 4 }
        
-- Power Mgmt Parameter Table

        powerMgmtParamTable OBJECT-TYPE
        SYNTAX SEQUENCE OF PowerMgmtParamEntry
        MAX-ACCESS not-accessible
        STATUS current
        DESCRIPTION
		"This table defines L0 to L2 power transition parameters.
		This table is supported by R1.02 and later versions."
        ::= { adslPort 5 }

	powerMgmtParamEntry OBJECT-TYPE
        SYNTAX PowerMgmtParamEntry
        MAX-ACCESS not-accessible
        STATUS current
        DESCRIPTION
        	"An entry in powerMgmtParamTable."
        INDEX { ifIndex }
        ::= { powerMgmtParamTable 1 }

        PowerMgmtParamEntry ::=
           SEQUENCE {
		powerMgmtL0Time		INTEGER,
		powerMgmtL2Time		INTEGER,
		powerMgmtL2Atpr		INTEGER,
		powerMgmtL2Atprt	INTEGER,
		powerMgmtL2MinRate	INTEGER,
		powerMgmtL2MaxRate	INTEGER,
		powerMgmtL2ThreshRate	INTEGER
           }

        powerMgmtL0Time OBJECT-TYPE
        SYNTAX INTEGER
        UNITS "second"
        MAX-ACCESS read-write
        STATUS current
        DESCRIPTION
		"The object specifies the minimum time in L0 mode before L2 mode may be entered."
        ::= { powerMgmtParamEntry 1 }
                
	powerMgmtL2Time OBJECT-TYPE
        SYNTAX INTEGER
        UNITS "second"
        MAX-ACCESS read-write
        STATUS current
        DESCRIPTION
		"The object specifies the minimum time in L2 mode before trimming and in between power trims."
        ::= { powerMgmtParamEntry 2 }
        
        powerMgmtL2Atpr OBJECT-TYPE
        SYNTAX INTEGER
        UNITS "dB"
        MAX-ACCESS read-write
        STATUS current
        DESCRIPTION
		"The maximum aggregate transmit power."
        ::= { powerMgmtParamEntry 3 }
        
        powerMgmtL2Atprt OBJECT-TYPE
        SYNTAX INTEGER
        UNITS "dB"
        MAX-ACCESS read-write
        STATUS current
        DESCRIPTION
		"The maximum total aggregate transmit power."
        ::= { powerMgmtParamEntry 4 }
        
        powerMgmtL2MinRate OBJECT-TYPE
        SYNTAX INTEGER
        UNITS "Kbps"
        MAX-ACCESS read-write
        STATUS current
        DESCRIPTION
		"The object specifies the minimum L2 rate."
        ::= { powerMgmtParamEntry 5 }
        
        powerMgmtL2MaxRate OBJECT-TYPE
        SYNTAX INTEGER
        UNITS "Kbps"
        MAX-ACCESS read-write
        STATUS current
        DESCRIPTION
		"The object specifies the maximum L2 rate."
        ::= { powerMgmtParamEntry 6 }
        
        powerMgmtL2ThreshRate OBJECT-TYPE
        SYNTAX INTEGER
        UNITS "percentage"
        MAX-ACCESS read-write
        STATUS current
        DESCRIPTION
		"The object specifies the rate threshold that triggers the line entering L0 or L2 mode."
        ::= { powerMgmtParamEntry 7 }

-- Power Mgmt PSD Table

        powerMgmtPSDTable OBJECT-TYPE
        SYNTAX SEQUENCE OF PowerMgmtPSDEntry
        MAX-ACCESS not-accessible
        STATUS current
        DESCRIPTION
		"This table provides the PSD setting for both ATU-C and ATU-R.
		This table is supported by R1.02 and later versions."
        ::= { adslPort 6 }

	powerMgmtPSDEntry OBJECT-TYPE
        SYNTAX PowerMgmtPSDEntry
        MAX-ACCESS not-accessible
        STATUS current
        DESCRIPTION
        	"An entry in powerMgmtPSDTable."
        INDEX { ifIndex }
        ::= { powerMgmtPSDTable 1 }

        PowerMgmtPSDEntry ::=
           SEQUENCE {
		powerMgmtAtucMaxPSD		INTEGER,
		powerMgmtAturMaxPSD		INTEGER
           }

        powerMgmtAtucMaxPSD OBJECT-TYPE
        SYNTAX INTEGER
        UNITS "0.1dBm/Hz"
        MAX-ACCESS read-write
        STATUS current
        DESCRIPTION
		"The object specifies the maximum ATU-C PSD."
        ::= { powerMgmtPSDEntry 1 }

        powerMgmtAturMaxPSD OBJECT-TYPE
        SYNTAX INTEGER
        UNITS "0.1dBm/Hz"
        MAX-ACCESS read-write
        STATUS current
        DESCRIPTION
		"The object specifies the maximum ATU-R PSD."
        ::= { powerMgmtPSDEntry 2 }
                        
--------------------
-- shdslPort
--------------------

-- SHDSL Line Table

        shdslLineConfTable OBJECT-TYPE
        SYNTAX SEQUENCE OF ShdslLineConfEntry
        MAX-ACCESS not-accessible
        STATUS current
        DESCRIPTION
		"This table includes common attributes describing the SHDSL line."
        ::= { shdslPort 1 }

	shdslLineConfEntry OBJECT-TYPE
        SYNTAX ShdslLineConfEntry
        MAX-ACCESS not-accessible
        STATUS current
        DESCRIPTION
        	"An entry in shdslLineConfTable."
        INDEX { ifIndex }
        ::= { shdslLineConfTable 1 }

        ShdslLineConfEntry ::=
           SEQUENCE {
		shdslLineConfShdslMode		INTEGER,
		shdslLineConfPmms		INTEGER,
		shdslLineConfPboMode		INTEGER,
		shdslLineConfPboValue		INTEGER,
		shdslLineConfModulation		INTEGER,
		shdslLineConfTCMode			INTEGER
           }

        shdslLineConfShdslMode OBJECT-TYPE
        SYNTAX 	INTEGER {
			stuc(1),
			stur(2)
		}
        MAX-ACCESS read-write
        STATUS current
        DESCRIPTION
		"Mode of the SHDSL port. This MIB object is not supported by R5.03 and later versions."
        ::= { shdslLineConfEntry 1 }

        shdslLineConfPmms OBJECT-TYPE
        SYNTAX 	INTEGER {
			normal(1),
			forced(2)
		}
        MAX-ACCESS read-write
        STATUS current
        DESCRIPTION
		"Negotiated noise margin mode of the SHDSL port."
        ::= { shdslLineConfEntry 2 }

        shdslLineConfPboMode OBJECT-TYPE
        SYNTAX 	INTEGER {
			normal-epl(1),
			forced-epl(2),
			forced-no-epl(3)
		}
        MAX-ACCESS read-write
        STATUS current
        DESCRIPTION
		"Power backoff mode of the SHDSL port."
        ::= { shdslLineConfEntry 3 }

        shdslLineConfPboValue OBJECT-TYPE
        SYNTAX INTEGER (0..31)
        UNITS "dB"
        MAX-ACCESS read-write
        STATUS current
        DESCRIPTION
		"Power backoff value of the SHDSL port."
        ::= { shdslLineConfEntry 4 }

        shdslLineConfModulation OBJECT-TYPE
        SYNTAX 	INTEGER {
			auto(1),
			pam16(2),
			pam32(3)
		}
        MAX-ACCESS read-write
        STATUS current
        DESCRIPTION
		"Modulation mode of the SHDSL port. This MIB object is supported by R5.03 and later versions."
        ::= { shdslLineConfEntry 5 }   
        
        shdslLineConfTCMode OBJECT-TYPE
        SYNTAX 	INTEGER {
			atm(1),
			efm(2)
		}
        MAX-ACCESS read-write
        STATUS current
        DESCRIPTION
		"Transmission Convergence layer. This MIB object is supported by R5.05 and later versions.
		1: atm
		2: efm"
        ::= { shdslLineConfEntry 6 }
-- SHDSL Port Batch Set

	shdslPortBatchSet		OBJECT IDENTIFIER ::= { shdslPort 2 }
	
        shdslPortTarget OBJECT-TYPE
        SYNTAX OCTET STRING
        MAX-ACCESS read-write
        STATUS current
        DESCRIPTION
		"The managed object is used for identify the target on which 
		the port configuration should be performed. The target is encoded as:
		Byte 1:   the octet specifies a set of eight chassis, chassis 0 through 7
		Byte 2~4: each octet specifies a set of eight slots, with the 
			  first octet specifying slots 1 through 8, and the second
		          octet specifying slots 9 through 16, and so on.
		Byte 5~:  each octet specifies a set of eight ports, with the first
		          octet specifying ports 1 through 8, etc."
        ::= { shdslPortBatchSet 1 }
        
        shdslPortOps OBJECT-TYPE
        SYNTAX INTEGER
        MAX-ACCESS read-write
        STATUS current
        DESCRIPTION
		"The managed object is for SHDSL line configuration. When the EMS
		wants to issue the desired operation, the EMS shall send SNMP-SET message to set 
		the corresponding bit value to be 1. The various bit positions are:
		BIT  1: enable port
		BIT  2: disable port
		BIT  3: set SHDSL mode			 
		BIT  4: set line profile
		BIT  5: set alarm profile
		BIT  6: set pmms mode to be normal
		BIT  7: set pmms mode to be forced
		BIT  8: set pbo mode to be normal-epl
		BIT  9: set pbo mode to be forced-epl
		BIT 10: set pbo mode to be forced-no-epl
		BIT 11: set pbo value"
        ::= { shdslPortBatchSet 2 }

        shdslModeForBatchSet OBJECT-TYPE
        SYNTAX 	INTEGER {
			stuc(1),
			stur(2)
		}
        MAX-ACCESS read-write
        STATUS current
        DESCRIPTION
		"Mode of the SHDSL port."
        ::= { shdslPortBatchSet 3 }

        shdslLineProfileForBatchSet OBJECT-TYPE
        SYNTAX DisplayString (SIZE (1..31))
        MAX-ACCESS read-write
        STATUS current
        DESCRIPTION
		"The SHDSL line profile."
        ::= { shdslPortBatchSet 4 }

        shdslAlarmProfileForBatchSet OBJECT-TYPE
        SYNTAX DisplayString (SIZE (1..31))
        MAX-ACCESS read-write
        STATUS current
        DESCRIPTION
		"The SHDSL alarm profile."
        ::= { shdslPortBatchSet 5 }

        shdslPboValueForBatchSet OBJECT-TYPE
        SYNTAX INTEGER (0..31)
        UNITS "dB"
        MAX-ACCESS read-write
        STATUS current
        DESCRIPTION
		"Power backoff value of the SHDSL port."
        ::= { shdslPortBatchSet 6 }

-- Line Status

        shdslLineStatusTable OBJECT-TYPE
        SYNTAX SEQUENCE OF ShdslLineStatusEntry
        MAX-ACCESS not-accessible
        STATUS current
        DESCRIPTION
        	"This table includes the SHDSL line status."
        ::= { shdslPort 3 }

	shdslLineStatusEntry OBJECT-TYPE
        SYNTAX ShdslLineStatusEntry
        MAX-ACCESS not-accessible
        STATUS current
        DESCRIPTION 
        	"An entry in shdslLineStatusTable."
        INDEX { ifIndex }
        ::= { shdslLineStatusTable 1 }

        ShdslLineStatusEntry ::=
           SEQUENCE {
        	shdslLineStatusWirePair		INTEGER
           }

        shdslLineStatusWirePair OBJECT-TYPE
        SYNTAX  INTEGER {
			twoWire(1),
           		fourWire(2),
           		mpair4(4)
		}
        MAX-ACCESS read-only
        STATUS current
        DESCRIPTION
        	"The link-up wire pair of the SHDSL line."
        ::= { shdslLineStatusEntry 1 }
                
--------------------
-- pvc
--------------------

        maxNumOfPvcs OBJECT-TYPE
        SYNTAX INTEGER
        MAX-ACCESS read-only
        STATUS current
        DESCRIPTION
        	"The maximum number of PVCs which could be created on a port."
        ::= { pvc 1 }

-- PVC Table

        pvcTable OBJECT-TYPE
        SYNTAX SEQUENCE OF PvcEntry
        MAX-ACCESS not-accessible
        STATUS current
        DESCRIPTION
        	"This table includes PVC configuration."
        ::= { pvc 2 }

	pvcEntry OBJECT-TYPE
        SYNTAX PvcEntry
        MAX-ACCESS not-accessible
        STATUS current
        DESCRIPTION
		"An entry in pvcTable."
        INDEX { ifIndex, pvcVpi, pvcVci, pvcPvid }
        ::= { pvcTable 1 }

        PvcEntry ::=
        	SEQUENCE {
			pvcVpi		INTEGER,
			pvcVci		INTEGER,
			pvcPvid		VlanIndex,
			pvcEncap	INTEGER,
			pvcPriority	INTEGER,
			pvcProfile	DisplayString,
			pvcRowStatus	RowStatus,
			pvcMvlanEnable	INTEGER,
			pvcAcName	DisplayString,
			pvcServiceName	DisplayString,
			pvcHelloTime	INTEGER
           	}

        pvcVpi OBJECT-TYPE
        SYNTAX INTEGER (0..255)
        MAX-ACCESS read-only
        STATUS current
        DESCRIPTION
                "VPI of the pvc."
         ::= { pvcEntry 1 }

        pvcVci OBJECT-TYPE
        SYNTAX INTEGER (1..65535)
        MAX-ACCESS read-only
       	STATUS current
        DESCRIPTION
                "VCI of the pvc."
         ::= { pvcEntry 2 }

        pvcPvid OBJECT-TYPE
        SYNTAX VlanIndex
        MAX-ACCESS read-only
        STATUS current
        DESCRIPTION
                "Default VID of the pvc."
         ::= { pvcEntry 3 }

        pvcEncap OBJECT-TYPE
        SYNTAX INTEGER {
        		llc(1),
        		vc(2),
        		auto(3)
        	}
        MAX-ACCESS read-create
        STATUS current
        DESCRIPTION
                "Encapsulation of the pvc."
         ::= { pvcEntry 4 }

        pvcPriority OBJECT-TYPE
        SYNTAX INTEGER (0..7)
        MAX-ACCESS read-create
        STATUS current
        DESCRIPTION
                "802.1p default priority of the pvc."
         ::= { pvcEntry 5 }

        pvcProfile OBJECT-TYPE
        SYNTAX DisplayString (SIZE (1..31))
        MAX-ACCESS read-create
        STATUS current
        DESCRIPTION
                "The value of this object identifies the row in the atmProfileTable, which applies for this pvc."
         ::= { pvcEntry 6 }

        pvcRowStatus OBJECT-TYPE
        SYNTAX RowStatus
        MAX-ACCESS read-create
        STATUS current
        DESCRIPTION
                "This object is used to create a new row or delete an existing row in this table."
         ::= { pvcEntry 7 }

        pvcMvlanEnable OBJECT-TYPE
        SYNTAX  INTEGER {
        		enable(1),
        		disable(2)
        	}
        MAX-ACCESS read-create
        STATUS current
        DESCRIPTION
                "Enable/disable multicast VLAN function for the PVC.
                This object is supported by R1.02 and later versions."
         ::= { pvcEntry 8 }
         
        pvcAcName OBJECT-TYPE
        SYNTAX DisplayString
        MAX-ACCESS read-create
        STATUS current
        DESCRIPTION
                "Access concentrator name."
         ::= { pvcEntry 9 }
         
        pvcServiceName OBJECT-TYPE
        SYNTAX DisplayString
        MAX-ACCESS read-create
        STATUS current
        DESCRIPTION
                "Service name."
         ::= { pvcEntry 10 }

        pvcHelloTime OBJECT-TYPE
        SYNTAX INTEGER
        UNITS "second"
        MAX-ACCESS read-create
        STATUS current
        DESCRIPTION
                "The system will close the PVC if there are not any LCP echo messages passed through 
                during the LCP hello time."
         ::= { pvcEntry 11 }
                  
  
         
-- PVC VLAN Table

        pvcVlanTable OBJECT-TYPE
        SYNTAX SEQUENCE OF PvcVlanEntry
        MAX-ACCESS not-accessible
        STATUS current
        DESCRIPTION
        	"This table includes the VLAN configuration for each PVC."
        ::= { pvc 3 }

	pvcVlanEntry OBJECT-TYPE
        SYNTAX PvcVlanEntry
        MAX-ACCESS not-accessible
        STATUS current
        DESCRIPTION
		"An entry in pvcVlanTable."
        INDEX { ifIndex, pvcVpi, pvcVci, dot1qVlanIndex }
        ::= { pvcVlanTable 1 }

        PvcVlanEntry ::=
        	SEQUENCE {
			pvcVlanReg		INTEGER,
			pvcVlanTag		INTEGER,
			pvcVlanRowStatus	RowStatus
           	}

        pvcVlanReg OBJECT-TYPE
        SYNTAX 	INTEGER {
        		egress(1),
        		forbidden(2)
        	}
        MAX-ACCESS read-create
        STATUS current
        DESCRIPTION
                "The PVC is egress or forbidden for this VLAN."
         ::= { pvcVlanEntry 1 }
         
        pvcVlanTag OBJECT-TYPE
        SYNTAX INTEGER {
        		tag(1),
        		untag(2)
        	}
        MAX-ACCESS read-create
        STATUS current
        DESCRIPTION
                "The PVC should transmit egress packets for this VLAN as tagged or untagged."
         ::= { pvcVlanEntry 2 }

        pvcVlanRowStatus OBJECT-TYPE
        SYNTAX RowStatus
        MAX-ACCESS read-create
        STATUS current
        DESCRIPTION
                "This object is used to create a new row or delete an existing row in this table."
         ::= { pvcVlanEntry 3 }

-- Upstream Rate Limit Table

        pvcUsRateLimitTable OBJECT-TYPE
        SYNTAX SEQUENCE OF PvcUsRateLimitEntry
        MAX-ACCESS not-accessible
        STATUS current
        DESCRIPTION
        	"This table defines the upstream rate limit for each PVC.
        	This table is supported by R1.03 and later versions."
        ::= { pvc 4 }

	pvcUsRateLimitEntry OBJECT-TYPE
        SYNTAX PvcUsRateLimitEntry
        MAX-ACCESS not-accessible
        STATUS current
        DESCRIPTION
		"An entry in pvcUsRateLimitTable."
        INDEX { ifIndex, pvcVpi, pvcVci }
        ::= { pvcUsRateLimitTable 1 }

        PvcUsRateLimitEntry ::=
        	SEQUENCE {
			pvcUsRateLimitEnable	INTEGER,
			pvcUsRateLimit		INTEGER
           	}

        pvcUsRateLimitEnable OBJECT-TYPE
        SYNTAX 	INTEGER {
        		enable(1),
        		disable(2)
        	}
        MAX-ACCESS read-write
        STATUS current
        DESCRIPTION
                "Enable/disable upstream rate limit for a PVC."
        ::= { pvcUsRateLimitEntry 1 }
         
        pvcUsRateLimit OBJECT-TYPE
        SYNTAX INTEGER
        UNITS "Kbps"
        MAX-ACCESS read-write
        STATUS current
        DESCRIPTION
                "Upstream rate limit in Kbps for a PVC."
         ::= { pvcUsRateLimitEntry 2 } 
         
--------------------
-- priority pvc
--------------------

        maxNumOfPriorityPvcs OBJECT-TYPE
        SYNTAX INTEGER
        MAX-ACCESS read-only
        STATUS current
        DESCRIPTION
        	"The maximum number of priority PVCs which could be created on a port."
        ::= { ppvc 1 }
        
-- Priority PVC Table
        
        ppvcTable OBJECT-TYPE
        SYNTAX SEQUENCE OF PpvcEntry
        MAX-ACCESS not-accessible
        STATUS current
        DESCRIPTION
        	"This table includes priority PVC configuration."
        ::= { ppvc 2 }

	ppvcEntry OBJECT-TYPE
        SYNTAX PpvcEntry
        MAX-ACCESS not-accessible
        STATUS current
        DESCRIPTION
		"An entry in ppvcTable."
        INDEX { ifIndex, ppvcVpi, ppvcVci, ppvcPvid }
        ::= { ppvcTable 1 }

        PpvcEntry ::=
        	SEQUENCE {
			ppvcVpi		INTEGER,
			ppvcVci		INTEGER,
			ppvcPvid	VlanIndex,
			ppvcEncap	INTEGER,
			ppvcPriority	INTEGER,
			ppvcRowStatus	RowStatus
           	}

        ppvcVpi OBJECT-TYPE
        SYNTAX INTEGER (0..255)
        MAX-ACCESS read-only
        STATUS current
        DESCRIPTION
                "VPI of the ppvc."
         ::= { ppvcEntry 1 }

        ppvcVci OBJECT-TYPE
        SYNTAX INTEGER (1..65535)
        MAX-ACCESS read-only
        STATUS current
        DESCRIPTION
                "VCI of the ppvc."
         ::= { ppvcEntry 2 }

        ppvcPvid OBJECT-TYPE
        SYNTAX VlanIndex
        MAX-ACCESS read-only
        STATUS current
        DESCRIPTION
                "Default VID of the ppvc."
         ::= { ppvcEntry 3 }

        ppvcEncap OBJECT-TYPE
        SYNTAX INTEGER {
        		llc(1),
        		vc(2)
        	}
        MAX-ACCESS read-create
        STATUS current
        DESCRIPTION
                "Encapsulation of the ppvc."
         ::= { ppvcEntry 4 }

        ppvcPriority OBJECT-TYPE
        SYNTAX INTEGER (0..7)
        MAX-ACCESS read-create
        STATUS current
        DESCRIPTION
                "802.1p default priority of the ppvc."
         ::= { ppvcEntry 5 }

        ppvcRowStatus OBJECT-TYPE
        SYNTAX RowStatus
        MAX-ACCESS read-create
        STATUS current
        DESCRIPTION
                "This object is used to create a new row or delete an existing row in this table."
         ::= { ppvcEntry 6 }
         
-- Priority PVC VLAN Table
        
        ppvcVlanTable OBJECT-TYPE
        SYNTAX SEQUENCE OF PpvcVlanEntry
        MAX-ACCESS not-accessible
        STATUS current
        DESCRIPTION
        	"This table includes the VLAN configuration for each priority PVC."
        ::= { ppvc 3 }

	ppvcVlanEntry OBJECT-TYPE
        SYNTAX PpvcVlanEntry
        MAX-ACCESS not-accessible
        STATUS current
        DESCRIPTION
		"An entry in ppvcVlanTable."
        INDEX { ifIndex, ppvcVpi, ppvcVci, dot1qVlanIndex }
        ::= { ppvcVlanTable 1 }

        PpvcVlanEntry ::=
        	SEQUENCE {
			ppvcVlanReg		INTEGER,
			ppvcVlanTag		INTEGER,
			ppvcVlanRowStatus	RowStatus
           	}

        ppvcVlanReg OBJECT-TYPE
        SYNTAX 	INTEGER {
        		egress(1),
        		forbidden(2)
        	}
        MAX-ACCESS read-create
        STATUS current
        DESCRIPTION
                "The PVC is egress or forbidden for this VLAN."
         ::= { ppvcVlanEntry 1 }
         
        ppvcVlanTag OBJECT-TYPE
        SYNTAX INTEGER {
        		tag(1),
        		untag(2)
        	}
        MAX-ACCESS read-create
        STATUS current
        DESCRIPTION
                "The PVC should transmit egress packets for this VLAN as tagged or untagged."
         ::= { ppvcVlanEntry 2 }

        ppvcVlanRowStatus OBJECT-TYPE
        SYNTAX RowStatus
        MAX-ACCESS read-create
        STATUS current
        DESCRIPTION
                "This object is used to create a new row or delete an existing row in this table."
         ::= { ppvcVlanEntry 3 }

-- Priority PVC Member Table

        ppvcMemberTable OBJECT-TYPE
        SYNTAX SEQUENCE OF PpvcMemberEntry
        MAX-ACCESS not-accessible
        STATUS current
        DESCRIPTION
        	"This table includes priority PVC member configuration."
        ::= { ppvc 4 }

	ppvcMemberEntry OBJECT-TYPE
        SYNTAX PpvcMemberEntry
        MAX-ACCESS not-accessible
        STATUS current
        DESCRIPTION
		"An entry in ppvcMemberTable."
        INDEX { ifIndex, ppvcVpi, ppvcVci, ppvcMemberVpi, ppvcMemberVci, ppvcMemberPriority }
        ::= { ppvcMemberTable 1 }

        PpvcMemberEntry ::=
        	SEQUENCE {
			ppvcMemberVpi		INTEGER,
			ppvcMemberVci		INTEGER,
			ppvcMemberPriority	INTEGER,
			ppvcMemberProfile	DisplayString,
			ppvcMemberRowStatus	RowStatus
           	}

        ppvcMemberVpi OBJECT-TYPE
        SYNTAX INTEGER (0..255)
        MAX-ACCESS read-only
        STATUS current
        DESCRIPTION
                "VPI of the member ppvc."
         ::= { ppvcMemberEntry 1 }

        ppvcMemberVci OBJECT-TYPE
        SYNTAX INTEGER (1..65535)
        MAX-ACCESS read-only
        STATUS current
        DESCRIPTION
                "VCI of the member ppvc."
         ::= { ppvcMemberEntry 2 }

        ppvcMemberPriority OBJECT-TYPE
        SYNTAX INTEGER (0..7)
        MAX-ACCESS read-only
        STATUS current
        DESCRIPTION
                "802.1p default priority of the member ppvc."
         ::= { ppvcMemberEntry 3 }

        ppvcMemberProfile OBJECT-TYPE
        SYNTAX DisplayString (SIZE (1..31))
        MAX-ACCESS read-create
        STATUS current
        DESCRIPTION
                "The profile of the member ppvc."
         ::= { ppvcMemberEntry 4 }
         
        ppvcMemberRowStatus OBJECT-TYPE
        SYNTAX RowStatus
        MAX-ACCESS read-create
        STATUS current
        DESCRIPTION
                "This object is used to create a new row or delete an existing row in this table."
         ::= { ppvcMemberEntry 5 }

--------------------
-- portOperation
--------------------

        portTarget OBJECT-TYPE
        SYNTAX OCTET STRING
        MAX-ACCESS read-write
        STATUS current
        DESCRIPTION
		"The managed object is used for identify the target on which 
		the port configuration should be performed. The target is encoded as:
		Byte 1:   the octet specifies a set of eight chassis, chassis 0 through 7
		Byte 2~4: each octet specifies a set of eight slots, with the 
			  first octet specifying slots 1 through 8, and the second
		          octet specifying slots 9 through 16, and so on.
		Byte 5~:  each octet specifies a set of eight ports, with the first
		          octet specifying ports 1 through 8, etc."
        ::= { portOperation 1 }
        
        portOps OBJECT-TYPE
        SYNTAX INTEGER
        MAX-ACCESS read-write
        STATUS current
        DESCRIPTION
		"The managed object is for xDSL line configuration. When the EMS
		wants to issue the desired operation, the EMS shall send SNMP-SET message to set 
		the corresponding bit value to be 1. The various bit positions are:
		BIT  1: enable port
		BIT  2: disable port
		BIT 3: reserved
		BIT 4: default port settings"
        ::= { portOperation 2 }

--------------------
-- pvcStats
--------------------

        pvcStatsTable OBJECT-TYPE
        SYNTAX SEQUENCE OF PvcStatsEntry
        MAX-ACCESS not-accessible
        STATUS current
        DESCRIPTION
        	"This table includes PVC statistics."
        ::= { pvcStats 1 }

	pvcStatsEntry OBJECT-TYPE
        SYNTAX PvcStatsEntry
        MAX-ACCESS not-accessible
        STATUS current
        DESCRIPTION
		"An entry in pvcStatsTable."
        INDEX { ifIndex, pvcVpi, pvcVci }
        ::= { pvcStatsTable 1 }

        PvcStatsEntry ::=
        	SEQUENCE {
			pvcStatsTxRate		Unsigned32,
			pvcStatsRxRate		Unsigned32,
			pvcStatsTxCells		Counter64,
			pvcStatsRxCells		Counter64,
			pvcStatsCrcErrors	Counter64,
			pvcStatsTxPackets	Counter64,
			pvcStatsRxPackets	Counter64,
			pvcStatsTxUnicast	Counter64,
			pvcStatsRxUnicast	Counter64,
			pvcStatsTxMulticast	Counter64,
			pvcStatsRxMulticast	Counter64,
			pvcStatsTxBroadcast	Counter64,
			pvcStatsRxBroadcast	Counter64,
			pvcStatsTxDiscard	Counter64,
			pvcStatsRxDiscard	Counter64
           	}

        pvcStatsTxRate OBJECT-TYPE
        SYNTAX Unsigned32
        MAX-ACCESS read-only
        STATUS current
        DESCRIPTION
                "Transmission Rate (byte/sec) on the PVC."
        ::= { pvcStatsEntry 1 }

        pvcStatsRxRate OBJECT-TYPE
        SYNTAX Unsigned32
        MAX-ACCESS read-only
        STATUS current
        DESCRIPTION
                "Receive rate (byte/sec) on the PVC."
        ::= { pvcStatsEntry 2 }
         
        pvcStatsTxCells OBJECT-TYPE
        SYNTAX Counter64
        MAX-ACCESS read-only
        STATUS current
        DESCRIPTION
                "The number of transmitted cells on the PVC since last counter reset."
        ::= { pvcStatsEntry 3 }
         
        pvcStatsRxCells OBJECT-TYPE
        SYNTAX Counter64
        MAX-ACCESS read-only
        STATUS current
        DESCRIPTION
                "The number of received packets on the PVC since last counter reset."
        ::= { pvcStatsEntry 4 }
         
        pvcStatsCrcErrors OBJECT-TYPE
        SYNTAX Counter64
        MAX-ACCESS read-only
        STATUS current
        DESCRIPTION
                "The number of detected CRC errors on the PVC since last counter reset."
        ::= { pvcStatsEntry 5 }
         
        pvcStatsTxPackets OBJECT-TYPE
        SYNTAX Counter64
        MAX-ACCESS read-only
        STATUS current
        DESCRIPTION
                "This object is supported by R1.02 and later versions.
                The number of transmitted packets on the PVC since last counter reset."
        ::= { pvcStatsEntry 6 }
        
        pvcStatsRxPackets OBJECT-TYPE
        SYNTAX Counter64
        MAX-ACCESS read-only
        STATUS current
        DESCRIPTION
                "This object is supported by R1.02 and later versions.
                The number of received packets on the PVC since last counter reset."
        ::= { pvcStatsEntry 7 }
        
        pvcStatsTxUnicast OBJECT-TYPE
        SYNTAX Counter64
        MAX-ACCESS read-only
        STATUS current
        DESCRIPTION
                "This object is supported by R1.02 and later versions.
                The number of transmitted unicast packets on the PVC since last counter reset."
        ::= { pvcStatsEntry 8 }
        
        pvcStatsRxUnicast OBJECT-TYPE
        SYNTAX Counter64
        MAX-ACCESS read-only
        STATUS current
        DESCRIPTION
                "This object is supported by R1.02 and later versions.
                The number of received unicast packets on the PVC since last counter reset."
        ::= { pvcStatsEntry 9 }
        
        pvcStatsTxMulticast OBJECT-TYPE
        SYNTAX Counter64
        MAX-ACCESS read-only
        STATUS current
        DESCRIPTION
                "This object is supported by R1.02 and later versions.
                The number of transmitted multicast packets on the PVC since last counter reset."
        ::= { pvcStatsEntry 10 }
        
        pvcStatsRxMulticast OBJECT-TYPE
        SYNTAX Counter64
        MAX-ACCESS read-only
        STATUS current
        DESCRIPTION
                "This object is supported by R1.02 and later versions.
                The number of received multicast packets on the PVC since last counter reset."
        ::= { pvcStatsEntry 11 }
        
        pvcStatsTxBroadcast OBJECT-TYPE
        SYNTAX Counter64
        MAX-ACCESS read-only
        STATUS current
        DESCRIPTION
                "This object is supported by R1.02 and later versions.
                The number of transmitted broadcast packets on the PVC since last counter reset."
        ::= { pvcStatsEntry 12 }
        
        pvcStatsRxBroadcast OBJECT-TYPE
        SYNTAX Counter64
        MAX-ACCESS read-only
        STATUS current
        DESCRIPTION
                "This object is supported by R1.02 and later versions.
                The number of received broadcast packets on the PVC since last counter reset."
        ::= { pvcStatsEntry 13 }

        pvcStatsTxDiscard OBJECT-TYPE
        SYNTAX Counter64
        MAX-ACCESS read-only
        STATUS current
        DESCRIPTION
                "This object is supported by R1.02 and later versions.
                The number of discarded packets when transmitted on the PVC since last counter reset."
        ::= { pvcStatsEntry 14 }
        
        pvcStatsRxDiscard OBJECT-TYPE
        SYNTAX Counter64
        MAX-ACCESS read-only
        STATUS current
        DESCRIPTION
                "This object is supported by R1.02 and later versions.
                The number of discarded packets when received on the PVC since last counter reset."
        ::= { pvcStatsEntry 15 }
        
        pvcCounterIfIndex OBJECT-TYPE
        SYNTAX INTEGER
        MAX-ACCESS read-write
        STATUS current
        DESCRIPTION
                "IfIndex of the PVC whose counters would be reset."
        ::= { pvcStats 2 }
         
        pvcCounterVpi OBJECT-TYPE
        SYNTAX INTEGER (0..255)
        MAX-ACCESS read-write
        STATUS current
        DESCRIPTION
                "VPI of the PVC whose counters would be reset."
        ::= { pvcStats 3 }
         
        pvcCounterVci OBJECT-TYPE
        SYNTAX INTEGER (1..65535)
        MAX-ACCESS read-write
        STATUS current
        DESCRIPTION
                "VCI of the PVC whose counters would be reset."
        ::= { pvcStats 4 }
                  
        pvcCounterReset OBJECT-TYPE
        SYNTAX INTEGER
        MAX-ACCESS read-write
        STATUS current
        DESCRIPTION
                "Set the object to 1 to reset PVC counters for the PVC which is identified by 
                pvcCounterIfIndex, pvcCounterVpi, and pvcCounterVci."
        ::= { pvcStats 5 }

--------------------
-- paepvc
--------------------

-- PPPoAoE PVC Table

        paepvcTable OBJECT-TYPE
        SYNTAX SEQUENCE OF PaepvcEntry
        MAX-ACCESS not-accessible
        STATUS current
        DESCRIPTION
        	"This table includes PPPoAoE PVC configuration.
        	This table is supported by R1.02 and later versions."
        ::= { paepvc 1 }

	paepvcEntry OBJECT-TYPE
        SYNTAX PaepvcEntry
        MAX-ACCESS not-accessible
        STATUS current
        DESCRIPTION
		"An entry of paepvcTable."
        INDEX { ifIndex, paepvcVpi, paepvcVci, paepvcPvid }
        ::= { paepvcTable 1 }

        PaepvcEntry ::=
        	SEQUENCE {
			paepvcVpi		INTEGER,
			paepvcVci		INTEGER,
			paepvcPvid		VlanIndex,
			paepvcEncap		INTEGER,
			paepvcPriority		INTEGER,
			paepvcProfile		DisplayString,
			paepvcAcName		DisplayString,
			paepvcServiceName	DisplayString,
			paepvcHelloTime		INTEGER,
			paepvcRowStatus		RowStatus
           	}

        paepvcVpi OBJECT-TYPE
        SYNTAX INTEGER (0..255)
        MAX-ACCESS read-only
        STATUS current
        DESCRIPTION
                "VPI of the pvc."
         ::= { paepvcEntry 1 }

        paepvcVci OBJECT-TYPE
        SYNTAX INTEGER (1..65535)
        MAX-ACCESS read-only
       	STATUS current
        DESCRIPTION
                "VCI of the pvc."
         ::= { paepvcEntry 2 }

        paepvcPvid OBJECT-TYPE
        SYNTAX VlanIndex
        MAX-ACCESS read-only
        STATUS current
        DESCRIPTION
                "Default VID of the pvc."
         ::= { paepvcEntry 3 }

        paepvcEncap OBJECT-TYPE
        SYNTAX INTEGER {
        		llc(1),
        		vc(2)
        	}
        MAX-ACCESS read-create
        STATUS current
        DESCRIPTION
                "Encapsulation of the pvc."
         ::= { paepvcEntry 4 }

        paepvcPriority OBJECT-TYPE
        SYNTAX INTEGER (0..7)
        MAX-ACCESS read-create
        STATUS current
        DESCRIPTION
                "802.1p default priority of the pvc."
         ::= { paepvcEntry 5 }

        paepvcProfile OBJECT-TYPE
        SYNTAX DisplayString (SIZE (1..31))
        MAX-ACCESS read-create
        STATUS current
        DESCRIPTION
                "The value of this object identifies the row in the atmProfileTable, which applies for this pvc."
         ::= { paepvcEntry 6 }

        paepvcAcName OBJECT-TYPE
        SYNTAX DisplayString
        MAX-ACCESS read-create
        STATUS current
        DESCRIPTION
                "Access concentrator name."
         ::= { paepvcEntry 7 }
         
        paepvcServiceName OBJECT-TYPE
        SYNTAX DisplayString
        MAX-ACCESS read-create
        STATUS current
        DESCRIPTION
                "Service name."
         ::= { paepvcEntry 8 }

        paepvcHelloTime OBJECT-TYPE
        SYNTAX INTEGER
        UNITS "second"
        MAX-ACCESS read-create
        STATUS current
        DESCRIPTION
                "The system will close the PVC if there are not any LCP echo messages passed through 
                during the LCP hello time."
         ::= { paepvcEntry 9 }
                  
        paepvcRowStatus OBJECT-TYPE
        SYNTAX RowStatus
        MAX-ACCESS read-create
        STATUS current
        DESCRIPTION
                "This object is used to create a new row or delete an existing row in this table."
         ::= { paepvcEntry 10 }
 
--------------------
-- tlspvc
--------------------

-- TLS PVC Table

        tlspvcTable OBJECT-TYPE
        SYNTAX SEQUENCE OF TlspvcEntry
        MAX-ACCESS not-accessible
        STATUS current
        DESCRIPTION
        	"This table includes Transparent LAN Service (TLS) PVC configuration.
        	This table is supported by R1.02 and later versions."
        ::= { tlspvc 1 }

	tlspvcEntry OBJECT-TYPE
        SYNTAX TlspvcEntry
        MAX-ACCESS not-accessible
        STATUS current
        DESCRIPTION
		"An entry of tlspvcTable."
        INDEX { ifIndex, tlspvcVpi, tlspvcVci, tlspvcSvid }
        ::= { tlspvcTable 1 }

        TlspvcEntry ::=
        	SEQUENCE {
			tlspvcVpi		INTEGER,
			tlspvcVci		INTEGER,
			tlspvcSvid		VlanIndex,
			tlspvcEncap		INTEGER,
			tlspvcSpriority		INTEGER,
			tlspvcProfile		DisplayString,
			tlspvcRowStatus		RowStatus
           	}

        tlspvcVpi OBJECT-TYPE
        SYNTAX INTEGER (0..255)
        MAX-ACCESS read-only
        STATUS current
        DESCRIPTION
                "VPI of the pvc."
         ::= { tlspvcEntry 1 }

        tlspvcVci OBJECT-TYPE
        SYNTAX INTEGER (1..65535)
        MAX-ACCESS read-only
       	STATUS current
        DESCRIPTION
                "VCI of the pvc."
         ::= { tlspvcEntry 2 }

        tlspvcSvid OBJECT-TYPE
        SYNTAX VlanIndex
        MAX-ACCESS read-only
        STATUS current
        DESCRIPTION
                "s-tag VLAN ID of the pvc."
         ::= { tlspvcEntry 3 }

        tlspvcEncap OBJECT-TYPE
        SYNTAX INTEGER {
        		llc(1),
        		vc(2)
        	}
        MAX-ACCESS read-create
        STATUS current
        DESCRIPTION
                "Encapsulation of the pvc."
         ::= { tlspvcEntry 4 }

        tlspvcSpriority OBJECT-TYPE
        SYNTAX INTEGER (0..7)
        MAX-ACCESS read-create
        STATUS current
        DESCRIPTION
                "s-tag priority of the pvc."
         ::= { tlspvcEntry 5 }

        tlspvcProfile OBJECT-TYPE
        SYNTAX DisplayString (SIZE (1..31))
        MAX-ACCESS read-create
        STATUS current
        DESCRIPTION
                "The value of this object identifies the row in the atmProfileTable, which applies for this pvc."
         ::= { tlspvcEntry 6 }

        tlspvcRowStatus OBJECT-TYPE
        SYNTAX RowStatus
        MAX-ACCESS read-create
        STATUS current
        DESCRIPTION
                "This object is used to create a new row or delete an existing row in this table."
         ::= { tlspvcEntry 7 }
        
--------------------
--  vdslPort
--------------------

-- VDSL Line Table

        vdslLineConfTable OBJECT-TYPE
        SYNTAX SEQUENCE OF VdslLineConfEntry
        MAX-ACCESS not-accessible
        STATUS current
        DESCRIPTION
		"This table includes common attributes describing the VDSL line.
		This table is supported by R2.00 and later versions."
        ::= { vdslPort 1 }

	vdslLineConfEntry OBJECT-TYPE
        SYNTAX VdslLineConfEntry
        MAX-ACCESS not-accessible
        STATUS current
        DESCRIPTION
        	"An entry in vdslLineConfTable."
        INDEX { ifIndex }
        ::= { vdslLineConfTable 1 }

        VdslLineConfEntry ::=
           SEQUENCE {
		vdslLineConfUpbo		INTEGER,
		vdslLineConfVdslProfile		INTEGER,
		vdslLineConfFrequencyPlan	INTEGER,
		vdslLineConfRfiBand		INTEGER,
		vdslLineConfIpqosProfile	DisplayString,
		vdslLineConfVturInp		INTEGER,
		vdslLineConfVtucInp		INTEGER,
		vdslLineConfOptionMask		INTEGER,
		vdslLineConfUpboForceLength	INTEGER,
		vdslLineConfPsdShape		INTEGER,
		vdslLineConfDpbo		INTEGER,
		vdslLineConfDpboParamEsel	INTEGER,
		vdslLineConfDpboParamEscma	INTEGER,
		vdslLineConfDpboParamEscmb	INTEGER,
		vdslLineConfDpboParamEscmc	INTEGER,
		vdslLineConfDpboParamMus	INTEGER,
		vdslLineConfDpboParamFmin	INTEGER,
		vdslLineConfDpboParamFmax	INTEGER,
		vdslLineConfDpboParamPsdId	INTEGER,
		vdslLineConfCompatible		INTEGER,
		vdslLineConfPowerMode		INTEGER,
		vdslLineConfVturMaxTxPower	INTEGER, 
		vdslLineConfVtucMaxTxPower	INTEGER,
        vdslLineConfMaxRxPower		INTEGER,
        vdslLineConfPMask 			INTEGER,
        vdslLineConfAturCarrierMask	OCTET STRING,
        vdslLineConfAtucCarrierMask0 OCTET STRING,
        vdslLineConfAtucCarrierMask1 OCTET STRING,
        vdslLineConfSnrModeDs   	 INTEGER,
        vdslLineConfSnrModeUs  		 INTEGER,
        vdslLineConfTxRefVnDs 		 OCTET STRING,
        vdslLineConfTxRefVnUs		 OCTET STRING,
        vdslLineConfTpstcTypeAdsl	INTEGER,
        vdslLineConfTpstcTypeVdsl	INTEGER,
        vdslLineConfVturInmEq		Unsigned32,
        vdslLineConfVtucInmEq		Unsigned32,
        vdslLineConfInmVturCC		Unsigned32,
        vdslLineConfInmVtucCC		Unsigned32,
        vdslLineConfInmVturIATO		Unsigned32,
        vdslLineConfInmVtucIATO		Unsigned32,
        vdslLineConfInmVturIATS		Unsigned32,
        vdslLineConfInmVtucIATS		Unsigned32,
        vdslLineConfInmVtucISDBUS	INTEGER,
        vdslLineConfGinpRtxModeDs	Xdsl2ConfigRtxMode,
        vdslLineConfGinpRtxModeUs	Xdsl2ConfigRtxMode,
        vdslLineConfGinpEtrMaxDs	Unsigned32,
        vdslLineConfGinpEtrMaxUs	Unsigned32,
        vdslLineConfGinpEtrMinDs	Unsigned32,
        vdslLineConfGinpEtrMinUs	Unsigned32,
        vdslLineConfGinpNdrMaxDs	Unsigned32,
        vdslLineConfGinpNdrMaxUs	Unsigned32,
        vdslLineConfGinpShineRatioDs	Unsigned32,
        vdslLineConfGinpShineRatioUs	Unsigned32,
        vdslLineConfGinpLeftrThresholdDs	Unsigned32,
        vdslLineConfGinpLeftrThresholdUs	Unsigned32,
        vdslLineConfGinpMaxDelayDs	Unsigned32,
        vdslLineConfGinpMaxDelayUs	Unsigned32,
        vdslLineConfGinpMinDelayDs	Unsigned32,
        vdslLineConfGinpMinDelayUs	Unsigned32,
        vdslLineConfGinpInpMinDs	Unsigned32,
        vdslLineConfGinpInpMinUs	Unsigned32,
        vdslLineConfGinpReinCfgInpDs	Unsigned32,
        vdslLineConfGinpReinCfgInpUs	Unsigned32,
        vdslLineConfGinpReinCfgFreqDs	Unsigned32,
        vdslLineConfGinpReinCfgFreqUs	Unsigned32,
        vdslLineConfSosMinRateB0Ds	Unsigned32,
        vdslLineConfSosMinRateB0Us	Unsigned32,
        vdslLineConfSosTimeDs	Unsigned32,
        vdslLineConfSosTimeUs	Unsigned32,
        vdslLineConfSosCrcDs	Unsigned32,
        vdslLineConfSosCrcUs	Unsigned32,
        vdslLineConfSosNToneDs	Unsigned32,
        vdslLineConfSosNToneUs	Unsigned32,
        vdslLineConfSosMaxDs	Unsigned32,
        vdslLineConfSosMaxUs	Unsigned32,
        vdslLineConfSosMultiStepDs	BITS,
        vdslLineConfSosMultiStepUs	BITS,
        vdslLineConfRocEnableDs	INTEGER,
        vdslLineConfRocEnableUs	INTEGER,
        vdslLineConfRocSnrmDs	Unsigned32,
        vdslLineConfRocSnrmUs	Unsigned32,
        vdslLineConfRocMinInpDs	Unsigned32,
        vdslLineConfRocMinInpUs	Unsigned32,
        vdslLineConfSosEnableDs	INTEGER,
        vdslLineConfSosEnableUs	INTEGER,
        vdslLineConfDynamicDepthDs	INTEGER,
        vdslLineConfDynamicDepthUs	INTEGER,
        vdslLineConfDpboParamType	INTEGER,
        vdslLineConfDpboParamEselMin	INTEGER,
        vdslLineConfHsTxA43Psd	INTEGER,
        vdslLineConfHsTxB43Psd	INTEGER,
        vdslLineConfHsTxA43cB43cPsd	INTEGER,
        vdslLineConfHsTxV43Carrier257Psd	INTEGER,
        vdslLineConfHsTxV43Carrier383Psd	INTEGER,
        vdslLineConfHsTxV43Carrier511Psd	INTEGER
           }

        vdslLineConfUpbo OBJECT-TYPE
        SYNTAX 	INTEGER {
			enable(1),
			disable(2)
		}
        MAX-ACCESS read-write
        STATUS current
        DESCRIPTION
		"Enable/disable upstream power backoff control."
        ::= { vdslLineConfEntry 1 }
        
        vdslLineConfVdslProfile OBJECT-TYPE
        SYNTAX 	INTEGER {
			vdsl-8a(1),
			vdsl-8b(2),
			vdsl-8c(3),
			vdsl-8d(4),
			vdsl-12a(5),
			vdsl-12b(6),
 			vdsl-17a(7),
 			auto(8),
 			adsl2plus(9),
 			vdsl2(10)
		}
        MAX-ACCESS read-write
        STATUS current
        DESCRIPTION
		"Set VDSL profile."
        ::= { vdslLineConfEntry 2 }
        
        vdslLineConfFrequencyPlan OBJECT-TYPE
        SYNTAX 	INTEGER {
			plan997(1),
			plan998(2)
		}
        MAX-ACCESS read-write
        STATUS current
        DESCRIPTION
		"Set VDSL frequency plan."
        ::= { vdslLineConfEntry 3 }

	vdslLineConfRfiBand OBJECT-TYPE
        SYNTAX 	INTEGER {
			disable(1),
			ansi(2),
			etsi(3),
			custom(4)
		}
        MAX-ACCESS read-write
        STATUS current
        DESCRIPTION
		"Set VDSL customized RFI configuration.
		disable: not apply RFI notch to port
		ansi: use pre-defined ANSI RFI notch
		etsi: use pre-defined ETSI notch
		custom: user needs to define customized RFI notch band through vdslRfiCustomTable"
        ::= { vdslLineConfEntry 4 }
        
        vdslLineConfIpqosProfile OBJECT-TYPE
        SYNTAX DisplayString
        MAX-ACCESS read-write
        STATUS current
        DESCRIPTION
		""
        ::= { vdslLineConfEntry 5 }
        
        vdslLineConfVturInp OBJECT-TYPE
        SYNTAX INTEGER (0..160)
        UNITS "0.1 DTM symbol"
        MAX-ACCESS read-write
        STATUS current
        DESCRIPTION
		"This object is supported by R5.01 and later versions."
        ::= { vdslLineConfEntry 6 }
        
        vdslLineConfVtucInp OBJECT-TYPE
        SYNTAX INTEGER (0..160)
        UNITS "0.1 DTM symbol"
        MAX-ACCESS read-write
        STATUS current
        DESCRIPTION
		"This object is supported by R5.01 and later versions."
        ::= { vdslLineConfEntry 7 }
        
        vdslLineConfOptionMask OBJECT-TYPE
        SYNTAX INTEGER
        MAX-ACCESS read-write
        STATUS current
        DESCRIPTION
		"This object is supported by R5.01 and later versions.
		Bit1: disable Trellis coding in ADSL mode
		Bit2: disable Reed-Solomon coding for ADSL
		Bit3: disable upstream bitswaps
		Bit4: disable downstream bitwaps
		Bit5: disable upstream 1-bit constellation support
		Bit6: disable the transmit windowing in ADSL2+ mode
		Bit7: disable S=0.5 support in G.dmt
		Bit8: reserved
		Bit9: enable nitro
		Bit12: enable US PTM optimization
		Bit13: enable DS PTM optimization
		Bit14: enable US PHYR
		Bit15: enable DS PHYR"
        ::= { vdslLineConfEntry 8 }
        
        vdslLineConfUpboForceLength OBJECT-TYPE
        SYNTAX INTEGER (0..1270)
        UNITS "0.1dB"
        MAX-ACCESS read-write
        STATUS current
        DESCRIPTION
		"-1 means auto electric length. This object is supported by R5.01 and later versions."
        ::= { vdslLineConfEntry 9 }
        
        vdslLineConfPsdShape OBJECT-TYPE
        SYNTAX INTEGER {
			vdsl2-a-nus0(1),                
			vdsl2-a-eu32(2),              
			vdsl2-a-eu36(3),                
			vdsl2-a-eu40(4),              
			vdsl2-a-eu44(5),                
			vdsl2-a-eu48(6),              
			vdsl2-a-eu52(7),                
			vdsl2-a-eu56(8),              
			vdsl2-a-eu60(9),                
			vdsl2-a-eu64(10),              
			vdsl2-a-eu128(11),               
			vdsl1-fttex-ansi-m1(12),       
			vdsl1-fttex-ansi-m2(13),         
			vdsl1-fttcab-ansi-m1(14),      
			vdsl1-fttcab-ansi-m2(15),        
			vdsl1-fttex-ansi-m1-e(16),     
			vdsl1-fttex-ansi-m2-e(17),       
			vdsl-fttcab-ansi-m1-e(18),     
			vdsl-fttcab-ansi-m2-e(19),       
			vdsl2-a-ct(20),                
			vdsl2-b8-1(21),                  
			vdsl2-b8-2(22),                
			vdsl2-b8-3(23),                  
			vdsl2-b8-4(24),                
			vdsl2-b8-5(25),                  
			vdsl2-b8-6(26),                
			vdsl2-b8-7(27),                  
			vdsl2-b8-8(28),                
			vdsl2-b8-9(29),                  
			vdsl2-b8-10(30),               
			vdsl2-b8-11(31),                 
			vdsl2-b8-12(32),               
			vdsl2-b8-13(33),                 
			vdsl2-b8-14(34),               
			vdsl2-b8-15(35),                 
			vdsl2-b8-16(36),               
			vdsl2-b7-1(37),                  
			vdsl2-b7-2(38),                
			vdsl2-b7-3(39),                  
			vdsl2-b7-4(40),                
			vdsl2-b7-5(41),                  
			vdsl2-b7-6(42),                
			vdsl2-b7-7(43),                  
			vdsl2-b7-8(44),                
			vdsl2-b7-9(45),                  
			vdsl2-b7-10(46),               
			vdsl2-bt-anfp(47),               
			vdsl2-c-138-b(48),             
			vdsl2-c-276-b(49),               
			vdsl2-c-138-co(50),            
			vdsl2-c-276-co(51)
		}
        MAX-ACCESS read-write
        STATUS current
        DESCRIPTION
		"This object is supported by R5.01 and later versions."
        ::= { vdslLineConfEntry 10 }
        
        vdslLineConfDpbo OBJECT-TYPE
        SYNTAX INTEGER {
        		enable(1),
        		disable(2)
        	}
        MAX-ACCESS read-write
        STATUS current
        DESCRIPTION
		"This object is supported by R5.01 and later versions."
        ::= { vdslLineConfEntry 11 }
        
        vdslLineConfDpboParamEsel OBJECT-TYPE
        SYNTAX INTEGER (0..511)
        UNITS "0.5dB"
        MAX-ACCESS read-write
        STATUS current
        DESCRIPTION
		"This object is supported by R5.01 and later versions."
        ::= { vdslLineConfEntry 12 }
        
        vdslLineConfDpboParamEscma OBJECT-TYPE
        SYNTAX INTEGER (0..640)
        MAX-ACCESS read-write
        STATUS current
        DESCRIPTION
		"-1~-1.5 in step of 1/256. This object is supported by R5.01 and later versions."
        ::= { vdslLineConfEntry 13 }
        
        vdslLineConfDpboParamEscmb OBJECT-TYPE
        SYNTAX INTEGER (0..640)
        MAX-ACCESS read-write
        STATUS current
        DESCRIPTION
		"-1~-1.5 in step of 1/256. This object is supported by R5.01 and later versions."
        ::= { vdslLineConfEntry 14 }
        
        vdslLineConfDpboParamEscmc OBJECT-TYPE
        SYNTAX INTEGER (0..640)
        MAX-ACCESS read-write
        STATUS current
        DESCRIPTION
		"-1~-1.5 in step of 1/256. This object is supported by R5.01 and later versions."
        ::= { vdslLineConfEntry 15 }
        
        vdslLineConfDpboParamMus OBJECT-TYPE
        SYNTAX INTEGER (0..255)
        UNITS "-0.5 dBm/Hz"
        MAX-ACCESS read-write
        STATUS current
        DESCRIPTION
		"This object is supported by R5.01 and later versions."
        ::= { vdslLineConfEntry 16 }
        
        vdslLineConfDpboParamFmin OBJECT-TYPE
        SYNTAX INTEGER (0..2048)
        UNITS "4.3125kHz"
        MAX-ACCESS read-write
        STATUS current
        DESCRIPTION
		"This object is supported by R5.01 and later versions."
        ::= { vdslLineConfEntry 17 }
        
        vdslLineConfDpboParamFmax OBJECT-TYPE
        SYNTAX INTEGER (32..6956)
        UNITS "4.3125kHz"
        MAX-ACCESS read-write
        STATUS current
        DESCRIPTION
		"This object is supported by R5.01 and later versions."
        ::= { vdslLineConfEntry 18 }
        
        vdslLineConfDpboParamPsdId OBJECT-TYPE
        SYNTAX INTEGER {
        		psd-co(1),
        		psd-flat(2),
        		psd-cab-ansi(3),
        		psd-cab-etsi(4),
        		psd-exch-etsi(5),
        		psd-exch-ansi(6),
        		psd-default(100)
		}
        MAX-ACCESS read-write
        STATUS current
        DESCRIPTION
		"Always return 0 when read. This object is supported by R5.01 and later versions."
        ::= { vdslLineConfEntry 19 }

        vdslLineConfCompatible OBJECT-TYPE
        SYNTAX INTEGER {
        		none(1),
        		adsl2(2),
        		adsl2Plus(3)
		}
        MAX-ACCESS read-write
        STATUS current
        DESCRIPTION
		"Compatible to spectrum usage of adsl2 or adsl2+ line. The object is supported by R5.02 and later versions."
        ::= { vdslLineConfEntry 20 } 
        
        vdslLineConfPowerMode OBJECT-TYPE
        SYNTAX 	INTEGER {
        		fix(1),
        		priorityToPower(2),
        		priorityToRate(3)
        	}
        MAX-ACCESS read-write
        STATUS current
        DESCRIPTION
		"The power mode of the VDSL line. This MIB object is supported by R5.05 and later versions.
		1: fix 
		2: priorityToPower 
		3: priorityToRate
		"
        ::= { vdslLineConfEntry 21 } 
        
        vdslLineConfVturMaxTxPower OBJECT-TYPE
        SYNTAX 	INTEGER
        MAX-ACCESS read-write
        STATUS current
        DESCRIPTION
		"The maximum allowed transmit power of VTU-R.
		-130~200"
        ::= { vdslLineConfEntry 22 } 
        
        vdslLineConfVtucMaxTxPower OBJECT-TYPE
        SYNTAX 	INTEGER
        MAX-ACCESS read-write
        STATUS current
        DESCRIPTION
		"The maximum allowed transmit power of VTU-C.
		-50~200"
        ::= { vdslLineConfEntry 23 } 
        
        vdslLineConfMaxRxPower OBJECT-TYPE
        SYNTAX 	INTEGER
        MAX-ACCESS read-write
        STATUS current
        DESCRIPTION
		"The maximum aggregate received power.
		-255~255"
        ::= { vdslLineConfEntry 24 }   
        
        vdslLineConfPMask OBJECT-TYPE
        SYNTAX 	INTEGER
        MAX-ACCESS read-write
        STATUS current
        DESCRIPTION
		"To configure a bit mask to select preferred protocols :
		0x00000001~0xffffffff
		0x00000001 G.992.1 A|B
		0x00000002 G.992.2 A
		0x00000004 G.992.3 A|B
		0x00000010 G.992.5 A|B
		0x00000020 ANSI T1.413
		0x00000040 ETSI TS 101 388                 
		0x00000080 G.993.2 8a
		0x00000100 G.993.2 8b
		0x00000200 G.993.2 8c
		0x00000400 G.993.2 8d
		0x00000800 G.993.2 12a
		0x00001000 G.993.2 12b
		0x00002000 G.993.2 17a
		0x00004000 G.992.3 M
		0x00008000 G.992.3 J
		0x00010000 G.992.3 L
		0x00020000 G.992.3 L Narrow PSD
		0x00040000 G.992.5 M
		0x00080000 G.992.5 J
		"
        ::= { vdslLineConfEntry 25 }
        
        vdslLineConfAturCarrierMask OBJECT-TYPE
        SYNTAX 	OCTET STRING
        MAX-ACCESS read-write
        STATUS current
        DESCRIPTION
		"Sub-carrier masking for ADSL2+ fallback, 
		Upstream sub-carrier mask.
		"
        ::= { vdslLineConfEntry 26 }
        
        vdslLineConfAtucCarrierMask0 OBJECT-TYPE
        SYNTAX 	OCTET STRING
        MAX-ACCESS read-write
        STATUS current
        DESCRIPTION
		"Sub-carrier masking for ADSL2+ fallback, 
		Downstream sub-carrier mask.
		"
        ::= { vdslLineConfEntry 27 }
        
        vdslLineConfAtucCarrierMask1 OBJECT-TYPE
        SYNTAX 	OCTET STRING
        MAX-ACCESS read-write
        STATUS current
        DESCRIPTION
		"Sub-carrier masking for ADSL2+ fallback, 
		Downstream sub-carrier mask.
		"
        ::= { vdslLineConfEntry 28 }
        
        vdslLineConfSnrModeDs OBJECT-TYPE
        SYNTAX 	INTEGER{
        		enable(1),
        		disable(2)
        	}
        MAX-ACCESS read-write
        STATUS current
        DESCRIPTION
		"To enable the transmitter referred virtual noise in the downstream direction.
		1: enable(1)
		2: disable(2)
		"
        ::= { vdslLineConfEntry 29 }
        
        vdslLineConfSnrModeUs OBJECT-TYPE
        SYNTAX 	INTEGER{
        		enable(1),
        		disable(2)
        	}
        MAX-ACCESS read-write
        STATUS current
        DESCRIPTION
		"To enable the transmitter referred virtual noise in the upstream direction.
		1: enable(1)
		2: disable(2)
		"
        ::= { vdslLineConfEntry 30 }
        
        vdslLineConfTxRefVnDs OBJECT-TYPE
        SYNTAX 	OCTET STRING
        MAX-ACCESS read-write
        STATUS current
        DESCRIPTION
		"To configure downstream transmitter referred virtual noise.
		"
        ::= { vdslLineConfEntry 31 }
        
        vdslLineConfTxRefVnUs OBJECT-TYPE
        SYNTAX 	OCTET STRING
        MAX-ACCESS read-write
        STATUS current
        DESCRIPTION
		"To configure upstream transmitter referred virtual noise.
		"
        ::= { vdslLineConfEntry 32 }

        vdslLineConfTpstcTypeAdsl OBJECT-TYPE
        SYNTAX 	INTEGER {
        		atm(1),
        		ptm(2)
        	}
        MAX-ACCESS read-write
        STATUS current
        DESCRIPTION
		"TPS-TC type for ADSL mode VLC.
		1: atm(1)
		2: ptm(2)
		"
        ::= { vdslLineConfEntry 33 }
        
        vdslLineConfTpstcTypeVdsl OBJECT-TYPE
        SYNTAX 	INTEGER{
        		atm(1),
        		ptm(2)
        	}
        MAX-ACCESS read-write
        STATUS current
        DESCRIPTION
		"TPS-TC type for VDSL mode VLC.
		1: atm(1)
		2: ptm(2)
		"
        ::= { vdslLineConfEntry 34 }
        
        vdslLineConfVturInmEq OBJECT-TYPE
        SYNTAX 	Unsigned32 (0..3)
        MAX-ACCESS read-write
        STATUS current
        DESCRIPTION
		"The INM Inmpulse Noise Protection Equivalent Mode. 
		Configuration parameter INM-INPEQ-MODE defines the way of computation of 
		Equivalent INP, as defined in ITU-T G.993.2 Amd2 11.4.2.2.1. This takes a 
		value in the range from 0 to 3."
        ::= { vdslLineConfEntry 35 }
        
        vdslLineConfVtucInmEq OBJECT-TYPE
        SYNTAX 	Unsigned32 (0..3)
        MAX-ACCESS read-write
        STATUS current
        DESCRIPTION
		"The INM Inmpulse Noise Protection Equivalent Mode. 
		Configuration parameter INM-INPEQ-MODE defines the way of computation of 
		Equivalent INP, as defined in ITU-T G.993.2 Amd2 11.4.2.2.1. This takes a 
		value in the range from 0 to 3."
        ::= { vdslLineConfEntry 36 } 
        
        vdslLineConfInmVturCC OBJECT-TYPE
        SYNTAX 	Unsigned32
        MAX-ACCESS read-write
        STATUS current
        DESCRIPTION
		"The INM Cluster Continuation. The valid values for INMCC range from 0 from 
		64 DMT symbols in steps of 1 DMT symbol. Up to and including INMCC nondegraded 
		symbols will be allowed before a cluster is deemed to be complete and the impulse 
		noise event over."
        ::= { vdslLineConfEntry 37 }
        
        vdslLineConfInmVtucCC OBJECT-TYPE
        SYNTAX 	Unsigned32
        MAX-ACCESS read-write
        STATUS current
        DESCRIPTION
		"The INM Cluster Continuation. The valid values for INMCC range from 0 from 
		64 DMT symbols in steps of 1 DMT symbol. Up to and including INMCC nondegraded 
		symbols will be allowed before a cluster is deemed to be complete and the impulse 
		noise event over."
        ::= { vdslLineConfEntry 38 }
        
        vdslLineConfInmVturIATO OBJECT-TYPE
        SYNTAX 	Unsigned32
        MAX-ACCESS read-write
        STATUS current
        DESCRIPTION
		"The INM Inter Arrival Time Offset for the IAT anomaly generation. The valid values 
		for INMIATO range from 3 from 511 DMT symbols in steps of 1 DMT symbol."
        ::= { vdslLineConfEntry 39 }
        
        vdslLineConfInmVtucIATO OBJECT-TYPE
        SYNTAX 	Unsigned32
        MAX-ACCESS read-write
        STATUS current
        DESCRIPTION
		"The INM Inter Arrival Time Offset for the IAT anomaly generation. The valid values 
		for INMIATO range from 3 from 511 DMT symbols in steps of 1 DMT symbol."
        ::= { vdslLineConfEntry 40 } 
        
        vdslLineConfInmVturIATS OBJECT-TYPE
        SYNTAX 	Unsigned32
        MAX-ACCESS read-write
        STATUS current
        DESCRIPTION
		"The INM Inter Arrival Time Step for the IAT anomaly generation. The valid values for 
		INMIATS range from 0 from 7 in steps. The range of values of inter-arrival times recorded 
		in a single bin is 2^(INMIATS). All inter-arrival times greater than or equal to INMIATO+6*(2^INMIATS) 
		are recorded in the 7th bin of INMAIAT."
        ::= { vdslLineConfEntry 41 }
        
        vdslLineConfInmVtucIATS OBJECT-TYPE
        SYNTAX 	Unsigned32
        MAX-ACCESS read-write
        STATUS current
        DESCRIPTION
		"The INM Inter Arrival Time Step for the IAT anomaly generation. The valid values for 
		INMIATS range from 0 from 7 in steps. The range of values of inter-arrival times recorded 
		in a single bin is 2^(INMIATS). All inter-arrival times greater than or equal to INMIATO+6*(2^INMIATS) 
		are recorded in the 7th bin of INMAIAT."
        ::= { vdslLineConfEntry 42 }
        
        vdslLineConfInmVtucISDBUS OBJECT-TYPE
        SYNTAX 	INTEGER
        MAX-ACCESS read-write
        STATUS current
        DESCRIPTION
		"ISDD sensitivity of VTU-C,-128~127 in unit of 0.1dB."
        ::= { vdslLineConfEntry 43 }
        
        vdslLineConfGinpRtxModeDs OBJECT-TYPE
        SYNTAX 	Xdsl2ConfigRtxMode
        MAX-ACCESS read-write
        STATUS current
        DESCRIPTION
		"G.inp(G.998.4) support setting on downstream direction. The possible values are: 
		Forbidden(0) - Support for G998.4 is disabled. Preferred(1) - If G998.4 is supported by the far-end, it is enabled.  
		Forced(2) - The line will only train if G998.4 can be enabled. 
		Test(3) - G998.4 is enabled in test mode (refer to G998.4, Clause 10.4)."
        ::= { vdslLineConfEntry 44 }
        
        vdslLineConfGinpRtxModeUs OBJECT-TYPE
        SYNTAX 	Xdsl2ConfigRtxMode
        MAX-ACCESS read-write
        STATUS current
        DESCRIPTION
		"G.inp(G.998.4) support setting on upstream direction. The possible values are: 
		Forbidden(0) - Support for G998.4 is disabled. Preferred(1) - If G998.4 is supported by the far-end, it is enabled.  
		Forced(2) - The line will only train if G998.4 can be enabled. 
		Test(3) - G998.4 is enabled in test mode (refer to G998.4, Clause 10.4)."
        ::= { vdslLineConfEntry 45 } 
        
        vdslLineConfGinpEtrMaxDs OBJECT-TYPE
        SYNTAX 	Unsigned32
        MAX-ACCESS read-write
        STATUS current
        DESCRIPTION
		"Defines the maximum allowed value for the ETR (Effective Throughput Rate)."
        ::= { vdslLineConfEntry 46 }
        
        vdslLineConfGinpEtrMaxUs OBJECT-TYPE
        SYNTAX 	Unsigned32
        MAX-ACCESS read-write
        STATUS current
        DESCRIPTION
		"Defines the maximum allowed value for the ETR (Effective Throughput Rate)."
        ::= { vdslLineConfEntry 47 }
        
        vdslLineConfGinpEtrMinDs OBJECT-TYPE
        SYNTAX 	Unsigned32
        MAX-ACCESS read-write
        STATUS current
        DESCRIPTION
		"Defines the minimum value for the ETR (Effective Throughput Rate)."
        ::= { vdslLineConfEntry 48 }
        
        vdslLineConfGinpEtrMinUs OBJECT-TYPE
        SYNTAX 	Unsigned32
        MAX-ACCESS read-write
        STATUS current
        DESCRIPTION
		"Defines the minimum value for the ETR (Effective Throughput Rate)."
        ::= { vdslLineConfEntry 49 }
        
        vdslLineConfGinpNdrMaxDs OBJECT-TYPE
        SYNTAX 	Unsigned32
        MAX-ACCESS read-write
        STATUS current
        DESCRIPTION
		"Overrules the wanted maximum data rate provided in the SetLineTrafficConfiguration"
        ::= { vdslLineConfEntry 50 }
        
        vdslLineConfGinpNdrMaxUs OBJECT-TYPE
        SYNTAX 	Unsigned32
        MAX-ACCESS read-write
        STATUS current
        DESCRIPTION
		"Overrules the wanted maximum data rate provided in the SetLineTrafficConfiguration"
        ::= { vdslLineConfEntry 51 }
        
        vdslLineConfGinpShineRatioDs OBJECT-TYPE
        SYNTAX 	Unsigned32
        MAX-ACCESS read-write
        STATUS current
        DESCRIPTION
		"The assumed fraction (0.001 to 0.255) of NDR necessary to correct SHINE noise."
        ::= { vdslLineConfEntry 52 }
        
        vdslLineConfGinpShineRatioUs OBJECT-TYPE
        SYNTAX 	Unsigned32
        MAX-ACCESS read-write
        STATUS current
        DESCRIPTION
		"The assumed fraction (0.001 to 0.255) of NDR necessary to correct SHINE noise."
        ::= { vdslLineConfEntry 53 }
        
        vdslLineConfGinpLeftrThresholdDs OBJECT-TYPE
        SYNTAX 	Unsigned32
        MAX-ACCESS read-write
        STATUS current
        DESCRIPTION
		"The rate threshold (fraction of NDR) below which the Low Error Free Rate (LEFTR) defect is declared."
        ::= { vdslLineConfEntry 54 }
        
        vdslLineConfGinpLeftrThresholdUs OBJECT-TYPE
        SYNTAX 	Unsigned32
        MAX-ACCESS read-write
        STATUS current
        DESCRIPTION
		"The rate threshold (fraction of NDR) below which the Low Error Free Rate (LEFTR) defect is declared."
        ::= { vdslLineConfEntry 55 }
        
        vdslLineConfGinpMaxDelayDs OBJECT-TYPE
        SYNTAX 	Unsigned32
        MAX-ACCESS read-write
        STATUS current
        DESCRIPTION
		"G.inp-specific value that overrules the traffic configuration setting."
        ::= { vdslLineConfEntry 56 }
        
        vdslLineConfGinpMaxDelayUs OBJECT-TYPE
        SYNTAX 	Unsigned32
        MAX-ACCESS read-write
        STATUS current
        DESCRIPTION
		"G.inp-specific value that overrules the traffic configuration setting."
        ::= { vdslLineConfEntry 57 }
        
        vdslLineConfGinpMinDelayDs OBJECT-TYPE
        SYNTAX 	Unsigned32
        MAX-ACCESS read-write
        STATUS current
        DESCRIPTION
		"G.inp-specific value that overrules the traffic configuration setting."
        ::= { vdslLineConfEntry 58 }
        
        vdslLineConfGinpMinDelayUs OBJECT-TYPE
        SYNTAX 	Unsigned32
        MAX-ACCESS read-write
        STATUS current
        DESCRIPTION
		"G.inp-specific value that overrules the traffic configuration setting."
        ::= { vdslLineConfEntry 59 }
        
        vdslLineConfGinpInpMinDs OBJECT-TYPE
        SYNTAX 	Unsigned32
        MAX-ACCESS read-write
        STATUS current
        DESCRIPTION
		"G.inp-specific value that overrules the traffic configuration setting. Unit is symbol. 
		The possible values are: 0-31"
        ::= { vdslLineConfEntry 60 }
        
        vdslLineConfGinpInpMinUs OBJECT-TYPE
        SYNTAX 	Unsigned32
        MAX-ACCESS read-write
        STATUS current
        DESCRIPTION
		"G.inp-specific value that overrules the traffic configuration setting. Unit is symbol. 
		The possible values are: 0-31"
        ::= { vdslLineConfEntry 61 }
        
        vdslLineConfGinpReinCfgInpDs OBJECT-TYPE
        SYNTAX 	Unsigned32
        MAX-ACCESS read-write
        STATUS current
        DESCRIPTION
		"G.inp-specific value that overrules the traffic configuration setting. Unit is symbol. 
		The possible values are: 0-7"
        ::= { vdslLineConfEntry 62 }
        
        vdslLineConfGinpReinCfgInpUs OBJECT-TYPE
        SYNTAX 	Unsigned32
        MAX-ACCESS read-write
        STATUS current
        DESCRIPTION
		"G.inp-specific value that overrules the traffic configuration setting. Unit is symbol. 
		The possible values are: 0-7"
        ::= { vdslLineConfEntry 63 }
        
        vdslLineConfGinpReinCfgFreqDs OBJECT-TYPE
        SYNTAX 	Unsigned32
        MAX-ACCESS read-write
        STATUS current
        DESCRIPTION
		"G.inp-specific value that overrules the traffic configuration setting. Unit is Hz. 
		The possible values are:
		100 - 100Hz
		120 - 120Hz"
        ::= { vdslLineConfEntry 64 }
        
        vdslLineConfGinpReinCfgFreqUs OBJECT-TYPE
        SYNTAX 	Unsigned32
        MAX-ACCESS read-write
        STATUS current
        DESCRIPTION
		"G.inp-specific value that overrules the traffic configuration setting. Unit is Hz. 
		The possible values are:
		100 - 100Hz
		120 - 120Hz"
        ::= { vdslLineConfEntry 65 }
        
        vdslLineConfSosMinRateB0Ds OBJECT-TYPE
        SYNTAX 	Unsigned32
        MAX-ACCESS read-write
        STATUS current
        DESCRIPTION
		"This parameter specifies the minimum net data rate required for a valid SOS request 
		in the downstream direction. The value shall be coded as an unsigned integer representing 
		the data rate as a multiple of 8 kbit/s."
        ::= { vdslLineConfEntry 66 }
        
        vdslLineConfSosMinRateB0Us OBJECT-TYPE
        SYNTAX 	Unsigned32
        MAX-ACCESS read-write
        STATUS current
        DESCRIPTION
		"This parameter specifies the minimum net data rate required for a valid SOS request 
		in the upstream direction. The value shall be coded as an unsigned integer representing 
		the data rate as a multiple of 8 kbit/s."
        ::= { vdslLineConfEntry 67 } 
        
        vdslLineConfSosTimeDs OBJECT-TYPE
        SYNTAX 	Unsigned32
        MAX-ACCESS read-write
        STATUS current
        DESCRIPTION
		"The parameter SOS-TIME-ds is used in the specification of the receiver initiated SOS (see 13.4.3/G.993.2). 
		If the value of this parameter is not zero, the standard SOS triggering criteria are enabled, and the value 
		corresponds with duration of the time window used in the standard SOS triggering criteria in the downstream 
		direction. See G.993.2 for detailed usage rules. The special value zero indicates that the standard SOS triggering 
		criteria are disabled, i.e., vendor-discretionary values may be used instead of the values configured in the 
		MIB for the following parameters: SOS-NTONES-ds, SOS-CRC-ds, SOS-TIME-ds. This parameter applies in the downstream 
		direction. The valid range of non-zero values is from 64 ms to 16320 ms in steps of 64 ms."
        ::= { vdslLineConfEntry 68 }
        
        vdslLineConfSosTimeUs OBJECT-TYPE
        SYNTAX 	Unsigned32
        MAX-ACCESS read-write
        STATUS current
        DESCRIPTION
		"The parameter SOS-TIME-ds is used in the specification of the receiver initiated SOS (see 13.4.3/G.993.2). 
		If the value of this parameter is not zero, the standard SOS triggering criteria are enabled, and the value 
		corresponds with duration of the time window used in the standard SOS triggering criteria in the upstream 
		direction. See G.993.2 for detailed usage rules. The special value zero indicates that the standard SOS triggering 
		criteria are disabled, i.e., vendor-discretionary values may be used instead of the values configured in the 
		MIB for the following parameters: SOS-NTONES-ds, SOS-CRC-ds, SOS-TIME-ds. This parameter applies in the upstream 
		direction. The valid range of non-zero values is from 64 ms to 16320 ms in steps of 64 ms."
        ::= { vdslLineConfEntry 69 }
        
        vdslLineConfSosCrcDs OBJECT-TYPE
        SYNTAX 	Unsigned32
        MAX-ACCESS read-write
        STATUS current
        DESCRIPTION
		"This parameter is defined as the minimum number of normalized CRC anomalies received in SOS-TIME-ds seconds 
		in order to arm the second sub condition of the standard SOS triggering criteria (see 13.4.3.2/G.993.2) in 
		the downstream direction. See G.993.2 for detailed usage rules. The valid range of SOS-CRC values is 0.02 to 
		((2^16)-1)*0.02, in steps of 0.02."
        ::= { vdslLineConfEntry 70 }
        
        vdslLineConfSosCrcUs OBJECT-TYPE
        SYNTAX 	Unsigned32
        MAX-ACCESS read-write
        STATUS current
        DESCRIPTION
		"This parameter is defined as the minimum number of normalized CRC anomalies received in SOS-TIME-ds seconds 
		in order to arm the second sub condition of the standard SOS triggering criteria (see 13.4.3.2/G.993.2) in 
		the upstream direction. See G.993.2 for detailed usage rules. The valid range of SOS-CRC values is 0.02 to 
		((2^16)-1)*0.02, in steps of 0.02."
        ::= { vdslLineConfEntry 71 }
        
        vdslLineConfSosNToneDs OBJECT-TYPE
        SYNTAX 	Unsigned32
        MAX-ACCESS read-write
        STATUS current
        DESCRIPTION
		"This parameter is defined as the minimum percentage of tones in the downstream MEDLEY SET that must be 
		degraded in order to arm the first sub-condition of the standard SOS triggering criteria (see 13.4.3.2/G.993.2) 
		in the downstream direction. The parameter SOS-NTONES-ds is defined as a percentage of tones. See G.993.2 for 
		detailed usage rules. The valid range of values is from 1 to 100 in steps of 1. Use of the special value 0 is 
		described in 13.4.3.2/G.993.2."
        ::= { vdslLineConfEntry 72 }
        
        vdslLineConfSosNToneUs OBJECT-TYPE
        SYNTAX 	Unsigned32
        MAX-ACCESS read-write
        STATUS current
        DESCRIPTION
		"This parameter is defined as the minimum percentage of tones in the upstream MEDLEY SET that must be 
		degraded in order to arm the first sub-condition of the standard SOS triggering criteria (see 13.4.3.2/G.993.2) 
		in the upstream direction. The parameter SOS-NTONES-ds is defined as a percentage of tones. See G.993.2 for 
		detailed usage rules. The valid range of values is from 1 to 100 in steps of 1. Use of the special value 0 is 
		described in 13.4.3.2/G.993.2."
        ::= { vdslLineConfEntry 73 }
        
        vdslLineConfSosMaxDs OBJECT-TYPE
        SYNTAX 	Unsigned32
        MAX-ACCESS read-write
        STATUS current
        DESCRIPTION
		"This parameter is used in G.993.2 de-activation (see 12.1.4/G.993.2). If the number of successful SOS procedures 
		in the downstream direction performed within a 120-second interval exceeds MAX-SOS-ds, the modem shall transition 
		to the L3 state. See G.993.2 for detailed usage rules (see 12.1.4/G.993.2). The valid range of values is 1 to 15. 
		Use of the special value 0 is described in 12.1/G.993.2."
        ::= { vdslLineConfEntry 74 }
        
        vdslLineConfSosMaxUs OBJECT-TYPE
        SYNTAX 	Unsigned32
        MAX-ACCESS read-write
        STATUS current
        DESCRIPTION
		"This parameter is used in G.993.2 de-activation (see 12.1.4/G.993.2). If the number of successful SOS procedures 
		in the upstream direction performed within a 120-second interval exceeds MAX-SOS-ds, the modem shall transition 
		to the L3 state. See G.993.2 for detailed usage rules (see 12.1.4/G.993.2). The valid range of values is 1 to 15. 
		Use of the special value 0 is described in 12.1/G.993.2."
        ::= { vdslLineConfEntry 75 }
        
        vdslLineConfSosMultiStepDs OBJECT-TYPE
        SYNTAX 	BITS
        MAX-ACCESS read-write
        STATUS current
        DESCRIPTION
		"Indicates the capabilities of the VTU-R to execute the SOS request in one step or in multiple steps in the downstream direction. 
		The field is formatted as [gggg 0000]. The first four MSBs [gggg] indicate the maximum number of tones (GSOS) that can be executed 
		in a single step (GSOS)in the downstream direction. The valid values are:
		- [0000]: No limitation
		- [0010]: GSOS = 256 tones
		- [0011]: GSOS = 512 tones
		- [0100]: GSOS = 1024 tones
		"
        ::= { vdslLineConfEntry 76 }
        
        vdslLineConfSosMultiStepUs OBJECT-TYPE
        SYNTAX 	BITS
        MAX-ACCESS read-write
        STATUS current
        DESCRIPTION
		"Indicates the capabilities of the VTU-R to execute the SOS request in one step or in multiple steps in the upstream direction. 
		The field is formatted as [gggg 0000]. The first four MSBs [gggg] indicate the maximum number of tones (GSOS) that can be executed 
		in a single step (GSOS)in the upstream direction. The valid values are:
		- [0000]: No limitation
		- [0010]: GSOS = 256 tones
		- [0011]: GSOS = 512 tones
		- [0100]: GSOS = 1024 tones
		"
        ::= { vdslLineConfEntry 77 } 
        
        vdslLineConfRocEnableDs OBJECT-TYPE
        SYNTAX 	INTEGER{
			disable (1),
			enable (2)
		}

        MAX-ACCESS read-write
        STATUS current
        DESCRIPTION
		"Enable the robust overhead channel.
		disable(1),
		enable(2)
		"
        ::= { vdslLineConfEntry 78 }
        
        vdslLineConfRocEnableUs OBJECT-TYPE
        SYNTAX 	INTEGER{
			disable (1),
			enable (2)
		}
        MAX-ACCESS read-write
        STATUS current
        DESCRIPTION
		"Enable the robust overhead channel.
		disable(1),
		enable(2)
		"
        ::= { vdslLineConfEntry 79 }
        
        vdslLineConfRocSnrmDs OBJECT-TYPE
        SYNTAX 	Unsigned32
        MAX-ACCESS read-write
        STATUS current
        DESCRIPTION
		"The parameter is defined as the SNR margin offset for the ROC channel in 
		the downstream direction. The parameter is used in the specification of the 
		channel initialization policy (see 12.3.7.1/G.993.2). The valid range of SNR 
		margin offset values is from 0 to 31 dB with 0.1 dB steps."
        ::= { vdslLineConfEntry 80 }
        
        vdslLineConfRocSnrmUs OBJECT-TYPE
        SYNTAX 	Unsigned32
        MAX-ACCESS read-write
        STATUS current
        DESCRIPTION
		"The parameter is defined as the SNR margin offset for the ROC channel in 
		the upstream direction. The parameter is used in the specification of the 
		channel initialization policy (see 12.3.7.1/G.993.2). The valid range of SNR 
		margin offset values is from 0 to 31 dB with 0.1 dB steps."
        ::= { vdslLineConfEntry 81 }
        
        vdslLineConfRocMinInpDs OBJECT-TYPE
        SYNTAX 	Unsigned32
        MAX-ACCESS read-write
        STATUS current
        DESCRIPTION
		"This parameter contains the minimum impulse noise protection to apply on the ROC 
		in the downstream direction. The minimum impulse noise protection is an integer ranging from 0 to 16."
        ::= { vdslLineConfEntry 82 }
        
        vdslLineConfRocMinInpUs OBJECT-TYPE
        SYNTAX 	Unsigned32
        MAX-ACCESS read-write
        STATUS current
        DESCRIPTION
		"This parameter contains the minimum impulse noise protection to apply on the ROC 
		in the upstream direction. The minimum impulse noise protection is an integer ranging from 0 to 16."
        ::= { vdslLineConfEntry 83 }
        
        vdslLineConfSosEnableDs OBJECT-TYPE
        SYNTAX 	INTEGER{
			disable (1),
			enable (2)
		}
        MAX-ACCESS read-write
        STATUS current
        DESCRIPTION
		"Enable the emergency rate reduction.
		disable(1),
		enable(2)
		"
        ::= { vdslLineConfEntry 84 }
        
        vdslLineConfSosEnableUs OBJECT-TYPE
        SYNTAX 	INTEGER{
			disable (1),
			enable (2)
		}
        MAX-ACCESS read-write
        STATUS current
        DESCRIPTION
		"Enable the emergency rate reduction.
		disable(1),
		enable(2)
		"
        ::= { vdslLineConfEntry 85 }
        
        vdslLineConfDynamicDepthDs OBJECT-TYPE
        SYNTAX 	INTEGER{
			disable (1),
			enable (2)
		}
        MAX-ACCESS read-write
        STATUS current
        DESCRIPTION
		"Enable the dynamic change of interleave depth."
        ::= { vdslLineConfEntry 86 }
        
        vdslLineConfDynamicDepthUs OBJECT-TYPE
        SYNTAX 	INTEGER{
			disable (1),
			enable (2)
		}
        MAX-ACCESS read-write
        STATUS current
        DESCRIPTION
		"Enable the dynamic change of interleave depth."
        ::= { vdslLineConfEntry 87 }
        
        vdslLineConfDpboParamType OBJECT-TYPE
        SYNTAX 	INTEGER{
			g9971 (1),
			t-com (2)
		}
        MAX-ACCESS read-write
        STATUS current
        DESCRIPTION
		""
        ::= { vdslLineConfEntry 88 } 
        
        vdslLineConfDpboParamEselMin OBJECT-TYPE
        SYNTAX 	INTEGER (0..511)
        UNITS "0.5 dB"
        MAX-ACCESS read-write
        STATUS current
        DESCRIPTION
		""
        ::= { vdslLineConfEntry 89 } 
        
        vdslLineConfHsTxA43Psd OBJECT-TYPE
        SYNTAX 	INTEGER (-128..-32)
        UNITS "dB/HzB"
        MAX-ACCESS read-write
        STATUS current
        DESCRIPTION
		""
        ::= { vdslLineConfEntry 90 }

        vdslLineConfHsTxB43Psd OBJECT-TYPE
        SYNTAX 	INTEGER (-128..-32)
        UNITS "dB/HzB"
        MAX-ACCESS read-write
        STATUS current
        DESCRIPTION
		""
        ::= { vdslLineConfEntry 91 }  
        
        vdslLineConfHsTxA43cB43cPsd OBJECT-TYPE
        SYNTAX 	INTEGER (-128..-32)
        UNITS "dB/HzB"
        MAX-ACCESS read-write
        STATUS current
        DESCRIPTION
		""
        ::= { vdslLineConfEntry 92 }

        vdslLineConfHsTxV43Carrier257Psd OBJECT-TYPE
        SYNTAX 	INTEGER (-128..-32)
        UNITS "dB/HzB"
        MAX-ACCESS read-write
        STATUS current
        DESCRIPTION
		""
        ::= { vdslLineConfEntry 93 }  
        
        vdslLineConfHsTxV43Carrier383Psd OBJECT-TYPE
        SYNTAX 	INTEGER (-128..-32)
        UNITS "dB/HzB"
        MAX-ACCESS read-write
        STATUS current
        DESCRIPTION
		""
        ::= { vdslLineConfEntry 94 } 
        
        vdslLineConfHsTxV43Carrier511Psd OBJECT-TYPE
        SYNTAX 	INTEGER (-128..-32)
        UNITS "dB/HzB"
        MAX-ACCESS read-write
        STATUS current
        DESCRIPTION
		""
        ::= { vdslLineConfEntry 95 }

        
	vdslVlan		OBJECT IDENTIFIER ::= { vdslPort 2 }

-- vdslPortConfTable

        vdslPortConfTable OBJECT-TYPE
        SYNTAX SEQUENCE OF VdslPortConfEntry
        MAX-ACCESS not-accessible
        STATUS current
        DESCRIPTION
		"This table includes common attributes describing the VDSL port.
		This table is supported by R2.00 and later versions."
        ::= { vdslVlan 1 }

	vdslPortConfEntry OBJECT-TYPE
        SYNTAX VdslPortConfEntry
        MAX-ACCESS not-accessible
        STATUS current
        DESCRIPTION
        	"An entry in vdslPortConfTable."
        INDEX { ifIndex }
        ::= { vdslPortConfTable 1 }

        VdslPortConfEntry ::=
           SEQUENCE {
		vdslPortConfPvid		VlanIndex,
		vdslPortConfPriority		INTEGER,
		vdslPortConfAcceptableFrameType	INTEGER,
		vdslPortConfTlsEnable		INTEGER,
		vdslPortConfTlsVid		VlanIndex,
		vdslPortConfTlsPriority		INTEGER,
		vdslPortConfDtEnable		INTEGER,
		vdslPortConfDtSvid		VlanIndex,
		vdslPortConfDtSpriority		INTEGER,
		vdslPortConfDtCvid		VlanIndex,
		vdslPortConfDtCpriority		INTEGER,
		vdslPortConfTlsPrioCopyEnable	INTEGER	
           }

        vdslPortConfPvid OBJECT-TYPE
        SYNTAX VlanIndex
        MAX-ACCESS read-write
        STATUS current
        DESCRIPTION
		"The PVID, the VLAN ID assigned to untagged frames or
 		Priority-Tagged frames received on this port."
        ::= { vdslPortConfEntry 1 }
        	
	vdslPortConfPriority OBJECT-TYPE
        SYNTAX INTEGER (0..7)
        MAX-ACCESS read-write
        STATUS current
        DESCRIPTION
		"The default ingress User Priority for this port."
        ::= { vdslPortConfEntry 2 }
        
        vdslPortConfAcceptableFrameType OBJECT-TYPE
        SYNTAX	INTEGER {
        		admitAll(1),
        		admitOnlyVlanTagged(2)
        	}
        MAX-ACCESS read-write
        STATUS current
        DESCRIPTION
		"When this is admitOnlyVlanTagged(2) the device will
 		discard untagged frames or Priority-Tagged frames
 		received on this port. When admitAll(1), untagged
 		frames or Priority-Tagged frames received on this port
 		will be accepted and assigned to the PVID for this port"
        ::= { vdslPortConfEntry 3 }

		vdslPortConfTlsEnable OBJECT-TYPE
        SYNTAX 	INTEGER {
        		enable(1),
        		disable(2)
        	}
        MAX-ACCESS read-write
        STATUS current
        DESCRIPTION
		"Enable/disable the transparent LAN service."
        ::= { vdslPortConfEntry 4 }
        
        vdslPortConfTlsVid OBJECT-TYPE
        SYNTAX VlanIndex
        MAX-ACCESS read-write
        STATUS current
        DESCRIPTION
		"The transparent LAN service s-tag VID."
        ::= { vdslPortConfEntry 5 }
        
        vdslPortConfTlsPriority OBJECT-TYPE
        SYNTAX INTEGER
        MAX-ACCESS read-write
        STATUS current
        DESCRIPTION
		"The transparent LAN service s-tag priority."
        ::= { vdslPortConfEntry 6 }   
        
        vdslPortConfDtEnable OBJECT-TYPE
        SYNTAX 	INTEGER {
        		enable(1),
        		disable(2)
        	}
        MAX-ACCESS read-write
        STATUS current
        DESCRIPTION
		"Enable/disable  double tag service on the specified subscriber port. 
		This MIB object is supported by R5.05 and later versions."
        ::= { vdslPortConfEntry 7 }
        
        vdslPortConfDtSvid OBJECT-TYPE
        SYNTAX VlanIndex
        MAX-ACCESS read-write
        STATUS current
        DESCRIPTION
		"The service provider VLAN ID. This MIB object is supported by R5.05 and later versions."
        ::= { vdslPortConfEntry 8 }
        
        vdslPortConfDtSpriority OBJECT-TYPE
        SYNTAX INTEGER
        MAX-ACCESS read-write
        STATUS current
        DESCRIPTION
		"The service VLAN priority. This MIB object is supported by R5.05 and later versions."
        ::= { vdslPortConfEntry 9 }
        
        vdslPortConfDtCvid OBJECT-TYPE
        SYNTAX VlanIndex
        MAX-ACCESS read-write
        STATUS current
        DESCRIPTION
		"The system-side customer VID. This MIB object is supported by R5.05 and later versions."
        ::= { vdslPortConfEntry 10 }
        
        vdslPortConfDtCpriority OBJECT-TYPE
        SYNTAX INTEGER
        MAX-ACCESS read-write
        STATUS current
        DESCRIPTION
		"The customer VLAN priority. This MIB object is supported by R5.05 and later versions."
        ::= { vdslPortConfEntry 11 }
        
        vdslPortConfTlsPrioCopyEnable OBJECT-TYPE
        SYNTAX 	INTEGER {
        		enable(1),
        		disable(2)
        	}
        MAX-ACCESS read-write
        STATUS current
        DESCRIPTION
		"Enable/disable the priority copy of TLS."
        ::= { vdslPortConfEntry 12 }  
        
-- vdslPortVlanTable

        vdslPortVlanTable OBJECT-TYPE
        SYNTAX SEQUENCE OF VdslPortVlanEntry
        MAX-ACCESS not-accessible
        STATUS current
        DESCRIPTION
		"This table includes common attributes describing the VDSL port.
		This table is supported by R2.00 and later versions."
        ::= { vdslVlan 2 }

	vdslPortVlanEntry OBJECT-TYPE
        SYNTAX VdslPortVlanEntry
        MAX-ACCESS not-accessible
        STATUS current
        DESCRIPTION
        	"An entry in vdslPortVlanTable."
        INDEX { ifIndex, dot1qVlanIndex }
        ::= { vdslPortVlanTable 1 }

        VdslPortVlanEntry ::=
           SEQUENCE {
		vdslPortVlanReg			INTEGER,
		vdslPortVlanTag			INTEGER,
		vdslPortVlanRowStatus		RowStatus
           }

        vdslPortVlanReg OBJECT-TYPE
        SYNTAX 	INTEGER {
        		egress(1),
        		forbidden(2)
        	}
        MAX-ACCESS read-create
        STATUS current
        DESCRIPTION
                "The port is egress or forbidden for this VLAN."
        ::= { vdslPortVlanEntry 1 }
         
        vdslPortVlanTag OBJECT-TYPE
        SYNTAX INTEGER {
        		tag(1),
        		untag(2)
        	}
        MAX-ACCESS read-create
        STATUS current
        DESCRIPTION
                "The port should transmit egress packets for this VLAN as tagged or untagged."
         ::= { vdslPortVlanEntry 2 }

        vdslPortVlanRowStatus OBJECT-TYPE
        SYNTAX RowStatus
        MAX-ACCESS read-create
        STATUS current
        DESCRIPTION
                "This object is used to create a new row or delete an existing row in this table."
        ::= { vdslPortVlanEntry 3 }
                
-- vdslVlanStaticTable

        vdslVlanStaticTable OBJECT-TYPE
        SYNTAX SEQUENCE OF VdslVlanStaticEntry
        MAX-ACCESS not-accessible
        STATUS current
        DESCRIPTION
		"A table containing static configuration information for
 		each VLAN configured into the device by (local or
 		network) management.  All entries are permanent and will
 		be restored after the device is reset.
 		This table is supported by R2.00 and later versions."
        ::= { vdslVlan 3 }

	vdslVlanStaticEntry OBJECT-TYPE
        SYNTAX VdslVlanStaticEntry
        MAX-ACCESS not-accessible
        STATUS current
        DESCRIPTION
        	"An entry in vdslVlanStaticTable."
        INDEX { dot1qVlanIndex }
        ::= { vdslVlanStaticTable 1 }

        VdslVlanStaticEntry ::=
           SEQUENCE {
		vdslVlanStaticEgressPorts		PortList,
		vdslVlanStaticUntaggedPorts		PortList,
		vdslVlanStaticRowStatus			RowStatus
           }

        vdslVlanStaticEgressPorts OBJECT-TYPE
        SYNTAX PortList
        MAX-ACCESS read-create
        STATUS current
        DESCRIPTION
                "The set of ports which are permanently assigned to the
 		egress list for this VLAN by management."
        ::= { vdslVlanStaticEntry 1 }
        
        vdslVlanStaticUntaggedPorts OBJECT-TYPE
        SYNTAX PortList
        MAX-ACCESS read-create
        STATUS current
        DESCRIPTION
                "The set of ports which should transmit egress packets for this VLAN as untagged."
        ::= { vdslVlanStaticEntry 2 }
         
        vdslVlanStaticRowStatus OBJECT-TYPE
        SYNTAX RowStatus
        MAX-ACCESS read-create
        STATUS current
        DESCRIPTION
                "This object indicates the status of this entry."
        ::= { vdslVlanStaticEntry 3 }

-- vdslPortPvlanTable

        vdslPortPvlanTable OBJECT-TYPE
        SYNTAX SEQUENCE OF VdslPortPvlanEntry
        MAX-ACCESS not-accessible
        STATUS current
        DESCRIPTION
		"This table is supported by R5.01 and later versions."
        ::= { vdslVlan 4 }

	vdslPortPvlanEntry OBJECT-TYPE
        SYNTAX VdslPortPvlanEntry
        MAX-ACCESS not-accessible
        STATUS current
        DESCRIPTION
        	"An entry in vdslPortPvlanTable."
        INDEX { ifIndex, vdslPortPvlanEtype, vdslPortPvlanVid }
        ::= { vdslPortPvlanTable 1 }

        VdslPortPvlanEntry ::=
           SEQUENCE {
		vdslPortPvlanEtype			Unsigned32,
		vdslPortPvlanVid			VlanIndex,
		vdslPortPvlanPriority			INTEGER,
		vdslPortPvlanRowStatus			RowStatus
           }

        vdslPortPvlanEtype OBJECT-TYPE
        SYNTAX Unsigned32
        MAX-ACCESS read-only
        STATUS current
        DESCRIPTION
                "0~0xffff."
        ::= { vdslPortPvlanEntry 1 }
        
        vdslPortPvlanVid OBJECT-TYPE
        SYNTAX VlanIndex
        MAX-ACCESS read-only
        STATUS current
        DESCRIPTION
                ""
        ::= { vdslPortPvlanEntry 2 }
        
        vdslPortPvlanPriority OBJECT-TYPE
        SYNTAX INTEGER (0..7)
        MAX-ACCESS read-create
        STATUS current
        DESCRIPTION
                ""
        ::= { vdslPortPvlanEntry 3 }
        
        vdslPortPvlanRowStatus OBJECT-TYPE
        SYNTAX RowStatus
        MAX-ACCESS read-create
        STATUS current
        DESCRIPTION
                ""
        ::= { vdslPortPvlanEntry 4 }
        
-- VDSL RFI Custom Table

        vdslRfiCustomTable OBJECT-TYPE
        SYNTAX SEQUENCE OF VdslRfiCustomEntry
        MAX-ACCESS not-accessible
        STATUS current
        DESCRIPTION
		"This table includes VDSL customized RFI configuration.
		This table is supported by R2.00 and later versions."
        ::= { vdslPort 3 }

	vdslRfiCustomEntry OBJECT-TYPE
        SYNTAX VdslRfiCustomEntry
        MAX-ACCESS not-accessible
        STATUS current
        DESCRIPTION
        	"An entry in vdslRfiCustomTable."
        INDEX { vdslRfiCustomIndex }
        ::= { vdslRfiCustomTable 1 }

        VdslRfiCustomEntry ::=
           SEQUENCE {
		vdslRfiCustomIndex		INTEGER,
		vdslRfiCustomStartFreq	INTEGER,
		vdslRfiCustomEndFreq	INTEGER,
		vdslRfiCustomEnable		INTEGER,
		vdslRfiCustomMode		INTEGER
           }

        vdslRfiCustomIndex OBJECT-TYPE
        SYNTAX INTEGER
        MAX-ACCESS read-only
        STATUS current
        DESCRIPTION
		"Index of the table."
        ::= { vdslRfiCustomEntry 1 }
        
        vdslRfiCustomStartFreq OBJECT-TYPE
        SYNTAX INTEGER
        UNITS "KHz"
        MAX-ACCESS read-write
        STATUS current
        DESCRIPTION
		"The start value of the customized frequency range."
        ::= { vdslRfiCustomEntry 2 }
        
        vdslRfiCustomEndFreq OBJECT-TYPE
        SYNTAX INTEGER
        UNITS "KHz"
        MAX-ACCESS read-write
        STATUS current
        DESCRIPTION
		"The end value of the customized frequency range."
        ::= { vdslRfiCustomEntry 3 }           
        
        vdslRfiCustomEnable OBJECT-TYPE
        SYNTAX	INTEGER {
        		enable(1),
        		disable(2)
        	}
        MAX-ACCESS read-write
        STATUS current
        DESCRIPTION
		"Enable or disable the customized frequency range setting."
        ::= { vdslRfiCustomEntry 4 } 
        
        vdslRfiCustomMode OBJECT-TYPE
        SYNTAX	INTEGER {
        		notch(1),
        		gap(2)
        	}
        MAX-ACCESS read-write
        STATUS current
        DESCRIPTION
		"Notch : sent at -80 dBm in the specified frequency bands.
		 Gap : cut the power completely in the specified frequency bands.
		 1: notch(1)
		 2: gap(2)
		"
        ::= { vdslRfiCustomEntry 5 }

-- vdslLineConfUpboParamTable

        vdslLineConfUpboParamTable OBJECT-TYPE
        SYNTAX SEQUENCE OF VdslLineConfUpboParamEntry
        MAX-ACCESS not-accessible
        STATUS current
        DESCRIPTION
		"This table includes VDSL UPBO configuration.
		This table is supported by R5.01 and later versions."
        ::= { vdslPort 4 }

	vdslLineConfUpboParamEntry OBJECT-TYPE
        SYNTAX VdslLineConfUpboParamEntry
        MAX-ACCESS not-accessible
        STATUS current
        DESCRIPTION
        	"An entry in vdslLineConfUpboParamTable."
        INDEX { ifIndex, vdslLineConfUpboParamBand }
        ::= { vdslLineConfUpboParamTable 1 }

        VdslLineConfUpboParamEntry ::=
           SEQUENCE {
		vdslLineConfUpboParamBand		INTEGER,
		vdslLineConfUpboParamA			INTEGER,
		vdslLineConfUpboParamB			INTEGER
           }

        vdslLineConfUpboParamBand OBJECT-TYPE
        SYNTAX INTEGER
        MAX-ACCESS read-only
        STATUS current
        DESCRIPTION
		"Index of the table."
        ::= { vdslLineConfUpboParamEntry 1 }
        
        vdslLineConfUpboParamA OBJECT-TYPE
        SYNTAX INTEGER (4000..8095)
        UNITS "0.01 dBm/Hz"
        MAX-ACCESS read-write
        STATUS current
        DESCRIPTION
		""
        ::= { vdslLineConfUpboParamEntry 2 }
        
        vdslLineConfUpboParamB OBJECT-TYPE
        SYNTAX INTEGER (0..4095)
        UNITS "0.01 dBm/Hz"
        MAX-ACCESS read-write
        STATUS current
        DESCRIPTION
		""
        ::= { vdslLineConfUpboParamEntry 3 }
        
-- vdslLineConfDpboTable

        vdslLineConfDpboTable OBJECT-TYPE
        SYNTAX SEQUENCE OF VdslLineConfDpboEntry
        MAX-ACCESS not-accessible
        STATUS current
        DESCRIPTION
		"This table includes VDSL DPBO configuration.
		This table is supported by R5.01 and later versions."
        ::= { vdslPort 5 }

	vdslLineConfDpboEntry OBJECT-TYPE
        SYNTAX VdslLineConfDpboEntry
        MAX-ACCESS not-accessible
        STATUS current
        DESCRIPTION
        	"An entry in vdslLineConfDpboTable."
        INDEX { ifIndex, vdslLineConfDpboIndex }
        ::= { vdslLineConfDpboTable 1 }

        VdslLineConfDpboEntry ::=
           SEQUENCE {
		vdslLineConfDpboIndex		INTEGER,
		vdslLineConfDpboTone		INTEGER,
		vdslLineConfDpboPsd		INTEGER
           }

        vdslLineConfDpboIndex OBJECT-TYPE
        SYNTAX INTEGER
        MAX-ACCESS read-only
        STATUS current
        DESCRIPTION
		"Index of the table."
        ::= { vdslLineConfDpboEntry 1 }
        
        vdslLineConfDpboTone OBJECT-TYPE
        SYNTAX INTEGER (1..512)
        MAX-ACCESS read-write
        STATUS current
        DESCRIPTION
		""
        ::= { vdslLineConfDpboEntry 2 }
        
        vdslLineConfDpboPsd OBJECT-TYPE
        SYNTAX INTEGER (0..255)
        UNITS "-0.5dBm/Hz"
        MAX-ACCESS read-write
        STATUS current
        DESCRIPTION
		""
        ::= { vdslLineConfDpboEntry 3 }
                
--------------------
-- ipbpvc
--------------------

-- Domain Table

        ipbpvcDomainTable OBJECT-TYPE
        SYNTAX SEQUENCE OF IpbpvcDomainEntry
        MAX-ACCESS not-accessible
        STATUS current
        DESCRIPTION
        	"This table includes ipbpvc domain configuration.
        	This table is supported by R3.00 and later versions."
        ::= { ipbpvc 1 }

	ipbpvcDomainEntry OBJECT-TYPE
        SYNTAX IpbpvcDomainEntry
        MAX-ACCESS not-accessible
        STATUS current
        DESCRIPTION
		"An entry of ipbpvcDomainTable."
        INDEX { ipbpvcDomainName }
        ::= { ipbpvcDomainTable 1 }

        IpbpvcDomainEntry ::=
        	SEQUENCE {
			ipbpvcDomainName		DisplayString,
			ipbpvcDomainRowStatus		RowStatus
           	}

        ipbpvcDomainName OBJECT-TYPE
        SYNTAX DisplayString (SIZE(1..31))
        MAX-ACCESS read-only
        STATUS current
        DESCRIPTION
                "Name of the domain."
        ::= { ipbpvcDomainEntry 1 }
        
        ipbpvcDomainRowStatus OBJECT-TYPE
        SYNTAX RowStatus
        MAX-ACCESS read-create
        STATUS current
        DESCRIPTION
                "Row status of the table."
        ::= { ipbpvcDomainEntry 2 } 
        
-- Domain VLAN Table

        ipbpvcDomainVlanTable OBJECT-TYPE
        SYNTAX SEQUENCE OF IpbpvcDomainVlanEntry
        MAX-ACCESS not-accessible
        STATUS current
        DESCRIPTION
        	"This table includes ipbpvc domain VLAN configuration.
        	This table is supported by R3.00 and later versions."
        ::= { ipbpvc 2 }

	ipbpvcDomainVlanEntry OBJECT-TYPE
        SYNTAX IpbpvcDomainVlanEntry
        MAX-ACCESS not-accessible
        STATUS current
        DESCRIPTION
		"An entry of ipbpvcDomainVlanTable."
        INDEX { ipbpvcDomainName, ipbpvcDomainVlanId }
        ::= { ipbpvcDomainVlanTable 1 }

        IpbpvcDomainVlanEntry ::=
        	SEQUENCE {
			ipbpvcDomainVlanId		VlanIndex,
			ipbpvcDomainDhcpVlanEnable	INTEGER,
			ipbpvcDomainVlanRowStatus	RowStatus
           	}

        ipbpvcDomainVlanId OBJECT-TYPE
        SYNTAX VlanIndex
        MAX-ACCESS read-only
        STATUS current
        DESCRIPTION
                "Set VLAN to join or leave the specified domain."
        ::= { ipbpvcDomainVlanEntry 1 }
        
        ipbpvcDomainDhcpVlanEnable OBJECT-TYPE
        SYNTAX	INTEGER {
        		enable(1),
        		disable(2)
        	}
        MAX-ACCESS read-create
        STATUS current
        DESCRIPTION
                "Enable/disable DHCP VLAN in a domain."
        ::= { ipbpvcDomainVlanEntry 2 }
        
        ipbpvcDomainVlanRowStatus OBJECT-TYPE
        SYNTAX RowStatus
        MAX-ACCESS read-create
        STATUS current
        DESCRIPTION
                "Row status of the table used to create/delete an entry."
        ::= { ipbpvcDomainVlanEntry 3 }
        
-- Edge Router Table

        ipbpvcEdgeRouterTable OBJECT-TYPE
        SYNTAX SEQUENCE OF IpbpvcEdgeRouterEntry
        MAX-ACCESS not-accessible
        STATUS current
        DESCRIPTION
        	"This table includes ipbpvc edge router configuration.
        	This table is supported by R3.00 and later versions."
        ::= { ipbpvc 3 }

	ipbpvcEdgeRouterEntry OBJECT-TYPE
        SYNTAX IpbpvcEdgeRouterEntry
        MAX-ACCESS not-accessible
        STATUS current
        DESCRIPTION
		"An entry of ipbpvcEdgeRouterTable."
        INDEX { ipbpvcDomainName, ipbpvcEdgeRouterIp, ipbpvcEdgeRouterMask, ipbpvcEdgeRouterVid }
        ::= { ipbpvcEdgeRouterTable 1 }

        IpbpvcEdgeRouterEntry ::=
        	SEQUENCE {
			ipbpvcEdgeRouterIp		IpAddress,
			ipbpvcEdgeRouterMask		INTEGER,
			ipbpvcEdgeRouterVid		VlanIndex,
			ipbpvcEdgeRouterRowStatus	RowStatus
           	}

        ipbpvcEdgeRouterIp OBJECT-TYPE
        SYNTAX IpAddress
        MAX-ACCESS read-only
        STATUS current
        DESCRIPTION
                "IP address of the edge router."
        ::= { ipbpvcEdgeRouterEntry 1 }
        
        ipbpvcEdgeRouterVid OBJECT-TYPE
        SYNTAX VlanIndex
        MAX-ACCESS read-only
        STATUS current
        DESCRIPTION
                "VLAN ID of the edge router."
        ::= { ipbpvcEdgeRouterEntry 2 }
        
        ipbpvcEdgeRouterMask OBJECT-TYPE
        SYNTAX INTEGER
        MAX-ACCESS read-only
        STATUS current
        DESCRIPTION
                "Netmask of the edge router."
        ::= { ipbpvcEdgeRouterEntry 3 }
        
        ipbpvcEdgeRouterRowStatus OBJECT-TYPE
        SYNTAX RowStatus
        MAX-ACCESS read-create
        STATUS current
        DESCRIPTION
                "Row status of the table used to create/delete an entry."
        ::= { ipbpvcEdgeRouterEntry 4 }
        
-- Interface Table

        ipbpvcInterfaceTable OBJECT-TYPE
        SYNTAX SEQUENCE OF IpbpvcInterfaceEntry
        MAX-ACCESS not-accessible
        STATUS current
        DESCRIPTION
        	"This table includes ipbpvc interface configuration.
        	This table is supported by R3.00 and later versions."
        ::= { ipbpvc 4 }

	ipbpvcInterfaceEntry OBJECT-TYPE
        SYNTAX IpbpvcInterfaceEntry
        MAX-ACCESS not-accessible
        STATUS current
        DESCRIPTION
		"An entry of ipbpvcInterfaceTable."
        INDEX { ipbpvcDomainName, ipbpvcInterfaceIp, ipbpvcInterfaceMask, ipbpvcInterfaceVid }
        ::= { ipbpvcInterfaceTable 1 }

        IpbpvcInterfaceEntry ::=
        	SEQUENCE {
			ipbpvcInterfaceIp		IpAddress,
			ipbpvcInterfaceMask		INTEGER,
			ipbpvcInterfaceVid		VlanIndex,
			ipbpvcInterfaceIfIndex		INTEGER,
			ipbpvcInterfaceVpi		INTEGER,
			ipbpvcInterfaceVci		INTEGER,
			ipbpvcInterfaceRowStatus	RowStatus
           	}

        ipbpvcInterfaceIp OBJECT-TYPE
        SYNTAX IpAddress
        MAX-ACCESS read-only
        STATUS current
        DESCRIPTION
                "IP address of the interface."
        ::= { ipbpvcInterfaceEntry 1 }
        
        ipbpvcInterfaceMask OBJECT-TYPE
        SYNTAX INTEGER
        MAX-ACCESS read-only
        STATUS current
        DESCRIPTION
                "Netmask of the interface."
        ::= { ipbpvcInterfaceEntry 2 }
        
        ipbpvcInterfaceVid OBJECT-TYPE
        SYNTAX VlanIndex
        MAX-ACCESS read-only
        STATUS current
        DESCRIPTION
                "VLAN ID of the interface."
        ::= { ipbpvcInterfaceEntry 3 }
        
        ipbpvcInterfaceIfIndex OBJECT-TYPE
        SYNTAX INTEGER
        MAX-ACCESS read-create
        STATUS current
        DESCRIPTION
                "IfIndex of the interface."
        ::= { ipbpvcInterfaceEntry 4 }
        
        ipbpvcInterfaceVpi OBJECT-TYPE
        SYNTAX INTEGER
        MAX-ACCESS read-create
        STATUS current
        DESCRIPTION
                "VPI of the interface."
        ::= { ipbpvcInterfaceEntry 5 }
        
        ipbpvcInterfaceVci OBJECT-TYPE
        SYNTAX INTEGER
        MAX-ACCESS read-create
        STATUS current
        DESCRIPTION
                "VCI of the interface."
        ::= { ipbpvcInterfaceEntry 6 }
        
        ipbpvcInterfaceRowStatus OBJECT-TYPE
        SYNTAX RowStatus
        MAX-ACCESS read-create
        STATUS current
        DESCRIPTION
                "Row status of the table used to create/delete an entry."
        ::= { ipbpvcInterfaceEntry 7 }
        
-- Route Table

        ipbpvcRouteTable OBJECT-TYPE
        SYNTAX SEQUENCE OF IpbpvcRouteEntry
        MAX-ACCESS not-accessible
        STATUS current
        DESCRIPTION
        	"This table includes ipbpvc route configuration.
        	This table is supported by R3.00 and later versions."
        ::= { ipbpvc 5 }

	ipbpvcRouteEntry OBJECT-TYPE
        SYNTAX IpbpvcRouteEntry
        MAX-ACCESS not-accessible
        STATUS current
        DESCRIPTION
		"An entry of ipbpvcRouteTable."
        INDEX { ipbpvcDomainName, ipbpvcRouteIp, ipbpvcRouteMask, ipbpvcRouteNextHop }
        ::= { ipbpvcRouteTable 1 }

        IpbpvcRouteEntry ::=
        	SEQUENCE {
			ipbpvcRouteIp			IpAddress,
			ipbpvcRouteMask			INTEGER,
			ipbpvcRouteNextHop		IpAddress,
			ipbpvcRouteMetric		INTEGER,
			ipbpvcRoutePriority		INTEGER,
			ipbpvcRouteRowStatus		RowStatus
           	}

        ipbpvcRouteIp OBJECT-TYPE
        SYNTAX IpAddress
        MAX-ACCESS read-only
        STATUS current
        DESCRIPTION
                "IP address of the route."
        ::= { ipbpvcRouteEntry 1 }
        
	ipbpvcRouteMask OBJECT-TYPE
        SYNTAX INTEGER
        MAX-ACCESS read-only
        STATUS current
        DESCRIPTION
                "Netmask of the route."
        ::= { ipbpvcRouteEntry 2 }
        
        ipbpvcRouteNextHop OBJECT-TYPE
        SYNTAX IpAddress
        MAX-ACCESS read-only
        STATUS current
        DESCRIPTION
                "Next hop IP address of the route."
        ::= { ipbpvcRouteEntry 3 }
        
        ipbpvcRouteMetric OBJECT-TYPE
        SYNTAX INTEGER (1..15)
        MAX-ACCESS read-create
        STATUS current
        DESCRIPTION
                "Metric of the route."
        ::= { ipbpvcRouteEntry 4 }
        
        ipbpvcRoutePriority OBJECT-TYPE
        SYNTAX INTEGER
        MAX-ACCESS read-create
        STATUS current
        DESCRIPTION
                "Priority of the route. Note that the default value of this object is 8, which means 
                we keep the original priority of the packet(frame)."
        ::= { ipbpvcRouteEntry 5 }
        
        ipbpvcRouteRowStatus OBJECT-TYPE
        SYNTAX RowStatus
        MAX-ACCESS read-create
        STATUS current
        DESCRIPTION
                "Row status of the table used to create/delete an entry."
        ::= { ipbpvcRouteEntry 6 }
        
-- PVC Table

        ipbpvcTable OBJECT-TYPE
        SYNTAX SEQUENCE OF IpbpvcEntry
        MAX-ACCESS not-accessible
        STATUS current
        DESCRIPTION
        	"This table includes ipbpvc configuration.
        	This table is supported by R3.00 and later versions."
        ::= { ipbpvc 6 }

	ipbpvcEntry OBJECT-TYPE
        SYNTAX IpbpvcEntry
        MAX-ACCESS not-accessible
        STATUS current
        DESCRIPTION
		"An entry of ipbpvcTable."
        INDEX { ifIndex, ipbpvcVpi, ipbpvcVci, ipbpvcPvid }
        ::= { ipbpvcTable 1 }

        IpbpvcEntry ::=
        	SEQUENCE {
			ipbpvcVpi		INTEGER,
			ipbpvcVci		INTEGER,
			ipbpvcPvid		INTEGER,
			ipbpvcEncap		INTEGER,
			ipbpvcPriority		INTEGER,
			ipbpvcProfile		DisplayString,
			ipbpvcRowStatus		RowStatus
           	}

        ipbpvcVpi OBJECT-TYPE
        SYNTAX INTEGER
        MAX-ACCESS read-only
        STATUS current
        DESCRIPTION
                "VPI of the PVC."
        ::= { ipbpvcEntry 1 }
        
        ipbpvcVci OBJECT-TYPE
        SYNTAX INTEGER
        MAX-ACCESS read-only
        STATUS current
        DESCRIPTION
                "VCI of the PVC."
        ::= { ipbpvcEntry 2 }
        
        ipbpvcPvid OBJECT-TYPE
        SYNTAX INTEGER
        MAX-ACCESS read-only
        STATUS current
        DESCRIPTION
                "PVID of the PVC."
        ::= { ipbpvcEntry 3 }
        
        ipbpvcEncap OBJECT-TYPE
        SYNTAX	INTEGER {
        		llc(1),
        		vc(2),
        		llc-r(3),
        		vc-r(4)
        	}
        MAX-ACCESS read-create
        STATUS current
        DESCRIPTION
                "Type of the PVC."
        ::= { ipbpvcEntry 4 }
        
        ipbpvcPriority OBJECT-TYPE
        SYNTAX INTEGER (0..7)
        MAX-ACCESS read-create
        STATUS current
        DESCRIPTION
                "Priority of the PVC."
        ::= { ipbpvcEntry 5 }
        
        ipbpvcProfile OBJECT-TYPE
        SYNTAX DisplayString (SIZE(1..31))
        MAX-ACCESS read-create
        STATUS current
        DESCRIPTION
                "Profile of the PVC."
        ::= { ipbpvcEntry 6 }
        
        ipbpvcRowStatus OBJECT-TYPE
        SYNTAX RowStatus
        MAX-ACCESS read-create
        STATUS current
        DESCRIPTION
                "Row status of the table used to create/delete an entry."
        ::= { ipbpvcEntry 7 }
        
-- PVC VLAN Table

        ipbpvcVlanTable OBJECT-TYPE
        SYNTAX SEQUENCE OF IpbpvcVlanEntry
        MAX-ACCESS not-accessible
        STATUS current
        DESCRIPTION
        	"This table includes ipbpvc VLAN configuration.
        	This table is supported by R3.00 and later versions."
        ::= { ipbpvc 7 }

	ipbpvcVlanEntry OBJECT-TYPE
        SYNTAX IpbpvcVlanEntry
        MAX-ACCESS not-accessible
        STATUS current
        DESCRIPTION
		"An entry of ipbpvcVlanTable."
        INDEX { ifIndex, ipbpvcVpi, ipbpvcVci, dot1qVlanIndex }
        ::= { ipbpvcVlanTable 1 }

        IpbpvcVlanEntry ::=
        	SEQUENCE {
			ipbpvcVlanReg		INTEGER,
			ipbpvcVlanTag		INTEGER,
			ipbpvcVlanRowStatus	RowStatus
           	}

        ipbpvcVlanReg OBJECT-TYPE
        SYNTAX 	INTEGER {
        		egress(1),
        		forbidden(2)
        	}
        MAX-ACCESS read-create
        STATUS current
        DESCRIPTION
                "The PVC is egress or forbidden for this VLAN."
         ::= { ipbpvcVlanEntry 1 }
         
        ipbpvcVlanTag OBJECT-TYPE
        SYNTAX INTEGER {
        		tag(1),
        		untag(2)
        	}
        MAX-ACCESS read-create
        STATUS current
        DESCRIPTION
                "The PVC should transmit egress packets for this VLAN as tagged or untagged."
        ::= { ipbpvcVlanEntry 2 }

        ipbpvcVlanRowStatus OBJECT-TYPE
        SYNTAX RowStatus
        MAX-ACCESS read-create
        STATUS current
        DESCRIPTION
                "This object is used to create a new row or delete an existing row in this table."
        ::= { ipbpvcVlanEntry 3 }

-- ARP Proxy

        arpproxy		OBJECT IDENTIFIER ::= { ipbpvc 8 }
                        
        arpproxyAge OBJECT-TYPE
        SYNTAX INTEGER (10..10000)
        UNITS "second"
        MAX-ACCESS read-write
        STATUS current
        DESCRIPTION
                "Aging time of the ARP proxy.
                This object is supported by R3.00 and later versions."
        ::= { arpproxy 1 }
                        
        arpproxyFlush		OBJECT IDENTIFIER ::= { arpproxy 2 }
        
        arpproxyFlushTarget OBJECT-TYPE
        SYNTAX	INTEGER {
        		all(1),
        		edgerouter(2),
        		interface(3)
        	}
        MAX-ACCESS read-write
        STATUS current
        DESCRIPTION
                "The target whose ARP table to be flushed.
                This object is supported by R3.00 and later versions."
        ::= { arpproxyFlush 1 }
        
        arpproxyFlushOps OBJECT-TYPE
        SYNTAX INTEGER
        MAX-ACCESS read-write
        STATUS current
        DESCRIPTION
                "Set the object to 1 to start flushing.
                This object is supported by R3.00 and later versions."
        ::= { arpproxyFlush 2 }
        
        arpproxyFlushEdgeRouterIp OBJECT-TYPE
        SYNTAX IpAddress
        MAX-ACCESS read-write
        STATUS current
        DESCRIPTION
                "Flush ARP table for the specified edge router.
                This object is supported by R3.00 and later versions."
        ::= { arpproxyFlush 3 }
        
        arpproxyFlushEdgeRouterVid OBJECT-TYPE
        SYNTAX VlanIndex
        MAX-ACCESS read-write
        STATUS current
        DESCRIPTION
                "Flush ARP table for the specified edge router.
                This object is supported by R3.00 and later versions."
        ::= { arpproxyFlush 4 }
        
        arpproxyFlushInterfaceIp OBJECT-TYPE
        SYNTAX IpAddress
        MAX-ACCESS read-write
        STATUS current
        DESCRIPTION
                "Flush ARP table for the specified interface.
                This object is supported by R3.00 and later versions."
        ::= { arpproxyFlush 5 }
        
        arpproxyFlushInterfaceMask OBJECT-TYPE
        SYNTAX INTEGER
        MAX-ACCESS read-write
        STATUS current
        DESCRIPTION
                "Flush ARP table for the specified interface.
                This object is supported by R3.00 and later versions."
        ::= { arpproxyFlush 6 }
        
        arpproxyFlushInterfaceVid OBJECT-TYPE
        SYNTAX VlanIndex
        MAX-ACCESS read-write
        STATUS current
        DESCRIPTION
                "Flush ARP table for the specified interface.
                This object is supported by R3.00 and later versions."
        ::= { arpproxyFlush 7 }

--------------------
--  voipPort
--------------------

-- voipSipLineConfTable

        voipSipLineConfTable OBJECT-TYPE
        SYNTAX SEQUENCE OF VoipSipLineConfEntry
        MAX-ACCESS not-accessible
        STATUS current
        DESCRIPTION
		"This table includes common attributes describing the VoIP line."
        ::= { voipPort 1 }

	voipSipLineConfEntry OBJECT-TYPE
        SYNTAX VoipSipLineConfEntry
        MAX-ACCESS not-accessible
        STATUS current
        DESCRIPTION
        	"An entry in voipSipLineConfTable."
        INDEX { voipIfIndex }
        ::= { voipSipLineConfTable 1 }

        VoipSipLineConfEntry ::=
           SEQUENCE {
		voipSipLineConfSipProfile			DisplayString,
		voipSipLineConfSipCallSvcProfile	DisplayString,
		voipSipLineConfDspProfile			DisplayString,
		voipSipLineConfAccount				DisplayString,
        	voipSipLineConfPassword				DisplayString,
        	voipSipLineConfDataProfile			DisplayString
           }

        voipSipLineConfSipProfile OBJECT-TYPE
        SYNTAX DisplayString (SIZE(1..31))
        MAX-ACCESS read-write
        STATUS current
        DESCRIPTION
		"SIP profile name."
        ::= { voipSipLineConfEntry 1 }
        
        voipSipLineConfSipCallSvcProfile OBJECT-TYPE
        SYNTAX DisplayString (SIZE(1..31))
        MAX-ACCESS read-write
        STATUS current
        DESCRIPTION
		"SIP call service profile name."
        ::= { voipSipLineConfEntry 2 }
        
        voipSipLineConfDspProfile OBJECT-TYPE
        SYNTAX DisplayString (SIZE(1..31))
        MAX-ACCESS read-write
        STATUS current
        DESCRIPTION
		"DSP profile name."
        ::= { voipSipLineConfEntry 3 }
        
        voipSipLineConfAccount OBJECT-TYPE
        SYNTAX DisplayString (SIZE(1..31))
        MAX-ACCESS read-write
        STATUS current
        DESCRIPTION
		"Account for SIP registration.
		This object is supported by R5.05 and later versions."
        ::= { voipSipLineConfEntry 4 }
        
        voipSipLineConfPassword OBJECT-TYPE
        SYNTAX DisplayString (SIZE(1..31))
        MAX-ACCESS read-write
        STATUS current
        DESCRIPTION
		"Password for SIP registration.
		This object is supported by R5.05 and later versions."
        ::= { voipSipLineConfEntry 5 }

        voipSipLineConfDataProfile OBJECT-TYPE
        SYNTAX DisplayString (SIZE(1..31))
        MAX-ACCESS read-write
        STATUS current
        DESCRIPTION
		"DSP profile name of data mode, up to 31 characters."
        ::= { voipSipLineConfEntry 6 }

-- H248

	voipPortH248		OBJECT IDENTIFIER ::= { voipPort 2 }                       
        
-- voipH248LineConfTable

        voipH248LineConfTable OBJECT-TYPE
        SYNTAX SEQUENCE OF VoipH248LineConfEntry
        MAX-ACCESS not-accessible
        STATUS current
        DESCRIPTION
		"This table includes common attributes describing the VoIP line.
		This table is supported by R5.01 and later versions."
        ::= { voipPortH248 1 }

	voipH248LineConfEntry OBJECT-TYPE
        SYNTAX VoipH248LineConfEntry
        MAX-ACCESS not-accessible
        STATUS current
        DESCRIPTION
        	"An entry in voipH248LineConfTable."
        INDEX { voipIfIndex }
        ::= { voipH248LineConfTable 1 }

        VoipH248LineConfEntry ::=
           SEQUENCE {
		voipH248LineConfMgName		DisplayString,
		voipH248LineConfDspProfile	DisplayString,
		voipH248LineConfDataProfile	DisplayString
           }

        voipH248LineConfMgName OBJECT-TYPE
        SYNTAX DisplayString (SIZE(1..31))
        MAX-ACCESS read-write
        STATUS current
        DESCRIPTION
		"MG name."
        ::= { voipH248LineConfEntry 1 }
        
        voipH248LineConfDspProfile OBJECT-TYPE
        SYNTAX DisplayString (SIZE(1..31))
        MAX-ACCESS read-write
        STATUS current
        DESCRIPTION
		"DSP profile."
        ::= { voipH248LineConfEntry 2 } 
        
        voipH248LineConfDataProfile OBJECT-TYPE
        SYNTAX DisplayString (SIZE(1..31))
        MAX-ACCESS read-write
        STATUS current
        DESCRIPTION
		"DSP profile name of data mode, up to 31 characters.
		This MIB object is supported by R5.06 and later versions."
        ::= { voipH248LineConfEntry 3 }
        
-- voipH248TerminationTable

        voipH248TerminationTable OBJECT-TYPE
        SYNTAX SEQUENCE OF VoipH248TerminationEntry
        MAX-ACCESS not-accessible
        STATUS current
        DESCRIPTION
		"This table is supported by R5.01 and later versions."
        ::= { voipPortH248 2 }

	voipH248TerminationEntry OBJECT-TYPE
        SYNTAX VoipH248TerminationEntry
        MAX-ACCESS not-accessible
        STATUS current
        DESCRIPTION
        	"An entry in voipH248TerminationTable."
        INDEX { voipIfIndex }
        ::= { voipH248TerminationTable 1 }

        VoipH248TerminationEntry ::=
           SEQUENCE {
		voipH248TerminationName		DisplayString
           }

        voipH248TerminationName OBJECT-TYPE
        SYNTAX DisplayString (SIZE(1..31))
        MAX-ACCESS read-write
        STATUS current
        DESCRIPTION
		"Termination name."
        ::= { voipH248TerminationEntry 1 }


-- voipPotsImpedanceConfTable

        voipPotsImpedanceConfTable OBJECT-TYPE
        SYNTAX SEQUENCE OF VoipPotsImpedanceConfEntry
        MAX-ACCESS not-accessible
        STATUS current
        DESCRIPTION
		"This table is supported by R5.01 and later versions."
        ::= { voipPort 3 }
        
        voipPotsImpedanceConfEntry OBJECT-TYPE
        SYNTAX VoipPotsImpedanceConfEntry
        MAX-ACCESS not-accessible
        STATUS current
        DESCRIPTION
        	"An entry in voipPotsImpedanceConfTable."
        INDEX { voipIfIndex }
        ::= { voipPotsImpedanceConfTable 1 }

        VoipPotsImpedanceConfEntry ::=
           SEQUENCE {
		voipPotsImpedance		INTEGER
           }

        voipPotsImpedance OBJECT-TYPE
        SYNTAX INTEGER {
        		impedance-600ohm(0),
        		impedance-600ohm-1000nf(1),
        		impedance-220ohm-820ohm-120nf(2),
			impedance-270ohm-750ohm-150nf(3),
			impedance-300ohm-1000ohm-220nf(4),
			impedance-370ohm-620ohm-310nf(5),
			impedance-220ohm-680ohm-100nf(6),
			impedance-220ohm-820ohm-115nf(7),
			impedance-900ohm(8), 
			impedance-200ohm-680ohm-100nf(9),
			impedance-900ohm-2160nf(10),
			default(255)
		}
        MAX-ACCESS read-write
        STATUS current
        DESCRIPTION
		"Default impedance is from impedance of country code."
        ::= { voipPotsImpedanceConfEntry 1 }
        
-- voipPotsGainConfTable
        
        voipPotsGainConfTable OBJECT-TYPE
        SYNTAX SEQUENCE OF VoipPotsGainConfEntry
        MAX-ACCESS not-accessible
        STATUS current
        DESCRIPTION
		"This table is supported by R5.01 and later versions."
        ::= { voipPort 4 }
        
        voipPotsGainConfEntry OBJECT-TYPE
        SYNTAX VoipPotsGainConfEntry
        MAX-ACCESS not-accessible
        STATUS current
        DESCRIPTION
        	"An entry in voipPotsGainConfTable."
        INDEX { voipIfIndex }
        ::= { voipPotsGainConfTable 1 }

        VoipPotsGainConfEntry ::=
           SEQUENCE {
		voipPotsTxGain		INTEGER,
		voipPotsRxGain		INTEGER,
		voipPotsDataTxGain	INTEGER,
		voipPotsDataRxGain	INTEGER
           }

        voipPotsTxGain OBJECT-TYPE
        SYNTAX INTEGER (-200..200)
        UNITS "0.1dB"
        MAX-ACCESS read-write
        STATUS current
        DESCRIPTION
		""
        ::= { voipPotsGainConfEntry 1 }
        
        voipPotsRxGain OBJECT-TYPE
        SYNTAX INTEGER (-200..200)
        UNITS "0.1dB"
        MAX-ACCESS read-write
        STATUS current
        DESCRIPTION
		""
        ::= { voipPotsGainConfEntry 2 }
        
        voipPotsDataTxGain OBJECT-TYPE
        SYNTAX INTEGER (-200..200)
        UNITS "0.1dB"
        MAX-ACCESS read-write
        STATUS current
        DESCRIPTION
		"This MIB object is supported by R5.06 and later versions."
        ::= { voipPotsGainConfEntry 3 }
        
        voipPotsDataRxGain OBJECT-TYPE
        SYNTAX INTEGER (-200..200)
        UNITS "0.1dB"
        MAX-ACCESS read-write
        STATUS current
        DESCRIPTION
		"This MIB object is supported by R5.06 and later versions."
        ::= { voipPotsGainConfEntry 4 }

-- voipOpmodeConfTable
-- ##DIST
        voipOpmodeConfTable OBJECT-TYPE
        SYNTAX SEQUENCE OF VoipOpmodeConfEntry
        MAX-ACCESS not-accessible
        STATUS current
        DESCRIPTION
		"This table is supported by R5.01 and later versions."
        ::= { voipPort 5 }
        
        voipOpmodeConfEntry OBJECT-TYPE
        SYNTAX VoipOpmodeConfEntry
        MAX-ACCESS not-accessible
        STATUS current
        DESCRIPTION
        	"An entry in voipOpmodeConfTable."
        INDEX { voipIfIndex }
        ::= { voipOpmodeConfTable 1 }

        VoipOpmodeConfEntry ::=
           SEQUENCE {
		voipOpMode		INTEGER
           }

        voipOpMode OBJECT-TYPE
        SYNTAX INTEGER {
        		default(0),
        		v5sip(1)
        	}
        MAX-ACCESS read-write
        STATUS current
        DESCRIPTION
		"Configure operation mode to specified subscribers. Default is normal SIP server 
		and v5sip is V5.2 access gateway."
        ::= { voipOpmodeConfEntry 1 }

-- voipPolarityReverseConfTable 
-- ##DIST        
        voipPolarityReverseConfTable  OBJECT-TYPE
        SYNTAX SEQUENCE OF VoipPolarityReverseConfEntry
        MAX-ACCESS not-accessible
        STATUS current
        DESCRIPTION
		"This table is supported by R5.05 and later versions."
        ::= { voipPort 6 }
        
        voipPolarityReverseConfEntry OBJECT-TYPE
        SYNTAX VoipPolarityReverseConfEntry
        MAX-ACCESS not-accessible
        STATUS current
        DESCRIPTION
        	"An entry in voipPolarityReverseConfTable."
        INDEX { voipIfIndex }
        ::= { voipPolarityReverseConfTable 1 }

        VoipPolarityReverseConfEntry ::=
           SEQUENCE {
		voipPolarityReverse		INTEGER
           }

        voipPolarityReverse OBJECT-TYPE
        SYNTAX INTEGER {
        		on(1),
        		off(2)
        	}
        MAX-ACCESS read-write
        STATUS current
        DESCRIPTION
		"Enable/disable polarity reverse function. Polarity reverse is feature to reversed tip and ring after call establish and terminate."
        ::= { voipPolarityReverseConfEntry 1 }
 
 -- voipPotsCidConfTable 
-- ##CENT        
        voipPotsCidConfTable  OBJECT-TYPE
        SYNTAX SEQUENCE OF VoipPotsCidConfEntry
        MAX-ACCESS not-accessible
        STATUS current
        DESCRIPTION
		""
        ::= { voipPort 7 }
        
        voipPotsCidConfEntry OBJECT-TYPE
        SYNTAX VoipPotsCidConfEntry
        MAX-ACCESS not-accessible
        STATUS current
        DESCRIPTION
        	"An entry in voipPotsCidConfTable."
        INDEX { voipIfIndex }
        ::= { voipPotsCidConfTable 1 }

        VoipPotsCidConfEntry ::=
           SEQUENCE {
		voipPotsCidASType		INTEGER,
		voipPotsCidPayloadType	INTEGER
           }

        voipPotsCidASType OBJECT-TYPE
        SYNTAX INTEGER {
        		defval(0),
        		cid-during-ring(1),
        		dtas-cid-before-ring(2),
        		rpas-cid-before-ring(3),
        		lr-dtas-cid-before-ring(4),
        		lr-cid-before-ring(5)
        	}
        MAX-ACCESS read-write
        STATUS current
        DESCRIPTION
		"0: DEFVAL (use the setting of country code)
		1: CID during ring
		2: DTAS CID before ring
		3: RPAS CID before ring
		4: LR DTAS CID before ring
		5: LR CID before ring
		6: CID before ring
		"
        ::= { voipPotsCidConfEntry 1 }
        
        voipPotsCidPayloadType OBJECT-TYPE
        SYNTAX INTEGER {
        		defval(0),
        		mdmf(1),
        		sdmf(2),
        		etsi-mdmf(3),
        		etsi-sdmf(4),
        		dtmf(5),
        		uk-mdmf(6),
        		uk-sdmf(7),
        		japanese-mdmf(8)
        	}
        MAX-ACCESS read-write
        STATUS current
        DESCRIPTION
		"0: DEFVAL (use the setting of country code)
		1: MDMF
		2: SDMF
		3: ETSI MDMF
		4: ETSI SDMF
		5: DTMF
		6: UK MDMF
		7: UK SDMF
		8: Japanese MDMF
		"
        ::= { voipPotsCidConfEntry 2 }

 -- voipPotsLineConfTable 
      
        voipPotsLineConfTable  OBJECT-TYPE
        SYNTAX SEQUENCE OF VoipPotsLineConfEntry
        MAX-ACCESS not-accessible
        STATUS current
        DESCRIPTION
		"per-interface table for pots configuration"
        ::= { voipPort 8 }
        
        voipPotsLineConfEntry OBJECT-TYPE
        SYNTAX VoipPotsLineConfEntry
        MAX-ACCESS not-accessible
        STATUS current
        DESCRIPTION
        	"An entry in voipPotsLineConfTable."
        INDEX { voipIfIndex }
        ::= { voipPotsLineConfTable 1 }

        VoipPotsLineConfEntry ::=
           SEQUENCE {
		voipPotsLineFlashDefault	INTEGER,
		voipPotsLineFlashMax	INTEGER,
		voipPotsLineFlashMin	INTEGER,
		voipPotsLineLoop	INTEGER
           }

        voipPotsLineFlashDefault OBJECT-TYPE
        SYNTAX INTEGER
        MAX-ACCESS read-write
        STATUS current
        DESCRIPTION
		"set positive non-zero value to configure default flash timer settings"
        ::= { voipPotsLineConfEntry 1 }

        voipPotsLineFlashMax OBJECT-TYPE
        SYNTAX INTEGER (20..1500)
        MAX-ACCESS read-write
        STATUS current
        DESCRIPTION
		"minimum flash period in ms"
        ::= { voipPotsLineConfEntry 2 }

        voipPotsLineFlashMin OBJECT-TYPE
        SYNTAX INTEGER
        MAX-ACCESS read-write
        STATUS current
        DESCRIPTION
		"maximum flash period in ms"
        ::= { voipPotsLineConfEntry 3 }

        voipPotsLineLoop OBJECT-TYPE
        SYNTAX INTEGER {
        	ohm-2600(0),
        	ohm-3200(1)
        }
        MAX-ACCESS read-write
        STATUS current
        DESCRIPTION
		"maximum loop resistance value"
        ::= { voipPotsLineConfEntry 4 }
                
--------------------
--  enetPort
--------------------

-- enetLineConfTable		

	enetLineConfTable OBJECT-TYPE
	SYNTAX SEQUENCE OF EnetLineConfEntry
	MAX-ACCESS not-accessible
	STATUS current
	DESCRIPTION
		"The table contains ethernet line configuration."
	::= { enetPort 1 }
			
	enetLineConfEntry OBJECT-TYPE
	SYNTAX EnetLineConfEntry
	MAX-ACCESS not-accessible
	STATUS current
	DESCRIPTION
		""
	INDEX { ifIndex }
	::= { enetLineConfTable 1 }
			
	EnetLineConfEntry ::=
		SEQUENCE {
			enetLineConfBandWidthIngress		INTEGER,
			enetLineConfBandWidthEgress   		INTEGER,
			enetLineConfFlowCtrlEnable		INTEGER,
			enetLineConfSpeed				INTEGER
		}
	
	enetLineConfBandWidthIngress OBJECT-TYPE
	SYNTAX INTEGER
	UNITS "Kbps"
	MAX-ACCESS read-write
	STATUS current
	DESCRIPTION
		"0~99968Kbps in step of 64Kbps, 0 means no limit."
	::= { enetLineConfEntry 1 }
	
	enetLineConfBandWidthEgress OBJECT-TYPE
	SYNTAX INTEGER
	UNITS "Kbps"
	MAX-ACCESS read-write
	STATUS current
	DESCRIPTION
		"0~99968Kbps in step of 64Kbps, 0 means no limit."
	::= { enetLineConfEntry 2 }
	
	enetLineConfFlowCtrlEnable OBJECT-TYPE
	SYNTAX INTEGER {
			enable(1),
			disable(2)
		}
	MAX-ACCESS read-write
	STATUS current
	DESCRIPTION
		"Enable/disable flow control."
	::= { enetLineConfEntry 3 }

	enetLineConfSpeed OBJECT-TYPE
	SYNTAX INTEGER {
			auto(1),
			i100baseFD(2),
			i1000baseFD(3)
		}
	MAX-ACCESS read-write
	STATUS current
	DESCRIPTION
		"Port spd/dplx configuration."
	::= { enetLineConfEntry 4 }
	
-- enetPortConfTable		

	enetPortConfTable OBJECT-TYPE
	SYNTAX SEQUENCE OF EnetPortConfEntry
	MAX-ACCESS not-accessible
	STATUS current
	DESCRIPTION
		"The table contains ethernet line configuration."
	::= { enetPort 2 }
			
	enetPortConfEntry OBJECT-TYPE
	SYNTAX EnetPortConfEntry
	MAX-ACCESS not-accessible
	STATUS current
	DESCRIPTION
		""
	INDEX { ifIndex }
	::= { enetPortConfTable 1 }
			
	EnetPortConfEntry ::=
		SEQUENCE {
			enetPortConfPriority					INTEGER,
			enetPortConfPvid   						VlanIndex,
			enetPortConfAcceptableFrameType			INTEGER,
			enetPortConfTlsEnable					INTEGER,
			enetPortConfTlsVid						VlanIndex,
			enetPortConfTlsPriority					INTEGER,
			enetPortConfRateLimitProfile			DisplayString,
			enetPortConfQueueRateLimitProfile		DisplayString,
			enetPortConfDtEnable					INTEGER,
			enetPortConfDtSvid						VlanIndex,
			enetPortConfDtSpriority					INTEGER,
			enetPortConfDtCvid						VlanIndex
		}
	
	enetPortConfPriority OBJECT-TYPE
	SYNTAX INTEGER (0..7)
	MAX-ACCESS read-write
	STATUS current
	DESCRIPTION
		"The default ingress User Priority for this port."
	::= { enetPortConfEntry 1 }
	
	enetPortConfPvid OBJECT-TYPE
	SYNTAX VlanIndex
	MAX-ACCESS read-write
	STATUS current
	DESCRIPTION
		"The PVID, the VLAN ID assigned to untagged frames or Priority-Tagged frames received on this port."
	::= { enetPortConfEntry 2 }
	
	enetPortConfAcceptableFrameType OBJECT-TYPE
	SYNTAX INTEGER {
			admitAll(1),
			admitOnlyVlanTagged(2)
		}
	MAX-ACCESS read-write
	STATUS current
	DESCRIPTION
		"When this is admitOnlyVlanTagged(2) the device will discard untagged frames or
		Priority-Tagged frames received on this port. When admitAll(1), untagged frames or 
		Priority-Tagged frames received on this port will be accepted and assigned to
		the PVID for this port."
	::= { enetPortConfEntry 3 }
	
	enetPortConfTlsEnable OBJECT-TYPE
	SYNTAX INTEGER {
			enable(1),
			disable(2)
		}
	MAX-ACCESS read-write
	STATUS current
	DESCRIPTION
		""
	::= { enetPortConfEntry 4 }
	
	enetPortConfTlsVid OBJECT-TYPE
	SYNTAX VlanIndex
	MAX-ACCESS read-write
	STATUS current
	DESCRIPTION
		"The transparent LAN VID."
	::= { enetPortConfEntry 5 }
	
	enetPortConfTlsPriority OBJECT-TYPE
	SYNTAX INTEGER
	MAX-ACCESS read-write
	STATUS current
	DESCRIPTION
		"The transparent LAN priority."
	::= { enetPortConfEntry 6 }

	enetPortConfRateLimitProfile OBJECT-TYPE
	SYNTAX DisplayString (SIZE (1..31))
	MAX-ACCESS read-write
	STATUS current
	DESCRIPTION
		"Rate Limit Profile name. This object is supported by R5.02 and later versions."
	::= { enetPortConfEntry 7 } 
	
	enetPortConfQueueRateLimitProfile OBJECT-TYPE
	SYNTAX DisplayString (SIZE (1..31))
	MAX-ACCESS read-write
	STATUS current
	DESCRIPTION
		"Set queue rate limit profile."
	::= { enetPortConfEntry 8 }

    enetPortConfDtEnable OBJECT-TYPE
    SYNTAX 	INTEGER {
    		enable(1),
    		disable(2)
    	}
    MAX-ACCESS read-write
    STATUS current
    DESCRIPTION
		"Enable/disable  double tag service on the specified subscriber port."
    ::= { enetPortConfEntry 9 }
    
    enetPortConfDtSvid OBJECT-TYPE
    SYNTAX VlanIndex
    MAX-ACCESS read-write
    STATUS current
    DESCRIPTION
		"The service provider VLAN ID."
    ::= { enetPortConfEntry 10 }
    
    enetPortConfDtSpriority OBJECT-TYPE
    SYNTAX INTEGER
    MAX-ACCESS read-write
    STATUS current
    DESCRIPTION
		"The service VLAN priority."
    ::= { enetPortConfEntry 11 }
    
    enetPortConfDtCvid OBJECT-TYPE
    SYNTAX VlanIndex
    MAX-ACCESS read-write
    STATUS current
    DESCRIPTION
		"The system-side customer VID."
    ::= { enetPortConfEntry 12 }
    
-- enetPortVlanTable		

	enetPortVlanTable OBJECT-TYPE
	SYNTAX SEQUENCE OF EnetPortVlanEntry
	MAX-ACCESS not-accessible
	STATUS current
	DESCRIPTION
		"The table contains ethernet line vlan configuration."
	::= { enetPort 3 }
			
	enetPortVlanEntry OBJECT-TYPE
	SYNTAX EnetPortVlanEntry
	MAX-ACCESS not-accessible
	STATUS current
	DESCRIPTION
		""
	INDEX { ifIndex, dot1qVlanIndex }
	::= { enetPortVlanTable 1 }
			
	EnetPortVlanEntry ::=
		SEQUENCE {
			enetPortVlanReg			INTEGER,
			enetPortVlanTag   		INTEGER,
			enetPortVlanRowStatus		RowStatus
		}
	
	enetPortVlanReg OBJECT-TYPE
	SYNTAX INTEGER {
			egress(1),
			forbidden(2)
		}
	MAX-ACCESS read-create
	STATUS current
	DESCRIPTION
		""
	::= { enetPortVlanEntry 1 }
	
	enetPortVlanTag OBJECT-TYPE
	SYNTAX INTEGER {
			tag(1),
			untag(2)
		}
	MAX-ACCESS read-create
	STATUS current
	DESCRIPTION
		""
	::= { enetPortVlanEntry 2 }
	
	enetPortVlanRowStatus OBJECT-TYPE
	SYNTAX RowStatus
	MAX-ACCESS read-create
	STATUS current
	DESCRIPTION
		"This object is used to create a new row or delete an existing row in this table."
	::= { enetPortVlanEntry 3 }


	elcDot3ad		OBJECT IDENTIFIER ::= { enetPort 4 }

-- elcDot3adTable		

	elcDot3adTable OBJECT-TYPE
	SYNTAX SEQUENCE OF ElcDot3adEntry
	MAX-ACCESS not-accessible
	STATUS current
	DESCRIPTION
		"The table contains dot3ad configuration. This table is supported by R5.01 and later versions."
	::= { elcDot3ad 1 }
			
	elcDot3adEntry OBJECT-TYPE
	SYNTAX ElcDot3adEntry
	MAX-ACCESS not-accessible
	STATUS current
	DESCRIPTION
		""
	INDEX { elcDot3adSlotId, elcDot3adGroupId }
	::= { elcDot3adTable 1 }
			
	ElcDot3adEntry ::=
		SEQUENCE {
			elcDot3adSlotId			INTEGER,
			elcDot3adGroupId  		INTEGER,
			elcDot3adEnable     		INTEGER
		}
	
	elcDot3adSlotId OBJECT-TYPE
	SYNTAX INTEGER
	MAX-ACCESS read-only
	STATUS current
	DESCRIPTION
		""
	::= { elcDot3adEntry 1 }
	
	elcDot3adGroupId OBJECT-TYPE
	SYNTAX INTEGER (1..10)
	MAX-ACCESS read-only
	STATUS current
	DESCRIPTION
		""
	::= { elcDot3adEntry 2 }
	
	elcDot3adEnable OBJECT-TYPE
	SYNTAX INTEGER {
			enable(1),
			enableWithLacp(2),
			disable(3)
		}
	MAX-ACCESS read-write
	STATUS current
	DESCRIPTION
		""
	::= { elcDot3adEntry 3 }		              

-- elcAggPortTable		

	elcAggPortTable OBJECT-TYPE
	SYNTAX SEQUENCE OF ElcAggPortEntry
	MAX-ACCESS not-accessible
	STATUS current
	DESCRIPTION
		"The table contains port aggregation configuration. This table is supported by R5.01 and later versions."
	::= { elcDot3ad 2 }
			
	elcAggPortEntry OBJECT-TYPE
	SYNTAX ElcAggPortEntry
	MAX-ACCESS not-accessible
	STATUS current
	DESCRIPTION
		""
	INDEX { ifIndex }
	::= { elcAggPortTable 1 }
			
	ElcAggPortEntry ::=
		SEQUENCE {
			elcAggPortJoin  		INTEGER
		}
	
	elcAggPortJoin OBJECT-TYPE
	SYNTAX INTEGER {
			disjoin(0),
			joinTrunkingGroup1(1),
			joinTrunkingGroup2(2),
			joinTrunkingGroup3(3),
			joinTrunkingGroup4(4),
			joinTrunkingGroup5(5),
			joinTrunkingGroup6(6),
			joinTrunkingGroup7(7),
			joinTrunkingGroup8(8),
			joinTrunkingGroup9(9),
			joinTrunkingGroup10(10)
		}
	MAX-ACCESS read-write
	STATUS current
	DESCRIPTION
		""
	::= { elcAggPortEntry 1 }
	
	enetQoS		OBJECT IDENTIFIER ::= { enetPort 5 }

-- enetQScheduleTable		

	enetQScheduleTable OBJECT-TYPE
	SYNTAX SEQUENCE OF EnetQScheduleEntry
	MAX-ACCESS not-accessible
	STATUS current
	DESCRIPTION
		""
	::= { enetQoS 1 }
			
	enetQScheduleEntry OBJECT-TYPE
	SYNTAX EnetQScheduleEntry
	MAX-ACCESS not-accessible
	STATUS current
	DESCRIPTION
		""
	INDEX { ifIndex }
	::= { enetQScheduleTable 1 }
			
	EnetQScheduleEntry ::=
		SEQUENCE {
			enetQScheduleType			INTEGER
		}
	
	enetQScheduleType OBJECT-TYPE
	SYNTAX INTEGER
	MAX-ACCESS read-write
	STATUS current
	DESCRIPTION
		"Queue scheduling type (strictly priority queue or weighted round robin)."
	::= { enetQScheduleEntry 1 }

-- enetQueueWeightTable		

	enetQueueWeightTable OBJECT-TYPE
	SYNTAX SEQUENCE OF EnetQueueWeightEntry
	MAX-ACCESS not-accessible
	STATUS current
	DESCRIPTION
		""
	::= { enetQoS 2 }
			
	enetQueueWeightEntry OBJECT-TYPE
	SYNTAX EnetQueueWeightEntry
	MAX-ACCESS not-accessible
	STATUS current
	DESCRIPTION
		""
	INDEX { ifIndex, dot1dTrafficClass }
	::= { enetQueueWeightTable 1 }
			
	EnetQueueWeightEntry ::=
		SEQUENCE {
			enetQueueWeight			INTEGER  
		}
		
	enetQueueWeight OBJECT-TYPE
	SYNTAX INTEGER
	MAX-ACCESS read-write
	STATUS current
	DESCRIPTION
		"Weight for the priority queue, 0 means strict priority"
	::= { enetQueueWeightEntry 1 }

			
-- enetPortPvlanTable

        enetPortPvlanTable OBJECT-TYPE
        SYNTAX SEQUENCE OF EnetPortPvlanEntry
        MAX-ACCESS not-accessible
        STATUS current
        DESCRIPTION
		""
        ::= { enetPort 6 }

	enetPortPvlanEntry OBJECT-TYPE
        SYNTAX EnetPortPvlanEntry
        MAX-ACCESS not-accessible
        STATUS current
        DESCRIPTION
        	"An entry in enetPortPvlanTable."
        INDEX { ifIndex, enetPortPvlanEtype, enetPortPvlanVid }
        ::= { enetPortPvlanTable 1 }

        EnetPortPvlanEntry ::=
           SEQUENCE {
		enetPortPvlanEtype			Unsigned32,
		enetPortPvlanVid			VlanIndex,
		enetPortPvlanPriority			INTEGER,
		enetPortPvlanRowStatus			RowStatus
           }

        enetPortPvlanEtype OBJECT-TYPE
        SYNTAX Unsigned32
        MAX-ACCESS read-only
        STATUS current
        DESCRIPTION
                ""
        ::= { enetPortPvlanEntry 1 }
        
        enetPortPvlanVid OBJECT-TYPE
        SYNTAX VlanIndex
        MAX-ACCESS read-only
        STATUS current
        DESCRIPTION
                ""
        ::= { enetPortPvlanEntry 2 }
        
        enetPortPvlanPriority OBJECT-TYPE
        SYNTAX INTEGER (0..7)
        MAX-ACCESS read-create
        STATUS current
        DESCRIPTION
                ""
        ::= { enetPortPvlanEntry 3 }
        
        enetPortPvlanRowStatus OBJECT-TYPE
        SYNTAX RowStatus
        MAX-ACCESS read-create
        STATUS current
        DESCRIPTION
                ""
        ::= { enetPortPvlanEntry 4 }


-- enetPortXvlanTable 
	enetPortXvlanTable OBJECT-TYPE
	SYNTAX SEQUENCE OF EnetPortXvlanEntry
	MAX-ACCESS not-accessible
	STATUS current
	DESCRIPTION
		""
	::= { enetPort 7 }
			
	enetPortXvlanEntry OBJECT-TYPE
	SYNTAX EnetPortXvlanEntry
	MAX-ACCESS not-accessible
	STATUS current
	DESCRIPTION
		""
	INDEX { ifIndex, enetPortXvlanCvid, enetPortXvlanSvid }
	::= { enetPortXvlanTable 1 }
			
	EnetPortXvlanEntry ::=
		SEQUENCE {
			enetPortXvlanCvid			Unsigned32,
			enetPortXvlanSvid 			Unsigned32,
			enetPortXvlanRowStatus		RowStatus
		}
	
	enetPortXvlanCvid OBJECT-TYPE
	SYNTAX Unsigned32 (1..4094)
	MAX-ACCESS read-only
	STATUS current
	DESCRIPTION
		"the original vlan id in the 8021q tag, 1~4094"
	::= { enetPortXvlanEntry 1 }   
	
	enetPortXvlanSvid OBJECT-TYPE
	SYNTAX Unsigned32 (1..4094)
	MAX-ACCESS read-only
	STATUS current
	DESCRIPTION
		"the result vlan id in the 8021q tag, or in the QinQ S-tag, 1~4094"
	::= { enetPortXvlanEntry 2 }
		
	enetPortXvlanRowStatus OBJECT-TYPE
	SYNTAX RowStatus
	MAX-ACCESS read-create
	STATUS current
	DESCRIPTION
		"This object is used to create a new row or delete an existing row in this table."
	::= { enetPortXvlanEntry 3 }		
	

-- gbondGroupTable		

	gbondGroupTable OBJECT-TYPE
	SYNTAX SEQUENCE OF GbondGroupEntry
	MAX-ACCESS not-accessible
	STATUS current
	DESCRIPTION
		"The table contains bonding group configuration. This table is supported by R5.01 and later versions."
	::= { port 14 }
			
	gbondGroupEntry OBJECT-TYPE
	SYNTAX GbondGroupEntry
	MAX-ACCESS not-accessible
	STATUS current
	DESCRIPTION
		""
	INDEX { slotId, IMPLIED gbondGroupName }
	::= { gbondGroupTable 1 }
			
	GbondGroupEntry ::=
		SEQUENCE {
			gbondGroupName			DisplayString,
			gbondGroupPorts   		OCTET STRING,
			gbondGroupRowStatus		RowStatus
		}
	
	gbondGroupName OBJECT-TYPE
	SYNTAX DisplayString
	MAX-ACCESS read-only
	STATUS current
	DESCRIPTION
		"An administratively assigned string, which may be used to identify bonding group."
	::= { gbondGroupEntry 1 }
	
	gbondGroupPorts OBJECT-TYPE
	SYNTAX OCTET STRING
	MAX-ACCESS read-create
	STATUS current
	DESCRIPTION
		"The set of ports which are currently assigned to 
		the bonding group of specified group name. Each bit in the octet specifies
		a port from MSB to LSB. For example: 32(hex) = 50(dec) = 00110010(bin) means
		the port 3, 4 and 7."
	::= { gbondGroupEntry 2 }
	
	gbondGroupRowStatus OBJECT-TYPE
	SYNTAX RowStatus
	MAX-ACCESS read-create
	STATUS current
	DESCRIPTION
		"This object is used to create a new row or delete an existing row in this table."
	::= { gbondGroupEntry 3 }

--------------------
-- dtpvc
--------------------

-- Double Tagging PVC Table

        dtpvcTable OBJECT-TYPE
        SYNTAX SEQUENCE OF DtpvcEntry
        MAX-ACCESS not-accessible
        STATUS current
        DESCRIPTION
        	"This table includes Double Tagging PVC configuration.
        	This table is supported by R5.02 and later versions."
        ::= { dtpvc 1 }

	dtpvcEntry OBJECT-TYPE
        SYNTAX DtpvcEntry
        MAX-ACCESS not-accessible
        STATUS current
        DESCRIPTION
		"An entry of dtpvcTable."
        INDEX { ifIndex, dtpvcVpi, dtpvcVci, dtpvcSvid, dtpvcCvid }
        ::= { dtpvcTable 1 }

        DtpvcEntry ::=
        	SEQUENCE {
			dtpvcVpi		INTEGER,
			dtpvcVci		INTEGER,
			dtpvcSvid		VlanIndex,
			dtpvcCvid		VlanIndex,
			dtpvcEncap		INTEGER,
			dtpvcSPriority		INTEGER,
			dtpvcCPriority		INTEGER,
			dtpvcProfile		DisplayString,
			dtpvcRowStatus		RowStatus,
			dtpvcMvlanEnable	INTEGER
           	}

        dtpvcVpi OBJECT-TYPE
        SYNTAX INTEGER (0..255)
        MAX-ACCESS read-only
        STATUS current
        DESCRIPTION
                "VPI of the pvc."
         ::= { dtpvcEntry 1 }

        dtpvcVci OBJECT-TYPE
        SYNTAX INTEGER (1..65535)
        MAX-ACCESS read-only
       	STATUS current
        DESCRIPTION
                "VCI of the pvc."
         ::= { dtpvcEntry 2 }

        dtpvcSvid OBJECT-TYPE
        SYNTAX VlanIndex
        MAX-ACCESS read-only
        STATUS current
        DESCRIPTION
                "s-tag of the pvc."
         ::= { dtpvcEntry 3 }

        dtpvcCvid OBJECT-TYPE
        SYNTAX VlanIndex
        MAX-ACCESS read-only
        STATUS current
        DESCRIPTION
                "c-tag of the pvc."
         ::= { dtpvcEntry 4 }

        dtpvcEncap OBJECT-TYPE
        SYNTAX INTEGER {
        		llc(1),
        		vc(2)
        	}
        MAX-ACCESS read-create
        STATUS current
        DESCRIPTION
                "Encapsulation of the pvc."
         ::= { dtpvcEntry 5 }

        dtpvcSPriority OBJECT-TYPE
        SYNTAX INTEGER (0..7)
        MAX-ACCESS read-create
        STATUS current
        DESCRIPTION
                "s-priority of the pvc."
         ::= { dtpvcEntry 6 }

        dtpvcCPriority OBJECT-TYPE
        SYNTAX INTEGER (0..7)
        MAX-ACCESS read-create
        STATUS current
        DESCRIPTION
                "c-priority of the pvc."
         ::= { dtpvcEntry 7 }

        dtpvcProfile OBJECT-TYPE
        SYNTAX DisplayString (SIZE (1..31))
        MAX-ACCESS read-create
        STATUS current
        DESCRIPTION
                "The value of this object identifies the row in the atmProfileTable, which applies for this pvc."
         ::= { dtpvcEntry 8 }

        dtpvcRowStatus OBJECT-TYPE
        SYNTAX RowStatus
        MAX-ACCESS read-create
        STATUS current
        DESCRIPTION
                "This object is used to create a new row or delete an existing row in this table."
         ::= { dtpvcEntry 9 }
         
         dtpvcMvlanEnable OBJECT-TYPE
        SYNTAX INTEGER {
        		enable(1),
						disable(2)
        	}
        MAX-ACCESS read-create
        STATUS current
        DESCRIPTION
                "Enable/disable multicast VLAN function for the DTPVC."
         ::= { dtpvcEntry 10 }   

--------------------
--  e1Port
--------------------
        
-- e1PortConfTable		

	e1PortConfTable OBJECT-TYPE
	SYNTAX SEQUENCE OF E1PortConfEntry
	MAX-ACCESS not-accessible
	STATUS current
	DESCRIPTION
		"This table is supported by R5.03 and later versions.
		The table contains E1 line configuration."
	::= { e1Port 1 }
			
	e1PortConfEntry OBJECT-TYPE
	SYNTAX E1PortConfEntry
	MAX-ACCESS not-accessible
	STATUS current
	DESCRIPTION
		""
	INDEX { ifIndex }
	::= { e1PortConfTable 1 }
			
	E1PortConfEntry ::=
		SEQUENCE {
			e1PortConfAdminStatus			INTEGER,
			e1PortConfAlarmProfile 			DisplayString,
			e1PortConfImpedance				INTEGER,
			e1PortConfTimingSrc				INTEGER
		}
	
	e1PortConfAdminStatus OBJECT-TYPE
	SYNTAX INTEGER {
			enable(1),
			disable(2)
		}
	MAX-ACCESS read-write
	STATUS current
	DESCRIPTION
		""
	::= { e1PortConfEntry 1 }   
	
	e1PortConfAlarmProfile OBJECT-TYPE
	SYNTAX DisplayString (SIZE (1..31))
	MAX-ACCESS read-write
	STATUS current
	DESCRIPTION
		""
	::= { e1PortConfEntry 2 }
		
	e1PortConfImpedance OBJECT-TYPE
	SYNTAX INTEGER {
			impedance-75ohm(1),
			impedance-120ohm(2)
		}
	MAX-ACCESS read-write
	STATUS current
	DESCRIPTION
		""
	::= { e1PortConfEntry 3 }   
	
	e1PortConfTimingSrc OBJECT-TYPE
	SYNTAX INTEGER
	MAX-ACCESS read-write
	STATUS current
	DESCRIPTION
		"0: local, 1~8 E1 port: the timing source port id"
	::= { e1PortConfEntry 4 }

--------------------
--  xvlan
--------------------
        
-- xvlanTable 
	xvlanTable OBJECT-TYPE
	SYNTAX SEQUENCE OF XvlanEntry
	MAX-ACCESS not-accessible
	STATUS current
	DESCRIPTION
		"This table is supported by R5.04 and later versions."
	::= { xvlan 1 }
			
	xvlanEntry OBJECT-TYPE
	SYNTAX XvlanEntry
	MAX-ACCESS not-accessible
	STATUS current
	DESCRIPTION
		""
	INDEX { ifIndex, xvlanCvid, xvlanSvid, xvlanCvids }
	::= { xvlanTable 1 }
			
	XvlanEntry ::=
		SEQUENCE {
			xvlanCvid			Unsigned32,
			xvlanSvid 			Unsigned32,
			xvlanCvids			Unsigned32,
			xvlanRowStatus		RowStatus
		}
	
	xvlanCvid OBJECT-TYPE
	SYNTAX Unsigned32 (1..4094)
	MAX-ACCESS read-only
	STATUS current
	DESCRIPTION
		"the original vlan id in the 8021q tag, 1~4094"
	::= { xvlanEntry 1 }   
	
	xvlanSvid OBJECT-TYPE
	SYNTAX Unsigned32 (1..4094)
	MAX-ACCESS read-only
	STATUS current
	DESCRIPTION
		"the result vlan id in the 8021q tag, or in the QinQ S-tag, 1~4094"
	::= { xvlanEntry 2 }
		
	xvlanCvids OBJECT-TYPE
	SYNTAX Unsigned32 (0..4094)
	MAX-ACCESS read-only
	STATUS current
	DESCRIPTION
		"the result vlan id in the QinQ C-tag, 0~4094, 0 means single tag"
	::= { xvlanEntry 3 }   
	
	xvlanRowStatus OBJECT-TYPE
	SYNTAX INTEGER
	MAX-ACCESS read-create
	STATUS current
	DESCRIPTION
		"This object is used to create a new row or delete an existing row in this table."
	::= { xvlanEntry 4 }		
	
--------------------
--  vdsl2Port
--------------------
        
-- vdsl2LineConfTable 
	vdsl2LineConfTable OBJECT-TYPE
	SYNTAX SEQUENCE OF Vdsl2LineConfEntry
	MAX-ACCESS not-accessible
	STATUS current
	DESCRIPTION
		"This table is supported by R5.06 and later versions."
	::= { vdsl2Port 1 }
			
	vdsl2LineConfEntry OBJECT-TYPE
	SYNTAX Vdsl2LineConfEntry
	MAX-ACCESS not-accessible
	STATUS current
	DESCRIPTION
		""
	INDEX { ifIndex }
	::= { vdsl2LineConfTable 1 }
			
	Vdsl2LineConfEntry ::=
		SEQUENCE {
			vdsl2LineConfRateLimitProfile			DisplayString,
			vdsl2LineConfQueueRateLimitProfile      DisplayString
		}
	
	vdsl2LineConfRateLimitProfile OBJECT-TYPE
	SYNTAX DisplayString
	MAX-ACCESS read-write
	STATUS current
	DESCRIPTION
		"Set rate limit profile"
	::= { vdsl2LineConfEntry 1 } 
	
	vdsl2LineConfQueueRateLimitProfile OBJECT-TYPE
	SYNTAX DisplayString
	MAX-ACCESS read-write
	STATUS current
	DESCRIPTION
		"Set queue rate limit profile"
	::= { vdsl2LineConfEntry 2 } 
	
	
-- vdsl2Pvc
	vdsl2Pvc		OBJECT IDENTIFIER ::= { vdsl2Port 2 }
	
	-- vdsl2PvcTable 
	vdsl2PvcTable OBJECT-TYPE
	SYNTAX SEQUENCE OF Vdsl2PvcEntry
	MAX-ACCESS not-accessible
	STATUS current
	DESCRIPTION
		"This table is supported by R5.06 and later versions."
	::= { vdsl2Pvc 1 }
			
	vdsl2PvcEntry OBJECT-TYPE
	SYNTAX Vdsl2PvcEntry
	MAX-ACCESS not-accessible
	STATUS current
	DESCRIPTION
		""
	INDEX { ifIndex, vdsl2PvcVpi, vdsl2PvcVci, vdsl2PvcPvid }
	::= { vdsl2PvcTable 1 }
			
	Vdsl2PvcEntry ::=
		SEQUENCE {
			vdsl2PvcVpi			INTEGER,
			vdsl2PvcVci         INTEGER,
			vdsl2PvcPvid        INTEGER,
			vdsl2PvcEncap		INTEGER,
			vdsl2PvcPriority	INTEGER,
			vdsl2PvcSuper		INTEGER,
			vdsl2PvcRowStatus	RowStatus
		}
	
	vdsl2PvcVpi OBJECT-TYPE
	SYNTAX INTEGER (0..255)
	MAX-ACCESS read-only
	STATUS current
	DESCRIPTION
		"VPI of the pvc."
	::= { vdsl2PvcEntry 1 }  
	
	vdsl2PvcVci OBJECT-TYPE
	SYNTAX INTEGER (1..65535)
	MAX-ACCESS read-only
	STATUS current
	DESCRIPTION
		"VCI of the pvc."
	::= { vdsl2PvcEntry 2 }
	
	vdsl2PvcPvid OBJECT-TYPE
	SYNTAX INTEGER (1..4094)
	MAX-ACCESS read-only
	STATUS current
	DESCRIPTION
		"Default VID of the pvc."
	::= { vdsl2PvcEntry 3 }
	
	vdsl2PvcEncap OBJECT-TYPE
	SYNTAX INTEGER {
	    llc(1),
	    vc(2)
	}
	MAX-ACCESS read-write
	STATUS current
	DESCRIPTION
		"Encapsulation of the pvc."
	::= { vdsl2PvcEntry 4 }
	
	vdsl2PvcPriority OBJECT-TYPE
	SYNTAX INTEGER (0..7)
	MAX-ACCESS read-write
	STATUS current
	DESCRIPTION
		"802.1p default priority of the pvc."
	::= { vdsl2PvcEntry 5 }
	
	vdsl2PvcSuper OBJECT-TYPE
	SYNTAX INTEGER
	MAX-ACCESS read-write
	STATUS current
	DESCRIPTION
		""
	::= { vdsl2PvcEntry 6 } 
	
	vdsl2PvcRowStatus OBJECT-TYPE
	SYNTAX RowStatus
	MAX-ACCESS read-write
	STATUS current
	DESCRIPTION
		"This object is used to create a new row or delete an existing row in this table."
	::= { vdsl2PvcEntry 7 } 
		
--------------------
-- vdsl2QSchedule
--------------------		
	vdsl2QSchedule	OBJECT IDENTIFIER ::= { vdsl2Port 3 }

-- Queue Schedule Port Table
	
	vdsl2QScheduleTable OBJECT-TYPE
	SYNTAX SEQUENCE OF Vdsl2QSchedulePortEntry
	MAX-ACCESS not-accessible
	STATUS current
	DESCRIPTION
		"The table contains queue schedule configuration for the vdsl2 ports."
	::= { vdsl2QSchedule 1 }
			
	vdsl2QScheduleEntry OBJECT-TYPE
	SYNTAX Vdsl2QSchedulePortEntry
	MAX-ACCESS not-accessible
	STATUS current
	DESCRIPTION
		""
	INDEX { ifIndex }
	::= { vdsl2QScheduleTable 1 }
			
	Vdsl2QSchedulePortEntry ::=
		SEQUENCE {
			vdsl2QScheduleType	INTEGER
		}

	vdsl2QScheduleType OBJECT-TYPE
	SYNTAX 	INTEGER {
			spq(1),
			wrr(2)
		}
	MAX-ACCESS read-write
	STATUS current
	DESCRIPTION
		"Queue scheduling type (strictly priority queue or weighted round robin)."
	::= { vdsl2QScheduleEntry 1 }

-- Queue Weight Table
		
	vdsl2QueueWeightTable OBJECT-TYPE
	SYNTAX SEQUENCE OF Vdsl2QueueWeightEntry
	MAX-ACCESS not-accessible
	STATUS current
	DESCRIPTION
		"The table contains weight configuration for the priority queues."
	::= { vdsl2QSchedule 2 }
			
	vdsl2QueueWeightEntry OBJECT-TYPE
	SYNTAX Vdsl2QueueWeightEntry
	MAX-ACCESS not-accessible
	STATUS current
	DESCRIPTION
		""
	INDEX { ifIndex, dot1dTrafficClass }
	::= { vdsl2QueueWeightTable 1 }
			
	Vdsl2QueueWeightEntry ::=
		SEQUENCE {
			vdsl2QueueWeight	INTEGER
		}

	vdsl2QueueWeight OBJECT-TYPE
	SYNTAX INTEGER (0..15)
	MAX-ACCESS read-write
	STATUS current
	DESCRIPTION
		"Weight for the priority queue, 0 means strict priority"
	::= { vdsl2QueueWeightEntry 1 } 
	
	pvcAll	OBJECT IDENTIFIER ::= { port 19 } 
	
	pvcAllFilter OBJECT-TYPE
	SYNTAX INTEGER
	MAX-ACCESS read-write
	STATUS current
	DESCRIPTION
		"Ifindex to filter pvc, value 0 indicates to display all."
	::= { pvcAll 1 }


-- pvcAllTable	
	pvcAllTable OBJECT-TYPE
	SYNTAX SEQUENCE OF PvcAllEntry
	MAX-ACCESS not-accessible
	STATUS current
	DESCRIPTION
		""
	::= { pvcAll 2 }
			
	pvcAllEntry OBJECT-TYPE
	SYNTAX PvcAllEntry
	MAX-ACCESS not-accessible
	STATUS current
	DESCRIPTION
		""
	INDEX { ifIndex, pvcVpi, pvcVci }
	::= { pvcAllTable 1 }
			
	PvcAllEntry ::=
		SEQUENCE {
			pvcAllVpi	INTEGER,
			pvcAllVci   INTEGER,
			pvcAllEncap INTEGER,
			pvcAllType	INTEGER
		}

	pvcAllVpi OBJECT-TYPE
    SYNTAX INTEGER (0..255)
    MAX-ACCESS read-only
    STATUS current
    DESCRIPTION
       "VPI of the pvc."
    ::= { pvcAllEntry 1 }

    pvcAllVci OBJECT-TYPE
    SYNTAX INTEGER (1..65535)
    MAX-ACCESS read-only
    STATUS current
    DESCRIPTION
       "VCI of the pvc."
    ::= { pvcAllEntry 2 }
    
    pvcAllEncap OBJECT-TYPE
	SYNTAX INTEGER {
	    llc(1),
	    vc(2)
	}
	MAX-ACCESS read-only
	STATUS current
	DESCRIPTION
		"Encapsulation of the pvc."
	::= { pvcAllEntry 3 }
	
	pvcAllType OBJECT-TYPE
	SYNTAX INTEGER {
	    pvc(1),
	    paepvc(2),
	    tlspvc(3),
	    ipbpvc(4),
	    dtpvc(5)
	}
	MAX-ACCESS read-only
	STATUS current
	DESCRIPTION
		"Type of the pvc."
	::= { pvcAllEntry 4 }


 --------------------
-- vdsl2Paepvc
--------------------
	vdsl2Paepvc	OBJECT IDENTIFIER ::= { vdsl2Port 4 }

-- PPPoAoE PVC Table

        vdsl2PaepvcTable OBJECT-TYPE
        SYNTAX SEQUENCE OF Vdsl2PaepvcEntry
        MAX-ACCESS not-accessible
        STATUS current
        DESCRIPTION
        	"This table includes PPPoAoE PVC configuration.
        	This table is supported by R1.02 and later versions."
        ::= { vdsl2Paepvc 1 }

	vdsl2PaepvcEntry OBJECT-TYPE
        SYNTAX Vdsl2PaepvcEntry
        MAX-ACCESS not-accessible
        STATUS current
        DESCRIPTION
		"An entry of vdsl2PaepvcTable."
        INDEX { ifIndex, vdsl2PaepvcVpi, vdsl2PaepvcVci, vdsl2PaepvcPvid }
        ::= { vdsl2PaepvcTable 1 }

        Vdsl2PaepvcEntry ::=
        	SEQUENCE {
			vdsl2PaepvcVpi		INTEGER,
			vdsl2PaepvcVci		INTEGER,
			vdsl2PaepvcPvid		VlanIndex,
			vdsl2PaepvcEncap		INTEGER,
			vdsl2PaepvcPriority		INTEGER,
			vdsl2PaepvcAcName		DisplayString,
			vdsl2PaepvcServiceName	DisplayString,
			vdsl2PaepvcHelloTime		INTEGER,
			vdsl2PaepvcRowStatus		RowStatus
           	}

        vdsl2PaepvcVpi OBJECT-TYPE
        SYNTAX INTEGER (0..255)
        MAX-ACCESS read-only
        STATUS current
        DESCRIPTION
                "VPI of the pvc."
         ::= { vdsl2PaepvcEntry 1 }

        vdsl2PaepvcVci OBJECT-TYPE
        SYNTAX INTEGER (1..65535)
        MAX-ACCESS read-only
       	STATUS current
        DESCRIPTION
                "VCI of the pvc."
         ::= { vdsl2PaepvcEntry 2 }

        vdsl2PaepvcPvid OBJECT-TYPE
        SYNTAX VlanIndex
        MAX-ACCESS read-only
        STATUS current
        DESCRIPTION
                "Default VID of the pvc."
         ::= { vdsl2PaepvcEntry 3 }

        vdsl2PaepvcEncap OBJECT-TYPE
        SYNTAX INTEGER {
        		llc(1),
        		vc(2)
        	}
        MAX-ACCESS read-create
        STATUS current
        DESCRIPTION
                "Encapsulation of the pvc."
         ::= { vdsl2PaepvcEntry 4 }

        vdsl2PaepvcPriority OBJECT-TYPE
        SYNTAX INTEGER (0..7)
        MAX-ACCESS read-create
        STATUS current
        DESCRIPTION
                "802.1p default priority of the pvc."
         ::= { vdsl2PaepvcEntry 5 }

        vdsl2PaepvcAcName OBJECT-TYPE
        SYNTAX DisplayString
        MAX-ACCESS read-create
        STATUS current
        DESCRIPTION
                "Access concentrator name."
         ::= { vdsl2PaepvcEntry 6 }
         
        vdsl2PaepvcServiceName OBJECT-TYPE
        SYNTAX DisplayString
        MAX-ACCESS read-create
        STATUS current
        DESCRIPTION
                "Service name."
         ::= { vdsl2PaepvcEntry 7 }

        vdsl2PaepvcHelloTime OBJECT-TYPE
        SYNTAX INTEGER
        UNITS "second"
        MAX-ACCESS read-create
        STATUS current
        DESCRIPTION
                "The system will close the PVC if there are not any LCP echo messages passed through 
                during the LCP hello time."
         ::= { vdsl2PaepvcEntry 8 }
                  
        vdsl2PaepvcRowStatus OBJECT-TYPE
        SYNTAX RowStatus
        MAX-ACCESS read-create
        STATUS current
        DESCRIPTION
                "This object is used to create a new row or delete an existing row in this table."
         ::= { vdsl2PaepvcEntry 9 }

----------------------------------------
-- profile
----------------------------------------

	adslProfile		OBJECT IDENTIFIER ::= { profile 1 }
	shdslProfile		OBJECT IDENTIFIER ::= { profile 2 }
	atmProfile		OBJECT IDENTIFIER ::= { profile 3 }
	profsvr			OBJECT IDENTIFIER ::= { profile 4 }
	aclProfile		OBJECT IDENTIFIER ::= { profile 5 }
	vdslProfile		OBJECT IDENTIFIER ::= { profile 6 }
	voipProfile		OBJECT IDENTIFIER ::= { profile 7 }
	ipqosProfile		OBJECT IDENTIFIER ::= { profile 8 }
	rateLimitProfile	OBJECT IDENTIFIER ::= { profile 9 }
	e1AlarmProfile		OBJECT IDENTIFIER ::= { profile 10 }
	vdsl2Profile		OBJECT IDENTIFIER ::= { profile 11 }
    queueRateLimitProfile	OBJECT IDENTIFIER ::= { profile 12 }	
    ipqos2Profile OBJECT IDENTIFIER ::= { profile 13 }	

--------------------
-- adslProfile
--------------------
	
        maxNumOfAdslLineProfiles OBJECT-TYPE
        SYNTAX INTEGER
        MAX-ACCESS read-only
        STATUS current
        DESCRIPTION
        	"The maximum number of ADSL line profiles supported by the system."
        ::= { adslProfile 1 }

        maxNumOfAdslAlarmProfiles OBJECT-TYPE
        SYNTAX INTEGER
        MAX-ACCESS read-only
        STATUS current
        DESCRIPTION
        	"The maximum number of ADSL alarm profiles supported by the system."
        ::= { adslProfile 2 }
        
--------------------
-- shdslProfile
--------------------

        maxNumOfShdslLineProfiles OBJECT-TYPE
        SYNTAX INTEGER
        MAX-ACCESS read-only
        STATUS current
        DESCRIPTION
        	"The maximum number of SHDSL line profiles supported by the system."
        ::= { shdslProfile 1 }

        maxNumOfShdslAlarmProfiles OBJECT-TYPE
        SYNTAX INTEGER
        MAX-ACCESS read-only
        STATUS current
        DESCRIPTION
        	"The maximum number of SHDSL alarm profiles supported by the system."
        ::= { shdslProfile 2 }
        
--------------------
-- atmProfile
--------------------
        
-- ATM Profile

        maxNumOfAtmProfiles OBJECT-TYPE
        SYNTAX INTEGER
        MAX-ACCESS read-only
        STATUS current
        DESCRIPTION
        	"The maximum number of ATM profiles supported by the system."
        ::= { atmProfile 1 }

        atmProfileTable OBJECT-TYPE
        SYNTAX SEQUENCE OF AtmProfileEntry
        MAX-ACCESS not-accessible
        STATUS current
        DESCRIPTION
                "This table contains information on the PVC configuration. One entry in this table
                reflects a profile which can be used to configure the PVC."
        ::= { atmProfile 2 }

	atmProfileEntry OBJECT-TYPE
        SYNTAX AtmProfileEntry
        MAX-ACCESS not-accessible
        STATUS current
        DESCRIPTION
		"An entry in atmProfileTable."
        INDEX { IMPLIED atmProfileName }
        ::= { atmProfileTable 1 }

        AtmProfileEntry ::=
        	SEQUENCE {
			atmProfileName		DisplayString,
			atmProfileAAL		INTEGER,
			atmProfileClass		INTEGER,
			atmProfilePcr		Unsigned32,
			atmProfileCdvt		INTEGER,
			atmProfileScrMcr	Unsigned32,
			atmProfileBt		INTEGER,
			atmProfileRowStatus	RowStatus
           	}

        atmProfileName OBJECT-TYPE
        SYNTAX DisplayString (SIZE (1..31))
        MAX-ACCESS read-only
        STATUS current
        DESCRIPTION
                "This object is used by the ATM profile table in order to identify a row of this table."
         ::= { atmProfileEntry 1 }

        atmProfileAAL OBJECT-TYPE
        SYNTAX INTEGER (0..5)
        MAX-ACCESS read-create
        STATUS current
        DESCRIPTION
                "ATM Adaptation Layer policy."
         ::= { atmProfileEntry 2 }

        atmProfileClass OBJECT-TYPE
        SYNTAX	INTEGER {
			cbr(1),
			rt-vbr(2),
			nrt-vbr(3),
			ubr(4),
			abr(5)
		}
        MAX-ACCESS read-create
        STATUS current
        DESCRIPTION
                "ATM traffic class, including constant bit rate,
		real-time variable bit rate, non real-time variable bit rate,
		unspecified bit rate, and available bit rate."
         ::= { atmProfileEntry 3 }

        atmProfilePcr OBJECT-TYPE
        SYNTAX Unsigned32
        UNITS "cells per second"
        MAX-ACCESS read-create
        STATUS current
        DESCRIPTION
                "Peak Cell Rate."
         ::= { atmProfileEntry 4 }

        atmProfileCdvt OBJECT-TYPE
        SYNTAX INTEGER (0..255)
        UNITS "cell"
        MAX-ACCESS read-create
        STATUS current
        DESCRIPTION
                "Cell Delay Variation Tolerance."
         ::= { atmProfileEntry 5 }

        atmProfileScrMcr OBJECT-TYPE
        SYNTAX Unsigned32
        UNITS "cells per second"
        MAX-ACCESS read-create
        STATUS current
        DESCRIPTION
                "Sustain Cell Rate for vbr or Minimum Cell Rate for abr."
         ::= { atmProfileEntry 6 }

        atmProfileBt OBJECT-TYPE
        SYNTAX INTEGER (0..255)
        UNITS "cell"
        MAX-ACCESS read-create
        STATUS current
        DESCRIPTION
                "Burst Tolerance for vbr."
         ::= { atmProfileEntry 7 }

        atmProfileRowStatus OBJECT-TYPE
        SYNTAX RowStatus
        MAX-ACCESS read-create
        STATUS current
        DESCRIPTION
                "This object is used to create a new row or delete an existing row in this table."
         ::= { atmProfileEntry 8 }

--------------------
-- profsvr
--------------------

        profileServerMode OBJECT-TYPE
        SYNTAX  INTEGER {
        		server(1),
        		client(2)
        	}
        MAX-ACCESS read-write
        STATUS current
        DESCRIPTION
        	"The object indicates the system is running profile server with server mode or client mode."
        ::= { profsvr 1 }

        profileServerIp OBJECT-TYPE
        SYNTAX IpAddress
        MAX-ACCESS read-write
        STATUS current
        DESCRIPTION
        	"IP address of the profile server."
        ::= { profsvr 2 }
                
        profsvrClientTable OBJECT-TYPE
        SYNTAX SEQUENCE OF ProfsvrClientEntry
        MAX-ACCESS not-accessible
        STATUS current
        DESCRIPTION
        	"This table includes the clients to be provisioned."
        ::= { profsvr 3 }

	profsvrClientEntry OBJECT-TYPE
        SYNTAX ProfsvrClientEntry
        MAX-ACCESS not-accessible
        STATUS current
        DESCRIPTION
		"An entry of profsvrClientTable."
        INDEX { profsvrClientIp }
        ::= { profsvrClientTable 1 }

        ProfsvrClientEntry ::=
        	SEQUENCE {
			profsvrClientIp		IpAddress,
			profsvrClientType	INTEGER,
			profsvrClientRowStatus	RowStatus
           	}

        profsvrClientIp OBJECT-TYPE
        SYNTAX IpAddress
        MAX-ACCESS read-only
        STATUS current
        DESCRIPTION
                "IP address of the client to be provisioned."
         ::= { profsvrClientEntry 1 }

        profsvrClientType OBJECT-TYPE
        SYNTAX  INTEGER {
        		nodelete(1),
        		delete(2)
        	}
        MAX-ACCESS read-create
        STATUS current
        DESCRIPTION
                "Provision type to decide whether deleting unmapped profiles in client or not."
         ::= { profsvrClientEntry 2 }

        profsvrClientRowStatus OBJECT-TYPE
        SYNTAX RowStatus
        MAX-ACCESS read-create
        STATUS current
        DESCRIPTION
                "The row status is used to create or delete a client."
         ::= { profsvrClientEntry 3 }
         
        profileServerSync OBJECT-TYPE
        SYNTAX INTEGER
        MAX-ACCESS read-write
        STATUS current
        DESCRIPTION
        	"The manager sets the object to be one to start profile synchronization.
        	The agent should clear the object to be zero when the operation is completed."
        ::= { profsvr 4 }

-- aclProfileTable

        aclProfileTable OBJECT-TYPE
        SYNTAX SEQUENCE OF AclProfileEntry
        MAX-ACCESS not-accessible
        STATUS current
        DESCRIPTION
        	"This table is supported by R1.03 and later versions."
        ::= { aclProfile 1 }

	aclProfileEntry OBJECT-TYPE
        SYNTAX AclProfileEntry
        MAX-ACCESS not-accessible
        STATUS current
        DESCRIPTION
		"An entry of aclProfileTable."
        INDEX { IMPLIED aclProfileRuleName  }
        ::= { aclProfileTable 1 }

        AclProfileEntry ::=
           SEQUENCE {
        	aclProfileRuleName  				DisplayString,
		aclProfileRuleNumber				INTEGER,
		aclProfileActionNumber				INTEGER,
		aclProfileRuleParamMask				INTEGER,
		aclProfileRuleEtype				INTEGER,
		aclProfileRuleVid				INTEGER,
		aclProfileRuleSmac				PhysAddress,
		aclProfileRuleDmac				PhysAddress,
		aclProfileRulePriority				INTEGER,
		aclProfileRuleProtocol				INTEGER,
		aclProfileRuleSrcIP				IpAddress,
		aclProfileRuleSrcIPMask				INTEGER,
		aclProfileRuleDestIP				IpAddress,
		aclProfileRuleDestIPMask			INTEGER,
		aclProfileRuleStartTos				INTEGER,
		aclProfileRuleEndTos				INTEGER,
		aclProfileRuleSrcStartPort			INTEGER,
		aclProfileRuleSrcEndPort			INTEGER,
		aclProfileRuleDestStartPort			INTEGER,
		aclProfileRuleDestEndPort			INTEGER,
		aclProfileActionRate				INTEGER,
		aclProfileActionrvlan				INTEGER,
		aclProfileActionrpri				INTEGER,
		aclProfileRowStatus				RowStatus,
		aclProfileRuleSip				IpAddress,
		aclProfileRuleDip				IpAddress,
		aclProfileRuleSport				INTEGER,
		aclProfileRuleDport				INTEGER,
		aclProfileRuleSrcIp6            InetAddress,
		aclProfileRuleDstIp6			InetAddress,
		aclProfileRuleSip6				InetAddress,
		aclProfileRuleDip6				InetAddress
           }

        aclProfileRuleName OBJECT-TYPE
        SYNTAX DisplayString
        MAX-ACCESS read-only
        STATUS current
        DESCRIPTION
        	"Profile rule name"
        ::= { aclProfileEntry 1 }

        aclProfileRuleNumber OBJECT-TYPE
        SYNTAX INTEGER
        MAX-ACCESS read-create
        STATUS current
        DESCRIPTION
		"The managed object is for acl profile rule configuration.
        	etype <etype> vlan <vid> (1),
        	etype <etype> smac <mac> (2),
        	etype <etype> dmac <mac> (3),
        	vlan <vid> smac <mac> (4),
        	vlan <vid> dmac <mac> (5),
        	smac <mac> dmac <mac> (6),
        	vlan <vid> priority <priority> (7),
        	etype <etype> (8),
        	vlan <vid> (9),
        	smac <mac> (10),
        	dmac <mac> (11),
        	priority <priority> (12),
        	protocol <protocol> (13),
        	{srcip <ip>/<mask>{|dstip <ip>/<mask>{|tos <stos> <etos>{|srcport <sport> <eport> {|dstport <sport> <eport>}}}}} (14),
        	vlan <vid> sip <ip> (15),
		vlan <vid> dip <ip> (16),
		vlan <vid> sport tcp|udp <port> (17),
		vlan <vid> dport tcp|udp <port> (18),
		vlan <vid> smac <mac> sip <ip> (19),
		vlan <vid> dmac <mac> dip <ip> (20),
		srcip <ip6>/<mask>|dstip <ip6/<mask>|tos <stos> <etos>|srcport <sport> <eport> |dstport <sport> <eport> (21),
		vlan <vid> sip <ip6> (22),
		vlan <vid> dip <ip6> (23)
		"
        ::= { aclProfileEntry 2 }

        aclProfileActionNumber OBJECT-TYPE
        SYNTAX INTEGER
        MAX-ACCESS read-create
        STATUS current
        DESCRIPTION
        	"Profile action number.
		  Bit 1: rate
		  Bit 2: rvlan
		  Bit 3: rpri
		  Bit 4: deny
		  Bit 1, Bit 2 & Bit 3 can multiple selection."
        ::= { aclProfileEntry 3 }

        aclProfileRuleParamMask OBJECT-TYPE
        SYNTAX INTEGER
        MAX-ACCESS read-create
        STATUS current
        DESCRIPTION
        	"Profile rule parameter mask.
		 BIT 1: srcip <ip>/<mask>
		 BIT 2: dstip <ip>/<mask>
		 BIT 3: tos <stos> <etos>
		 BIT 4: srcport <sport> <eport>
		 BIT 5: dstport <sport> <eport>"
        ::= { aclProfileEntry 4 }

        aclProfileRuleEtype OBJECT-TYPE
        SYNTAX INTEGER (0..65535)
        MAX-ACCESS read-create
        STATUS current
        DESCRIPTION
        	"Profile rule etype."
        ::= { aclProfileEntry 5 }

        aclProfileRuleVid OBJECT-TYPE
        SYNTAX INTEGER (1..4094)
        MAX-ACCESS read-create
        STATUS current
        DESCRIPTION
        	"Profile rule vid."
        ::= { aclProfileEntry 6 }

        aclProfileRuleSmac OBJECT-TYPE
        SYNTAX PhysAddress
        MAX-ACCESS read-create
        STATUS current
        DESCRIPTION
        	"Profile rule source MAC."
        ::= { aclProfileEntry 7 }

        aclProfileRuleDmac OBJECT-TYPE
        SYNTAX PhysAddress
        MAX-ACCESS read-create
        STATUS current
        DESCRIPTION
        	"Profile rule destination MAC."
        ::= { aclProfileEntry 8 }

        aclProfileRulePriority OBJECT-TYPE
        SYNTAX INTEGER (0..7)
        MAX-ACCESS read-create
        STATUS current
        DESCRIPTION
        	"Profile rule priority."
        ::= { aclProfileEntry 9 }

        aclProfileRuleProtocol OBJECT-TYPE
        SYNTAX INTEGER (0..65535)
        MAX-ACCESS read-create
        STATUS current
        DESCRIPTION
        	"Profile rule protocol.
		icmp(1),igmp(2),ip(4),tcp(6),udp(17),gre(47),ospf(89), and other protocol types."
        ::= { aclProfileEntry 10 }

        aclProfileRuleSrcIP OBJECT-TYPE
        SYNTAX IpAddress
        MAX-ACCESS read-create
        STATUS current
        DESCRIPTION
        	"Profile rule source IP"
        ::= { aclProfileEntry 11 }

        aclProfileRuleSrcIPMask OBJECT-TYPE
        SYNTAX INTEGER (0..32)
        MAX-ACCESS read-create
        STATUS current
        DESCRIPTION
        	"The subnet mask of source IP mask."
        ::= { aclProfileEntry 12 }

        aclProfileRuleDestIP OBJECT-TYPE
        SYNTAX IpAddress
        MAX-ACCESS read-create
        STATUS current
        DESCRIPTION
        	"Profile rule source IP."
        ::= { aclProfileEntry 13 }

        aclProfileRuleDestIPMask OBJECT-TYPE
        SYNTAX INTEGER (0..32)
        MAX-ACCESS read-create
        STATUS current
        DESCRIPTION
        	"The subnet mask of destination IP mask."
        ::= { aclProfileEntry 14 }

        aclProfileRuleStartTos OBJECT-TYPE
        SYNTAX INTEGER (0..255)
        MAX-ACCESS read-create
        STATUS current
        DESCRIPTION
        	"Profile rule start type of service."
        ::= { aclProfileEntry 15 }

        aclProfileRuleEndTos OBJECT-TYPE
        SYNTAX INTEGER (0..255)
        MAX-ACCESS read-create
        STATUS current
        DESCRIPTION
        	"Profile rule end type of service."
        ::= { aclProfileEntry 16 }

        aclProfileRuleSrcStartPort OBJECT-TYPE
        SYNTAX INTEGER (0..65535)
        MAX-ACCESS read-create
        STATUS current
        DESCRIPTION
        	"Profile rule source start port."
        ::= { aclProfileEntry 17 }

        aclProfileRuleSrcEndPort OBJECT-TYPE
        SYNTAX INTEGER (0..65535)
        MAX-ACCESS read-create
        STATUS current
        DESCRIPTION
        	"Profile rule source end port."
        ::= { aclProfileEntry 18 }

        aclProfileRuleDestStartPort OBJECT-TYPE
        SYNTAX INTEGER (0..65535)
        MAX-ACCESS read-create
        STATUS current
        DESCRIPTION
        	"Profile rule destination start port."
        ::= { aclProfileEntry 19 }

        aclProfileRuleDestEndPort OBJECT-TYPE
        SYNTAX INTEGER (0..65535)
        MAX-ACCESS read-create
        STATUS current
        DESCRIPTION
        	"Profile rule destination end port."
        ::= { aclProfileEntry 20 }

        aclProfileActionRate OBJECT-TYPE
        SYNTAX INTEGER (1..100032)
        MAX-ACCESS read-create
        STATUS current
        DESCRIPTION
        	"Profile action to replace to this rate."
        ::= { aclProfileEntry 21 }

        aclProfileActionrvlan OBJECT-TYPE
        SYNTAX INTEGER (1..4094)
        MAX-ACCESS read-create
        STATUS current
        DESCRIPTION
        	"Profile action to replace to this vlan."
       	::= { aclProfileEntry 22 }

        aclProfileActionrpri OBJECT-TYPE
        SYNTAX INTEGER (0..7)
        MAX-ACCESS read-create
        STATUS current
        DESCRIPTION
        	"Profile action to replace to this priority."
        ::= { aclProfileEntry 23 }

        aclProfileRowStatus OBJECT-TYPE
        SYNTAX RowStatus
        MAX-ACCESS read-create
        STATUS current
        DESCRIPTION
        	"The row status of the entry."
        ::= { aclProfileEntry 24 }
        
        aclProfileRuleSip OBJECT-TYPE
        SYNTAX IpAddress
        MAX-ACCESS read-create
        STATUS current
        DESCRIPTION
        	"Source IP."
        ::= { aclProfileEntry 25 }
        
        aclProfileRuleDip OBJECT-TYPE
        SYNTAX IpAddress
        MAX-ACCESS read-create
        STATUS current
        DESCRIPTION
        	"Destination IP."
        ::= { aclProfileEntry 26 }
        
        aclProfileRuleSport OBJECT-TYPE
        SYNTAX INTEGER (0..65535)
        MAX-ACCESS read-create
        STATUS current
        DESCRIPTION
        	"Source port."
        ::= { aclProfileEntry 27 }
        
        aclProfileRuleDport OBJECT-TYPE
        SYNTAX INTEGER (0..65535)
        MAX-ACCESS read-create
        STATUS current
        DESCRIPTION
        	"Destination port."
        ::= { aclProfileEntry 28 } 
        
        aclProfileRuleSrcIp6 OBJECT-TYPE
        SYNTAX InetAddress
        MAX-ACCESS read-create
        STATUS current
        DESCRIPTION
        	"srcip <ip6> for RuleNumber (21)."
        ::= { aclProfileEntry 29 } 
        
        aclProfileRuleDstIp6 OBJECT-TYPE
        SYNTAX InetAddress
        MAX-ACCESS read-create
        STATUS current
        DESCRIPTION
        	"dstip <ip6> for RuleNumber (21)."
        ::= { aclProfileEntry 30 } 
        
        aclProfileRuleSip6 OBJECT-TYPE
        SYNTAX InetAddress
        MAX-ACCESS read-create
        STATUS current
        DESCRIPTION
        	"sip <ip6> for RuleNumber (19), (22)."
        ::= { aclProfileEntry 31 } 
        
        aclProfileRuleDip6 OBJECT-TYPE
        SYNTAX InetAddress
        MAX-ACCESS read-create
        STATUS current
        DESCRIPTION
        	"dip <ip6> for RuleNumber (20), (23)."
        ::= { aclProfileEntry 32 }

                  
--------------------
-- vdslProfile
--------------------
	
        maxNumOfVdslLineProfiles OBJECT-TYPE
        SYNTAX INTEGER
        MAX-ACCESS read-only
        STATUS current
        DESCRIPTION
        	"The maximum number of VDSL line profiles supported by the system."
        ::= { vdslProfile 1 }

        maxNumOfVdslAlarmProfiles OBJECT-TYPE
        SYNTAX INTEGER
        MAX-ACCESS read-only
        STATUS current
        DESCRIPTION
        	"The maximum number of VDSL alarm profiles supported by the system."
        ::= { vdslProfile 2 }

-- vdslProfileTable

        vdslLineConfProfileExtendedTable OBJECT-TYPE
        SYNTAX SEQUENCE OF VdslLineConfProfileExtendedEntry
        MAX-ACCESS not-accessible
        STATUS current
        DESCRIPTION
                "This table contains information on the VDSL line profile extension configuration.
		This table is supported by R5.02 and later versions."
        ::= { vdslProfile 3 }

	vdslLineConfProfileExtendedEntry OBJECT-TYPE
        SYNTAX VdslLineConfProfileExtendedEntry
        MAX-ACCESS not-accessible
        STATUS current
        DESCRIPTION
		"An entry in vdslLineConfProfileExtendedTable."
        INDEX { vdslLineConfProfileName }
        ::= { vdslLineConfProfileExtendedTable 1 }

        VdslLineConfProfileExtendedEntry ::=
        	SEQUENCE {
			vdsl2LConfProfRaModeDs		INTEGER,
			vdsl2LConfProfRaModeUs		INTEGER,
			vdsl2LConfProfRaUsNrmDs		Unsigned32,
			vdsl2LConfProfRaUsNrmUs		Unsigned32,
			vdsl2LConfProfRaDsNrmDs		Unsigned32,
			vdsl2LConfProfRaDsNrmUs		Unsigned32,
			vdsl2LConfProfProfileName	DisplayString
           	}

        vdsl2LConfProfRaModeDs OBJECT-TYPE
	SYNTAX  INTEGER {
			manual(1),
			raInit(2),
			dynamicRa(3)
		}
	MAX-ACCESS read-write
	STATUS current
	DESCRIPTION
		"(RA-MODEds).
		The mode of operation of a rate-adaptive xTU-C in the transmit
		direction.  The parameter can take three values:
		manual(1),
		raInit(2),
		dynamicRa(3)."
	REFERENCE "ITU-T G.997.1, paragraph #7.3.1.4.1"
	DEFVAL { manual }
	::= { vdslLineConfProfileExtendedEntry 1 }

	vdsl2LConfProfRaModeUs OBJECT-TYPE
	SYNTAX  INTEGER {
			manual(1),
			raInit(2),
			dynamicRa(3)
		}
	MAX-ACCESS read-write
	STATUS current
	DESCRIPTION
		"(RA-MODEus).
		The mode of operation of a rate-adaptive xTU-R in the transmit
		direction.  The parameter can take three values:
		manual(1),
		raInit(2),
		dynamicRa(3)."
	REFERENCE "ITU-T G.997.1, paragraph #7.3.1.4.2"
	DEFVAL { manual }
	::= { vdslLineConfProfileExtendedEntry 2 }

	vdsl2LConfProfRaUsNrmDs OBJECT-TYPE
	SYNTAX Unsigned32(0..310)
	UNITS "0.1 dB"
	MAX-ACCESS read-write
	STATUS current
	DESCRIPTION
		"(RA-USNRMds).
		The Downstream Up-Shift Noise Margin value, to be used when
		xdsl2LConfProfRaModeDs is set to dynamicRa.  If the downstream
		noise margin is above this value and stays above it for
		more than the time specified by the xdsl2LConfProfRaUsTimeDs,
		the xTU-R shall attempt to increase the downstream net data
		rate.  The Downstream Up-shift Noise Margin ranges from 0 to
		310 units of 0.1 dB (Physical values are 0 to 31 dB)."
	REFERENCE "ITU-T G.997.1, paragraph #7.3.1.4.3"
	DEFVAL { 10 }
	::= { vdslLineConfProfileExtendedEntry 3 }

	vdsl2LConfProfRaUsNrmUs OBJECT-TYPE
	SYNTAX Unsigned32(0..310)
	UNITS "0.1 dB"
	MAX-ACCESS read-write
	STATUS current
	DESCRIPTION
		"(RA-USNRMus).
		The Upstream Up-Shift Noise Margin value, to be used when
		xdsl2LConfProfRaModeUs is set to dynamicRa.  If the upstream
		noise margin is above this value and stays above it for more 
		than the time specified by the xdsl2LConfProfRaUsTimeUs, the 
		xTU-C shall attempt to increase the upstream net data rate. 
		The Upstream Up-shift Noise Margin ranges from 0 to 310 units 
		of 0.1 dB (Physical values are 0 to 31 dB)."
	REFERENCE "ITU-T G.997.1, paragraph #7.3.1.4.4"
	DEFVAL { 10 }
	::= { vdslLineConfProfileExtendedEntry 4 }

	vdsl2LConfProfRaDsNrmDs OBJECT-TYPE
	SYNTAX Unsigned32(0..310)
	UNITS "0.1 dB"
	MAX-ACCESS read-write
	STATUS current
	DESCRIPTION
		"(RA-DSNRMds).
		The Downstream Down-Shift Noise Margin value, to be used when
		xdsl2LConfProfRaModeDs is set to dynamicRa.  If the downstream
		noise margin is below this value and stays below that for more
		than the time specified by the xdsl2LConfProfRaDsTimeDs, the
		xTU-R shall attempt to decrease the downstream net data rate.
		The Downstream Down-shift Noise Margin ranges from 0 to 310
		units of 0.1 dB (Physical values are 0 to 31 dB)."
	REFERENCE "ITU-T G.997.1, paragraph #7.3.1.4.7"
	DEFVAL { 10 }
	::= { vdslLineConfProfileExtendedEntry 5 }

	vdsl2LConfProfRaDsNrmUs OBJECT-TYPE
	SYNTAX Unsigned32(0..310)
	UNITS "0.1 dB"
	MAX-ACCESS read-write
	STATUS current
	DESCRIPTION
	"(RA-DSNRMus).
	The Upstream Downshift Noise Margin value, to be used when
	xdsl2LConfProfRaModeUs is set to dynamicRa.  If the upstream
	noise margin is below this value and stays below that for more
	than the time specified by the xdsl2LConfProfRaDsTimeUs, the
	xTU-C shall attempt to decrease the upstream net data rate.
	The Upstream Down-shift Noise Margin ranges from 0 to 310
	units of 0.1 dB (Physical values are 0 to 31 dB)."
	REFERENCE "ITU-T G.997.1, paragraph #7.3.1.4.8"
	DEFVAL { 10 }
	::= { vdslLineConfProfileExtendedEntry 6 } 
	
	vdsl2LConfProfProfileName OBJECT-TYPE
	SYNTAX DisplayString
	MAX-ACCESS read-only
	STATUS current
	DESCRIPTION
	""
	::= { vdslLineConfProfileExtendedEntry 7 }

 -- vdslLineAlarmConfProfileExtendedTable

        vdslLineAlarmConfProfileExtendedTable OBJECT-TYPE
        SYNTAX SEQUENCE OF VdslLineAlarmConfProfileExtendedEntry
        MAX-ACCESS not-accessible
        STATUS current
        DESCRIPTION
                "This table contains information on the VDSL line alarm profile extension configuration.
		This table is supported by R5.06 and later versions."
        ::= { vdslProfile 4 }

	vdslLineAlarmConfProfileExtendedEntry OBJECT-TYPE
        SYNTAX VdslLineAlarmConfProfileExtendedEntry
        MAX-ACCESS not-accessible
        STATUS current
        DESCRIPTION
		"An entry in vdslLineAlarmConfProfileExtendedTable."
        INDEX { vdslLineAlarmConfProfileName }
        ::= { vdslLineAlarmConfProfileExtendedTable 1 }

    VdslLineAlarmConfProfileExtendedEntry ::=
        SEQUENCE {
			vdslLAlarmConfProfProfileName	DisplayString
        }

    vdslLAlarmConfProfProfileName OBJECT-TYPE
	SYNTAX  DisplayString
	MAX-ACCESS read-only
	STATUS current
	DESCRIPTION
		""
	::= { vdslLineAlarmConfProfileExtendedEntry 1 }
	       
--------------------
-- voipProfile
--------------------

	sipProfile	OBJECT IDENTIFIER ::= { voipProfile 1 }
	h248Profile	OBJECT IDENTIFIER ::= { voipProfile 4 }

-- sip profile
        
        maxNumOfSipProfiles OBJECT-TYPE
        SYNTAX INTEGER
        MAX-ACCESS read-only
        STATUS current
        DESCRIPTION
        	"The maximum number of SIP profiles supported by the system."
        ::= { sipProfile 1 }
        
        sipProfileTable OBJECT-TYPE
        SYNTAX SEQUENCE OF SipProfileEntry
        MAX-ACCESS not-accessible
        STATUS current
        DESCRIPTION
                "This table includes SIP protocol related configuration.
                This table is supported by R4.01 and later versions."
        ::= { sipProfile 2 }

	sipProfileEntry OBJECT-TYPE
        SYNTAX SipProfileEntry
        MAX-ACCESS not-accessible
        STATUS current
        DESCRIPTION
		"An entry in sipProfileTable."
        INDEX { IMPLIED sipProfileName }
        ::= { sipProfileTable 1 }

        SipProfileEntry ::=
        	SEQUENCE {
			sipProfileName		DisplayString,
			sipProfileSipSvr	DisplayString,
			sipProfileRegSvr	DisplayString,
			sipProfileProxySvr	DisplayString,
			sipProfileSipPort	INTEGER,
			sipProfileRegSvrPort	INTEGER,
			sipProfileProxySvrPort	INTEGER,
			sipProfileUriType	INTEGER,
			sipProfilePbit		INTEGER,
			sipProfileDscp		INTEGER,
			sipProfileKeepAlive	INTEGER,
			sipProfileSe		INTEGER,
			sipProfilePrack		INTEGER,
			sipProfileRowStatus	RowStatus,
			sipProfileReSend	INTEGER, 
			sipProfileNonceCountKeep	INTEGER,
			sipProfileQopQuote	INTEGER,
			sipProfileRefertobracket	INTEGER,
			sipProfileRefertodot	INTEGER,
			sipProfileRtpStartPort	INTEGER,
			sipProfileRtpEndPort	INTEGER
           	}

        sipProfileName OBJECT-TYPE
        SYNTAX DisplayString (SIZE (1..31))
        MAX-ACCESS read-only
        STATUS current
        DESCRIPTION
                "This object is used by the SIP profile table in order to identify a row of this table."
        ::= { sipProfileEntry 1 }

        sipProfileSipSvr OBJECT-TYPE
        SYNTAX DisplayString
        MAX-ACCESS read-create
        STATUS current
        DESCRIPTION
                "IP used for SIP registration or SIP domain name."
        ::= { sipProfileEntry 2 }

	sipProfileRegSvr OBJECT-TYPE
        SYNTAX DisplayString
        MAX-ACCESS read-create
        STATUS current
        DESCRIPTION
                "Registration server IP or registration server domain name."
        ::= { sipProfileEntry 3 }
        
        sipProfileProxySvr OBJECT-TYPE
        SYNTAX DisplayString
        MAX-ACCESS read-create
        STATUS current
        DESCRIPTION
                "Proxy server IP or proxy server doamin name."
        ::= { sipProfileEntry 4 }
        
        sipProfileSipPort OBJECT-TYPE
        SYNTAX INTEGER (1025..65535)
        MAX-ACCESS read-create
        STATUS current
        DESCRIPTION
                "SIP UA port number."
        ::= { sipProfileEntry 5 }
        
        sipProfileRegSvrPort OBJECT-TYPE
        SYNTAX INTEGER (1025..65535)
        MAX-ACCESS read-create
        STATUS current
        DESCRIPTION
                "Registration server port number."
        ::= { sipProfileEntry 6 }
        
        sipProfileProxySvrPort OBJECT-TYPE
        SYNTAX INTEGER (1025..65535)
        MAX-ACCESS read-create
        STATUS current
        DESCRIPTION
                "Proxy server port number."
        ::= { sipProfileEntry 7 }
        
        sipProfileUriType OBJECT-TYPE
        SYNTAX INTEGER {
        		use-sip-uri(1),
        		use-tel-uri(2)
        	}
        MAX-ACCESS read-create
        STATUS current
        DESCRIPTION
                ""
        ::= { sipProfileEntry 8 }
        
        sipProfilePbit OBJECT-TYPE
        SYNTAX INTEGER (0..7)
        MAX-ACCESS read-create
        STATUS current
        DESCRIPTION
                "802.1p bit for SIP and RTP packet."
        ::= { sipProfileEntry 9 }
        
        sipProfileDscp OBJECT-TYPE
        SYNTAX INTEGER (0..63)
        MAX-ACCESS read-create
        STATUS current
        DESCRIPTION
                "DSCP for SIP and RTP packet."
        ::= { sipProfileEntry 10 }
        
        sipProfileKeepAlive OBJECT-TYPE
        SYNTAX INTEGER {
        		on(1),
        		off(2)
        	}
        MAX-ACCESS read-create
        STATUS current
        DESCRIPTION
                ""
        ::= { sipProfileEntry 11 }
        
        sipProfileSe OBJECT-TYPE
        SYNTAX INTEGER (90..65535)
        UNITS "second"
        MAX-ACCESS read-create
        STATUS current
        DESCRIPTION
                "Session expiration time in seconds."
        ::= { sipProfileEntry 12 }
        
        sipProfilePrack OBJECT-TYPE
        SYNTAX INTEGER {
        		on(1),
        		off(2)
        	}
        MAX-ACCESS read-create
        STATUS current
        DESCRIPTION
                ""
        ::= { sipProfileEntry 13 }
        
        sipProfileRowStatus OBJECT-TYPE
        SYNTAX RowStatus
        MAX-ACCESS read-create
        STATUS current
        DESCRIPTION
                "This object is used to create a new row or delete an existing row in the table."
        ::= { sipProfileEntry 14 }
        
        sipProfileReSend OBJECT-TYPE
        SYNTAX INTEGER
        MAX-ACCESS read-create
        STATUS current
        DESCRIPTION
                "resend factor of session expiration time. This MIB object is supported by R5.05 and later versions."
        ::= { sipProfileEntry 15 }

        sipProfileNonceCountKeep OBJECT-TYPE
        SYNTAX INTEGER {
        		on(1),
        		off(2)
        	}
        MAX-ACCESS read-create
        STATUS current
        DESCRIPTION
                "This MIB object is supported by R5.05 and later versions."
        ::= { sipProfileEntry 16 } 
        
        sipProfileQopQuote OBJECT-TYPE
        SYNTAX INTEGER {
        		on(1),
        		off(2)
        	}
        MAX-ACCESS read-create
        STATUS current
        DESCRIPTION
                "This MIB object is supported by R5.05 and later versions."
        ::= { sipProfileEntry 17 }    
        
        sipProfileRefertobracket OBJECT-TYPE
        SYNTAX INTEGER {
        		on(1),
        		off(2)
        	}
        MAX-ACCESS read-create
        STATUS current
        DESCRIPTION
                "This MIB object is supported by R5.05 and later versions."
        ::= { sipProfileEntry 18 }  
        
        sipProfileRefertodot OBJECT-TYPE
        SYNTAX INTEGER {
        		dot(1),
        		hex(2)
        	}
        MAX-ACCESS read-create
        STATUS current
        DESCRIPTION
                "This MIB object is supported by R5.05 and later versions."
        ::= { sipProfileEntry 19 }    
        
        sipProfileRtpStartPort OBJECT-TYPE
        SYNTAX INTEGER
        MAX-ACCESS read-create
        STATUS current
        DESCRIPTION
                "start of RTP port number. This MIB object is supported by R5.05 and later versions."
        ::= { sipProfileEntry 20 }   
        
        sipProfileRtpEndPort OBJECT-TYPE
        SYNTAX INTEGER
        MAX-ACCESS read-create
        STATUS current
        DESCRIPTION
                "end of RTP port number. This MIB object is supported by R5.05 and later versions."
        ::= { sipProfileEntry 21 }


-- sip call service profile

	maxNumOfSipCallSvcProfiles OBJECT-TYPE
        SYNTAX INTEGER
        MAX-ACCESS read-only
        STATUS current
        DESCRIPTION
        	"The maximum number of SIP call service profiles supported by the system."
        ::= { sipProfile 3 }
        
	sipCallSvcProfileTable OBJECT-TYPE
        SYNTAX SEQUENCE OF SipCallSvcProfileEntry
        MAX-ACCESS not-accessible
        STATUS current
        DESCRIPTION
                "This table includes SIP call service related configuration.
                This table is supported by R4.01 and later versions."
        ::= { sipProfile 4 }

	sipCallSvcProfileEntry OBJECT-TYPE
        SYNTAX SipCallSvcProfileEntry
        MAX-ACCESS not-accessible
        STATUS current
        DESCRIPTION
		"An entry in sipCallSvcProfileTable."
        INDEX { IMPLIED sipCallSvcProfileName }
        ::= { sipCallSvcProfileTable 1 }

        SipCallSvcProfileEntry ::=
        	SEQUENCE {
			sipCallSvcProfileName			DisplayString,
			sipCallSvcProfilePasswdOn		INTEGER,
			sipCallSvcProfilePasswd			DisplayString,
			sipCallSvcProfileNumberPlanOn		INTEGER,
			sipCallSvcProfileNumberPlanCc		DisplayString,
			sipCallSvcProfileNumberPlanNdc		DisplayString,
			sipCallSvcProfileNumberPlanTable	DisplayString,
			sipCallSvcProfileStateMask		INTEGER,
			sipCallSvcProfileDtmf			INTEGER,
			sipCallSvcProfileFax			INTEGER,
			sipCallSvcProfileRowStatus		RowStatus,
			sipCallSvcProfileKeypattern		DisplayString,
			sipCallSvcProfileRegTime		INTEGER,
			sipCallSvcProfileFlash			INTEGER,
			sipCallSvcProfileFlashPattern		DisplayString,
			sipCallSvcProfileReanswerTime		INTEGER,
			sipCallSvcProfileFirstDigit		INTEGER,
			sipCallSvcProfileInterdigit		INTEGER
           	}

        sipCallSvcProfileName OBJECT-TYPE
        SYNTAX DisplayString (SIZE (1..31))
        MAX-ACCESS read-only
        STATUS current
        DESCRIPTION
                "This object is used by the SIP call service profile table in order to identify a row of this table."
        ::= { sipCallSvcProfileEntry 1 }

        sipCallSvcProfilePasswdOn OBJECT-TYPE
        SYNTAX INTEGER {
        		on(1),
        		off(2)
        	}
        MAX-ACCESS read-create
        STATUS current
        DESCRIPTION
                "Password is necessary or not for SIP registration."
        ::= { sipCallSvcProfileEntry 2 }
        
        sipCallSvcProfilePasswd OBJECT-TYPE
        SYNTAX DisplayString (SIZE(1..31))
        MAX-ACCESS read-create
        STATUS current
        DESCRIPTION
                "SIP registration password."
        ::= { sipCallSvcProfileEntry 3 }
        
        sipCallSvcProfileNumberPlanOn OBJECT-TYPE
        SYNTAX INTEGER {
        		on(1),
        		off(2)
        	}
        MAX-ACCESS read-create
        STATUS current
        DESCRIPTION
                ""
        ::= { sipCallSvcProfileEntry 4 }
        
        sipCallSvcProfileNumberPlanCc OBJECT-TYPE
        SYNTAX DisplayString (SIZE(1..7))
        MAX-ACCESS read-create
        STATUS current
        DESCRIPTION
                "Country code, only digit 0..9 are allowed."
        ::= { sipCallSvcProfileEntry 5 }
        
        sipCallSvcProfileNumberPlanNdc OBJECT-TYPE
        SYNTAX DisplayString (SIZE(1..7))
        MAX-ACCESS read-create
        STATUS current
        DESCRIPTION
                "National destination code, only digit 0..9 are allowed."
        ::= { sipCallSvcProfileEntry 6 }
        
        sipCallSvcProfileNumberPlanTable OBJECT-TYPE
        SYNTAX DisplayString (SIZE(1..31))
        MAX-ACCESS read-create
        STATUS current
        DESCRIPTION
                "Numbering plan table name."
        ::= { sipCallSvcProfileEntry 7 }
        
        sipCallSvcProfileStateMask OBJECT-TYPE
        SYNTAX INTEGER
        MAX-ACCESS read-create
        STATUS current
        DESCRIPTION
                "Bit 1	reserved : reserved
		 Bit 2	callhold : call hold
		 Bit 3	callwait : call waiting
		 Bit 4	callreturn : call return
		 Bit 5	calltransfer : call transfer
		 Bit 6	clip : caller line identification presentation (Caller ID)
		 Bit 7	clir : caller line identification restriction
		 Bit 8	dnd : do not disturb
		 Bit 9  registration
		 Bit 10 localcall
		 Bit 11 mwi : message waiting indicator
		 Bit 12 cidcw : caller identity with call waiting
		 Bit 13 conference
		 Bit 14 callsvcmode : europe(0) usa(1)
		 Bit 15 on hook transfer
		 Bit 16 conference transfer"
        ::= { sipCallSvcProfileEntry 8 }
        
        sipCallSvcProfileDtmf OBJECT-TYPE
        SYNTAX INTEGER {
        		bypass(1),
        		rfc2833(2),
        		rfc2833like(3),
        		sipinfo(4),
        		plaintext(5)
        	}
        MAX-ACCESS read-create
        STATUS current
        DESCRIPTION
                "dtmf bypass : bypass DTMF tone
		 dtmf rfc2833 : DTMF tone relay according to RFC2833
		 dtmf rfc2833like : DTMF tone relay by SIP INFO message, but RFC2833 payload
		 dtmf sipinfo : DTMF tone relay by SIP INFO signal message
		 dtmf plaintext : DTMF tone relay by SIP INFO plain text message"
        ::= { sipCallSvcProfileEntry 9 }
        
        sipCallSvcProfileFax OBJECT-TYPE
        SYNTAX INTEGER {
        		g711(1),
        		t38(2),
        		t38rtp(3)
        	}
        MAX-ACCESS read-create
        STATUS current
        DESCRIPTION
                "fax g711 : FAX service pass through by ITU-T G.711
		 fax t38 : FAX service by ITU-T T.38 UDP
		 fax t38rtp : FAX service by ITU-T T.38 RTP"
        ::= { sipCallSvcProfileEntry 10 }
        
        sipCallSvcProfileRowStatus OBJECT-TYPE
        SYNTAX RowStatus
        MAX-ACCESS read-create
        STATUS current
        DESCRIPTION
                "This object is used to create a new row or delete an existing row in the table."
        ::= { sipCallSvcProfileEntry 11 }
        
        sipCallSvcProfileKeypattern OBJECT-TYPE
        SYNTAX DisplayString (SIZE(1..31))
        MAX-ACCESS read-create
        STATUS current
        DESCRIPTION
                "Key pattern table name. This object is supported by R5.01 and later versions."
        ::= { sipCallSvcProfileEntry 12 }

	sipCallSvcProfileRegTime OBJECT-TYPE
        SYNTAX INTEGER (120..65535)
        UNITS "seconds"
        MAX-ACCESS read-create
        STATUS current
        DESCRIPTION
                "Registration expiration time in seconds."
        ::= { sipCallSvcProfileEntry 13 }
        
        sipCallSvcProfileFlash OBJECT-TYPE
        SYNTAX INTEGER {
        		invite(1),
        		rfc2833(2),
        		rfc2833like(3),
        		sipinfo1(4),
        		sipinfo2(5),
        		sipinfo3(6),
        		sipinfo4(7),
        		sipinfo5(8),
        		sipinfo6(9)
        	}
        MAX-ACCESS read-create
        STATUS current
        DESCRIPTION
                "flash invite : send SIP INVITE message
		 flash rfc2833 : flash relay according to RFC2833
		 flash rfc2833like : flash relay by SIP INFO message, but RFC2833 payload
		 flash sipinfo1 : flash relay by SIP INFO signal=16 message
		 flash sipinfo2 : flash relay by SIP INFO signal=hf message
		 flash sipinfo3 : flash relay by SIP INFO signal=hook-flash message
		 flash sipinfo4 : flash relay by SIP INFO plain text message
		 flash sipinfo5 : flash relay by multiple SIP INFO signal messages and
		                   signal content come from specified pattern string
		 flash sipinfo6 : flash relay by SIP INFO specified information message"
        ::= { sipCallSvcProfileEntry 14 }
        
        sipCallSvcProfileFlashPattern OBJECT-TYPE
        SYNTAX DisplayString
        MAX-ACCESS read-create
        STATUS current
        DESCRIPTION
                ""
        ::= { sipCallSvcProfileEntry 15 }
        
        sipCallSvcProfileReanswerTime OBJECT-TYPE
        SYNTAX INTEGER
        UNITS "seconds"
        MAX-ACCESS read-create
        STATUS current
        DESCRIPTION
                "Reanswer time. The time period after user hangs up and before call is disconnected."
        ::= { sipCallSvcProfileEntry 16 } 
        
        sipCallSvcProfileFirstDigit OBJECT-TYPE
        SYNTAX INTEGER
        MAX-ACCESS read-create
        STATUS current
        DESCRIPTION
                "first digit timeout. This MIB object is supported by R5.05 and later versions."
        ::= { sipCallSvcProfileEntry 17 }
        
        sipCallSvcProfileInterdigit OBJECT-TYPE
        SYNTAX INTEGER
        MAX-ACCESS read-create
        STATUS current
        DESCRIPTION
                "inter digit timeout. This MIB object is supported by R5.05 and later versions."
        ::= { sipCallSvcProfileEntry 18 }
        
-- sip call service profile local help table

	sipCallSvcProfileLocalHelpTable OBJECT-TYPE
        SYNTAX SEQUENCE OF SipCallSvcProfileLocalHelpEntry
        MAX-ACCESS not-accessible
        STATUS current
        DESCRIPTION
                "This table is supported by R5.01 and later versions."
        ::= { sipProfile 5 }

	sipCallSvcProfileLocalHelpEntry OBJECT-TYPE
        SYNTAX SipCallSvcProfileLocalHelpEntry
        MAX-ACCESS not-accessible
        STATUS current
        DESCRIPTION
		"An entry in sipCallSvcProfileLocalHelpTable."
        INDEX { sipCallSvcProfileName, sipCallSvcProfileLocalHelpIndex  }
        ::= { sipCallSvcProfileLocalHelpTable 1 }

        SipCallSvcProfileLocalHelpEntry ::=
        	SEQUENCE {
			sipCallSvcProfileLocalHelpIndex  	INTEGER,
			sipCallSvcProfileLocalHelpTableName	DisplayString,
			sipCallSvcProfileLocalHelpTableTel	DisplayString
           	}

        sipCallSvcProfileLocalHelpIndex OBJECT-TYPE
        SYNTAX INTEGER (1..8)
        MAX-ACCESS read-only
        STATUS current
        DESCRIPTION
                "Index number."
        ::= { sipCallSvcProfileLocalHelpEntry 1 }
        
        sipCallSvcProfileLocalHelpTableName OBJECT-TYPE
        SYNTAX DisplayString (SIZE(1..31))
        MAX-ACCESS read-write
        STATUS current
        DESCRIPTION
                "Local help table name."
        ::= { sipCallSvcProfileLocalHelpEntry 2 }
        
        sipCallSvcProfileLocalHelpTableTel OBJECT-TYPE
        SYNTAX DisplayString (SIZE(1..15))
        MAX-ACCESS read-write
        STATUS current
        DESCRIPTION
                "Local help telephone number. Only digit characters are allowed.
                Note that sipCallSvcProfileLocalHelpTableName and sipCallSvcProfileLocalHelpTableTel
                must be set sequentially."
        ::= { sipCallSvcProfileLocalHelpEntry 3 }

-- sip dialplan profile

	maxNumOfSipDialPlanProfiles OBJECT-TYPE
        SYNTAX INTEGER
        MAX-ACCESS read-only
        STATUS current
        DESCRIPTION
        	"The maximum number of SIP dial plan profiles supported by the system."
        ::= { sipProfile 6 }
        
	sipDialPlanProfileTable OBJECT-TYPE
        SYNTAX SEQUENCE OF SipDialPlanProfileEntry
        MAX-ACCESS not-accessible
        STATUS current
        DESCRIPTION
                "Configure dial plan related configuration of specified profile.
                This table is supported by R5.01 and later versions."
        ::= { sipProfile 7 }

	sipDialPlanProfileEntry OBJECT-TYPE
        SYNTAX SipDialPlanProfileEntry
        MAX-ACCESS not-accessible
        STATUS current
        DESCRIPTION
		"An entry in sipDialPlanProfileTable."
        INDEX { sipDialPlanProfileName, sipDialPlanProfileIndex  }
        ::= { sipDialPlanProfileTable 1 }

        SipDialPlanProfileEntry ::=
        	SEQUENCE {
			sipDialPlanProfileName  		DisplayString,
			sipDialPlanProfileIndex			INTEGER,
			sipDialPlanProfileDialPlanTableName	DisplayString,
			sipDialPlanProfileRowStatus		RowStatus
           	}

        sipDialPlanProfileName OBJECT-TYPE
        SYNTAX DisplayString (SIZE(1..31))
        MAX-ACCESS read-only
        STATUS current
        DESCRIPTION
                "Profile name."
        ::= { sipDialPlanProfileEntry 1 }
        
        sipDialPlanProfileIndex OBJECT-TYPE
        SYNTAX INTEGER (1..16)
        MAX-ACCESS read-only
        STATUS current
        DESCRIPTION
                "Index number. 1-32 means dialplan pattern, 255 means default SIP server profile name"
        ::= { sipDialPlanProfileEntry 2 }
        
        sipDialPlanProfileDialPlanTableName OBJECT-TYPE
        SYNTAX DisplayString (SIZE(1..31))
        MAX-ACCESS read-write
        STATUS current
        DESCRIPTION
                "Dial plan table name. 1-32 means dialplan pattern, 255 means default SIP server profile name"
        ::= { sipDialPlanProfileEntry 3 }
        
        sipDialPlanProfileRowStatus OBJECT-TYPE
        SYNTAX RowStatus
        MAX-ACCESS read-create
        STATUS current
        DESCRIPTION
                "This object is used to create a new row or delete an existing row in the table."
        ::= { sipDialPlanProfileEntry 4 } 
         
-- h248 profile
        
        maxNumOfH248Profiles OBJECT-TYPE
        SYNTAX INTEGER
        MAX-ACCESS read-only
        STATUS current
        DESCRIPTION
        	"The maximum number of H.248 profiles supported by the system."
        ::= { h248Profile 1 }
        
        h248ProfileTable OBJECT-TYPE
        SYNTAX SEQUENCE OF H248ProfileEntry
        MAX-ACCESS not-accessible
        STATUS current
        DESCRIPTION
                "This table includes H.248 protocol related configuration.
                This table is supported by R5.01 and later versions."
        ::= { h248Profile 2 }

	h248ProfileEntry OBJECT-TYPE
        SYNTAX H248ProfileEntry
        MAX-ACCESS not-accessible
        STATUS current
        DESCRIPTION
		"An entry in h248ProfileTable."
        INDEX { IMPLIED h248ProfileName }
        ::= { h248ProfileTable 1 }

        H248ProfileEntry ::=
        	SEQUENCE {
			h248ProfileName		DisplayString,
			h248ProfileMgc		DisplayString,
			h248ProfileMgcPort	INTEGER,
			h248ProfileMgc2On	INTEGER,
			h248ProfileMgc2		DisplayString,
			h248ProfileMgc2Port	INTEGER,
			h248ProfileTransport	INTEGER,
			h248ProfileEncode	INTEGER,
			h248ProfilePbit		INTEGER,
			h248ProfileDscp		INTEGER,
			h248ProfileRowStatus	RowStatus,
			h248ProfileSoftswitch	INTEGER,
			h248ProfileInactivityTimer	INTEGER,
			h248ProfilePrefixName		DisplayString,
			h248ProfileRtpPortStart	INTEGER,
			h248ProfileRtpPortEnd	INTEGER,
			h248ProfileInitRetranTime	INTEGER,
			h248ProfileMinRetranTime	INTEGER,
			h248ProfileMaxRetranTime	INTEGER,
			h248ProfileRetranWindow	INTEGER,
			h248ProfileStartTimeout	INTEGER,
			h248ProfileShortTimeout	INTEGER,
			h248ProfileLongTimeout	INTEGER,
			h248ProfileVBD	INTEGER,
			h248ProfileSuffixStartNum	DisplayString,
			h248ProfileSuffixSuffixLen	INTEGER,
			h248ProfileRFC2833	INTEGER,
			h248ProfileRFC2833PT	INTEGER,
			h248ProfileT38	INTEGER,
			h248ProfileForceVersion	INTEGER,
			h248ProfileLocalcall	INTEGER,
			h248ProfileCallthrough	INTEGER
           	}

        h248ProfileName OBJECT-TYPE
        SYNTAX DisplayString (SIZE (1..31))
        MAX-ACCESS read-only
        STATUS current
        DESCRIPTION
                "This object is used by the H.248 profile table in order to identify a row of this table."
        ::= { h248ProfileEntry 1 }

        h248ProfileMgc OBJECT-TYPE
        SYNTAX DisplayString (SIZE(1..63))
        MAX-ACCESS read-create
        STATUS current
        DESCRIPTION
                "MGC IP or domain name."
        ::= { h248ProfileEntry 2 }
        
        h248ProfileMgcPort OBJECT-TYPE
        SYNTAX INTEGER (1025..65535)
        MAX-ACCESS read-create
        STATUS current
        DESCRIPTION
                "MGC port number."
        ::= { h248ProfileEntry 3 }
        
        h248ProfileMgc2On OBJECT-TYPE
        SYNTAX INTEGER {
        		on(1),
        		off(2)
        	}
        MAX-ACCESS read-create
        STATUS current
        DESCRIPTION
                "Secondary MGC on/off."
        ::= { h248ProfileEntry 4 }
        
        h248ProfileMgc2 OBJECT-TYPE
        SYNTAX DisplayString
        MAX-ACCESS read-create
        STATUS current
        DESCRIPTION
                "Secondary MGC IP or domain name."
        ::= { h248ProfileEntry 5 }
        
        h248ProfileMgc2Port OBJECT-TYPE
        SYNTAX INTEGER (1025..65535)
        MAX-ACCESS read-create
        STATUS current
        DESCRIPTION
                "Secondary MGC port."
        ::= { h248ProfileEntry 6 }
        
        h248ProfileTransport OBJECT-TYPE
        SYNTAX INTEGER {
        		udp(1),
        		tcp(2)
        	}
        MAX-ACCESS read-create
        STATUS current
        DESCRIPTION
                "Transport protocol."
        ::= { h248ProfileEntry 7 }
        
        h248ProfileEncode OBJECT-TYPE
        SYNTAX INTEGER {
        		long(1),
        		short(2)
        	}
        MAX-ACCESS read-create
        STATUS current
        DESCRIPTION
                "H.248 coding type."
        ::= { h248ProfileEntry 8 }
        
        h248ProfilePbit OBJECT-TYPE
        SYNTAX INTEGER (0..7)
        MAX-ACCESS read-create
        STATUS current
        DESCRIPTION
                "802.1p bit for H.248 and RTP packet."
        ::= { h248ProfileEntry 9 }
        
        h248ProfileDscp OBJECT-TYPE
        SYNTAX INTEGER (0..63)
        MAX-ACCESS read-create
        STATUS current
        DESCRIPTION
                "DSCP for H.248 and RTP packet."
        ::= { h248ProfileEntry 10 }
        
        h248ProfileRowStatus OBJECT-TYPE
        SYNTAX RowStatus
        MAX-ACCESS read-create
        STATUS current
        DESCRIPTION
                "This object is used to create a new row or delete an existing row in the table."
        ::= { h248ProfileEntry 11 } 
        
        h248ProfileSoftswitch OBJECT-TYPE
        SYNTAX INTEGER {
        		defval(1),
        		zxss10-ss(2),
        		nortel-cs1500(3),
        		nortel-cs2000(4),
        		huawei-soft3000(5),
        		alu-5020(6),
        		nsn(7),
        		iskratel(8),
        		alu-5060(9)
        	}
        MAX-ACCESS read-create
        STATUS current
        DESCRIPTION
                "This MIB object is supported by R5.06 and later versions."
        ::= { h248ProfileEntry 12 }

        h248ProfileInactivityTimer OBJECT-TYPE
        SYNTAX INTEGER (0..65535)
        MAX-ACCESS read-create
        STATUS current
        DESCRIPTION
                "This MIB object is supported by R5.06 and later versions."
        ::= { h248ProfileEntry 13 }
        
        h248ProfilePrefixName OBJECT-TYPE
        SYNTAX DisplayString
        MAX-ACCESS read-create
        STATUS current
        DESCRIPTION
                "ephemeral termination prefix, up to 31 characters.
                This MIB object is supported by R5.06 and later versions."
        ::= { h248ProfileEntry 14 }
        
        h248ProfileRtpPortStart OBJECT-TYPE
        SYNTAX INTEGER 
        MAX-ACCESS read-create
        STATUS current
        DESCRIPTION
                "start port of RTP 4000 ~ 64000
                This MIB object is supported by R5.06 and later versions."
        ::= { h248ProfileEntry 15 }
        
        h248ProfileRtpPortEnd OBJECT-TYPE
        SYNTAX INTEGER 
        MAX-ACCESS read-create
        STATUS current
        DESCRIPTION
                "end port of RTP 5000 ~ 65000
                This MIB object is supported by R5.06 and later versions."
        ::= { h248ProfileEntry 16 }
        
        h248ProfileInitRetranTime OBJECT-TYPE
        SYNTAX INTEGER 
        MAX-ACCESS read-create
        STATUS current
        DESCRIPTION
                "init retransmit time 100 ~ 20000 ms
                This MIB object is supported by R5.06 and later versions."
        ::= { h248ProfileEntry 17 }
        
        h248ProfileMinRetranTime OBJECT-TYPE
        SYNTAX INTEGER 
        MAX-ACCESS read-create
        STATUS current
        DESCRIPTION
                "min retransmit time 100 ~ 1000 ms
                This MIB object is supported by R5.06 and later versions."
        ::= { h248ProfileEntry 18 }
        
        h248ProfileMaxRetranTime OBJECT-TYPE
        SYNTAX INTEGER 
        MAX-ACCESS read-create
        STATUS current
        DESCRIPTION
                "max retransmit time 1000 ~ 20000 ms
                This MIB object is supported by R5.06 and later versions."
        ::= { h248ProfileEntry 19 }
        
        h248ProfileRetranWindow OBJECT-TYPE
        SYNTAX INTEGER 
        MAX-ACCESS read-create
        STATUS current
        DESCRIPTION
                "retransmit window 1000 ~ 60000 ms
                This MIB object is supported by R5.06 and later versions."
        ::= { h248ProfileEntry 20 }
        
        h248ProfileStartTimeout OBJECT-TYPE
        SYNTAX INTEGER 
        MAX-ACCESS read-create
        STATUS current
        DESCRIPTION
                "start timeout 0 ~ 99 seconds
                This MIB object is supported by R5.06 and later versions."
        ::= { h248ProfileEntry 21 }
        
        h248ProfileShortTimeout OBJECT-TYPE
        SYNTAX INTEGER 
        MAX-ACCESS read-create
        STATUS current
        DESCRIPTION
                "short timeout 1 ~ 99 seconds
                This MIB object is supported by R5.06 and later versions."
        ::= { h248ProfileEntry 22 }
        
        h248ProfileLongTimeout OBJECT-TYPE
        SYNTAX INTEGER 
        MAX-ACCESS read-create
        STATUS current
        DESCRIPTION
                "long timeout 1 ~ 99 seconds
                This MIB object is supported by R5.06 and later versions."
        ::= { h248ProfileEntry 23 }
        
        h248ProfileVBD OBJECT-TYPE
        SYNTAX INTEGER {
        		on(1),
        		off(2)
        	}
        MAX-ACCESS read-create
        STATUS current
        DESCRIPTION
                "VBD mode support enable/disable
                This MIB object is supported by R5.06 and later versions."
        ::= { h248ProfileEntry 24 } 
        
        h248ProfileSuffixStartNum OBJECT-TYPE
        SYNTAX DisplayString
        MAX-ACCESS read-create
        STATUS current
        DESCRIPTION
                "suffix start number 1 ~ 15.
                This MIB object is supported by R5.06 and later versions."
        ::= { h248ProfileEntry 25 } 
        
        h248ProfileSuffixSuffixLen OBJECT-TYPE
        SYNTAX INTEGER 
        MAX-ACCESS read-create
        STATUS current
        DESCRIPTION
                "suffix length 0 ~ 15
                This MIB object is supported by R5.06 and later versions."
        ::= { h248ProfileEntry 26 }
        
        h248ProfileRFC2833 OBJECT-TYPE
        SYNTAX INTEGER {
        		on(1),
        		off(2)
        	}
        MAX-ACCESS read-create
        STATUS current
        DESCRIPTION
                "rfc2833 mode support enable/disable
                This MIB object is supported by R5.06 and later versions."
        ::= { h248ProfileEntry 27 }
        
        h248ProfileRFC2833PT OBJECT-TYPE
        SYNTAX INTEGER 
        MAX-ACCESS read-create
        STATUS current
        DESCRIPTION
                "rfc2833 payload type 96~127
                This MIB object is supported by R5.06 and later versions."
        ::= { h248ProfileEntry 28 }
        
        h248ProfileT38 OBJECT-TYPE
        SYNTAX INTEGER {
        		on(1),
        		off(2)
        	}
        MAX-ACCESS read-create
        STATUS current
        DESCRIPTION
                "fax t.38 mode support enable/disable
                This MIB object is supported by R5.06 and later versions."
        ::= { h248ProfileEntry 29 }  
        
        h248ProfileForceVersion OBJECT-TYPE
        SYNTAX INTEGER {
        		on(1),
        		off(2)
        	}
        MAX-ACCESS read-create
        STATUS current
        DESCRIPTION
                "force using h.248 version 1
                This MIB object is supported by R5.06 and later versions."
        ::= { h248ProfileEntry 30 } 
        
        h248ProfileLocalcall OBJECT-TYPE
        SYNTAX INTEGER {
        		on(1),
        		off(2)
        	}
        MAX-ACCESS read-write
        STATUS current
        DESCRIPTION
                "Turn on the localcall utility
                This MIB object is supported by R5.08 and later versions."
        ::= { h248ProfileEntry 31 }
        
        h248ProfileCallthrough OBJECT-TYPE
        SYNTAX INTEGER {
        		on(1),
        		off(2)
        	}
        MAX-ACCESS read-write
        STATUS current
        DESCRIPTION
                "Turn on the callthrough utility
                This MIB object is supported by R5.08 and later versions."
        ::= { h248ProfileEntry 32 }
                
-- dsp profile

	maxNumOfDspProfiles OBJECT-TYPE
        SYNTAX INTEGER
        MAX-ACCESS read-only
        STATUS current
        DESCRIPTION
        	"The maximum number of DSP profiles supported by the system."
        ::= { voipProfile 2 }
        
	dspProfileTable OBJECT-TYPE
        SYNTAX SEQUENCE OF DspProfileEntry
        MAX-ACCESS not-accessible
        STATUS current
        DESCRIPTION
                "This table includes DSP related configuration. This table is supported by R4.01 and later versions."
        ::= { voipProfile 3 }

	dspProfileEntry OBJECT-TYPE
        SYNTAX DspProfileEntry
        MAX-ACCESS not-accessible
        STATUS current
        DESCRIPTION
		"An entry in dspProfileTable."
        INDEX { IMPLIED dspProfileName }
        ::= { dspProfileTable 1 }

        DspProfileEntry ::=
        	SEQUENCE {
			dspProfileName			DisplayString,
			dspProfileCodec			INTEGER,
			dspProfilePlayBufferMinDelay	INTEGER,
			dspProfilePlayBufferMaxDelay	INTEGER,
			dspProfileEchoTail		INTEGER,
			dspProfileRowStatus		RowStatus,
			dspProfileEchocancelOn		INTEGER,
			dspProfileVadOn			INTEGER,
			dspProfileg711vpi		INTEGER,
			dspProfileg723vpi		INTEGER,
			dspProfileg726vpi		INTEGER,
			dspProfileg729vpi		INTEGER,
			dspProfilePbit			INTEGER,
			dspProfileDscp			INTEGER,
			dspProfileCodecPriority	DisplayString
           	}

        dspProfileName OBJECT-TYPE
        SYNTAX DisplayString (SIZE (1..31))
        MAX-ACCESS read-only
        STATUS current
        DESCRIPTION
                "This object is used by the DSP profile table in order to identify a row of this table."
        ::= { dspProfileEntry 1 }

        dspProfileCodec OBJECT-TYPE
        SYNTAX INTEGER
        MAX-ACCESS read-create
        STATUS current
        DESCRIPTION
                "Bit 1: g711a
                 Bit 2: g711mu
                 Bit 3: g723
                 Bit 4: g726-16
                 Bit 5: g726-24
                 Bit 6: g726-32
                 Bit 7: g726-40
                 Bit 8: g729ab"
        ::= { dspProfileEntry 2 }
        
        dspProfilePlayBufferMinDelay OBJECT-TYPE
        SYNTAX INTEGER (10..500)
        UNITS "millisecond"
        MAX-ACCESS read-create
        STATUS current
        DESCRIPTION
                "Play buffer minimum delay in milliseconds.
                It should be less than or equal to dspProfilePlayBufferMaxDelay."
        ::= { dspProfileEntry 3 }
        
        dspProfilePlayBufferMaxDelay OBJECT-TYPE
        SYNTAX INTEGER (10..500)
        UNITS "millisecond"
        MAX-ACCESS read-create
        STATUS current
        DESCRIPTION
                "Play buffer maximum delay in milliseconds.
                It should be greater than or equal to dspProfilePlayBufferMinDelay."
        ::= { dspProfileEntry 4 }
        
        dspProfileEchoTail OBJECT-TYPE
        SYNTAX INTEGER {
        		echotail-8(1),
        		echotail-16(2),
        		echotail-32(3),
        		echotail-128(4)
        	}
        MAX-ACCESS read-create
        STATUS current
        DESCRIPTION
                "Echo cancellation echo tail period in milliseconds."
        ::= { dspProfileEntry 5 }
        
        dspProfileRowStatus OBJECT-TYPE
        SYNTAX RowStatus
        MAX-ACCESS read-create
        STATUS current
        DESCRIPTION
                "This object is used to create a new row or delete an existing row in the table."
        ::= { dspProfileEntry 6 }

	dspProfileEchocancelOn OBJECT-TYPE
        SYNTAX INTEGER {
        		on(1),
        		off(2)
        	}
        MAX-ACCESS read-create
        STATUS current
        DESCRIPTION
                "Echo cancellation."
        ::= { dspProfileEntry 7 }
        
        dspProfileVadOn OBJECT-TYPE
        SYNTAX INTEGER {
        		on(1),
        		off(2)
        	}
        MAX-ACCESS read-create
        STATUS current
        DESCRIPTION
                "voice activity detection."
        ::= { dspProfileEntry 8 }
        
        dspProfileg711vpi OBJECT-TYPE
        SYNTAX INTEGER {
        		interval-10ms(1),
        		interval-20ms(2),
        		interval-30ms(3),
        		interval-40ms(4)
        	}
        MAX-ACCESS read-create
        STATUS current
        DESCRIPTION
                "G.711 voice packet interval time in milliseconds."
        ::= { dspProfileEntry 9 }
        
        dspProfileg723vpi OBJECT-TYPE
        SYNTAX INTEGER {
        		interval-30ms(1),
        		interval-60ms(2)
        	}
        MAX-ACCESS read-create
        STATUS current
        DESCRIPTION
                "G.723 voice packet interval time in milliseconds."
        ::= { dspProfileEntry 10 }
        
        dspProfileg726vpi OBJECT-TYPE
        SYNTAX INTEGER {
        		interval-10ms(1),
        		interval-20ms(2),
        		interval-30ms(3),
        		interval-40ms(4)
        	}
        MAX-ACCESS read-create
        STATUS current
        DESCRIPTION
                "G.726 voice packet interval time in milliseconds."
        ::= { dspProfileEntry 11 }
        
        dspProfileg729vpi OBJECT-TYPE
        SYNTAX INTEGER {
        		interval-10ms(1),
        		interval-20ms(2),
        		interval-30ms(3),
        		interval-40ms(4),
        		interval-50ms(5),
        		interval-60ms(6)
        	}
        MAX-ACCESS read-create
        STATUS current
        DESCRIPTION
                "G.729 voice packet interval time in milliseconds."
        ::= { dspProfileEntry 12 }

        dspProfilePbit OBJECT-TYPE
        SYNTAX INTEGER (0..7)
        MAX-ACCESS read-create
        STATUS current
        DESCRIPTION
                ""
        ::= { dspProfileEntry 13 }
        
        dspProfileDscp OBJECT-TYPE
        SYNTAX INTEGER (0..63)
        MAX-ACCESS read-create
        STATUS current
        DESCRIPTION
                ""
        ::= { dspProfileEntry 14 } 
        
        dspProfileCodecPriority OBJECT-TYPE
        SYNTAX DisplayString (SIZE (1..31))
        MAX-ACCESS read-create
        STATUS current
        DESCRIPTION
                "every octet mean a codec, the order of octets means codec priority.
              0x1: g711a
              0x2: g711mu
              0x3: g723
              0x4: g726-16
              0x5: g726-24
              0x6: g726-32
              0x7: g726-40
              0x8: g729ab
              "
        ::= { dspProfileEntry 15 }

        
--------------------
-- ipqosProfile
--------------------

-- ipqosProfileTable

	maxNumOfIpqosProfiles OBJECT-TYPE
        SYNTAX INTEGER
        MAX-ACCESS read-only
        STATUS current
        DESCRIPTION
        	"The maximum number of IPQOS profiles supported by the system."
        ::= { ipqosProfile 1 }
        
	ipqosProfileTable OBJECT-TYPE
        SYNTAX SEQUENCE OF IpqosProfileEntry
        MAX-ACCESS not-accessible
        STATUS current
        DESCRIPTION
                "This table includes IPQOS related configuration."
        ::= { ipqosProfile 2 }

	ipqosProfileEntry OBJECT-TYPE
        SYNTAX IpqosProfileEntry
        MAX-ACCESS not-accessible
        STATUS current
        DESCRIPTION
		"An entry in ipqosProfileTable."
        INDEX { ipqosProfileName , ipqosProfileNumOfQueue }
        ::= { ipqosProfileTable 1 }

        IpqosProfileEntry ::=
        	SEQUENCE {
			ipqosProfileName		DisplayString,
			ipqosProfileNumOfQueue		INTEGER,
			ipqosProfileRowStatus		RowStatus
           	}

        ipqosProfileName OBJECT-TYPE
        SYNTAX DisplayString (SIZE (1..31))
        MAX-ACCESS read-only
        STATUS current
        DESCRIPTION
                "This object is used by the IPQOS profile table in order to identify a row of this table."
        ::= { ipqosProfileEntry 1 }

        ipqosProfileNumOfQueue OBJECT-TYPE
        SYNTAX INTEGER (1..8)
        MAX-ACCESS read-only
        STATUS current
        DESCRIPTION
                "The number of IPQOS queues."
        ::= { ipqosProfileEntry 2 }
        
        ipqosProfileRowStatus OBJECT-TYPE
        SYNTAX RowStatus
        MAX-ACCESS read-create
        STATUS current
        DESCRIPTION
                "This object is used to create a new row or delete an existing row in the table."
        ::= { ipqosProfileEntry 3 }
	
-- ipqosProfileQueueTable

	ipqosProfileQueueTable OBJECT-TYPE
        SYNTAX SEQUENCE OF IpqosProfileQueueEntry
        MAX-ACCESS not-accessible
        STATUS current
        DESCRIPTION
                "This table includes IPQOS queue related configuration."
        ::= { ipqosProfile 3 }

	ipqosProfileQueueEntry OBJECT-TYPE
        SYNTAX IpqosProfileQueueEntry
        MAX-ACCESS not-accessible
        STATUS current
        DESCRIPTION
		"An entry in ipqosProfileQueueTable."
        INDEX { ipqosProfileName , ipqosProfileQueueIndex }
        ::= { ipqosProfileQueueTable 1 }

        IpqosProfileQueueEntry ::=
        	SEQUENCE {
			ipqosProfileQueueIndex		INTEGER,
			ipqosProfileQueuePIR		INTEGER,
			ipqosProfileQueueCIR		INTEGER,
			ipqosProfileQueuePBS		INTEGER,
			ipqosProfileQueueCBS		INTEGER,
			ipqosProfileQueueLevel		INTEGER,
			ipqosProfileQueueWeight		INTEGER
           	}

        ipqosProfileQueueIndex OBJECT-TYPE
        SYNTAX INTEGER
        MAX-ACCESS read-only
        STATUS current
        DESCRIPTION
                "IPQOS queue index."
        ::= { ipqosProfileQueueEntry 1 }

        ipqosProfileQueuePIR OBJECT-TYPE
        SYNTAX INTEGER
        UNITS "Kbps"
        MAX-ACCESS read-write
        STATUS current
        DESCRIPTION
                "Peak rate."
        ::= { ipqosProfileQueueEntry 2 }
        
        ipqosProfileQueueCIR OBJECT-TYPE
        SYNTAX INTEGER
        UNITS "Kbps"
        MAX-ACCESS read-write
        STATUS current
        DESCRIPTION
                "Commited rate."
        ::= { ipqosProfileQueueEntry 3 }
        
        ipqosProfileQueuePBS OBJECT-TYPE
        SYNTAX INTEGER
        UNITS "byte"
        MAX-ACCESS read-write
        STATUS current
        DESCRIPTION
                "Peak burst size."
        ::= { ipqosProfileQueueEntry 4 }
        
        ipqosProfileQueueCBS OBJECT-TYPE
        SYNTAX INTEGER
        UNITS "byts"
        MAX-ACCESS read-write
        STATUS current
        DESCRIPTION
                "Commited burst size."
        ::= { ipqosProfileQueueEntry 5 }

        ipqosProfileQueueLevel OBJECT-TYPE
        SYNTAX INTEGER (0..7)
        MAX-ACCESS read-write
        STATUS current
        DESCRIPTION
                "Queue level."
        ::= { ipqosProfileQueueEntry 6 }
        
        ipqosProfileQueueWeight OBJECT-TYPE
        SYNTAX INTEGER (1..127)
        MAX-ACCESS read-write
        STATUS current
        DESCRIPTION
                "Queue weight."
        ::= { ipqosProfileQueueEntry 7 }

--------------------
-- rateLimitProfile
--------------------

-- rateLimitProfileTable

	maxNumOfRateLimitProfiles OBJECT-TYPE
        SYNTAX INTEGER
        MAX-ACCESS read-only
        STATUS current
        DESCRIPTION
        	"The maximum number of Rate Limit profiles supported by the system. This object is supported by R5.02 and later versions."
        ::= { rateLimitProfile 1 }
        
	rateLimitProfileTable OBJECT-TYPE
        SYNTAX SEQUENCE OF RateLimitProfileEntry
        MAX-ACCESS not-accessible
        STATUS current
        DESCRIPTION
                "This table includes Rate Limit related configuration. This table is supported by R5.02 and later versions."
        ::= { rateLimitProfile 2 }

	rateLimitProfileEntry OBJECT-TYPE
        SYNTAX RateLimitProfileEntry
        MAX-ACCESS not-accessible
        STATUS current
        DESCRIPTION
		"An entry in rateLimitProfileTable."
        INDEX { IMPLIED rateLimitProfileName }
        ::= { rateLimitProfileTable 1 }

        RateLimitProfileEntry ::=
        	SEQUENCE {
			rateLimitProfileName		DisplayString,
			rateLimitProfileIngressRate	INTEGER,
			rateLimitProfileEgressRate	INTEGER,
			rateLimitProfileRowStatus	RowStatus
           	}

        rateLimitProfileName OBJECT-TYPE
        SYNTAX DisplayString (SIZE (1..31))
        MAX-ACCESS read-only
        STATUS current
        DESCRIPTION
                "This object is used by the Rate Limit profile table in order to identify a row of this table."
        ::= { rateLimitProfileEntry 1 }

        rateLimitProfileIngressRate OBJECT-TYPE
        SYNTAX INTEGER (0..100032)
        MAX-ACCESS read-write
        STATUS current
        DESCRIPTION
                "Ingress rate between 0~100032 in kbps in step of 64, oo0oo means no limiting."
        ::= { rateLimitProfileEntry 2 }

        rateLimitProfileEgressRate OBJECT-TYPE
        SYNTAX INTEGER (0..100032)
        MAX-ACCESS read-write
        STATUS current
        DESCRIPTION
                "Egress rate between 0~100032 in kbps in step of 64, oo0oo means no limiting."
        ::= { rateLimitProfileEntry 3 }
        
        rateLimitProfileRowStatus OBJECT-TYPE
        SYNTAX RowStatus
        MAX-ACCESS read-create
        STATUS current
        DESCRIPTION
                "This object is used to create a new row or delete an existing row in the table."
        ::= { rateLimitProfileEntry 4 }

--------------------
-- e1AlarmProfile
--------------------

-- e1AlarmProfileTable

	maxNumOfE1AlarmProfile OBJECT-TYPE
        SYNTAX INTEGER
        MAX-ACCESS read-only
        STATUS current
        DESCRIPTION
        	"The maximum number of E1 Alarm profiles supported by the system. This object is supported by R5.03 and later versions."
        ::= { e1AlarmProfile 1 }
        
	e1AlarmProfileTable OBJECT-TYPE
        SYNTAX SEQUENCE OF E1AlarmProfileEntry
        MAX-ACCESS not-accessible
        STATUS current
        DESCRIPTION
                "This table includes Rate Limit related configuration. This table is supported by R5.03 and later versions."
        ::= { e1AlarmProfile 2 }

	e1AlarmProfileEntry OBJECT-TYPE
        SYNTAX E1AlarmProfileEntry
        MAX-ACCESS not-accessible
        STATUS current
        DESCRIPTION
		"An entry in e1AlarmProfileTable."
        INDEX { IMPLIED e1AlarmProfileName }
        ::= { e1AlarmProfileTable 1 }

        E1AlarmProfileEntry ::=
        	SEQUENCE {
			e1AlarmProfileName			DisplayString,
			e1AlarmProfileQEs	INTEGER,
			e1AlarmProfileQSes	INTEGER,  
			e1AlarmProfileQUas	INTEGER,
			e1AlarmProfileDayEs	INTEGER,
			e1AlarmProfileDaySes	INTEGER,
			e1AlarmProfileDayUas	INTEGER,
			e1AlarmProfileRowStatus	RowStatus
           	}

        e1AlarmProfileName OBJECT-TYPE
        SYNTAX DisplayString (SIZE (1..31))
        MAX-ACCESS read-only
        STATUS current
        DESCRIPTION
                "This object is used by the E1 Alarm profile table in order to identify a row of this table."
        ::= { e1AlarmProfileEntry 1 }

        e1AlarmProfileQEs OBJECT-TYPE
        SYNTAX INTEGER (0..900)
        MAX-ACCESS read-write
        STATUS current
        DESCRIPTION
                "15Min error second"
        ::= { e1AlarmProfileEntry 2 }

        e1AlarmProfileQSes OBJECT-TYPE
        SYNTAX INTEGER (0..900)
        MAX-ACCESS read-write
        STATUS current
        DESCRIPTION
                "15Min severe error second"
        ::= { e1AlarmProfileEntry 3 } 
        
        e1AlarmProfileQUas OBJECT-TYPE
        SYNTAX INTEGER (0..900)
        MAX-ACCESS read-write
        STATUS current
        DESCRIPTION
                "15Min un-available second"
        ::= { e1AlarmProfileEntry 4 }  
        
        e1AlarmProfileDayEs OBJECT-TYPE
        SYNTAX INTEGER (0..900)
        MAX-ACCESS read-write
        STATUS current
        DESCRIPTION
                "1Day error second"
        ::= { e1AlarmProfileEntry 5 }
        
        e1AlarmProfileDaySes OBJECT-TYPE
        SYNTAX INTEGER (0..900)
        MAX-ACCESS read-write
        STATUS current
        DESCRIPTION
                "1Day severe error second"
        ::= { e1AlarmProfileEntry 6 }
        
        e1AlarmProfileDayUas OBJECT-TYPE
        SYNTAX INTEGER (0..900)
        MAX-ACCESS read-write
        STATUS current
        DESCRIPTION
                "1Day un-available second"
        ::= { e1AlarmProfileEntry 7 }
        
        e1AlarmProfileRowStatus OBJECT-TYPE
        SYNTAX RowStatus
        MAX-ACCESS read-create
        STATUS current
        DESCRIPTION
                "This object is used to create a new row or delete an existing row in the table."
        ::= { e1AlarmProfileEntry 8 }


--------------------
-- vdsl2Profile
--------------------
	    
	    maxNumOfVdsl2TemplateProfiles OBJECT-TYPE
        SYNTAX INTEGER
        MAX-ACCESS read-only
        STATUS current
        DESCRIPTION
        	"The maximum number of VDSL2 template profiles supported by the system.
        	This MIB object is supported by R5.06 and later versions."
        ::= { vdsl2Profile 1 }
        
        maxNumOfVdsl2LineProfiles OBJECT-TYPE
        SYNTAX INTEGER
        MAX-ACCESS read-only
        STATUS current
        DESCRIPTION
        	"The maximum number of VDSL2 line profiles supported by the system.
        	This MIB object is supported by R5.06 and later versions."
        ::= { vdsl2Profile 2 }  
        
        maxNumOfVdsl2ChanProfiles OBJECT-TYPE
        SYNTAX INTEGER
        MAX-ACCESS read-only
        STATUS current
        DESCRIPTION
        	"The maximum number of VDSL2 chan profiles supported by the system.
        	This MIB object is supported by R5.06 and later versions."
        ::= { vdsl2Profile 3 }

        maxNumOfVdsl2AlarmTemplateProfiles OBJECT-TYPE
        SYNTAX INTEGER
        MAX-ACCESS read-only
        STATUS current
        DESCRIPTION
        	"The maximum number of VDSL2 alarm template profiles supported by the system.
        	This MIB object is supported by R5.06 and later versions."
        ::= { vdsl2Profile 4 } 
        
        maxNumOfVdsl2AlarmLineProfiles OBJECT-TYPE
        SYNTAX INTEGER
        MAX-ACCESS read-only
        STATUS current
        DESCRIPTION
        	"The maximum number of VDSL2 alarm line profiles supported by the system.
        	This MIB object is supported by R5.06 and later versions."
        ::= { vdsl2Profile 5 }
        
        maxNumOfVdsl2AlarmChanProfiles OBJECT-TYPE
        SYNTAX INTEGER
        MAX-ACCESS read-only
        STATUS current
        DESCRIPTION
        	"The maximum number of VDSL2 alarm chan profiles supported by the system.
        	This MIB object is supported by R5.06 and later versions."
        ::= { vdsl2Profile 6 }

-- Vdsl2LineProfileExtendedTable

        vdsl2LineConfProfileExtendedTable OBJECT-TYPE
        SYNTAX SEQUENCE OF Vdsl2LineConfProfileExtendedEntry
        MAX-ACCESS not-accessible
        STATUS current
        DESCRIPTION
                "This table contains information on the VDSL2 line profile extension configuration.
		This table is supported by R5.06 and later versions."
        ::= { vdsl2Profile 7 }

		vdsl2LineConfProfileExtendedEntry OBJECT-TYPE
        SYNTAX Vdsl2LineConfProfileExtendedEntry
        MAX-ACCESS not-accessible
        STATUS current
        DESCRIPTION
		"An entry in vdsl2LineProfileExtendedEntry."
        INDEX { xdsl2LConfProfProfileName }
        ::= { vdsl2LineConfProfileExtendedTable 1 }

        Vdsl2LineConfProfileExtendedEntry ::=
        	SEQUENCE {
			vdsl2LineProfDpboEPsdID		INTEGER,
			vdsl2LineProfBitSwapDs		INTEGER,
			vdsl2LineProfBitSwapUs		INTEGER,
	      	vdsl2LineProfProfileName   DisplayString,
	      	vdsl2LineProfDynamicDepthEnableDs	INTEGER,
	        vdsl2LineProfDynamicDepthEnableUs	INTEGER,
	        vdsl2LineProfSosTimeDs     Unsigned32,
	       	vdsl2LineProfSosTimeUs     Unsigned32,
	       	vdsl2LineProfSosCrcDs      Unsigned32,
	       	vdsl2LineProfSosCrcUs      Unsigned32,
	       	vdsl2LineProfSosNToneDs    Unsigned32,   
	       	vdsl2LineProfSosNToneUs    Unsigned32,
	       	vdsl2LineProfSosMaxDs      Unsigned32,
	       	vdsl2LineProfSosMaxUs      Unsigned32,
	       	vdsl2LineProfSosMultiStepDs	BITS,
	       	vdsl2LineProfSosMultiStepUs BITS,
	       	vdsl2LineProfRocEnableDs   INTEGER,
	       	vdsl2LineProfRocEnableUs   INTEGER,
	       	vdsl2LineProfRocSnrmDs     Unsigned32,
	       	vdsl2LineProfRocSnrmUs     Unsigned32,
	       	vdsl2LineProfRocMinInpDs   Unsigned32,
	      	vdsl2LineProfRocMinInpUs   Unsigned32,
	      	vdsl2LineProfDpboType      INTEGER,
	      	vdsl2LineProfDpboEselMin   INTEGER,
	      	vdsl2LineProfCompatible    INTEGER,
	      	vdsl2LineProfTransmissionType	BITS
           	}

        vdsl2LineProfDpboEPsdID OBJECT-TYPE
		SYNTAX  INTEGER {
				psd-co(1),
				psd-flat(2),
				psd-cab-ansi(3),
				psd-cab-etsi(4),
				psd-exch-etsi(5),
				psd-exch-ansi(6)
			}
		MAX-ACCESS read-write
		STATUS current
		DESCRIPTION
			"standard psd shape id for psd toolbox"
		::= { vdsl2LineConfProfileExtendedEntry 1 } 
		
		vdsl2LineProfBitSwapDs OBJECT-TYPE
		SYNTAX  INTEGER {
				enable(1),
				disable(2)
			}
		MAX-ACCESS read-write
		STATUS current
		DESCRIPTION
			""
		::= { vdsl2LineConfProfileExtendedEntry 2 }
		
		vdsl2LineProfBitSwapUs OBJECT-TYPE
		SYNTAX  INTEGER {
				enable(1),
				disable(2)
			}
		MAX-ACCESS read-write
		STATUS current
		DESCRIPTION
			""
		::= { vdsl2LineConfProfileExtendedEntry 3 }  
	    
	    vdsl2LineProfProfileName OBJECT-TYPE
	    SYNTAX DisplayString 
	    MAX-ACCESS  read-only
	    STATUS  current
	    DESCRIPTION
	       ""
	    ::= { vdsl2LineConfProfileExtendedEntry 4 } 
	    
	    vdsl2LineProfDynamicDepthEnableDs OBJECT-TYPE
	    SYNTAX INTEGER {
	    	enable(1),
	    	disable(2)
	    }
	    MAX-ACCESS read-write
	    STATUS current
		DESCRIPTION
			"Enable the dynamic change of interleave depth."
		::= { vdsl2LineConfProfileExtendedEntry 5 }
		
		vdsl2LineProfDynamicDepthEnableUs OBJECT-TYPE
		SYNTAX  INTEGER {
				enable(1),
				disable(2)
			}
		MAX-ACCESS read-write
		STATUS current
		DESCRIPTION
			"Enable the dynamic change of interleave depth."
		::= { vdsl2LineConfProfileExtendedEntry 6 }
		
		vdsl2LineProfSosTimeDs OBJECT-TYPE
	    SYNTAX Unsigned32 
	    MAX-ACCESS  read-write
	    STATUS  current
	    DESCRIPTION
	       "The parameter SOS-TIME-ds is used in the specification of the receiver initiated SOS 
	       (see 13.4.3/G.993.2). If the value of this parameter is not zero, the standard SOS 
	       triggering criteria are enabled, and the value corresponds with duration of the time 
	       window used in the standard SOS triggering criteria in the downstream direction. 
	       See G.993.2 for detailed usage rules.
			
		   The special value zero indicates that the standard SOS triggering criteria are disabled, 
		   i.e., vendor-discretionary values may be used instead of the values configured in the MIB 
		   for the following parameters: SOS-NTONES-ds, SOS-CRC-ds, SOS-TIME-ds.
		   
		   This parameter applies in the downstream direction. The valid range of non-zero values 
		   is from 64 ms to 16320 ms in steps of 64 ms.
	       "
	    ::= { vdsl2LineConfProfileExtendedEntry 7 }
	
	    vdsl2LineProfSosTimeUs OBJECT-TYPE
	    SYNTAX Unsigned32 
	    MAX-ACCESS  read-write
	    STATUS  current
	    DESCRIPTION
	       "The parameter SOS-TIME-u	s is used in the specification of the receiver initiated SOS 
	       (see 13.4.3/G.993.2). If the value of this parameter is not zero, the standard SOS 
	       triggering criteria are enabled, and the value corresponds with duration of the time 
	       window used in the standard SOS triggering criteria in the downstream direction. 
	       See G.993.2 for detailed usage rules.
			
		   The special value zero indicates that the standard SOS triggering criteria are disabled, 
		   i.e., vendor-discretionary values may be used instead of the values configured in the MIB 
		   for the following parameters: SOS-NTONES-ds, SOS-CRC-ds, SOS-TIME-ds.
		   
		   This parameter applies in the downstream direction. The valid range of non-zero values 
		   is from 64 ms to 16320 ms in steps of 64 ms.
	       "
	    ::= { vdsl2LineConfProfileExtendedEntry 8 }
	   
	    vdsl2LineProfSosCrcDs OBJECT-TYPE
	    SYNTAX Unsigned32 
	    MAX-ACCESS  read-write
	    STATUS  current
	    DESCRIPTION
	       "This parameter is defined as the minimum number of normalized CRC anomalies received 
	       in SOS-TIME-ds seconds in order to arm the second sub condition of the standard SOS 
	       triggering criteria (see 13.4.3.2/G.993.2) in the downstream direction. See G.993.2 
	       for detailed usage rules. The valid range of SOS-CRC values is 0.02 to ((2^16)-1)*0.02, 
	       in steps of 0.02."
	    ::= { vdsl2LineConfProfileExtendedEntry 9 }
	
	    vdsl2LineProfSosCrcUs OBJECT-TYPE
	    SYNTAX Unsigned32 
	    MAX-ACCESS  read-write
	    STATUS  current
	    DESCRIPTION
	       "This parameter is defined as the minimum number of normalized CRC anomalies received 
	       in SOS-TIME-ds seconds in order to arm the second sub condition of the standard SOS 
	       triggering criteria (see 13.4.3.2/G.993.2) in the downstream direction. See G.993.2 
	       for detailed usage rules. The valid range of SOS-CRC values is 0.02 to ((2^16)-1)*0.02, 
	       in steps of 0.02."
	    ::= { vdsl2LineConfProfileExtendedEntry 10 }
	
	    vdsl2LineProfSosNToneDs OBJECT-TYPE
	    SYNTAX Unsigned32 
	    MAX-ACCESS  read-write
	    STATUS  current
	    DESCRIPTION
	       "This parameter is defined as the minimum percentage of tones in the downstream 
	       MEDLEY SET that must be degraded in order to arm the first sub-condition of the 
	       standard SOS triggering criteria (see 13.4.3.2/G.993.2) in the downstream direction. 
	       The parameter SOS-NTONES-ds is defined as a percentage of tones. See G.993.2 for 
	       detailed usage rules. The valid range of values is from 1 to 100 in steps of 1. 
	       Use of the special value 0 is described in 13.4.3.2/G.993.2."
	    ::= { vdsl2LineConfProfileExtendedEntry 11 }
	
	    vdsl2LineProfSosNToneUs OBJECT-TYPE
	    SYNTAX Unsigned32 
	    MAX-ACCESS  read-write
	    STATUS  current
	    DESCRIPTION
	       "This parameter is defined as the minimum percentage of tones in the downstream 
	       MEDLEY SET that must be degraded in order to arm the first sub-condition of the 
	       standard SOS triggering criteria (see 13.4.3.2/G.993.2) in the downstream direction. 
	       The parameter SOS-NTONES-ds is defined as a percentage of tones. See G.993.2 for 
	       detailed usage rules. The valid range of values is from 1 to 100 in steps of 1. 
	       Use of the special value 0 is described in 13.4.3.2/G.993.2."
	    ::= { vdsl2LineConfProfileExtendedEntry 12 }
	
	    vdsl2LineProfSosMaxDs OBJECT-TYPE
	    SYNTAX Unsigned32 
	    MAX-ACCESS  read-write
	    STATUS  current
	    DESCRIPTION
	       "This parameter is used in G.993.2 de-activation (see 12.1.4/G.993.2). If the number 
	       of successful SOS procedures in the downstream direction performed within a 120-second 
	       interval exceeds MAX-SOS-ds, the modem shall transition to the L3 state. See G.993.2 
	       for detailed usage rules (see 12.1.4/G.993.2). The valid range of values is 1 to 15. 
	       Use of the special value 0 is described in 12.1/G.993.2."
	    ::= { vdsl2LineConfProfileExtendedEntry 13 }
	
	    vdsl2LineProfSosMaxUs OBJECT-TYPE
	    SYNTAX Unsigned32 
	    MAX-ACCESS  read-write
	    STATUS  current
	    DESCRIPTION
	       "This parameter is used in G.993.2 de-activation (see 12.1.4/G.993.2). If the number 
	       of successful SOS procedures in the downstream direction performed within a 120-second 
	       interval exceeds MAX-SOS-ds, the modem shall transition to the L3 state. See G.993.2 
	       for detailed usage rules (see 12.1.4/G.993.2). The valid range of values is 1 to 15. 
	       Use of the special value 0 is described in 12.1/G.993.2."
	    ::= { vdsl2LineConfProfileExtendedEntry 14 }
	
	    vdsl2LineProfSosMultiStepDs OBJECT-TYPE
	    SYNTAX BITS 
	    MAX-ACCESS  read-write
	    STATUS  current
	    DESCRIPTION
	       "Indicates the capabilities of the VTU-R to execute the SOS request in one step or in
			multiple steps in the downstream direction. The field is formatted as [gggg 0000]. 
			The first four MSBs [gggg] indicate the maximum number of tones (GSOS) that can be 
			executed in a single step (GSOS)in the downstream direction. The valid values are:
			- [0000]: No limitation
			- [0010]: GSOS = 256 tones
			- [0011]: GSOS = 512 tones
			- [0100]: GSOS = 1024 tones"
	    ::= { vdsl2LineConfProfileExtendedEntry 15 }
	
	    vdsl2LineProfSosMultiStepUs OBJECT-TYPE
	    SYNTAX BITS 
	    MAX-ACCESS  read-write
	    STATUS  current
	    DESCRIPTION
	       "Indicates the capabilities of the VTU-R to execute the SOS request in one step or in
			multiple steps in the downstream direction. The field is formatted as [gggg 0000]. 
			The first four MSBs [gggg] indicate the maximum number of tones (GSOS) that can be 
			executed in a single step (GSOS)in the downstream direction. The valid values are:
			- [0000]: No limitation
			- [0010]: GSOS = 256 tones
			- [0011]: GSOS = 512 tones
			- [0100]: GSOS = 1024 tones"
	    ::= { vdsl2LineConfProfileExtendedEntry 16 }
	
	    vdsl2LineProfRocEnableDs OBJECT-TYPE
	    SYNTAX INTEGER{
	    	enable(1),
	    	disable(2)
	    } 
	    MAX-ACCESS  read-write
	    STATUS  current
	    DESCRIPTION
	       "Enable the robust overhead channel."
	    ::= { vdsl2LineConfProfileExtendedEntry 17 }
	
	    vdsl2LineProfRocEnableUs OBJECT-TYPE
	    SYNTAX INTEGER{
	    	enable(1),
	    	disable(2)
	    } 
	    MAX-ACCESS  read-write
	    STATUS  current
	    DESCRIPTION
	       "Enable the robust overhead channel."
	    ::= { vdsl2LineConfProfileExtendedEntry 18 }
	
	    vdsl2LineProfRocSnrmDs OBJECT-TYPE
	    SYNTAX Unsigned32 
	    MAX-ACCESS  read-write
	    STATUS  current
	    DESCRIPTION
	       "The parameter is defined as the SNR margin offset for the ROC channel in the downstream 
	       	direction. The parameter is used in the specification of the channel initialization 
	       	policy (see 12.3.7.1/G.993.2).
			The valid range of SNR margin offset values is from 0 to 31 dB with 0.1 dB steps."
	    ::= { vdsl2LineConfProfileExtendedEntry 19 }
	
	    vdsl2LineProfRocSnrmUs OBJECT-TYPE
	    SYNTAX Unsigned32 
	    MAX-ACCESS  read-write
	    STATUS  current
	    DESCRIPTION
	       "The parameter is defined as the SNR margin offset for the ROC channel in the downstream 
	       	direction. The parameter is used in the specification of the channel initialization 
	       	policy (see 12.3.7.1/G.993.2).
			The valid range of SNR margin offset values is from 0 to 31 dB with 0.1 dB steps."
	    ::= { vdsl2LineConfProfileExtendedEntry 20 }
	 
	    vdsl2LineProfRocMinInpDs OBJECT-TYPE
	    SYNTAX Unsigned32 
	    MAX-ACCESS  read-write
	    STATUS  current
	    DESCRIPTION
	       "This parameter contains the minimum impulse noise protection to apply on the ROC in the 
	       downstream direction. The minimum impulse noise protection is an integer ranging from 
	       0 to 16."
	    ::= { vdsl2LineConfProfileExtendedEntry 21 }
	
	    vdsl2LineProfRocMinInpUs OBJECT-TYPE
	    SYNTAX Unsigned32 
	    MAX-ACCESS  read-write
	    STATUS  current
	    DESCRIPTION
	       "This parameter contains the minimum impulse noise protection to apply on the ROC in the 
	       downstream direction. The minimum impulse noise protection is an integer ranging from 
	       0 to 16."
	    ::= { vdsl2LineConfProfileExtendedEntry 22 }

	    vdsl2LineProfDpboType OBJECT-TYPE
        SYNTAX 	INTEGER{
			g9971 (1),
			t-com (2)
		}
        MAX-ACCESS read-write
        STATUS current
        DESCRIPTION
			""
	    ::= { vdsl2LineConfProfileExtendedEntry 23 }

	    vdsl2LineProfDpboEselMin OBJECT-TYPE
        SYNTAX 	INTEGER (0..511)
        UNITS "0.5 dB"
        MAX-ACCESS read-write
        STATUS current
        DESCRIPTION
			""
	    ::= { vdsl2LineConfProfileExtendedEntry 24 }

	    vdsl2LineProfCompatible OBJECT-TYPE
        SYNTAX 	INTEGER{
			none(1),
			adsl2(2),
			adsl2Plus(3)
		}
	    MAX-ACCESS  read-write
	    STATUS  current
	    DESCRIPTION
			"Compatible to spectrum usage of adsl2 or adsl2+ line."
	    ::= { vdsl2LineConfProfileExtendedEntry 25 }

	    vdsl2LineProfTransmissionType OBJECT-TYPE
        SYNTAX BITS
        MAX-ACCESS read-write
        STATUS current
        DESCRIPTION
	       "Configure the desired transmission types. They are:
	        vdsl2(0)
	        adsl2+(1)
	        adsl2(2)
	        gdmt(3)
	        t1413(4)
	        glite(5)
	        annex-m(6)
	        annex-l(7)
			"
         ::= { vdsl2LineConfProfileExtendedEntry 26 }
 

 -- Vdsl2ChanConfProfileExtendedTable
 		vdsl2ChanConfProfileExtendedTable OBJECT-TYPE
        SYNTAX SEQUENCE OF Vdsl2ChanConfProfileExtendedEntry
        MAX-ACCESS not-accessible
        STATUS current
        DESCRIPTION
                "This table contains information on the VDSL2 channel profile extension configuration.
		This table is supported by R5.06 and later versions."
        ::= { vdsl2Profile 8 }

		vdsl2ChanConfProfileExtendedEntry OBJECT-TYPE
        SYNTAX Vdsl2ChanConfProfileExtendedEntry
        MAX-ACCESS not-accessible
        STATUS current
        DESCRIPTION
		"An entry in vdsl2ChanConfProfileExtendedEntry."
        INDEX { xdsl2ChConfProfProfileName  }
        ::= { vdsl2ChanConfProfileExtendedTable 1 }

        Vdsl2ChanConfProfileExtendedEntry ::=
        	SEQUENCE {
			vdsl2ChanConfProfphyRds						INTEGER,
			vdsl2ChanConfProfphyRus						INTEGER,
	        vdsl2ChanConfProfProfileName				DisplayString,
	        vdsl2ChanConfProfGinpRtxModeDs        	Xdsl2ConfigRtxMode,
  	        vdsl2ChanConfProfGinpRtxModeUs        	Xdsl2ConfigRtxMode,
	        vdsl2ChanConfProfGinpEtrMaxDs        	Unsigned32,
	        vdsl2ChanConfProfGinpEtrMaxUs        	Unsigned32,
	        vdsl2ChanConfProfGinpEtrMinDs        	Unsigned32,
	        vdsl2ChanConfProfGinpEtrMinUs        	Unsigned32,
	        vdsl2ChanConfProfGinpNdrMaxDs        	Unsigned32,
	        vdsl2ChanConfProfGinpNdrMaxUs        	Unsigned32,
	        vdsl2ChanConfProfGinpShineRatioDs       Unsigned32,
	        vdsl2ChanConfProfGinpShineRatioUs       Unsigned32,
	        vdsl2ChanConfProfGinpLeftrThresholdDs   Unsigned32,
	        vdsl2ChanConfProfGinpLeftrThresholdUs   Unsigned32,
	        vdsl2ChanConfProfGinpMaxDelayDs        	Unsigned32,
	        vdsl2ChanConfProfGinpMaxDelayUs        	Unsigned32,
	        vdsl2ChanConfProfGinpMinDelayDs        	Unsigned32,
	        vdsl2ChanConfProfGinpMinDelayUs        	Unsigned32,
	        vdsl2ChanConfProfGinpInpMinDs        	Unsigned32,
	        vdsl2ChanConfProfGinpInpMinUs        	Unsigned32,
	        vdsl2ChanConfProfGinpReinCfgInpDs       Unsigned32,
	        vdsl2ChanConfProfGinpReinCfgInpUs       Unsigned32,
	        vdsl2ChanConfProfGinpReinCfgFreqDs      Unsigned32,
	        vdsl2ChanConfProfGinpReinCfgFreqUs      Unsigned32,
	        vdsl2ChanConfProfSosMinRateB0Ds			Unsigned32,
	        vdsl2ChanConfProfSosMinRateB0Us			Unsigned32
           	}

        vdsl2ChanConfProfphyRds OBJECT-TYPE
		SYNTAX  INTEGER {
				enable(1),
				disable(2),
				auto(3)
			}
		MAX-ACCESS read-write
		STATUS current
		DESCRIPTION
			"retransmission mode"
		::= { vdsl2ChanConfProfileExtendedEntry 1 } 
		
		vdsl2ChanConfProfphyRus OBJECT-TYPE
		SYNTAX  INTEGER {
				enable(1),
				disable(2),
				auto(3)
			}
		MAX-ACCESS read-write
		STATUS current
		DESCRIPTION
			"retransmission mode"
		::= { vdsl2ChanConfProfileExtendedEntry 2 } 
		 
	    vdsl2ChanConfProfProfileName OBJECT-TYPE
	    SYNTAX DisplayString 
	    MAX-ACCESS  read-only
	    STATUS  current
	    DESCRIPTION
	       ""
	    ::= { vdsl2ChanConfProfileExtendedEntry 3 }
	    
	    vdsl2ChanConfProfGinpRtxModeDs OBJECT-TYPE
	    SYNTAX Xdsl2ConfigRtxMode 
	    MAX-ACCESS  read-create
	    STATUS  current
	    DESCRIPTION
	       "G.inp(G.998.4) support setting on downstream direction.
	       The possible values are:
	        Forbidden(0) - Support for G998.4 is disabled.
	        Preferred(1) - If G998.4 is supported by the far-end, it is enabled.
	        Forced(2)    - The line will only train if G998.4 can be enabled.
	        Test(3)      - G998.4 is enabled in test mode (refer to G998.4, Clause 10.4)."
	    ::= { vdsl2ChanConfProfileExtendedEntry 4 }
	
	    vdsl2ChanConfProfGinpRtxModeUs OBJECT-TYPE
	    SYNTAX Xdsl2ConfigRtxMode 
	    MAX-ACCESS  read-create
	    STATUS  current
	    DESCRIPTION
	       "G.inp(G.998.4) support setting on upstream direction.
	       The possible values are:
	        Forbidden(0) - Support for G998.4 is disabled.
	        Preferred(1) - If G998.4 is supported by the far-end, it is enabled.
	        Forced(2)    - The line will only train if G998.4 can be enabled.
	        Test(3)      - G998.4 is enabled in test mode (refer to G998.4, Clause 10.4)."
	    ::= { vdsl2ChanConfProfileExtendedEntry 5 }
	    
	    vdsl2ChanConfProfGinpEtrMaxDs OBJECT-TYPE
	    SYNTAX Unsigned32 
	    MAX-ACCESS  read-create
	    STATUS  current
	    DESCRIPTION
	       "Defines the maximum allowed value for the ETR (Effective Throughput Rate)."
	    ::= { vdsl2ChanConfProfileExtendedEntry 6 }
	
	    vdsl2ChanConfProfGinpEtrMaxUs OBJECT-TYPE
	    SYNTAX Unsigned32 
	    MAX-ACCESS  read-create
	    STATUS  current
	    DESCRIPTION
	       "Defines the maximum allowed value for the ETR (Effective Throughput Rate)."
	    ::= { vdsl2ChanConfProfileExtendedEntry 7 }
	    
	    vdsl2ChanConfProfGinpEtrMinDs OBJECT-TYPE
	    SYNTAX Unsigned32 
	    MAX-ACCESS  read-create
	    STATUS  current
	    DESCRIPTION
	       "Defines the minimum value for the ETR (Effective Throughput Rate)."
	    ::= { vdsl2ChanConfProfileExtendedEntry 8 }
	
	    vdsl2ChanConfProfGinpEtrMinUs OBJECT-TYPE
	    SYNTAX Unsigned32 
	    MAX-ACCESS  read-create
	    STATUS  current
	    DESCRIPTION
	       "Defines the minimum value for the ETR (Effective Throughput Rate)."
	    ::= { vdsl2ChanConfProfileExtendedEntry 9 }
	    
	    vdsl2ChanConfProfGinpNdrMaxDs OBJECT-TYPE
	    SYNTAX Unsigned32 
	    MAX-ACCESS  read-create
	    STATUS  current
	    DESCRIPTION
	       "Overrules the wanted maximum data rate provided in the SetLineTrafficConfiguration"
	    ::= { vdsl2ChanConfProfileExtendedEntry 10 }
	
	    vdsl2ChanConfProfGinpNdrMaxUs OBJECT-TYPE
	    SYNTAX Unsigned32 
	    MAX-ACCESS  read-create
	    STATUS  current
	    DESCRIPTION
	       "Overrules the wanted maximum data rate provided in the SetLineTrafficConfiguration"
	    ::= { vdsl2ChanConfProfileExtendedEntry 11 }
	    
	    vdsl2ChanConfProfGinpShineRatioDs OBJECT-TYPE
	    SYNTAX Unsigned32 
	    MAX-ACCESS  read-create
	    STATUS  current
	    DESCRIPTION
	       "The assumed fraction (0.001 to 0.255) of NDR necessary to correct SHINE noise."
	    ::= { vdsl2ChanConfProfileExtendedEntry 12 }
	
	    vdsl2ChanConfProfGinpShineRatioUs OBJECT-TYPE
	    SYNTAX Unsigned32 
	    MAX-ACCESS  read-create
	    STATUS  current
	    DESCRIPTION
	       "The assumed fraction (0.001 to 0.255) of NDR necessary to correct SHINE noise."
	    ::= { vdsl2ChanConfProfileExtendedEntry 13 }
	    
	    vdsl2ChanConfProfGinpLeftrThresholdDs OBJECT-TYPE
	    SYNTAX Unsigned32 
	    MAX-ACCESS  read-create
	    STATUS  current
	    DESCRIPTION
	       "The rate threshold (fraction of NDR) below which the Low Error Free Rate (LEFTR) defect is declared."
	    ::= { vdsl2ChanConfProfileExtendedEntry 14 }
	
	    vdsl2ChanConfProfGinpLeftrThresholdUs OBJECT-TYPE
	    SYNTAX Unsigned32 
	    MAX-ACCESS  read-create
	    STATUS  current
	    DESCRIPTION
	       "The rate threshold (fraction of NDR) below which the Low Error Free Rate (LEFTR) defect is declared."
	    ::= { vdsl2ChanConfProfileExtendedEntry 15 }
	    
	    vdsl2ChanConfProfGinpMaxDelayDs OBJECT-TYPE
	    SYNTAX Unsigned32 
	    MAX-ACCESS  read-create
	    STATUS  current
	    DESCRIPTION
	       "G.inp-specific value that overrules the traffic configuration setting."
	    ::= { vdsl2ChanConfProfileExtendedEntry 16 }
	
	    vdsl2ChanConfProfGinpMaxDelayUs OBJECT-TYPE
	    SYNTAX Unsigned32 
	    MAX-ACCESS  read-create
	    STATUS  current
	    DESCRIPTION
	       "G.inp-specific value that overrules the traffic configuration setting."
	    ::= { vdsl2ChanConfProfileExtendedEntry 17 }
	    
	    vdsl2ChanConfProfGinpMinDelayDs OBJECT-TYPE
	    SYNTAX Unsigned32 
	    MAX-ACCESS  read-create
	    STATUS  current
	    DESCRIPTION
	       "G.inp-specific value that overrules the traffic configuration setting."
	    ::= { vdsl2ChanConfProfileExtendedEntry 18 }
	
	    vdsl2ChanConfProfGinpMinDelayUs OBJECT-TYPE
	    SYNTAX Unsigned32 
	    MAX-ACCESS  read-create
	    STATUS  current
	    DESCRIPTION
	       "G.inp-specific value that overrules the traffic configuration setting."
	    ::= { vdsl2ChanConfProfileExtendedEntry 19 }
	    
	    vdsl2ChanConfProfGinpInpMinDs OBJECT-TYPE
	    SYNTAX Unsigned32 
	    MAX-ACCESS  read-create
	    STATUS  current
	    DESCRIPTION
	       "G.inp-specific value that overrules the traffic configuration setting. Unit is symbol.
	        The possible values are: 0-31"
	    ::= { vdsl2ChanConfProfileExtendedEntry 20 }
	
	    vdsl2ChanConfProfGinpInpMinUs OBJECT-TYPE
	    SYNTAX Unsigned32 
	    MAX-ACCESS  read-create
	    STATUS  current
	    DESCRIPTION
	       "G.inp-specific value that overrules the traffic configuration setting. Unit is symbol.
	        The possible values are: 0-31"
	    ::= { vdsl2ChanConfProfileExtendedEntry 21 }
	    
	    vdsl2ChanConfProfGinpReinCfgInpDs OBJECT-TYPE
	    SYNTAX Unsigned32 
	    MAX-ACCESS  read-create
	    STATUS  current
	    DESCRIPTION
	       "G.inp-specific value that overrules the traffic configuration setting. Unit is symbol.
	        The possible values are: 0-7"
	    ::= { vdsl2ChanConfProfileExtendedEntry 22 }
	
	    vdsl2ChanConfProfGinpReinCfgInpUs OBJECT-TYPE
	    SYNTAX Unsigned32 
	    MAX-ACCESS  read-create
	    STATUS  current
	    DESCRIPTION
	       "G.inp-specific value that overrules the traffic configuration setting. Unit is symbol.
	        The possible values are: 0-7"
	    ::= { vdsl2ChanConfProfileExtendedEntry 23 }
	    
	    vdsl2ChanConfProfGinpReinCfgFreqDs OBJECT-TYPE
	    SYNTAX Unsigned32 
	    MAX-ACCESS  read-create
	    STATUS  current
	    DESCRIPTION
	       "G.inp-specific value that overrules the traffic configuration setting. Unit is Hz.
	        The possible values are:
	        100 - 100Hz
	        120 - 120Hz"
	    ::= { vdsl2ChanConfProfileExtendedEntry 24 }
	
	    vdsl2ChanConfProfGinpReinCfgFreqUs OBJECT-TYPE
	    SYNTAX Unsigned32 
	    MAX-ACCESS  read-create
	    STATUS  current
	    DESCRIPTION
	       "G.inp-specific value that overrules the traffic configuration setting. Unit is Hz.
	        The possible values are:
	        100 - 100Hz
	        120 - 120Hz"
	    ::= { vdsl2ChanConfProfileExtendedEntry 25 }
	
	    vdsl2ChanConfProfSosMinRateB0Ds OBJECT-TYPE
	    SYNTAX Unsigned32 
	    MAX-ACCESS  read-create
	    STATUS  current
	    DESCRIPTION
	       "This parameter specifies the minimum net data rate required for a valid SOS request 
	       in the downstream direction. The value shall be coded as an unsigned integer representing 
	       the data rate as a multiple of 8 kbit/s."
	    ::= { vdsl2ChanConfProfileExtendedEntry 26 }
	    
	    vdsl2ChanConfProfSosMinRateB0Us OBJECT-TYPE
	    SYNTAX Unsigned32 
	    MAX-ACCESS  read-create
	    STATUS  current
	    DESCRIPTION
	       "This parameter specifies the minimum net data rate required for a valid SOS request 
	       in the downstream direction. The value shall be coded as an unsigned integer representing 
	       the data rate as a multiple of 8 kbit/s."
	    ::= { vdsl2ChanConfProfileExtendedEntry 27 }

--------------------
-- vdsl2AlarmProfile 
--------------------
-- vdsl2LineAlarmConfProfileExtendedTable

        vdsl2LineAlarmConfProfileExtendedTable OBJECT-TYPE
        SYNTAX SEQUENCE OF Vdsl2LineAlarmConfProfileExtendedEntry
        MAX-ACCESS not-accessible
        STATUS current
        DESCRIPTION
                "This table contains information on the VDSL2 line alarm profile extension configuration.
		This table is supported by R5.06 and later versions."
        ::= { vdsl2Profile 9 }

		vdsl2LineAlarmConfProfileExtendedEntry OBJECT-TYPE
        SYNTAX Vdsl2LineAlarmConfProfileExtendedEntry
        MAX-ACCESS not-accessible
        STATUS current
        DESCRIPTION
		"An entry in vdsl2LineAlarmConfProfileExtendedEntry."
        INDEX { xdsl2LineAlarmConfProfileName  }
        ::= { vdsl2LineAlarmConfProfileExtendedTable 1 }

        Vdsl2LineAlarmConfProfileExtendedEntry ::=
        	SEQUENCE {
			xdsl2LineAlarmConfProfileXtucThresh15MinLofs		Unsigned32,
			xdsl2LineAlarmConfProfileXturThresh15MinLofs		Unsigned32,
			xdsl2LineAlarmConfProfileThresh15MinLprs   			Unsigned32,
			xdsl2LineAlarmConfProfileProfileName				DisplayString,
			xdsl2LineAlarmConfProfileXtucThresh15MinLols		Unsigned32
           	}

        xdsl2LineAlarmConfProfileXtucThresh15MinLofs OBJECT-TYPE
		SYNTAX  Unsigned32
		MAX-ACCESS read-write
		STATUS current
		DESCRIPTION
			"A threshold for the xdsl2PMLCurr15MLofs counter, when xdsl2PMLCurrUnit is xtuc 1. 
			The value 0 means that no threshold is specified for the associated counter.
			Units:seconds"
		::= { vdsl2LineAlarmConfProfileExtendedEntry 1 } 
		
		xdsl2LineAlarmConfProfileXturThresh15MinLofs OBJECT-TYPE
		SYNTAX  Unsigned32
		MAX-ACCESS read-write
		STATUS current
		DESCRIPTION
			"A threshold for the xdsl2PMLCurr15MLofs counter, when xdsl2PMLCurrUnit is xtur 2. 
			The value 0 means that no threshold is specified for the associated counter.
			Units:seconds"
		::= { vdsl2LineAlarmConfProfileExtendedEntry 2 }
		
		xdsl2LineAlarmConfProfileThresh15MinLprs OBJECT-TYPE
		SYNTAX  Unsigned32
		MAX-ACCESS read-write
		STATUS current
		DESCRIPTION
			"A threshold for the xdsl2PMLCurr15MLprs counter. 
			The value 0 means that no threshold is specified for the associated counter.
			Units:seconds"
		::= { vdsl2LineAlarmConfProfileExtendedEntry 3 }
		
		xdsl2LineAlarmConfProfileProfileName OBJECT-TYPE
	    SYNTAX DisplayString 
	    MAX-ACCESS  read-only
	    STATUS  current
	    DESCRIPTION
	       ""
	    ::= { vdsl2LineAlarmConfProfileExtendedEntry 4 }
	    
	    xdsl2LineAlarmConfProfileXtucThresh15MinLols OBJECT-TYPE
	    SYNTAX  Unsigned32
        MAX-ACCESS read-write
        STATUS current
        DESCRIPTION
            "A threshold for the xdsl2PMLCurr15MLols counter, when xdsl2PMLCurrUnit is xtuc. 
            The value 0 means that no threshold is specified for the associated counter.
            Units:seconds"

        ::= { vdsl2LineAlarmConfProfileExtendedEntry 5 }
        
--------------------
-- vdsl2LineConfTemp 
--------------------
-- vdsl2LineConfTempExtendedTable

        vdsl2LineConfTempExtendedTable OBJECT-TYPE
        SYNTAX SEQUENCE OF Vdsl2LineConfTempExtendedEntry
        MAX-ACCESS not-accessible
        STATUS current
        DESCRIPTION
                "This table contains information on the VDSL2 line template profile extension configuration.
		This table is supported by R5.06 and later versions."
        ::= { vdsl2Profile 10 }

		vdsl2LineConfTempExtendedEntry OBJECT-TYPE
        SYNTAX Vdsl2LineConfTempExtendedEntry
        MAX-ACCESS not-accessible
        STATUS current
        DESCRIPTION
		"An entry in vdsl2LineConfTempExtendedTable."
        INDEX { xdsl2LConfTempTemplateName  }
        ::= { vdsl2LineConfTempExtendedTable 1 }

        Vdsl2LineConfTempExtendedEntry ::=
        	SEQUENCE {
			vdsl2LineConfTempTemplateName						DisplayString,
			vdsl2LineConfTempTemplatePortMap					PortList,
			vdsl2LineConfTempInmProfile							DisplayString		
           	}

        vdsl2LineConfTempTemplateName OBJECT-TYPE
		SYNTAX  DisplayString
		MAX-ACCESS read-only
		STATUS current
		DESCRIPTION
			""
		::= { vdsl2LineConfTempExtendedEntry 1 }  
		
		vdsl2LineConfTempTemplatePortMap OBJECT-TYPE
		SYNTAX  PortList
		MAX-ACCESS read-only
		STATUS current
		DESCRIPTION
			"Profile mapping port list"
		::= { vdsl2LineConfTempExtendedEntry 2 }
		
		vdsl2LineConfTempInmProfile OBJECT-TYPE
		SYNTAX  DisplayString
		MAX-ACCESS read-write
		STATUS      current
		DESCRIPTION
			""
		::= { vdsl2LineConfTempExtendedEntry 3 } 
		
--------------------
-- vdsl2AlarmConfTemp 
--------------------
-- vdsl2AlarmConfTempExtendedTable

        vdsl2AlarmConfTempExtendedTable OBJECT-TYPE
        SYNTAX SEQUENCE OF Vdsl2AlarmConfTempExtendedEntry
        MAX-ACCESS not-accessible
        STATUS current
        DESCRIPTION
                "This table contains information on the VDSL2 line alarm template profile extension configuration.
		This table is supported by R5.06 and later versions."
        ::= { vdsl2Profile 11 }

		vdsl2AlarmConfTempExtendedEntry OBJECT-TYPE
        SYNTAX Vdsl2AlarmConfTempExtendedEntry
        MAX-ACCESS not-accessible
        STATUS current
        DESCRIPTION
		"An entry in vdsl2AlarmConfTempExtendedTable."
        INDEX { xdsl2LAlarmConfTempTemplateName  }
        ::= { vdsl2AlarmConfTempExtendedTable 1 }

        Vdsl2AlarmConfTempExtendedEntry ::=
        	SEQUENCE {
        	vdsl2AlarmConfTempTemplateName						DisplayString
           	}

        vdsl2AlarmConfTempTemplateName OBJECT-TYPE
		SYNTAX  DisplayString
		MAX-ACCESS read-only
		STATUS current
		DESCRIPTION
			""
		::= { vdsl2AlarmConfTempExtendedEntry 1 } 
		
--------------------
-- vdsl2ChanAlarmConfProfile 
--------------------
-- vdsl2ChanAlarmConfProfileExtendedTable

        vdsl2ChanAlarmConfProfileExtendedTable OBJECT-TYPE
        SYNTAX SEQUENCE OF Vdsl2ChanAlarmConfProfileExtendedEntry
        MAX-ACCESS not-accessible
        STATUS current
        DESCRIPTION
                "This table contains information on the VDSL2 channel alarm profile extension configuration.
		This table is supported by R5.06 and later versions."
        ::= { vdsl2Profile 12 }

		vdsl2ChanAlarmConfProfileExtendedEntry OBJECT-TYPE
        SYNTAX Vdsl2ChanAlarmConfProfileExtendedEntry
        MAX-ACCESS not-accessible
        STATUS current
        DESCRIPTION
		"An entry in vdsl2ChanAlarmConfProfileExtendedTable."
        INDEX { xdsl2ChAlarmConfProfileName  }
        ::= { vdsl2ChanAlarmConfProfileExtendedTable 1 }

        Vdsl2ChanAlarmConfProfileExtendedEntry ::=
        	SEQUENCE {
        	vdsl2ChanAlarmConfProfProfileName						DisplayString
           	}

        vdsl2ChanAlarmConfProfProfileName OBJECT-TYPE
		SYNTAX  DisplayString
		MAX-ACCESS read-only
		STATUS current
		DESCRIPTION
			""
		::= { vdsl2ChanAlarmConfProfileExtendedEntry 1 }     		


-- maxNumOfVdsl2InmProfiles
		maxNumOfVdsl2InmProfiles OBJECT-TYPE
        SYNTAX INTEGER
        MAX-ACCESS read-only
        STATUS current
        DESCRIPTION
        	"The maximum number of VDSL2 Inm profiles supported by the system.
        	This MIB object is supported by R5.06 and later versions."
        ::= { vdsl2Profile 13 } 		

-- vdsl2InmConfProfileExtendedTable
		vdsl2InmConfProfileExtendedTable  OBJECT-TYPE
	    SYNTAX      SEQUENCE  OF  Vdsl2InmConfProfileExtendedEntry
	    MAX-ACCESS  not-accessible
	    STATUS      current
	    DESCRIPTION
	       "vdsl2InmConfProfileExtendedTable."
	    REFERENCE    "ITU-T G.993.2 Amd2, paragraph 11.4.2.2.1 (INM 
	    			 procedure)"   
	    ::= { vdsl2Profile 14 }
	
	    vdsl2InmConfProfileExtendedEntry  OBJECT-TYPE
	    SYNTAX      Vdsl2InmConfProfileExtendedEntry
	    MAX-ACCESS  not-accessible
	    STATUS      current
	    DESCRIPTION
	       "vdsl2InmConfProfileExtendedTable." 
	    REFERENCE    "ITU-T G.993.2 Amd2, paragraph 11.4.2.2.1 (INM 
	    			 procedure)"
	    INDEX  { xdsl2InmConfProfProfileName }
	    ::= { vdsl2InmConfProfileExtendedTable 1 }
	
	    Vdsl2InmConfProfileExtendedEntry  ::=
		SEQUENCE {
	      xdsl2InmConfProfProfileName		DisplayString,
	      xdsl2InmConfProfVtucInpEq			Unsigned32,
	      xdsl2InmConfProfVturInpEq			Unsigned32,
	      xdsl2InmConfProfVtucCC            	Unsigned32,
	      xdsl2InmConfProfVturCC            	Unsigned32,
	      xdsl2InmConfProfVtucIATO			Unsigned32,
	      xdsl2InmConfProfVturIATO			Unsigned32,
	      xdsl2InmConfProfVtucIATS			Unsigned32,
	      xdsl2InmConfProfVturIATS			Unsigned32, 
	      xdsl2InmConfProfRowStatus          RowStatus,
	      xdsl2InmConfProfVtucISDBUS		INTEGER
		}
	
		xdsl2InmConfProfProfileName  OBJECT-TYPE
		SYNTAX      DisplayString (SIZE(1..32))
		MAX-ACCESS  not-accessible
		STATUS      current
		DESCRIPTION
	      "This object identifies a row in this table."
	    REFERENCE    "ITU-T G.993.2 Amd2, paragraph 11.4.2.2.1 (INM 
	    			 procedure)"
	     ::= { vdsl2InmConfProfileExtendedEntry 1 }
	
	    xdsl2InmConfProfVtucInpEq OBJECT-TYPE
	    SYNTAX Unsigned32 (0..3)
	    MAX-ACCESS  read-write
	    STATUS  current
	    DESCRIPTION
	       "The INM Inmpulse Noise Protection Equivalent Mode. 
	    Configuration parameter INM-INPEQ-MODE defines the way of 
	    computation of Equivalent INP, as defined in ITU-T G.993.2 Amd2 
	    11.4.2.2.1
	       This takes a value in the range from 0 to 3."
	    REFERENCE    "ITU-T G.993.2 Amd2, paragraph 11.4.2.2.1 (INM 
	    			 procedure)"
	    DEFVAL       { 0 }
	    ::= { vdsl2InmConfProfileExtendedEntry 2 }
	
	    xdsl2InmConfProfVturInpEq OBJECT-TYPE
	    SYNTAX Unsigned32 (0..3)
	    MAX-ACCESS  read-write
	    STATUS  current
	    DESCRIPTION
	       "The INM Inmpulse Noise Protection Equivalent Mode. 
	    Configuration parameter INM-INPEQ-MODE defines the way of 
	    computation of Equivalent INP, as defined in ITU-T G.993.2 Amd2 
	    11.4.2.2.1
	       This takes a value in the range from 0 to 3."
	    REFERENCE    "ITU-T G.993.2 Amd2, paragraph 11.4.2.2.1 (INM 
	    			 procedure)"
	    DEFVAL       { 0 }
	    ::= { vdsl2InmConfProfileExtendedEntry 3 }
	
	    xdsl2InmConfProfVtucCC OBJECT-TYPE
	    SYNTAX Unsigned32 
	    MAX-ACCESS  read-write
	    STATUS  current
	    DESCRIPTION
	       "The INM Cluster Continuation. The valid values for INMCC range 
	    from 0 from 64 DMT symbols in steps of 1 DMT symbol.
	       Up to and including INMCC nondegraded symbols will be allowed before
	    a cluster is deemed to be complete and the impulse noise event over."
	    REFERENCE    "ITU-T G.993.2 Amd2, paragraph 11.4.2.2.1 (INM 
	    			 procedure)"  
	    DEFVAL       { 0 }
	    ::= { vdsl2InmConfProfileExtendedEntry 4 } 
	    
	    xdsl2InmConfProfVturCC OBJECT-TYPE
	    SYNTAX Unsigned32 
	    MAX-ACCESS  read-write
	    STATUS  current
	    DESCRIPTION
	       "The INM Cluster Continuation. The valid values for INMCC range 
	    from 0 from 64 DMT symbols in steps of 1 DMT symbol.
	       Up to and including INMCC nondegraded symbols will be allowed before
	    a cluster is deemed to be complete and the impulse noise event over."
	    REFERENCE    "ITU-T G.993.2 Amd2, paragraph 11.4.2.2.1 (INM 
	    			 procedure)"  
	    DEFVAL       { 0 }
	    ::= { vdsl2InmConfProfileExtendedEntry 5 }
	    
	    xdsl2InmConfProfVtucIATO OBJECT-TYPE
	    SYNTAX Unsigned32 
	    MAX-ACCESS  read-write
	    STATUS  current
	    DESCRIPTION
	       "The INM Inter Arrival Time Offset for the IAT anomaly generation. 
	    The valid values for INMIATO range from 3 from 511 DMT symbols in steps
	    of 1 DMT symbol."
	    REFERENCE    "ITU-T G.993.2 Amd2, paragraph 11.4.2.2.1 (INM 
	    			 procedure)"     
	    DEFVAL       { 3 }    
	    ::= { vdsl2InmConfProfileExtendedEntry 6 }
	    
	    xdsl2InmConfProfVturIATO OBJECT-TYPE
	    SYNTAX Unsigned32 
	    MAX-ACCESS  read-write
	    STATUS  current
	    DESCRIPTION
	       "The INM Inter Arrival Time Offset for the IAT anomaly generation. 
	    The valid values for INMIATO range from 3 from 511 DMT symbols in steps
	    of 1 DMT symbol."
	    REFERENCE    "ITU-T G.993.2 Amd2, paragraph 11.4.2.2.1 (INM 
	    			 procedure)"     
	    DEFVAL       { 3 }    
	    ::= { vdsl2InmConfProfileExtendedEntry 7 }    
	
	    xdsl2InmConfProfVtucIATS OBJECT-TYPE
	    SYNTAX Unsigned32 
	    MAX-ACCESS  read-write
	    STATUS  current
	    DESCRIPTION
	       "The INM Inter Arrival Time Step for the IAT anomaly generation. 
	    The valid values for INMIATS range from 0 from 7 in steps. The range of 
	    values of inter-arrival times recorded in a single bin is 2^(INMIATS).
	    All inter-arrival times greater than or equal to INMIATO+6*(2^INMIATS)
	    are recorded in the 7th bin of INMAIAT."
	    REFERENCE    "ITU-T G.993.2 Amd2, paragraph 11.4.2.2.1 (INM 
	    			 procedure)"     
	    DEFVAL       { 0 }    
	    ::= { vdsl2InmConfProfileExtendedEntry 8 }
	
	    xdsl2InmConfProfVturIATS OBJECT-TYPE
	    SYNTAX Unsigned32 
	    MAX-ACCESS  read-write
	    STATUS  current
	    DESCRIPTION
	       "The INM Inter Arrival Time Step for the IAT anomaly generation. 
	    The valid values for INMIATS range from 0 from 7 in steps. The range of 
	    values of inter-arrival times recorded in a single bin is 2^(INMIATS).
	    All inter-arrival times greater than or equal to INMIATO+6*(2^INMIATS)
	    are recorded in the 7th bin of INMAIAT."
	    REFERENCE    "ITU-T G.993.2 Amd2, paragraph 11.4.2.2.1 (INM 
	    			 procedure)"     
	    DEFVAL       { 0 }    
	    ::= { vdsl2InmConfProfileExtendedEntry 9 }
	
	    xdsl2InmConfProfRowStatus  OBJECT-TYPE
	    SYNTAX      RowStatus
	    MAX-ACCESS  read-create
	    STATUS      current
	    DESCRIPTION
	      "This object is used to create a new row or to modify or
	 	delete an existing row in this table."
	    ::= { vdsl2InmConfProfileExtendedEntry 10 }

       
       	xdsl2InmConfProfVtucISDBUS OBJECT-TYPE
	    SYNTAX INTEGER 
	    MAX-ACCESS  read-write
	    STATUS  current
	    DESCRIPTION	   
	    	"ISDD sensitivity of VTU-C, -128~127 in unit of 0.1dB."
	    DEFVAL       { 0 }    
	    ::= { vdsl2InmConfProfileExtendedEntry 11 }
	    
--------------------
-- queueRateLimitProfile
--------------------

-- queueRateLimitProfileTable

	maxNumOfQueueRateLimitProfiles OBJECT-TYPE
        SYNTAX INTEGER
        MAX-ACCESS read-only
        STATUS current
        DESCRIPTION
        	"The maximum number of Queue Rate Limit profiles supported by the system."
        ::= { queueRateLimitProfile 1 }  

        queueRateLimitProfileTable OBJECT-TYPE
        SYNTAX	SEQUENCE OF QueueRateLimitProfileEntry
        MAX-ACCESS  not-accessible
        STATUS  current
        DESCRIPTION
                 	"This table includes Queue Rate Limit related configuration."
        ::= { queueRateLimitProfile 2 }

        queueRateLimitProfileEntry OBJECT-TYPE
        SYNTAX	QueueRateLimitProfileEntry
        MAX-ACCESS	not-accessible
        STATUS	current
        DESCRIPTION    	"An entry in queueRateLimitProfileTable."
        INDEX          	{ IMPLIED queueRateLimitProfileName }
        ::= { queueRateLimitProfileTable 1 }

        QueueRateLimitProfileEntry ::=
	SEQUENCE {
        		queueRateLimitProfileName		DisplayString,
		queueRateLimitProfileQueue0CIR	INTEGER,
		queueRateLimitProfileQueue0PIR	INTEGER,
		queueRateLimitProfileQueue1CIR	INTEGER,
		queueRateLimitProfileQueue1PIR	INTEGER,
		queueRateLimitProfileQueue2CIR	INTEGER,
		queueRateLimitProfileQueue2PIR	INTEGER,
		queueRateLimitProfileQueue3CIR	INTEGER,
		queueRateLimitProfileQueue3PIR	INTEGER,
		queueRateLimitProfileQueue4CIR	INTEGER,
		queueRateLimitProfileQueue4PIR	INTEGER,
		queueRateLimitProfileQueue5CIR	INTEGER,
		queueRateLimitProfileQueue5PIR	INTEGER,
		queueRateLimitProfileQueue6CIR	INTEGER,
		queueRateLimitProfileQueue6PIR	INTEGER,
		queueRateLimitProfileQueue7CIR	INTEGER,
		queueRateLimitProfileQueue7PIR	INTEGER,
        		queueRateLimitProfileRowStatus	RowStatus
        }

        queueRateLimitProfileName OBJECT-TYPE
        SYNTAX  DisplayString (SIZE (1..31))
        MAX-ACCESS  read-only
        STATUS  current
        DESCRIPTION
                      	"This object is used by the Queue Rate Limit profile table and Queue Rate Limit Profile Queue table in order to identify a row of these table."
        ::= { queueRateLimitProfileEntry 1 }

        queueRateLimitProfileQueue0CIR OBJECT-TYPE
        SYNTAX  INTEGER (0..99968)
        MAX-ACCESS  read-write
        STATUS  current
        DESCRIPTION
                      	"CIR of a queue between 0~99968 in kbps in step of 64,'0' means no limiting."
        ::= { queueRateLimitProfileEntry 2 }

        queueRateLimitProfileQueue0PIR OBJECT-TYPE
        SYNTAX  INTEGER (0..99968)
        MAX-ACCESS  read-write
        STATUS  current
        DESCRIPTION
                      	"PIR of a queue between 0~99968 in kbps in step of 64,'0' means no limiting."
        ::= { queueRateLimitProfileEntry 3 }
        
        queueRateLimitProfileQueue1CIR OBJECT-TYPE
        SYNTAX  INTEGER (0..99968)
        MAX-ACCESS  read-write
        STATUS  current
        DESCRIPTION
                      	"CIR of a queue between 0~99968 in kbps in step of 64,'0' means no limiting."
        ::= { queueRateLimitProfileEntry 4 }

        queueRateLimitProfileQueue1PIR OBJECT-TYPE
        SYNTAX  INTEGER (0..99968)
        MAX-ACCESS  read-write
        STATUS  current
        DESCRIPTION
                      	"PIR of a queue between 0~99968 in kbps in step of 64,'0' means no limiting."
        ::= { queueRateLimitProfileEntry 5 }

        queueRateLimitProfileQueue2CIR OBJECT-TYPE
        SYNTAX  INTEGER (0..99968)
        MAX-ACCESS  read-write
        STATUS  current
        DESCRIPTION
                      	"CIR of a queue between 0~99968 in kbps in step of 64,'0' means no limiting."
        ::= { queueRateLimitProfileEntry 6 }

        queueRateLimitProfileQueue2PIR OBJECT-TYPE
        SYNTAX  INTEGER (0..99968)
        MAX-ACCESS  read-write
        STATUS  current
        DESCRIPTION
                      	"PIR of a queue between 0~99968 in kbps in step of 64,'0' means no limiting."
        ::= { queueRateLimitProfileEntry 7 }

        queueRateLimitProfileQueue3CIR OBJECT-TYPE
        SYNTAX  INTEGER (0..99968)
        MAX-ACCESS  read-write
        STATUS  current
        DESCRIPTION
                      	"CIR of a queue between 0~99968 in kbps in step of 64,'0' means no limiting."
        ::= { queueRateLimitProfileEntry 8 }

        queueRateLimitProfileQueue3PIR OBJECT-TYPE
        SYNTAX  INTEGER (0..99968)
        MAX-ACCESS  read-write
        STATUS  current
        DESCRIPTION
                      	"PIR of a queue between 0~99968 in kbps in step of 64,'0' means no limiting."
        ::= { queueRateLimitProfileEntry 9 }

        queueRateLimitProfileQueue4CIR OBJECT-TYPE
        SYNTAX  INTEGER (0..99968)
        MAX-ACCESS  read-write
        STATUS  current
        DESCRIPTION
                      	"CIR of a queue between 0~99968 in kbps in step of 64,'0' means no limiting."
        ::= { queueRateLimitProfileEntry 10 }

        queueRateLimitProfileQueue4PIR OBJECT-TYPE
        SYNTAX  INTEGER (0..99968)
        MAX-ACCESS  read-write
        STATUS  current
        DESCRIPTION
                      	"PIR of a queue between 0~99968 in kbps in step of 64,'0' means no limiting."
        ::= { queueRateLimitProfileEntry 11 }

        queueRateLimitProfileQueue5CIR OBJECT-TYPE
        SYNTAX  INTEGER (0..99968)
        MAX-ACCESS  read-write
        STATUS  current
        DESCRIPTION
                      	"CIR of a queue between 0~99968 in kbps in step of 64,'0' means no limiting."
        ::= { queueRateLimitProfileEntry 12 }

        queueRateLimitProfileQueue5PIR OBJECT-TYPE
        SYNTAX  INTEGER (0..99968)
        MAX-ACCESS  read-write
        STATUS  current
        DESCRIPTION
                      	"PIR of a queue between 0~99968 in kbps in step of 64,'0' means no limiting."
        ::= { queueRateLimitProfileEntry 13 }

        queueRateLimitProfileQueue6CIR OBJECT-TYPE
        SYNTAX  INTEGER (0..99968)
        MAX-ACCESS  read-write
        STATUS  current
        DESCRIPTION
                      	"CIR of a queue between 0~99968 in kbps in step of 64,'0' means no limiting."
        ::= { queueRateLimitProfileEntry 14 }

        queueRateLimitProfileQueue6PIR OBJECT-TYPE
        SYNTAX  INTEGER (0..99968)
        MAX-ACCESS  read-write
        STATUS  current
        DESCRIPTION
                      	"PIR of a queue between 0~99968 in kbps in step of 64,'0' means no limiting."
        ::= { queueRateLimitProfileEntry 15 }

        queueRateLimitProfileQueue7CIR OBJECT-TYPE
        SYNTAX  INTEGER (0..99968)
        MAX-ACCESS  read-write
        STATUS  current
        DESCRIPTION
                      	"CIR of a queue between 0~99968 in kbps in step of 64,'0' means no limiting."
        ::= { queueRateLimitProfileEntry 16 }

        queueRateLimitProfileQueue7PIR OBJECT-TYPE
        SYNTAX  INTEGER (0..99968)
        MAX-ACCESS  read-write
        STATUS  current
        DESCRIPTION
                      	"PIR of a queue between 0~99968 in kbps in step of 64,'0' means no limiting."
        ::= { queueRateLimitProfileEntry 17 }

        queueRateLimitProfileRowStatus OBJECT-TYPE
        SYNTAX  RowStatus
        MAX-ACCESS  read-create
        STATUS  current
        DESCRIPTION
                      	"This object is used to create a new row or delete an existing row in the table."
        ::= { queueRateLimitProfileEntry 18 }
		
--------------------
-- ipqos2Profile
--------------------
		
	maxNumOfIpqos2Profiles OBJECT-TYPE
        SYNTAX INTEGER
        MAX-ACCESS read-only
        STATUS current
        DESCRIPTION
        	"The maximum number of IPQoS2 profiles supported by the system."
        ::= { ipqos2Profile 1 }  

        ipqos2ProfileTable OBJECT-TYPE
        SYNTAX	SEQUENCE OF Ipqos2ProfileEntry
        MAX-ACCESS  not-accessible
        STATUS  current
        DESCRIPTION
                 	"This table includes IPQoS2 profiles."
        ::= { ipqos2Profile 2 }

        ipqos2ProfileEntry OBJECT-TYPE
        SYNTAX	Ipqos2ProfileEntry
        MAX-ACCESS	not-accessible
        STATUS	current
        DESCRIPTION    	"An entry in ipqos2ProfileTable."
        INDEX          	{ IMPLIED ipqos2ProfileName }
        ::= { ipqos2ProfileTable 1 }

        Ipqos2ProfileEntry ::=
	SEQUENCE {
        		ipqos2ProfileName		DisplayString,
		ipqos2ProfileAlgorithm	INTEGER,
		ipqos2ProfileVcLevel	INTEGER,
		ipqos2ProfileVcMaxRate	INTEGER,
		ipqos2ProfileVcDepth	INTEGER,
		ipqos2ProfileQueue0Weight	INTEGER,
		ipqos2ProfileQueue0MaxRate	INTEGER,
		ipqos2ProfileQueue0Depth	INTEGER,
		ipqos2ProfileQueue1Weight	INTEGER,
		ipqos2ProfileQueue1MaxRate	INTEGER,
		ipqos2ProfileQueue1Depth	INTEGER,
		ipqos2ProfileQueue2Weight	INTEGER,
		ipqos2ProfileQueue2MaxRate	INTEGER,
		ipqos2ProfileQueue2Depth	INTEGER,
		ipqos2ProfileQueue3Weight	INTEGER,
		ipqos2ProfileQueue3MaxRate	INTEGER,
		ipqos2ProfileQueue3Depth	INTEGER,
		ipqos2ProfileQueue4Weight	INTEGER,
		ipqos2ProfileQueue4MaxRate	INTEGER,
		ipqos2ProfileQueue4Depth	INTEGER,
		ipqos2ProfileQueue5Weight	INTEGER,
		ipqos2ProfileQueue5MaxRate	INTEGER,
		ipqos2ProfileQueue5Depth	INTEGER,
		ipqos2ProfileQueue6Weight	INTEGER,
		ipqos2ProfileQueue6MaxRate	INTEGER,
		ipqos2ProfileQueue6Depth	INTEGER,
		ipqos2ProfileQueue7Weight	INTEGER,
		ipqos2ProfileQueue7MaxRate	INTEGER,
		ipqos2ProfileQueue7Depth	INTEGER,
 		ipqos2ProfileRowStatus	RowStatus
        }		

        ipqos2ProfileName OBJECT-TYPE
        SYNTAX  DisplayString (SIZE (1..31))
        MAX-ACCESS  read-only
        STATUS  current
        DESCRIPTION
           "profile name."
        ::= { ipqos2ProfileEntry 1 }

        ipqos2ProfileAlgorithm OBJECT-TYPE
        SYNTAX  INTEGER (1..5)
        MAX-ACCESS  read-write
        STATUS  current
        DESCRIPTION
            "1:sp, 2:wfq, 3-sp+wfq, 4:shaping, 5:vc-shaping."
        ::= { ipqos2ProfileEntry 2 }

        ipqos2ProfileVcLevel OBJECT-TYPE
        SYNTAX  INTEGER (0..7)
        MAX-ACCESS  read-write
        STATUS  current
        DESCRIPTION
            "level of the PVC. For vc-shaping only. Displayed as -1 when ipqos2ProfileAlgorithm 
        is not vc-shaping."
        ::= { ipqos2ProfileEntry 3 }

        ipqos2ProfileVcMaxRate OBJECT-TYPE
        SYNTAX  INTEGER (32..32000)
        MAX-ACCESS  read-write
        STATUS  current
        DESCRIPTION
            "max rate of the queues of PVCs. For vc-shaping only. Displayed as -1 when ipqos2ProfileAlgorithm 
        is not vc-shaping."
        ::= { ipqos2ProfileEntry 4 }

        ipqos2ProfileVcDepth OBJECT-TYPE
        SYNTAX  INTEGER (30..255)
        MAX-ACCESS  read-write
        STATUS  current
        DESCRIPTION
            "depth of queues of PVCs. For vc-shaping only. Displayed as -1 when ipqos2ProfileAlgorithm 
        is not vc-shaping."
        ::= { ipqos2ProfileEntry 5 }

        ipqos2ProfileQueue0Weight OBJECT-TYPE
        SYNTAX  INTEGER (1..50)
        MAX-ACCESS  read-write
        STATUS  current
        DESCRIPTION
            "weight of queue 0 of PVCs. For wfq, sp+wfq only. Displayed as -1 when ipqos2ProfileAlgorithm 
        is not wfq, sp+wfq."
        ::= { ipqos2ProfileEntry 6 }

        ipqos2ProfileQueue0MaxRate	OBJECT-TYPE
        SYNTAX  INTEGER (32..32000)
        MAX-ACCESS  read-write
        STATUS  current
        DESCRIPTION
            "max rate of queue 0 of PVCs. For shaping only. Displayed as -1 when ipqos2ProfileAlgorithm 
        is not shaping."
        ::= { ipqos2ProfileEntry 7 }

        ipqos2ProfileQueue0Depth OBJECT-TYPE
        SYNTAX  INTEGER (30..255)
        MAX-ACCESS  read-write
        STATUS  current
        DESCRIPTION
            "depth of queue 0 of PVCs. For wfq, sp+wfq, shaping. Displayed as -1 when ipqos2ProfileAlgorithm 
        is not wfq, sp+wfq, shaping."
        ::= { ipqos2ProfileEntry 8 }

        ipqos2ProfileQueue1Weight OBJECT-TYPE
        SYNTAX  INTEGER (1..50)
        MAX-ACCESS  read-write
        STATUS  current
        DESCRIPTION
            "weight of queue 1 of PVCs. For wfq, sp+wfq only. Displayed as -1 when ipqos2ProfileAlgorithm 
        is not wfq, sp+wfq."
        ::= { ipqos2ProfileEntry 9 }

        ipqos2ProfileQueue1MaxRate	OBJECT-TYPE
        SYNTAX  INTEGER (32..32000)
        MAX-ACCESS  read-write
        STATUS  current
        DESCRIPTION
            "max rate of queue 1 of PVCs. For shaping only. Displayed as -1 when ipqos2ProfileAlgorithm 
        is not shaping."
        ::= { ipqos2ProfileEntry 10 }

        ipqos2ProfileQueue1Depth OBJECT-TYPE
        SYNTAX  INTEGER (30..255)
        MAX-ACCESS  read-write
        STATUS  current
        DESCRIPTION
            "depth of queue 1 of PVCs. For wfq, sp+wfq, shaping. Displayed as -1 when ipqos2ProfileAlgorithm 
        is not wfq, sp+wfq, shaping."
        ::= { ipqos2ProfileEntry 11 }

        ipqos2ProfileQueue2Weight OBJECT-TYPE
        SYNTAX  INTEGER (1..50)
        MAX-ACCESS  read-write
        STATUS  current
        DESCRIPTION
            "weight of queue 2 of PVCs. For wfq, sp+wfq only. Displayed as -1 when ipqos2ProfileAlgorithm 
        is not wfq, sp+wfq."
        ::= { ipqos2ProfileEntry 12 }

        ipqos2ProfileQueue2MaxRate	OBJECT-TYPE
        SYNTAX  INTEGER (32..32000)
        MAX-ACCESS  read-write
        STATUS  current
        DESCRIPTION
            "max rate of queue 2 of PVCs. For shaping only. Displayed as -1 when ipqos2ProfileAlgorithm 
        is not shaping."
        ::= { ipqos2ProfileEntry 13 }

        ipqos2ProfileQueue2Depth OBJECT-TYPE
        SYNTAX  INTEGER (30..255)
        MAX-ACCESS  read-write
        STATUS  current
        DESCRIPTION
            "depth of queue 2 of PVCs. For wfq, sp+wfq, shaping. Displayed as -1 when ipqos2ProfileAlgorithm 
        is not wfq, sp+wfq, shaping."
        ::= { ipqos2ProfileEntry 14 }

        ipqos2ProfileQueue3Weight OBJECT-TYPE
        SYNTAX  INTEGER (1..50)
        MAX-ACCESS  read-write
        STATUS  current
        DESCRIPTION
            "weight of queue 3 of PVCs. For wfq, sp+wfq only. Displayed as -1 when ipqos2ProfileAlgorithm 
        is not wfq, sp+wfq."
        ::= { ipqos2ProfileEntry 15 }

        ipqos2ProfileQueue3MaxRate	OBJECT-TYPE
        SYNTAX  INTEGER (32..32000)
        MAX-ACCESS  read-write
        STATUS  current
        DESCRIPTION
            "max rate of queue 3 of PVCs. For shaping only. Displayed as -1 when ipqos2ProfileAlgorithm 
        is not shaping."
        ::= { ipqos2ProfileEntry 16 }

        ipqos2ProfileQueue3Depth OBJECT-TYPE
        SYNTAX  INTEGER (30..255)
        MAX-ACCESS  read-write
        STATUS  current
        DESCRIPTION
            "depth of queue 3 of PVCs. For wfq, sp+wfq, shaping. Displayed as -1 when ipqos2ProfileAlgorithm 
        is not wfq, sp+wfq, shaping."
        ::= { ipqos2ProfileEntry 17 }

        ipqos2ProfileQueue4Weight OBJECT-TYPE
        SYNTAX  INTEGER (1..50)
        MAX-ACCESS  read-write
        STATUS  current
        DESCRIPTION
            "weight of queue 4 of PVCs. For wfq, sp+wfq only. Displayed as -1 when ipqos2ProfileAlgorithm 
        is not wfq, sp+wfq."
        ::= { ipqos2ProfileEntry 18 }

        ipqos2ProfileQueue4MaxRate	OBJECT-TYPE
        SYNTAX  INTEGER (32..32000)
        MAX-ACCESS  read-write
        STATUS  current
        DESCRIPTION
            "max rate of queue 4 of PVCs. For shaping only. Displayed as -1 when ipqos2ProfileAlgorithm 
        is not shaping."
        ::= { ipqos2ProfileEntry 19 }

        ipqos2ProfileQueue4Depth OBJECT-TYPE
        SYNTAX  INTEGER (30..255)
        MAX-ACCESS  read-write
        STATUS  current
        DESCRIPTION
            "depth of queue 4 of PVCs. For wfq, sp+wfq, shaping. Displayed as -1 when ipqos2ProfileAlgorithm 
        is not wfq, sp+wfq, shaping."
        ::= { ipqos2ProfileEntry 20 }

        ipqos2ProfileQueue5Weight OBJECT-TYPE
        SYNTAX  INTEGER (1..50)
        MAX-ACCESS  read-write
        STATUS  current
        DESCRIPTION
            "weight of queue 5 of PVCs. For wfq, sp+wfq only. Displayed as -1 when ipqos2ProfileAlgorithm 
        is not wfq, sp+wfq, shaping."
        ::= { ipqos2ProfileEntry 21 }

        ipqos2ProfileQueue5MaxRate	OBJECT-TYPE
        SYNTAX  INTEGER (32..32000)
        MAX-ACCESS  read-write
        STATUS  current
        DESCRIPTION
            "max rate of queue 5 of PVCs. For shaping only. Displayed as -1 when ipqos2ProfileAlgorithm 
        is not shaping."
        ::= { ipqos2ProfileEntry 22 }

        ipqos2ProfileQueue5Depth OBJECT-TYPE
        SYNTAX  INTEGER (30..255)
        MAX-ACCESS  read-write
        STATUS  current
        DESCRIPTION
            "depth of queue 5 of PVCs. For wfq, sp+wfq, shaping. Displayed as -1 when ipqos2ProfileAlgorithm 
        is not wfq, sp+wfq, shaping."
        ::= { ipqos2ProfileEntry 23 }

        ipqos2ProfileQueue6Weight OBJECT-TYPE
        SYNTAX  INTEGER (1..50)
        MAX-ACCESS  read-write
        STATUS  current
        DESCRIPTION
            "weight of queue 6 of PVCs. For wfq, sp+wfq only. Displayed as -1 when ipqos2ProfileAlgorithm 
        is not wfq, sp+wfq."
        ::= { ipqos2ProfileEntry 24 }

        ipqos2ProfileQueue6MaxRate	OBJECT-TYPE
        SYNTAX  INTEGER (32..32000)
        MAX-ACCESS  read-write
        STATUS  current
        DESCRIPTION
            "max rate of queue 6 of PVCs. For shaping only. Displayed as -1 when ipqos2ProfileAlgorithm 
        is not shaping."
        ::= { ipqos2ProfileEntry 25 }

        ipqos2ProfileQueue6Depth OBJECT-TYPE
        SYNTAX  INTEGER (30..255)
        MAX-ACCESS  read-write
        STATUS  current
        DESCRIPTION
            "depth of queue 6 of PVCs. For wfq, sp+wfq, shaping. Displayed as -1 when ipqos2ProfileAlgorithm 
        is not wfq, sp+wfq, shaping."
        ::= { ipqos2ProfileEntry 26 }

        ipqos2ProfileQueue7Weight OBJECT-TYPE
        SYNTAX  INTEGER (1..50)
        MAX-ACCESS  read-write
        STATUS  current
        DESCRIPTION
            "weight of queue 7 of PVCs. For wfq, sp+wfq only. Displayed as -1 when ipqos2ProfileAlgorithm 
        is not wfq, sp+wfq."
        ::= { ipqos2ProfileEntry 27 }

        ipqos2ProfileQueue7MaxRate	OBJECT-TYPE
        SYNTAX  INTEGER (32..32000)
        MAX-ACCESS  read-write
        STATUS  current
        DESCRIPTION
            "max rate of queue 7 of PVCs. For shaping only. Displayed as -1 when ipqos2ProfileAlgorithm 
        is not shaping."
        ::= { ipqos2ProfileEntry 28 }

        ipqos2ProfileQueue7Depth OBJECT-TYPE
        SYNTAX  INTEGER (30..255)
        MAX-ACCESS  read-write
        STATUS  current
        DESCRIPTION
            "depth of queue 7 of PVCs. For wfq, sp+wfq, shaping. Displayed as -1 when ipqos2ProfileAlgorithm 
        is not wfq, sp+wfq, shaping."
        ::= { ipqos2ProfileEntry 29 }


        ipqos2ProfileRowStatus OBJECT-TYPE
        SYNTAX  RowStatus
        MAX-ACCESS  read-create
        STATUS  current
        DESCRIPTION
            "This object is used to create a new row or delete an existing row in the table."
        ::= { ipqos2ProfileEntry 30 }
		    		
----------------------------------------
-- switch
----------------------------------------

	enetport	OBJECT IDENTIFIER ::= { switch 3 }
	bandwidth	OBJECT IDENTIFIER ::= { switch 4 }
	qschedule	OBJECT IDENTIFIER ::= { switch 5 }
	dot3ad		OBJECT IDENTIFIER ::= { switch 6 }
	stp		OBJECT IDENTIFIER ::= { switch 7 }
	bcastCtrl	OBJECT IDENTIFIER ::= { switch 8 }
	portIsolation	OBJECT IDENTIFIER ::= { switch 9 }
	dscp		OBJECT IDENTIFIER ::= { switch 10 }
	mstp		OBJECT IDENTIFIER ::= { switch 11 }
	vlanIsolation	OBJECT IDENTIFIER ::= { switch 12 }
	mac		OBJECT IDENTIFIER ::= { switch 13 }
	cfm		OBJECT IDENTIFIER ::= { switch 14 }
	oam		OBJECT IDENTIFIER ::= { switch 15 }
	vlanpriority		OBJECT IDENTIFIER ::= { switch 16 }
	mirror		OBJECT IDENTIFIER ::= { switch 17 }
	lldp		OBJECT IDENTIFIER ::= { switch 18 }
	
	managementVLANId OBJECT-TYPE
	SYNTAX VlanIndex
	MAX-ACCESS read-write
	STATUS current
	DESCRIPTION
		"The VLAN ID for management."
	::= { switch 1 }
	
	maxNumOfStaticVlans OBJECT-TYPE
	SYNTAX INTEGER
	MAX-ACCESS read-only
	STATUS current
	DESCRIPTION
		"The maximum number of VLANs supported by the system."
	::= { switch 2 }

--------------------
-- enetport
--------------------

-- enetPortTable		

	enetPortTable OBJECT-TYPE
	SYNTAX SEQUENCE OF EnetPortEntry
	MAX-ACCESS not-accessible
	STATUS current
	DESCRIPTION
		"The table contains ethernet port information."
	::= { enetport 1 }
			
	enetPortEntry OBJECT-TYPE
	SYNTAX EnetPortEntry
	MAX-ACCESS not-accessible
	STATUS current
	DESCRIPTION
		""
	INDEX { dot1dBasePort }
	::= { enetPortTable 1 }
			
	EnetPortEntry ::=
		SEQUENCE {
			enetPortSpeed			INTEGER,
			enetPortFlowControl   	INTEGER,
			enetPortMode			INTEGER,
			enetPortVLANTrunkEnable	INTEGER,
			enetPortDscpEnable		INTEGER,
			enetPortTpid			INTEGER
		}
	
	enetPortSpeed OBJECT-TYPE
	SYNTAX 	INTEGER {
			auto(1),
			e1000M-fullduplex(2),
			e100M-fullduplex(3),
			e100M-halfduplex(4),
			e10M-fullduplex(5),
			e10M-halfduplex(6),
			e10G-fullduplex(7)
		}
	MAX-ACCESS read-write
	STATUS current
	DESCRIPTION
		"Speed configuration of the ethernet port."
	::= { enetPortEntry 1 }
	
	enetPortFlowControl OBJECT-TYPE
	SYNTAX	INTEGER {
			enable(1),
			disable(2)
		}
	MAX-ACCESS read-write
	STATUS current
	DESCRIPTION
		"Enable/disable flow control for the ethernet port."
	::= { enetPortEntry 2 }
	
	enetPortMode OBJECT-TYPE
	SYNTAX	INTEGER {
			uplink(1),
			subtending(2)
		} 
	MAX-ACCESS read-write
	STATUS current
	DESCRIPTION
		"The operational mode for uplink and subtending ports."
	::= { enetPortEntry 3 }

	enetPortVLANTrunkEnable OBJECT-TYPE
	SYNTAX	INTEGER {
			enable(1),
			disable(2)
		} 
	MAX-ACCESS read-write
	STATUS current
	DESCRIPTION
		"Enable/disable VLAN trunking for the ethernet port."
	::= { enetPortEntry 4 }

	enetPortDscpEnable OBJECT-TYPE
	SYNTAX	INTEGER {
			enable(1),
			disable(2)
		} 
	MAX-ACCESS read-write
	STATUS current
	DESCRIPTION
		"Enable/disable DSCP mapping for the ethernet port.
		This object is supported by R1.02 and later versions."
	::= { enetPortEntry 5 } 
	
	enetPortTpid OBJECT-TYPE
	SYNTAX	INTEGER  
	MAX-ACCESS read-write
	STATUS current
	DESCRIPTION
		"Set TPID value for the ethernet port,
		 0x0000 ~ 0xffff.
		"
	::= { enetPortEntry 6 }

-- enetPortSfpTable		

	enetPortSfpTable OBJECT-TYPE
	SYNTAX SEQUENCE OF EnetPortSfpEntry
	MAX-ACCESS not-accessible
	STATUS current
	DESCRIPTION
		"The table contains ethernet SFP port information."
	::= { enetport 2 }
			
	enetPortSfpEntry OBJECT-TYPE
	SYNTAX EnetPortSfpEntry
	MAX-ACCESS not-accessible
	STATUS current
	DESCRIPTION
		""
	INDEX {  ifIndex }
	::= { enetPortSfpTable 1 }
			
	EnetPortSfpEntry ::=
		SEQUENCE {
			sfpTempLow			INTEGER,
			sfpTempHigh		   	INTEGER,
			sfpVccLow			INTEGER,
			sfpVccHigh			INTEGER,
			sfpTxBiasLow		INTEGER,
			sfpTxBiasHigh		INTEGER,
			sfpTxPowerLow		INTEGER,
			sfpTxPowerHigh		INTEGER,
			sfpRxPowerLow		INTEGER,
			sfpRxPowerHigh		INTEGER
		}
	
	sfpTempLow OBJECT-TYPE
	SYNTAX 	INTEGER 
	MAX-ACCESS read-write
	STATUS current
	DESCRIPTION
		"temperature low threshold in 0.001 degree."
	::= { enetPortSfpEntry 1 }   
	
	sfpTempHigh OBJECT-TYPE
	SYNTAX 	INTEGER 
	MAX-ACCESS read-write
	STATUS current
	DESCRIPTION
		"temperature high threshold in 0.001 degree."
	::= { enetPortSfpEntry 2 } 
	
	sfpVccLow OBJECT-TYPE
	SYNTAX 	INTEGER 
	MAX-ACCESS read-write
	STATUS current
	DESCRIPTION
		"voltage low threshold in mV."
	::= { enetPortSfpEntry 3 }   
	
	sfpVccHigh OBJECT-TYPE
	SYNTAX 	INTEGER 
	MAX-ACCESS read-write
	STATUS current
	DESCRIPTION
		"voltage high threshold in mV."
	::= { enetPortSfpEntry 4 }

    sfpTxBiasLow OBJECT-TYPE
	SYNTAX 	INTEGER 
	MAX-ACCESS read-write
	STATUS current
	DESCRIPTION
		"bias current low threshold in uA."
	::= { enetPortSfpEntry 5 } 
	
	sfpTxBiasHigh OBJECT-TYPE
	SYNTAX 	INTEGER 
	MAX-ACCESS read-write
	STATUS current
	DESCRIPTION
		"bias current high threshold in uA."
	::= { enetPortSfpEntry 6 }  
	
	sfpTxPowerLow OBJECT-TYPE
	SYNTAX 	INTEGER 
	MAX-ACCESS read-write
	STATUS current
	DESCRIPTION
		"tx power low threshold in 0.001 uW."
	::= { enetPortSfpEntry 7 }  
	
	sfpTxPowerHigh OBJECT-TYPE
	SYNTAX 	INTEGER 
	MAX-ACCESS read-write
	STATUS current
	DESCRIPTION
		"tx power high threshold in 0.001 uW."
	::= { enetPortSfpEntry 8 }
	
	sfpRxPowerLow OBJECT-TYPE
	SYNTAX 	INTEGER 
	MAX-ACCESS read-write
	STATUS current
	DESCRIPTION
		"tx power low threshold in 0.001 uW."
	::= { enetPortSfpEntry 9 }
	
	sfpRxPowerHigh OBJECT-TYPE
	SYNTAX 	INTEGER 
	MAX-ACCESS read-write
	STATUS current
	DESCRIPTION
		"tx power high threshold in 0.001 uW."
	::= { enetPortSfpEntry 10 }
				
--------------------
-- bandwidth
--------------------		

	bwPortTable OBJECT-TYPE
	SYNTAX SEQUENCE OF BwPortEntry
	MAX-ACCESS not-accessible
	STATUS current
	DESCRIPTION
		"The table contains bandwidth configuration for the ethernet ports."
	::= { bandwidth 1 }
			
	bwPortEntry OBJECT-TYPE
	SYNTAX BwPortEntry
	MAX-ACCESS not-accessible
	STATUS current
	DESCRIPTION
		""
	INDEX { dot1dBasePort }
	::= { bwPortTable 1 }
			
	BwPortEntry ::=
		SEQUENCE {
			bwPortEnable		INTEGER,
			bwPortIngressRate	INTEGER,
			bwPortEgressRate	INTEGER
		}
	
	bwPortEnable OBJECT-TYPE
	SYNTAX 	INTEGER {
			enable(1),
			disable(2)
		}
	MAX-ACCESS read-write
	STATUS current
	DESCRIPTION
		"Enable/disable bandwidth control for the ethernet port."
	::= { bwPortEntry 1 }

	bwPortIngressRate OBJECT-TYPE
	SYNTAX INTEGER (0..1000)
	UNITS "Mbps"
	MAX-ACCESS read-write
	STATUS current
	DESCRIPTION
		"The ingress rate for the ethernet port."
	::= { bwPortEntry 2 }
	
	bwPortEgressRate OBJECT-TYPE
	SYNTAX INTEGER (0..1000)
	UNITS "Mbps"
	MAX-ACCESS read-write
	STATUS current
	DESCRIPTION
		"The egress rate for the ethernet port."
	::= { bwPortEntry 3 }

--------------------
-- qschedule
--------------------		

-- Queue Schedule Port Table
	
	qschedulePortTable OBJECT-TYPE
	SYNTAX SEQUENCE OF QschedulePortEntry
	MAX-ACCESS not-accessible
	STATUS current
	DESCRIPTION
		"The table contains queue schedule configuration for the ethernet ports."
	::= { qschedule 1 }
			
	qschedulePortEntry OBJECT-TYPE
	SYNTAX QschedulePortEntry
	MAX-ACCESS not-accessible
	STATUS current
	DESCRIPTION
		""
	INDEX { dot1dBasePort }
	::= { qschedulePortTable 1 }
			
	QschedulePortEntry ::=
		SEQUENCE {
			qschedulePortType	INTEGER
		}

	qschedulePortType OBJECT-TYPE
	SYNTAX 	INTEGER {
			spq(1),
			wrr(2)
		}
	MAX-ACCESS read-write
	STATUS current
	DESCRIPTION
		"Queue scheduling type (strictly priority queue or weighted round robin)."
	::= { qschedulePortEntry 1 }

-- Queue Weight Table
		
	queueWeightTable OBJECT-TYPE
	SYNTAX SEQUENCE OF QueueWeightEntry
	MAX-ACCESS not-accessible
	STATUS current
	DESCRIPTION
		"The table contains weight configuration for the priority queues."
	::= { qschedule 2 }
			
	queueWeightEntry OBJECT-TYPE
	SYNTAX QueueWeightEntry
	MAX-ACCESS not-accessible
	STATUS current
	DESCRIPTION
		""
	INDEX { dot1dBasePort, dot1dTrafficClass }
	::= { queueWeightTable 1 }
			
	QueueWeightEntry ::=
		SEQUENCE {
			queueWeight	INTEGER
		}

	queueWeight OBJECT-TYPE
	SYNTAX INTEGER (1..15)
	MAX-ACCESS read-write
	STATUS current
	DESCRIPTION
		"Weight for the priority queue."
	::= { queueWeightEntry 1 }
	
--------------------
-- dot3ad
--------------------		

-- dot3adTable

	dot3adTable OBJECT-TYPE
	SYNTAX SEQUENCE OF Dot3adEntry
	MAX-ACCESS not-accessible
	STATUS current
	DESCRIPTION
		"The table contains 802.3ad configuration."
	::= { dot3ad 1 }
			
	dot3adEntry OBJECT-TYPE
	SYNTAX Dot3adEntry
	MAX-ACCESS not-accessible
	STATUS current
	DESCRIPTION
		""
	INDEX { dot3adGroupId }
	::= { dot3adTable 1 }
			
	Dot3adEntry ::=
		SEQUENCE {
			dot3adGroupId		INTEGER,
			dot3adEnable		INTEGER,
			dot3adGroupName		DisplayString,
			dot3adGroupPortList	PortList
		}

	dot3adGroupId OBJECT-TYPE
	SYNTAX INTEGER
	MAX-ACCESS read-only
	STATUS current
	DESCRIPTION
		"Group ID 1 for subtending group and 2 for uplink group in IES-5000/5005.
		Group ID 1~4 in IES-6000."
	::= { dot3adEntry 1 }
	
	dot3adEnable OBJECT-TYPE
	SYNTAX 	INTEGER {
			enable(1),
			enableWithLacp(2),
			disable(3)
		}
	MAX-ACCESS read-write
	STATUS current
	DESCRIPTION
		"Enable/disable 802.3ad function."
	::= { dot3adEntry 2 }
	
	dot3adGroupName OBJECT-TYPE
	SYNTAX DisplayString
	MAX-ACCESS read-only
	STATUS current
	DESCRIPTION
		"The trunking group name."
	::= { dot3adEntry 3 }
	
	dot3adGroupPortList OBJECT-TYPE
	SYNTAX PortList
	MAX-ACCESS read-only
	STATUS current
	DESCRIPTION
		"The port list which joins the trunking group."
	::= { dot3adEntry 4 }
	

	lacpPriority OBJECT-TYPE
	SYNTAX INTEGER (0..65535)
	MAX-ACCESS read-write
	STATUS current
	DESCRIPTION
		"LACP system priority."
	::= { dot3ad 2 }

	lacpTimeout OBJECT-TYPE
	SYNTAX INTEGER {
			shorttimeout(1),
			longtimeout(2)
		}
	MAX-ACCESS read-write
	STATUS current
	DESCRIPTION
		"The time interval to exchange LACP packets in order to check that the peer port
		in the trunk group is still up."
	::= { dot3ad 3 }

-- portTrunkingTable

	portTrunkingTable OBJECT-TYPE
	SYNTAX SEQUENCE OF PortTrunkingEntry
	MAX-ACCESS not-accessible
	STATUS current
	DESCRIPTION
		"The table contains current status of port trunking."
	::= { dot3ad 4 }
			
	portTrunkingEntry OBJECT-TYPE
	SYNTAX PortTrunkingEntry
	MAX-ACCESS not-accessible
	STATUS current
	DESCRIPTION
		"An entry of portTrunkingTable."
	INDEX { portTrunkingGroupId }
	::= { portTrunkingTable 1 }
			
	PortTrunkingEntry ::=
		SEQUENCE {
			portTrunkingGroupId	INTEGER,
			portTrunkingStatus	INTEGER,
			portTrunkingPortList	PortList
		}

	portTrunkingGroupId OBJECT-TYPE
	SYNTAX INTEGER
	MAX-ACCESS read-only
	STATUS current
	DESCRIPTION
		"Group ID 1 for subtending group and 2 for uplink group in IES-5000/5005.
		Group ID 1~4 in IES-6000."
	::= { portTrunkingEntry 1 }
	
	portTrunkingStatus OBJECT-TYPE
	SYNTAX 	INTEGER {
			up(1),
			down(2)
		}
	MAX-ACCESS read-only
	STATUS current
	DESCRIPTION
		"Port trunking status."
	::= { portTrunkingEntry 2 }

	portTrunkingPortList OBJECT-TYPE
	SYNTAX PortList
	MAX-ACCESS read-only
	STATUS current
	DESCRIPTION
		"The port list which actually joins the trunking group."
	::= { portTrunkingEntry 3 }
	
-- aggPortTable
	
	aggPortTable OBJECT-TYPE
	SYNTAX SEQUENCE OF AggPortEntry
	MAX-ACCESS not-accessible
	STATUS current
	DESCRIPTION
		"The table specifies the setting of port trunking."
	::= { dot3ad 5 }
			
	aggPortEntry OBJECT-TYPE
	SYNTAX AggPortEntry
	MAX-ACCESS not-accessible
	STATUS current
	DESCRIPTION
		"An entry of aggPortTable."
	INDEX { dot1dBasePort }
	::= { aggPortTable 1 }
			
	AggPortEntry ::=
		SEQUENCE {
			aggPortJoin	INTEGER
		}

	aggPortJoin OBJECT-TYPE
	SYNTAX	INTEGER {
			disjoin(0),
			joinTrunkingGroup1(1),
			joinTrunkingGroup2(2),
			joinTrunkingGroup3(3),
			joinTrunkingGroup4(4)
		}
	MAX-ACCESS read-write
	STATUS current
	DESCRIPTION
		"Join/disjoin the trunking group."
	::= { aggPortEntry 1 }

-- elcPortTrunkingTable

	elcPortTrunkingTable OBJECT-TYPE
	SYNTAX SEQUENCE OF ElcPortTrunkingEntry
	MAX-ACCESS not-accessible
	STATUS current
	DESCRIPTION
		"The table is supported by R5.01 and later versions."
	::= { dot3ad 6 }
			
	elcPortTrunkingEntry OBJECT-TYPE
	SYNTAX ElcPortTrunkingEntry
	MAX-ACCESS not-accessible
	STATUS current
	DESCRIPTION
		""
	INDEX { elcPortTrunkingSlot, elcPortTrunkingGroupId  }
	::= { elcPortTrunkingTable 1 }
			
	ElcPortTrunkingEntry ::=
		SEQUENCE {
			elcPortTrunkingSlot  		INTEGER,
			elcPortTrunkingGroupId   	INTEGER,
			elcPortTrunkingStatus 		INTEGER,
			elcPortTrunkingPortList  	PortList
		}

	elcPortTrunkingSlot OBJECT-TYPE
	SYNTAX INTEGER
	MAX-ACCESS read-only
	STATUS current
	DESCRIPTION
		""
	::= { elcPortTrunkingEntry 1 }
	
	elcPortTrunkingGroupId OBJECT-TYPE
	SYNTAX INTEGER
	MAX-ACCESS read-only
	STATUS current
	DESCRIPTION
		""
	::= { elcPortTrunkingEntry 2 }
	
	elcPortTrunkingStatus OBJECT-TYPE
	SYNTAX INTEGER {
			up(1),
			down(2)
		}
	MAX-ACCESS read-only
	STATUS current
	DESCRIPTION
		""
	::= { elcPortTrunkingEntry 3 }
	
	elcPortTrunkingPortList OBJECT-TYPE
	SYNTAX PortList
	MAX-ACCESS read-only
	STATUS current
	DESCRIPTION
		""
	::= { elcPortTrunkingEntry 4 }
		
--------------------
-- stp
--------------------

	rstpEnable OBJECT-TYPE
	SYNTAX INTEGER {
			enable(1),
			disable(2)
		}
	MAX-ACCESS read-write
	STATUS current
	DESCRIPTION
		"Enable/disable RSTP protocol."
	::= { stp 1 }
		
--------------------
-- bcastCtrl
--------------------

	bctrlPortTable OBJECT-TYPE
	SYNTAX SEQUENCE OF BctrlPortEntry
	MAX-ACCESS not-accessible
	STATUS current
	DESCRIPTION
		"The table contains broadcast storm control configuration for the ethernet ports."
	::= { bcastCtrl 1 }
			
	bctrlPortEntry OBJECT-TYPE
	SYNTAX BctrlPortEntry
	MAX-ACCESS not-accessible
	STATUS current
	DESCRIPTION
		""
	INDEX { dot1dBasePort }
	::= { bctrlPortTable 1 }
			
	BctrlPortEntry ::=
		SEQUENCE {
			bctrlPortBcastEnable		INTEGER,
			bctrlPortMcastEnable		INTEGER,
			bctrlPortUcastEnable		INTEGER,
			bctrlPortBcastThresh		INTEGER,
			bctrlPortMcastThresh		INTEGER,
			bctrlPortUcastThresh		INTEGER
		}
	
	bctrlPortBcastEnable OBJECT-TYPE
	SYNTAX 	INTEGER {
			enable(1),
			disable(2)
		}
	MAX-ACCESS read-write
	STATUS current
	DESCRIPTION
		"Enable/disable storm control for broadcast packets."
	::= { bctrlPortEntry 1 }

	bctrlPortMcastEnable OBJECT-TYPE
	SYNTAX 	INTEGER {
			enable(1),
			disable(2)
		}
	MAX-ACCESS read-write
	STATUS current
	DESCRIPTION
		"Enable/disable storm control for multicast packets."
	::= { bctrlPortEntry 2 }
	
	bctrlPortUcastEnable OBJECT-TYPE
	SYNTAX 	INTEGER {
			enable(1),
			disable(2)
		}
	MAX-ACCESS read-write
	STATUS current
	DESCRIPTION
		"Enable/disable storm control for unicast packets."
	::= { bctrlPortEntry 3 }
	
	bctrlPortBcastThresh OBJECT-TYPE
	SYNTAX INTEGER (0..262143)
	UNITS "packets per second"
	MAX-ACCESS read-write
	STATUS current
	DESCRIPTION
		"The threshold of broadcast storm control."
	::= { bctrlPortEntry 4 }

	bctrlPortMcastThresh OBJECT-TYPE
	SYNTAX INTEGER (0..262143)
	UNITS "packets per second"
	MAX-ACCESS read-write
	STATUS current
	DESCRIPTION
		"The threshold of multicast storm control."
	::= { bctrlPortEntry 5 }
	
	bctrlPortUcastThresh OBJECT-TYPE
	SYNTAX INTEGER (0..262143)
	UNITS "packets per second"
	MAX-ACCESS read-write
	STATUS current
	DESCRIPTION
		"The threshold of unicast storm control."
	::= { bctrlPortEntry 6 }

--------------------
-- portIsolation
--------------------

	portIsolationEnable OBJECT-TYPE
        SYNTAX 	INTEGER {
        		enable(1),
        		disable(2)
        	}
	MAX-ACCESS read-write
	STATUS current
	DESCRIPTION
		"Enable/disable port isolation."
	::= { portIsolation 1 }

--------------------
-- dscp
--------------------

	dscpMappingPortTable OBJECT-TYPE
	SYNTAX SEQUENCE OF DscpMappingPortEntry
	MAX-ACCESS not-accessible
	STATUS current
	DESCRIPTION
		"The table contains DSCP mapping configuration for the ethernet ports.
		This table is supported by R1.02 and later versions."
	::= { dscp 1 }
			
	dscpMappingPortEntry OBJECT-TYPE
	SYNTAX DscpMappingPortEntry
	MAX-ACCESS not-accessible
	STATUS current
	DESCRIPTION
		"An entry of dscpMappingPortTable."
	INDEX { dot1dBasePort, dscpMappingPortSrcCodePoint }
	::= { dscpMappingPortTable 1 }
			
	DscpMappingPortEntry ::=
		SEQUENCE {
			dscpMappingPortSrcCodePoint	INTEGER,
			dscpMappingPortMapCodePoint	INTEGER,
			dscpMappingPortMapPriority	INTEGER
		}
	
	dscpMappingPortSrcCodePoint OBJECT-TYPE
	SYNTAX INTEGER
	MAX-ACCESS read-only
	STATUS current
	DESCRIPTION
		"The DSCP source code point used for mapping."
	::= { dscpMappingPortEntry 1 }
	
	dscpMappingPortMapCodePoint OBJECT-TYPE
	SYNTAX INTEGER (0..63)
	MAX-ACCESS read-write
	STATUS current
	DESCRIPTION
		"The mapping code point that will replace the source code point in the incoming packet."
	::= { dscpMappingPortEntry 2 }
	
	dscpMappingPortMapPriority OBJECT-TYPE
	SYNTAX INTEGER (0..7)
	MAX-ACCESS read-write
	STATUS current
	DESCRIPTION
		"The mapping p bits that will replace the source p bits in the incoming packet."
	::= { dscpMappingPortEntry 3 }

--------------------
-- mstp
--------------------

	mstpEnable OBJECT-TYPE
	SYNTAX INTEGER {
			enable(1),
			disable(2)
		}
	MAX-ACCESS read-write
	STATUS current
	DESCRIPTION
		"Enable/disable MSTP protocol. This object is supported by R1.02 and later versions."
	::= { mstp 1 }	

	mstpProtocolVersion OBJECT-TYPE
        SYNTAX	INTEGER {
        		forceDot1w(2),
        		autoDot1s(3)
        	}
        MAX-ACCESS read-write
        STATUS current
        DESCRIPTION
        	"The MSTP protocol version. This object is supported by R1.02 and later versions."
       	::= { mstp 2 }

	mstpBridgeMaxAge OBJECT-TYPE
        SYNTAX Timeout (600..4000)
        MAX-ACCESS read-write
        STATUS current
        DESCRIPTION
        	"The value that all bridges use for MaxAge when this bridge is acting as the root.
        	This object is supported by R1.02 and later versions."
        ::= { mstp 3 }

	mstpBridgeHelloTime OBJECT-TYPE
        SYNTAX Timeout (100..1000)
        MAX-ACCESS read-write
        STATUS current
        DESCRIPTION
        	"The value that all bridges use for HelloTime when this bridge is acting as the root.
        	This object is supported by R1.02 and later versions."
        ::= { mstp 4 }
        
        mstpBridgeForwardDelay OBJECT-TYPE
        SYNTAX Timeout (400..3000)
        MAX-ACCESS read-write
        STATUS current
        DESCRIPTION
        	"The value that all bridges use for ForwardDelay when this bridge is acting as the root.
        	This object is supported by R1.02 and later versions."
        ::= { mstp 5 }

	mstpMaxHops OBJECT-TYPE
        SYNTAX INTEGER (1..255)
        MAX-ACCESS read-write
        STATUS current
        DESCRIPTION
		"The maximum hops that is allowed. This object is supported by R1.02 and later versions."
        ::= { mstp 6 }
                                                      
	mstpCfgName OBJECT-TYPE
        SYNTAX DisplayString (SIZE(1..31))
        MAX-ACCESS read-write
        STATUS current
        DESCRIPTION
        	"The configuration name that identifies the MST region and is used as 
        	one of the inputs in the computation of the MST Configuration Identifier.
        	This object is supported by R1.02 and later versions."
	::= { mstp 7 }
	
	mstpCfgRevLevel OBJECT-TYPE
        SYNTAX INTEGER (0..65535)
        MAX-ACCESS read-write
        STATUS current
        DESCRIPTION
        	"This object identifies the MST revision that identifies the MST region and
        	is used as one of the inputs in the computation of the MST configuration Identifier.
        	This object is supported by R1.02 and later versions."
	::= { mstp 8 }
	
	mstpCfgDigest OBJECT-TYPE
        SYNTAX OCTET STRING (SIZE(16))
        MAX-ACCESS read-only
        STATUS current
        DESCRIPTION
        	"Configuration Digest. This object is supported by R1.02 and later versions."
        ::= { mstp 9 }
        
-- mstpMapTable

	mstpMapTable OBJECT-TYPE
        SYNTAX SEQUENCE OF MstpMapEntry
        MAX-ACCESS not-accessible
        STATUS current
        DESCRIPTION
        	"This table contains one entry for each instance of MSTP.
        	This table is supported by R1.02 and later versions."
        ::= { mstp 10 }

	mstpMapEntry OBJECT-TYPE
        SYNTAX MstpMapEntry
        MAX-ACCESS not-accessible
        STATUS current
        DESCRIPTION
        	"A conceptual row containing the status of the MSTP instance."
        INDEX { mstpMapIndex }
        ::= { mstpMapTable 1 }

	MstpMapEntry ::= SEQUENCE {
        	mstpMapIndex		INTEGER,
        	mstpMapVlans1k		OCTET STRING,
        	mstpMapVlans2k		OCTET STRING,
        	mstpMapVlans3k		OCTET STRING,
        	mstpMapVlans4k		OCTET STRING
	}

	mstpMapIndex OBJECT-TYPE
        SYNTAX INTEGER
        MAX-ACCESS read-only
        STATUS current
        DESCRIPTION
        	"Uniquely identifies an instance."
        ::= { mstpMapEntry 1 }

	mstpMapVlans1k OBJECT-TYPE
        SYNTAX OCTET STRING (SIZE (0..128))
        MAX-ACCESS read-write
        STATUS current
        DESCRIPTION
        	"A string of octets containing one bit per VLAN for VLANS with VlanIndex values 
        	0 through 1023. The first octet corresponds to VLANs with VlanIndex values 
        	0 through 7; the second octet to VLANs 8 through 15 etc. The most significant bit 
        	of each octet corresponds to the lowest VlanIndex value in that octet. For each VLAN 
        	that is mapped to this MSTP instance, the bit corresponding to that VLAN is set to '1'."
        ::= { mstpMapEntry 2 }

	mstpMapVlans2k OBJECT-TYPE
        SYNTAX OCTET STRING (SIZE (0..128))
        MAX-ACCESS read-write
        STATUS current
        DESCRIPTION
        	"A string of octets containing one bit per VLAN for VLANS with VlanIndex values 
        	1024 through 2047. The first octet corresponds to VLANs with VlanIndex values 
        	1024 through 1031; the second octet to VLANs 1032 through 1039 etc. The most significant bit 
        	of each octet corresponds to the lowest VlanIndex value in that octet. For each VLAN 
        	that is mapped to this MSTP instance, the bit corresponding to that VLAN is set to '1'."
        ::= { mstpMapEntry 3 }
        
       	mstpMapVlans3k OBJECT-TYPE
        SYNTAX OCTET STRING (SIZE (0..128))
        MAX-ACCESS read-write
        STATUS current
        DESCRIPTION
        	"A string of octets containing one bit per VLAN for VLANS with VlanIndex values 
        	2048 through 3071. The first octet corresponds to VLANs with VlanIndex values 
        	2048 through 2055; the second octet to VLANs 2056 through 2063 etc. The most significant bit 
        	of each octet corresponds to the lowest VlanIndex value in that octet. For each VLAN 
        	that is mapped to this MSTP instance, the bit corresponding to that VLAN is set to '1'."
        ::= { mstpMapEntry 4 }
        
        mstpMapVlans4k OBJECT-TYPE
        SYNTAX OCTET STRING (SIZE (0..128))
        MAX-ACCESS read-write
        STATUS current
        DESCRIPTION
        	"A string of octets containing one bit per VLAN for VLANS with VlanIndex values 
        	3072 through 4095. The first octet corresponds to VLANs with VlanIndex values 
        	3072 through 3079; the second octet to VLANs 3080 through 3087 etc. The most significant bit 
        	of each octet corresponds to the lowest VlanIndex value in that octet. For each VLAN 
        	that is mapped to this MSTP instance, the bit corresponding to that VLAN is set to '1'."
        ::= { mstpMapEntry 5 }

-- mstpVlanTable

	mstpVlanTable OBJECT-TYPE
        SYNTAX SEQUENCE OF MstpVlanEntry
        MAX-ACCESS not-accessible
        STATUS current
        DESCRIPTION
        	"This table contains one entry for each VlanId.
        	This table is supported by R1.02 and later versions."
        ::= { mstp 11 }

	mstpVlanEntry OBJECT-TYPE
        SYNTAX MstpVlanEntry
        MAX-ACCESS not-accessible
        STATUS current
        DESCRIPTION
        	"Information regarding the instance to which each Vlan is mapped."
        INDEX { mstpVlanIndex }
        ::= { mstpVlanTable 1 }

	MstpVlanEntry ::= SEQUENCE {
        	mstpVlanIndex		VlanIndex,
        	mstpVlanMstIndex	INTEGER
	}

	mstpVlanIndex OBJECT-TYPE
        SYNTAX VlanIndex
        MAX-ACCESS read-only
        STATUS current
        DESCRIPTION
        	"The VlanId for which this entry contains the instance mapped."
        ::= { mstpVlanEntry 1 }

	mstpVlanMstIndex OBJECT-TYPE
        SYNTAX INTEGER
        MAX-ACCESS read-only
        STATUS current
        DESCRIPTION
        	"An integer with values ranging from 0 to 64 that identify a 
        	the CIST/MSTI instance to which this VLAN is mapped" 
        ::= { mstpVlanEntry 2 }

-- mstpPortTable

	mstpPortTable OBJECT-TYPE
        SYNTAX SEQUENCE OF MstpPortEntry
        MAX-ACCESS not-accessible
        STATUS current
        DESCRIPTION
        	"A table that contains port-specific MSTP information.
        	This table is supported by R1.02 and later versions."
        ::= { mstp 12 }

	mstpPortEntry OBJECT-TYPE
        SYNTAX MstpPortEntry
        MAX-ACCESS not-accessible
        STATUS current
        DESCRIPTION
        	"A list of MSTP information maintained by each port."
        INDEX { dot1dBasePort }
        ::= { mstpPortTable 1 }

	MstpPortEntry ::= SEQUENCE {
        	mstpPortAdminEdgePort		INTEGER,
                mstpPortAdminPointToPoint	INTEGER
        }

	mstpPortAdminEdgePort OBJECT-TYPE
    	SYNTAX  INTEGER {
    			true(1),
    			false(2)
    		}
    	MAX-ACCESS read-write
    	STATUS current
    	DESCRIPTION
        	"The administrative value of the Edge Port parameter. A value of true(1)
        	indicates that this port should be assumed as an edge-port and a value of 
        	false(2) indicates that this port should be assumed as a non-edge-port."
    	::= { mstpPortEntry 1 }

	mstpPortAdminPointToPoint OBJECT-TYPE
    	SYNTAX	INTEGER {
    			auto(1),
        		forceTrue(2),
        		forceFalse(3)
                }
    	MAX-ACCESS read-write
    	STATUS current
    	DESCRIPTION
        	"The administrative point-to-point status of the LAN segment
         	attached to this port. A value of forceTrue(0) indicates
         	that this port should always be treated as if it is connected
         	to a point-to-point link.  A value of forceFalse(1) indicates
         	that this port should be treated as having a shared media
         	connection. A value of auto(2) indicates that this port is
         	considered to have a point-to-point link if it is an Aggregator
         	and all of its members are aggregatable, or if the MAC entity
         	is configured for full duplex operation, either through
         	auto-negotiation or by management means."
   	::= { mstpPortEntry 2 }
                     
-- mstpXstTable

	mstpXstTable OBJECT-TYPE
        SYNTAX SEQUENCE OF MstpXstEntry
        MAX-ACCESS not-accessible
        STATUS current
        DESCRIPTION
                "Bridge priority configuration for multiple spanning trees.
                This table is supported by R1.02 and later versions."
        ::= { mstp 13 }

	mstpXstEntry OBJECT-TYPE
        SYNTAX MstpXstEntry
        MAX-ACCESS not-accessible
        STATUS current
        DESCRIPTION
        	"An entry of mstpXstTable."
        INDEX { mstpXstId }
        ::= { mstpXstTable 1 }

	MstpXstEntry ::= SEQUENCE {
		mstpXstId               INTEGER,
		mstpXstBridgePriority	INTEGER
    	}

	mstpXstId OBJECT-TYPE
        SYNTAX INTEGER
        MAX-ACCESS read-only
        STATUS current
        DESCRIPTION
        	"Identifies a spanning tree."
        ::= { mstpXstEntry 1 }

	mstpXstBridgePriority OBJECT-TYPE
        SYNTAX INTEGER (0..61440)
        MAX-ACCESS read-write
        STATUS current
        DESCRIPTION
        	"Bridge priority, in steps of 4096."
        ::= { mstpXstEntry 2 }                                          

-- mstpXstPortTable

	mstpXstPortTable OBJECT-TYPE
        SYNTAX SEQUENCE OF MstpXstPortEntry
        MAX-ACCESS not-accessible
        STATUS current
        DESCRIPTION
        	"Port configuration for multiple spanning trees.
        	This table is supported by R1.02 and later versions."
        ::= { mstp 14 }

	mstpXstPortEntry OBJECT-TYPE
        SYNTAX MstpXstPortEntry
        MAX-ACCESS not-accessible
        STATUS current
        DESCRIPTION
        	"An entry of mstpXstPortTable."
        INDEX { mstpXstPortXstId, mstpXstPortIndex }
        ::= { mstpXstPortTable 1 }

        MstpXstPortEntry ::=
		SEQUENCE {
			mstpXstPortXstId		INTEGER,
			mstpXstPortIndex		INTEGER,
			mstpXstPortEnable		INTEGER,
			mstpXstPortPriority		INTEGER,
			mstpXstPortAdminPathCost	INTEGER
              }

	mstpXstPortXstId OBJECT-TYPE
        SYNTAX INTEGER
        MAX-ACCESS read-only
        STATUS current
        DESCRIPTION
        	"Identifies a spanning tree."
        ::= { mstpXstPortEntry 1 }

	mstpXstPortIndex OBJECT-TYPE
        SYNTAX INTEGER
        MAX-ACCESS read-only
        STATUS current
        DESCRIPTION
		"The port number of the port for which this entry contains MSTP management information."
        ::= { mstpXstPortEntry 2 }

	mstpXstPortEnable OBJECT-TYPE
        SYNTAX	INTEGER {
        		enable(1),
        		disable(2)
        	}
        MAX-ACCESS read-write
        STATUS current
        DESCRIPTION
		"The enabled/disabled status of the port."
        ::= { mstpXstPortEntry 3 }

	mstpXstPortPriority OBJECT-TYPE
        SYNTAX INTEGER (0..255)
        MAX-ACCESS read-write
        STATUS current
        DESCRIPTION
        	"The value of the priority field which is contained in the first 
        	(in network byte order) octet of the (2 octet long) Port ID."
        ::= { mstpXstPortEntry 4 }

	mstpXstPortAdminPathCost OBJECT-TYPE
        SYNTAX INTEGER (0..200000000)
        MAX-ACCESS read-write
        STATUS current
        DESCRIPTION
        	"The contribution of this port to the path cost of paths towards the spanning tree 
        	root which include this port. 0 menas it is determined by link speed."
        ::= { mstpXstPortEntry 5 }
                                                                                                                                                        
--------------------
-- Vlan Isolation
--------------------

	vlanIsolationTable OBJECT-TYPE
        SYNTAX SEQUENCE OF VlanIsolationEntry
        MAX-ACCESS not-accessible
        STATUS current
        DESCRIPTION
        	"A table contains configuration of isolated VLAN.
        	This table is supported by R3.00 and later versions."
        ::= { vlanIsolation 1 }

	vlanIsolationEntry OBJECT-TYPE
        SYNTAX VlanIsolationEntry
        MAX-ACCESS not-accessible
        STATUS current
        DESCRIPTION
        	"An entry of vlanIsolationTable."
        INDEX { dot1qVlanIndex }
        ::= { vlanIsolationTable 1 }

        VlanIsolationEntry ::=
		SEQUENCE {
			vlanIsolationRowStatus		INTEGER
              }

	vlanIsolationRowStatus OBJECT-TYPE
        SYNTAX RowStatus
        MAX-ACCESS read-create
        STATUS current
        DESCRIPTION
        	"Row status of the table used to create/delete an entry."
        ::= { vlanIsolationEntry 1 }

--------------------
-- MAC Forwarding
--------------------

	macAgingTime OBJECT-TYPE
        SYNTAX INTEGER
        UNITS "seconds"
        MAX-ACCESS read-write
        STATUS current
        DESCRIPTION
        	"The mac aging time in seconds."
        ::= { mac 1 }

--------------------
-- CFM
--------------------

-- cfmLoopbackPortTable

	cfmLoopbackPortTable OBJECT-TYPE
        SYNTAX SEQUENCE OF CfmLoopbackPortEntry
        MAX-ACCESS not-accessible
        STATUS current
        DESCRIPTION
        	"A table that contains CFM information.
        	This table is supported by R5.02 and later versions."
        ::= { cfm 1 }

	cfmLoopbackPortEntry OBJECT-TYPE
        SYNTAX CfmLoopbackPortEntry
        MAX-ACCESS not-accessible
        STATUS current
        DESCRIPTION
        	"An entry in cfmLoopbackPortTable."
        INDEX { ifIndex }
        ::= { cfmLoopbackPortTable 1 }

	CfmLoopbackPortEntry ::= SEQUENCE {
        	cfmLoopbackPortState 	INTEGER
        }

	cfmLoopbackPortState OBJECT-TYPE
    	SYNTAX  INTEGER {
    			enable(1),
    			disable(2)
    		}
    	MAX-ACCESS read-write
    	STATUS current
    	DESCRIPTION
        	"CFM loopback enable/disable on the port."
    	::= { cfmLoopbackPortEntry 1 }

-- cfmMIPTable

        cfmMIPTable OBJECT-TYPE
        SYNTAX SEQUENCE OF CfmMIPEntry
        MAX-ACCESS not-accessible
        STATUS current
        DESCRIPTION
                 ""
        ::= { cfm 2 }

	cfmMIPEntry OBJECT-TYPE
        SYNTAX CfmMIPEntry
        MAX-ACCESS not-accessible
        STATUS current
        DESCRIPTION
		"An entry in cfmMIPTable."
        INDEX { cfmLevel, cfmVlanID, cfmPort }
        ::= { cfmMIPTable 1 }

        CfmMIPEntry ::=
	SEQUENCE {
		cfmLevel			INTEGER,
		cfmVlanID			INTEGER,
        cfmPort				INTEGER,
        cfmMIPRowStatus		RowStatus,
        cfmMIPMacAddress 	MacAddress 
        }

        cfmLevel OBJECT-TYPE
        SYNTAX  INTEGER
        MAX-ACCESS  read-only
        STATUS  current
        DESCRIPTION
                      	""
        ::= { cfmMIPEntry 1 }

        cfmVlanID OBJECT-TYPE
        SYNTAX  INTEGER
        MAX-ACCESS  read-only
        STATUS  current
        DESCRIPTION
                      	""
        ::= { cfmMIPEntry 2 }

        cfmPort OBJECT-TYPE
        SYNTAX  INTEGER
        MAX-ACCESS  read-only
        STATUS  current
        DESCRIPTION
                      	""
        ::= { cfmMIPEntry 3 }

        cfmMIPRowStatus OBJECT-TYPE
        SYNTAX  RowStatus
        MAX-ACCESS  read-create
        STATUS  current
        DESCRIPTION
                      	""
        ::= { cfmMIPEntry 4 } 
        
        cfmMIPMacAddress OBJECT-TYPE
        SYNTAX  MacAddress
        MAX-ACCESS  read-create
        STATUS  current
        DESCRIPTION
                      	"MAC address of maintenance domain intermediate point"
        ::= { cfmMIPEntry 5 }

	cfmActionEnableStatus OBJECT-TYPE
    	SYNTAX  INTEGER {
    			enable(1),
    			disable(2)
    		}
        MAX-ACCESS  read-write
        STATUS  current
        DESCRIPTION
                      	"CFM Action enable status for the CO device"
        ::= { cfm 3 }  
        
    cfmMode OBJECT-TYPE
    	SYNTAX  INTEGER {
    			dot1ag(1),
    			y1731(2)
    		}
        MAX-ACCESS  read-write
        STATUS  current
        DESCRIPTION
                      	"The compliant CFM standard"
        ::= { cfm 4 } 
        
    cfmMIPRespondMcastLbm OBJECT-TYPE
    	SYNTAX  INTEGER {
    			enable(1),
    			disable(2)
    		}
        MAX-ACCESS  read-write
        STATUS  current
        DESCRIPTION
                      	"The status indicate whether a MIP respond to mulcast lbms or not."
        ::= { cfm 5 }  
        
    cfmLoopbackTimeout OBJECT-TYPE
    	SYNTAX  INTEGER (1..86400)
        MAX-ACCESS  read-write
        STATUS  current
        DESCRIPTION
                      	"CFM loopback timeout value."
        ::= { cfm 6 }   
        
 -- cfmLbrTable   
    cfmLbrTable OBJECT-TYPE
        SYNTAX SEQUENCE OF CfmLbrEntry
        MAX-ACCESS not-accessible
        STATUS current
        DESCRIPTION
                 "This table contains a list of Loopback replies received by a specific MEP in response to a loopback message."
        ::= { cfm 7 }

	cfmLbrEntry OBJECT-TYPE
        SYNTAX CfmLbrEntry
        MAX-ACCESS not-accessible
        STATUS current
        DESCRIPTION
		"The Loopback Reply table entry."
        INDEX { dot1agCfmMdIndex, dot1agCfmMaIndex, dot1agCfmMepIdentifier, cfmLbrSeqNumber, cfmLbrReceiveOrder }
        ::= { cfmLbrTable 1 }

        CfmLbrEntry ::=
	SEQUENCE {
		    cfmLbrSeqNumber		Unsigned32,
		    cfmLbrReceiveOrder	Unsigned32,
        	cfmLbrSrcMac		MacAddress
        }

        cfmLbrSeqNumber OBJECT-TYPE
        SYNTAX  Unsigned32 (0..4294967295)
        MAX-ACCESS  not-accessible
        STATUS  current
        DESCRIPTION
                      	"Transaction identifier/Sequence number returned by 
                      	a previous transmit loopback message command, indicating 
                      	which LBM's response is going to be returned."
        ::= { cfmLbrEntry 1 }

        cfmLbrReceiveOrder OBJECT-TYPE
        SYNTAX  Unsigned32 (0..4294967295)
        MAX-ACCESS  not-accessible
        STATUS  current
        DESCRIPTION
                      	"An index to distinguish among multiple LBRs with the same 
                      	LBR Transaction Identifier field value.  cfmLbrReceiveOrder 
                      	are assigned sequentially from 1, in the order that the 
                      	Loopback Initiator received the LBRs."
        ::= { cfmLbrEntry 2 }

        cfmLbrSrcMac OBJECT-TYPE
        SYNTAX  MacAddress
        MAX-ACCESS  read-only
        STATUS  current
        DESCRIPTION
                      	"Source MAC address returned in the LBR."
        ::= { cfmLbrEntry 3 }
--------------------
-- OAM
--------------------

-- remoteLoopbackTable

	remoteLoopbackTable OBJECT-TYPE
        SYNTAX SEQUENCE OF RemoteLoopbackEntry
        MAX-ACCESS not-accessible
        STATUS current
        DESCRIPTION
        	"A table that contains OAM information.
        	This table is supported by R5.02 and later versions."
        ::= { oam 1 }

	remoteLoopbackEntry OBJECT-TYPE
        SYNTAX RemoteLoopbackEntry
        MAX-ACCESS not-accessible
        STATUS current
        DESCRIPTION
        	"An entry in remoteLoopbackTable."
        INDEX { ifIndex }
        ::= { remoteLoopbackTable 1 }

	RemoteLoopbackEntry ::= SEQUENCE {
        	remoteLoopbackEnable 	INTEGER
        }

	remoteLoopbackEnable OBJECT-TYPE
    	SYNTAX  INTEGER {
    			enable(1),
    			disable(2)
    		}
    	MAX-ACCESS read-write
    	STATUS current
    	DESCRIPTION
        	"OAM remote loopback enable/disable on the port."
    	::= { remoteLoopbackEntry 1 }    
    	
--------------------
-- vlanpriority
--------------------

-- vlanpriorityEnable
	vlanpriorityEnable OBJECT-TYPE
    	SYNTAX  INTEGER {
    			enable(1),
    			disable(2)
    		}
        MAX-ACCESS  read-write
        STATUS  current
        DESCRIPTION
            ""
        ::= { vlanpriority 1 }

-- vlanpriorityTable
	vlanpriorityTable OBJECT-TYPE
        SYNTAX SEQUENCE OF VlanpriorityEntry
        MAX-ACCESS not-accessible
        STATUS current
        DESCRIPTION
        	"A table that contains VLAN Priority information.
        	This table is supported by R5.04 and later versions."
        ::= { vlanpriority 2 }

	vlanpriorityEntry OBJECT-TYPE
        SYNTAX VlanpriorityEntry
        MAX-ACCESS not-accessible
        STATUS current
        DESCRIPTION
        	"An entry in vlanpriorityTable."
        INDEX { vlanpriorityVid }
        ::= { vlanpriorityTable 1 }

	VlanpriorityEntry ::= SEQUENCE {
        	vlanpriorityVid 	INTEGER,
        	vlanpriorityPri		INTEGER,
        	vlanpriorityRowStatus RowStatus
        }

	vlanpriorityVid OBJECT-TYPE
    	SYNTAX  INTEGER (1..4094)
    	MAX-ACCESS read-write
    	STATUS current
    	DESCRIPTION
        	""
    	::= { vlanpriorityEntry 1 }
    
    vlanpriorityPri OBJECT-TYPE
    	SYNTAX  INTEGER (0..7)
    	MAX-ACCESS read-write
    	STATUS current
    	DESCRIPTION
        	""
    	::= { vlanpriorityEntry 2 }
    
    vlanpriorityRowStatus OBJECT-TYPE
    	SYNTAX  RowStatus
    	MAX-ACCESS read-write
    	STATUS current
    	DESCRIPTION
        	""
    	::= { vlanpriorityEntry 3 }

--------------------
-- mirror
--------------------

-- mirrorEnable
	mirrorEnable OBJECT-TYPE
    SYNTAX  INTEGER {
    			enable(1),
    			disable(2)
    	}
    MAX-ACCESS  read-write
    STATUS  current
    DESCRIPTION
            "set to 'enable' to enable mirroring"
        ::= { mirror 1 } 
   
   mirrorMonitorPort OBJECT-TYPE
   SYNTAX  INTEGER 
   MAX-ACCESS  read-write
   STATUS  current
   DESCRIPTION
            "monitor port"
        ::= { mirror 2 }

-- mirrorPortTable
	mirrorPortTable OBJECT-TYPE
        SYNTAX SEQUENCE OF MirrorPortEntry
        MAX-ACCESS not-accessible
        STATUS current
        DESCRIPTION
        	"This table is supported by R5.06 and later versions."
        ::= { mirror 3 }

	mirrorPortEntry OBJECT-TYPE
        SYNTAX MirrorPortEntry
        MAX-ACCESS not-accessible
        STATUS current
        DESCRIPTION
        	"An entry in mirrorPortTable."
        INDEX { dot1dBasePort }
        ::= { mirrorPortTable 1 }

	MirrorPortEntry ::= SEQUENCE {
        	mirrorPortDirection 	INTEGER
        }

	mirrorPortDirection OBJECT-TYPE
    	SYNTAX  INTEGER{
    			ingress(1), 
    			egress(2), 
    			both(3), 
    			none(4)
    	}
    	MAX-ACCESS read-write
    	STATUS current
    	DESCRIPTION
        	"Set to 'ingress' to mirror ingress traffic, 
        	'egress' to mirror egress traffic, 
        	'both' to mirror bi-directional traffic, 
        	'none' to disable mirroring in this port"
    	::= { mirrorPortEntry 1 }
--------------------
-- LLDP
--------------------

	lldpEnable OBJECT-TYPE
    SYNTAX  INTEGER {
    			enable(1),
    			disable(2)
    	}
    MAX-ACCESS  read-write
    STATUS  current
    DESCRIPTION
            "set to 'enable' to enable lldp"
        ::= { lldp 1 }

--------------------
----------------------------------------
-- sys
----------------------------------------
	
	sysState	OBJECT IDENTIFIER ::= { sys 1 }
	sysOperation	OBJECT IDENTIFIER ::= { sys 2 }
	hwMonitor	OBJECT IDENTIFIER ::= { sys 3 }
	timeSetup	OBJECT IDENTIFIER ::= { sys 4 }
	accessCtrl	OBJECT IDENTIFIER ::= { sys 5 }
	syslog		OBJECT IDENTIFIER ::= { sys 6 }
	snmp		OBJECT IDENTIFIER ::= { sys 7 }
	user		OBJECT IDENTIFIER ::= { sys 8 }
	aaa			OBJECT IDENTIFIER ::= { sys 9 }
	session		OBJECT IDENTIFIER ::= { sys 10 }
	bootimage OBJECT IDENTIFIER ::= {sys 11 }

--------------------
-- System State
--------------------

-- systemStatus
	systemStatus OBJECT-TYPE
    	SYNTAX INTEGER
    	MAX-ACCESS read-only
    	STATUS current
    	DESCRIPTION 
    		"This variable indicates the alarm status of the module.
 	It is a bit map represented a sum, therefore, it can represent 
 	multiple defects simultaneously. The moduleNoDefect should be set 
 	if and only if no other flag is set.
 	
 	The various bit positions are:
 	     1   moduleNoDefect
 	     2   moduleOverHeat
 	     3	 moduleFanRpmLow
 	     4	 moduleVoltageLow
 	     5   moduleThermalSensorFailure
 	     6   modulePullOut
 	     7   powerDC48VAFailure
 	     8   powerDC48VBFailure
 	     9   extAlarmInputTrigger
 	    10   moduleDown
 	    11 	 mscSwitchOverOK
 	    12	 networkTopologyChange
 	    13	 macSpoof
 	    14   cpuHigh
 	    15   memoryUsageHigh
 	    16   packetBufferUsageHigh
 	    17	 loopguardOccurence"    
     	::= {sysState 1 }

--  ledStatus    	
    ledStatus	OBJECT IDENTIFIER ::= { sysState 2 } 
    
    ledAlarmStatus OBJECT-TYPE
    	SYNTAX  INTEGER {
    			on(1),
    			off(2)
    		}
    	MAX-ACCESS read-only
    	STATUS current
    	DESCRIPTION 
    		""    
     	::= {ledStatus 1 }
     	
--  chassisStats    	
    chassisStats	OBJECT IDENTIFIER ::= { sysState 3 } 
    
    dcPowerStatus OBJECT-TYPE
    	SYNTAX INTEGER
    	MAX-ACCESS read-only
    	STATUS current
    	DESCRIPTION 
    		"This variable indicates the status of DC Power Status.
		The dcPowerStatus is a bit map represented
		as a sum, therefore, it can represent multiple defects
		simultaneously.

		The various bit positions are:
		 BIT0: POWER Input A
		 BIT1: POWER Input B"    
     	::= {chassisStats 1 }
 
 -- extAlarmStatus
	extAlarmStatus OBJECT-TYPE
    	SYNTAX INTEGER
    	MAX-ACCESS read-only
    	STATUS current
    	DESCRIPTION
    		"This variable indicates the status of the external alarm.
    		Every bit record one kind of external alarm, and there are totally 4 kind of them.
    		Every bit of the variable will be 0 or 1 only, indicate the alarm is clear or set now."
    	::= {sysState 4 } 
    	
--------------------
-- System Operation
--------------------

        sysTarget OBJECT-TYPE
        SYNTAX INTEGER
        MAX-ACCESS read-write
        STATUS current
        DESCRIPTION
        	"IfIndex of the operation target."
        ::= { sysOperation 1 }
        
        sysOps OBJECT-TYPE
        SYNTAX INTEGER
        MAX-ACCESS read-write
        STATUS current
        DESCRIPTION
        	"The manager sets the corresponding bit value to 1 to start the operation
        	and the agent clears the object to zero when the operation is successfully completed.
        	The various bit positions are:
		BIT 1: reset"
        ::= { sysOperation 2 }
        
        sysRebootTime OBJECT-TYPE
        SYNTAX INTEGER (1..2147483647)
        UNITS "seconds"
        MAX-ACCESS read-write
        STATUS current
        DESCRIPTION
        	"Write a non-zero value to schedule a reboot. Write oo0oo to cancel it.
        	When read, it returns the remaining time to the schedule reboot."
        ::= { sysOperation 3 }
        
--------------------
-- Hardware Monitor
--------------------

-- Fan Table

        fanRpmTable OBJECT-TYPE
        SYNTAX SEQUENCE OF FanRpmEntry
        MAX-ACCESS not-accessible
        STATUS current
        DESCRIPTION
        	"A table that contains rpm information about the fans."
        ::= { hwMonitor 1 }

        fanRpmEntry OBJECT-TYPE
        SYNTAX FanRpmEntry
        MAX-ACCESS not-accessible
        STATUS current
        DESCRIPTION
        	"A list of rpm information for each fan."
        INDEX  { chassisId, fanRpmIndex }
        ::= { fanRpmTable 1 }

        FanRpmEntry ::=
        	SEQUENCE {
        		fanRpmIndex		INTEGER,
			fanRpmCurValue		INTEGER,
			fanRpmMaxValue		INTEGER,
			fanRpmMinValue		INTEGER,
			fanRpmLowThresh		INTEGER,
			fanRpmDescr		DisplayString,
			fanRpmHighThresh        INTEGER
           	}

        fanRpmIndex OBJECT-TYPE
        SYNTAX INTEGER
        MAX-ACCESS read-only
        STATUS current
        DESCRIPTION
		"The identity of the fan."
        ::= { fanRpmEntry 1 }

        fanRpmCurValue OBJECT-TYPE
        SYNTAX INTEGER
        MAX-ACCESS read-only
        STATUS current
        DESCRIPTION
		"The current rpm of the fan."
        ::= { fanRpmEntry 2 }

        fanRpmMaxValue OBJECT-TYPE
        SYNTAX INTEGER
        MAX-ACCESS read-only
        STATUS current
        DESCRIPTION
		"The maximum rpm ever performed by the fan."
        ::= { fanRpmEntry 3 }

        fanRpmMinValue OBJECT-TYPE
        SYNTAX INTEGER
        MAX-ACCESS read-only
        STATUS current
        DESCRIPTION
		"The minimum rpm ever performed by the fan."
        ::= { fanRpmEntry 4 }

        fanRpmLowThresh OBJECT-TYPE
        SYNTAX INTEGER
        MAX-ACCESS read-write
        STATUS current
        DESCRIPTION
		"The low threshold of the rpm of the fan."
        ::= { fanRpmEntry 5 }

        fanRpmDescr OBJECT-TYPE
        SYNTAX DisplayString
        MAX-ACCESS read-only
        STATUS current
        DESCRIPTION
		"The description of the fan (e.g. location, function, etc.)."
        ::= { fanRpmEntry 6 }

        fanRpmHighThresh OBJECT-TYPE
        SYNTAX INTEGER
        MAX-ACCESS read-write
        STATUS current
        DESCRIPTION
		"The high threshold of the rpm of the fan."
        ::= { fanRpmEntry 7 }

-- Voltage Table

        voltageTable OBJECT-TYPE
        SYNTAX SEQUENCE OF VoltageEntry
        MAX-ACCESS not-accessible
        STATUS current
        DESCRIPTION
		"A table that contains voltage information about the system."
        ::= { hwMonitor 2 }

        voltageEntry OBJECT-TYPE
        SYNTAX VoltageEntry
        MAX-ACCESS not-accessible
        STATUS current
        DESCRIPTION
		"A list of voltage information for each sensor."
        INDEX { chassisId, slotId, voltageIndex }
        ::= { voltageTable 1 }

        VoltageEntry ::=
        	SEQUENCE {
        		voltageIndex		INTEGER,
			voltageCurValue		INTEGER,
			voltageMaxValue		INTEGER,
			voltageMinValue		INTEGER,
			voltageNominalValue	INTEGER,
			voltageLowThresh	INTEGER,
			voltageDescr		DisplayString,
			voltageHighThresh       INTEGER
           	}

        voltageIndex OBJECT-TYPE
        SYNTAX INTEGER
        MAX-ACCESS read-only
        STATUS current
        DESCRIPTION
		"The identity of the sensor."
        ::= { voltageEntry 1 }

        voltageCurValue OBJECT-TYPE
        SYNTAX INTEGER
        UNITS "milli-voltage"
        MAX-ACCESS read-only
        STATUS current
        DESCRIPTION
		"The current voltage detected by the sensor."
        ::= { voltageEntry 2 }

        voltageMaxValue OBJECT-TYPE
        SYNTAX INTEGER
        UNITS "milli-voltage"
        MAX-ACCESS read-only
        STATUS current
        DESCRIPTION
		"The maximum voltage ever detected by the sensor."
        ::= { voltageEntry 3 }

        voltageMinValue OBJECT-TYPE
        SYNTAX INTEGER
        UNITS "milli-voltage"
        MAX-ACCESS read-only
        STATUS current
        DESCRIPTION
		"The minimum voltage ever detected by the sensor."
        ::= { voltageEntry 4 }

        voltageNominalValue OBJECT-TYPE
        SYNTAX INTEGER
        UNITS "milli-voltage"
        MAX-ACCESS read-only
        STATUS current
        DESCRIPTION
		"The nominal voltage which the power should supply."
        ::= { voltageEntry 5 }

        voltageLowThresh OBJECT-TYPE
        SYNTAX INTEGER
        UNITS "milli-voltage"
        MAX-ACCESS read-write
        STATUS current
        DESCRIPTION
		"The low threshold of the voltage."
        ::= { voltageEntry 6 }

        voltageDescr OBJECT-TYPE
        SYNTAX DisplayString
        MAX-ACCESS read-only
        STATUS current
        DESCRIPTION
		"The description of the voltage (e.g. location, nominal value, etc.)."
        ::= { voltageEntry 7 }

        voltageHighThresh OBJECT-TYPE
        SYNTAX INTEGER
        UNITS "milli-voltage"
        MAX-ACCESS read-write
        STATUS current
        DESCRIPTION
		"The high threshold of the voltage."
        ::= { voltageEntry 8 }

-- Temperature Table

        temperatureTable OBJECT-TYPE
        SYNTAX SEQUENCE OF TemperatureEntry
        MAX-ACCESS not-accessible
        STATUS current
        DESCRIPTION
		"A table that contains temperature information."
        ::= { hwMonitor 3 }

        temperatureEntry OBJECT-TYPE
        SYNTAX TemperatureEntry
        MAX-ACCESS not-accessible
        STATUS current
        DESCRIPTION
        	"A list of temperature information for each sensor."
        INDEX { chassisId, slotId, temperatureIndex }
        ::= { temperatureTable 1 }

        TemperatureEntry ::=
        	SEQUENCE {
        		temperatureIndex	INTEGER,
			temperatureCurValue	INTEGER,
			temperatureMaxValue	INTEGER,
			temperatureMinValue	INTEGER,
			temperatureHighThresh	INTEGER,
			temperatureDescr	DisplayString,
			temperatureLowThresh    INTEGER
           	}

        temperatureIndex OBJECT-TYPE
        SYNTAX INTEGER
        MAX-ACCESS read-only
        STATUS current
        DESCRIPTION
		"The identity of the sensor."
        ::= { temperatureEntry 1 }

        temperatureCurValue OBJECT-TYPE
        SYNTAX INTEGER
        UNITS "Celsius"
        MAX-ACCESS read-only
        STATUS current
        DESCRIPTION
        	"The current temperature detected by the sensor."
        ::= { temperatureEntry 2 }

        temperatureMaxValue OBJECT-TYPE
        SYNTAX INTEGER
        UNITS "Celsius"
        MAX-ACCESS read-only
        STATUS current
        DESCRIPTION
		"The maximum temperature ever detected by the sensor."
        ::= { temperatureEntry 3 }

        temperatureMinValue OBJECT-TYPE
        SYNTAX INTEGER
        UNITS "Celsius"
        MAX-ACCESS read-only
        STATUS current
        DESCRIPTION
		"The minimum temperature ever detected by the sensor."
        ::= { temperatureEntry 4 }

        temperatureHighThresh OBJECT-TYPE
        SYNTAX INTEGER
        UNITS "Celsius"
        MAX-ACCESS read-write
        STATUS current
        DESCRIPTION
		"The high threshold of the temperature."
        ::= { temperatureEntry 5 }

        temperatureDescr OBJECT-TYPE
        SYNTAX DisplayString
        MAX-ACCESS read-only
        STATUS current
        DESCRIPTION
		"The description of the temperature sensor (e.g. location, function, etc.)."
        ::= { temperatureEntry 6 }

        temperatureLowThresh OBJECT-TYPE
        SYNTAX INTEGER
        UNITS "Celsius"
        MAX-ACCESS read-write
        STATUS current
        DESCRIPTION
		"The low threshold of the temperature."
        ::= { temperatureEntry 7 }

-- CPU Utilization Table

        cpuUtilizationTable OBJECT-TYPE
        SYNTAX SEQUENCE OF CpuUtilizationEntry
        MAX-ACCESS not-accessible
        STATUS current
        DESCRIPTION
		"A table that contains CPU utilization information.
		This table is supported by R1.03 and later versions."
        ::= { hwMonitor 4 }

        cpuUtilizationEntry OBJECT-TYPE
        SYNTAX CpuUtilizationEntry
        MAX-ACCESS not-accessible
        STATUS current
        DESCRIPTION
        	"An entry of cpuUtilizationTable."
        INDEX { chassisId, slotId, cpuIndex }
        ::= { cpuUtilizationTable 1 }

        CpuUtilizationEntry ::=
        	SEQUENCE {
        		cpuIndex	INTEGER,
			cpuCurValue	INTEGER,
			cpuMaxValue	INTEGER,
			cpuHighThresh	INTEGER,
			cpuDescr	DisplayString
           	}

        cpuIndex OBJECT-TYPE
        SYNTAX INTEGER
        MAX-ACCESS read-only
        STATUS current
        DESCRIPTION
		"The identity of the CPU."
        ::= { cpuUtilizationEntry 1 }
        
        cpuCurValue OBJECT-TYPE
        SYNTAX INTEGER
        UNITS "Percent"
        MAX-ACCESS read-only
        STATUS current
        DESCRIPTION
        	"The CPU utilization in the past 60 seconds."
        ::= { cpuUtilizationEntry 2 }

        cpuMaxValue OBJECT-TYPE
        SYNTAX INTEGER
        UNITS "Percent"
        MAX-ACCESS read-only
        STATUS current
        DESCRIPTION
		"The maximum CPU utilization ever detected."
        ::= { cpuUtilizationEntry 3 }
        
        cpuHighThresh OBJECT-TYPE
        SYNTAX INTEGER
        UNITS "Percent"
        MAX-ACCESS read-write
        STATUS current
        DESCRIPTION
		"The high threshold of CPU usage. If cpuCurValue
		is larger than the threshold, the device will initiate the eqptCpuHigh trap.
		This trap is supported by R1.03 and later versions."
        ::= { cpuUtilizationEntry 4 }

        cpuDescr OBJECT-TYPE
        SYNTAX DisplayString
        MAX-ACCESS read-only
        STATUS current
        DESCRIPTION
		"The description of the CPU. This trap is supported by R1.03 and later versions."
        ::= { cpuUtilizationEntry 5 }

-- Packet Buffer Usage Table

        packetBufferUsageTable OBJECT-TYPE
        SYNTAX SEQUENCE OF PacketBufferUsageEntry
        MAX-ACCESS not-accessible
        STATUS current
        DESCRIPTION
		"A table that contains packet buffer usage information."
	::= { hwMonitor 5 }

        packetBufferUsageEntry OBJECT-TYPE
        SYNTAX PacketBufferUsageEntry
        MAX-ACCESS not-accessible
        STATUS current
        DESCRIPTION
        	"An entry of packetBufferUsageTable."
        INDEX { chassisId, slotId, packetBufferIndex }
        ::= { packetBufferUsageTable 1 }

        PacketBufferUsageEntry ::=
        	SEQUENCE {
        		packetBufferIndex	INTEGER,
			packetBufferCurValue	INTEGER,
			packetBufferMaxValue	INTEGER,
			packetBufferHighThresh	INTEGER,
			packetBufferDescr	DisplayString
           	}

        packetBufferIndex OBJECT-TYPE
        SYNTAX INTEGER
        MAX-ACCESS read-only
        STATUS current
        DESCRIPTION
		"The identity of the packet buffer."
        ::= { packetBufferUsageEntry 1 }
        
        packetBufferCurValue OBJECT-TYPE
        SYNTAX INTEGER
        UNITS "Percent"
        MAX-ACCESS read-only
        STATUS current
        DESCRIPTION
        	"The packet buffer usage in the past 60 seconds."
        ::= { packetBufferUsageEntry 2 }

        packetBufferMaxValue OBJECT-TYPE
        SYNTAX INTEGER
        UNITS "Percent"
        MAX-ACCESS read-only
        STATUS current
        DESCRIPTION
		"The maximum packet buffer usage ever detected."
        ::= { packetBufferUsageEntry 3 }
        
        packetBufferHighThresh OBJECT-TYPE
        SYNTAX INTEGER
        UNITS "Percent"
        MAX-ACCESS read-write
        STATUS current
        DESCRIPTION
		"The high threshold of packet buffer usage. If packetBufferCurValue
		is larger than the threshold, the device will initiate the eqptPacketBufferUsageHigh trap."
        ::= { packetBufferUsageEntry 4 }

        packetBufferDescr OBJECT-TYPE
        SYNTAX DisplayString
        MAX-ACCESS read-only
        STATUS current
        DESCRIPTION
		"The description of the packet buffer."
        ::= { packetBufferUsageEntry 5 }
 
-- Memory Usage Table

        memoryUsageTable OBJECT-TYPE
        SYNTAX SEQUENCE OF MemoryUsageEntry
        MAX-ACCESS not-accessible
        STATUS current
        DESCRIPTION
		"A table that contains memory usage information."
	::= { hwMonitor 6 }

        memoryUsageEntry OBJECT-TYPE
        SYNTAX MemoryUsageEntry
        MAX-ACCESS not-accessible
        STATUS current
        DESCRIPTION
        	"An entry of memoryUsageTable."
        INDEX { chassisId, slotId, memoryIndex }
        ::= { memoryUsageTable 1 }

        MemoryUsageEntry ::=
        	SEQUENCE {
        		memoryIndex			INTEGER,
			memoryCurValue			INTEGER,
			memoryMaxValue			INTEGER,
			memoryHighThresh		INTEGER,
			memoryDescr			DisplayString
           	}

        memoryIndex OBJECT-TYPE
        SYNTAX INTEGER
        MAX-ACCESS read-only
        STATUS current
        DESCRIPTION
		"The identity of the memory."
        ::= { memoryUsageEntry 1 }
        
        memoryCurValue OBJECT-TYPE
        SYNTAX INTEGER
        UNITS "Percent"
        MAX-ACCESS read-only
        STATUS current
        DESCRIPTION
        	"The memory usage in the past 60 seconds."
        ::= { memoryUsageEntry 2 }

        memoryMaxValue OBJECT-TYPE
        SYNTAX INTEGER
        UNITS "Percent"
        MAX-ACCESS read-only
        STATUS current
        DESCRIPTION
		"The maximum memory usage ever detected."
        ::= { memoryUsageEntry 3 }
        
        memoryHighThresh OBJECT-TYPE
        SYNTAX INTEGER
        UNITS "Percent"
        MAX-ACCESS read-write
        STATUS current
        DESCRIPTION
		"The high threshold of memory usage. If memoryCurValue
		is larger than the threshold, the device will initiate the eqptMemoryUsageHigh trap."
        ::= { memoryUsageEntry 4 }

        memoryDescr OBJECT-TYPE
        SYNTAX DisplayString
        MAX-ACCESS read-only
        STATUS current
        DESCRIPTION
		"The description of the memory."
        ::= { memoryUsageEntry 5 }
                        
--------------------
-- Time Setup
--------------------

        timeServerMode OBJECT-TYPE
        SYNTAX	INTEGER {
        		none(1),
			daytime(2),
			time(3),
			ntp(4)
		}
	MAX-ACCESS read-write
	STATUS current
	DESCRIPTION
		"The mechanism of Time Server when the system boots up."
	::= { timeSetup 1 }
	
	timeServerIP OBJECT-TYPE
        SYNTAX IpAddress
	MAX-ACCESS read-write
	STATUS current
	DESCRIPTION
		"The IP Address of Time Server."
	::= { timeSetup 2 }
	
	systemTime OBJECT-TYPE
        SYNTAX DisplayString
	MAX-ACCESS read-write
	STATUS current
	DESCRIPTION
		"The system time in the format 'HH:MM:SS'."
	::= { timeSetup 3 }
		
	systemDate OBJECT-TYPE
        SYNTAX DisplayString
	MAX-ACCESS read-write
	STATUS current
	DESCRIPTION
		"The system date in the format 'YYYY-MM-DD'"
	::= { timeSetup 4 }
	
	systemTimeZone OBJECT-TYPE
	SYNTAX INTEGER {
        		utc-minus-1200(1),
        		utc-minus-1100(2),
        		utc-minus-1000(3),
        		utc-minus-0900(4),
        		utc-minus-0800(5),
        		utc-minus-0700(6),
        		utc-minus-0600(7),
        		utc-minus-0500(8),
        		utc-minus-0400(9),
        		utc-minus-0300(10),
        		utc-minus-0200(11),
        		utc-minus-0100(12),
        		utc(13),
        		utc-plus-0100(14),
        		utc-plus-0200(15),
        		utc-plus-0300(16),
        		utc-plus-0400(17),
        		utc-plus-0500(18),
        		utc-plus-0600(19),
        		utc-plus-0700(20),
        		utc-plus-0800(21),
        		utc-plus-0900(22),
        		utc-plus-1000(23),
        		utc-plus-1100(24),
        		utc-plus-1200(25),
        		utc-minus-0330(26),
        		utc-plus-0330(27),
        		utc-plus-0430(28),
        		utc-plus-0530(29),
        		utc-plus-0545(30),
        		utc-plus-0630(31),
        		utc-plus-0930(32),
        		utc-plus-1300(33)
		}
	MAX-ACCESS read-write
	STATUS current
	DESCRIPTION
		"The system time zone."
	::= { timeSetup 5 }

	timeServerSync OBJECT-TYPE
        SYNTAX INTEGER
	MAX-ACCESS read-write
	STATUS current
	DESCRIPTION
		"Set the object to 1 to synchronize with the time server."
	::= { timeSetup 6 }

-- 	dayLightSaving 

	dayLightSaving	OBJECT IDENTIFIER ::= { timeSetup 7 }
	
	dayLightSavingAdminStatus OBJECT-TYPE
	SYNTAX INTEGER {
        		enable(1),
        		disable(2)
		}
	MAX-ACCESS read-write
	STATUS current
	DESCRIPTION
		""
	::= { dayLightSaving 1 }	  
	
	dayLightSavingStartTime	OBJECT IDENTIFIER ::= { dayLightSaving 2 }
	
	dayLightSavingStartMonth OBJECT-TYPE
	SYNTAX INTEGER {
        		jan(1),
        		feb(2),
        		mar(3), 
				apr(4),
				may(5), 
				jun(6), 
				jul(7), 
				aug(8), 
				sep(9), 
				oct(10), 
				nov(11), 
				dec(12)
		}
	MAX-ACCESS read-write
	STATUS current
	DESCRIPTION
		""
	::= { dayLightSavingStartTime 1 } 
	
	dayLightSavingStartWeek OBJECT-TYPE
	SYNTAX INTEGER {
        		first(1), 
				second(2), 
				third(3), 
				fourth(4), 
				last(5)
		}
	MAX-ACCESS read-write
	STATUS current
	DESCRIPTION
		""
	::= { dayLightSavingStartTime 2 } 
	
	dayLightSavingStartWday OBJECT-TYPE
	SYNTAX INTEGER {
        		sun(1), 
				mon(2), 
				tus(3), 
				wed(4), 
				thu(5), 
				fri(6), 
				sat(7)
		}
	MAX-ACCESS read-write
	STATUS current
	DESCRIPTION
		""
	::= { dayLightSavingStartTime 3 } 
	
	dayLightSavingStartHour OBJECT-TYPE
	SYNTAX INTEGER (1..24)
	MAX-ACCESS read-write
	STATUS current
	DESCRIPTION
		"1: 01:00,
		2: 02:00
		3: 03:00
		4: 04:00
		5: 05:00
		6: 06:00
		7: 07:00
		8: 08:00
		9: 09:00
		10: 10:00
		11: 11:00
		12: 12:00
		13: 13:00
		14: 14:00
		15: 15:00
		16: 16:00
		17: 17:00
		18: 18:00
		19: 19:00
		20: 20:00
		21: 21:00
		22: 22:00
		23: 23:00
		24: 00:00"
	::= { dayLightSavingStartTime 4 }

	
	dayLightSavingEndTime	OBJECT IDENTIFIER ::= { dayLightSaving 3 }
	
	dayLightSavingEndMonth OBJECT-TYPE
	SYNTAX INTEGER {
        		jan(1),
        		feb(2),
        		mar(3), 
				apr(4),
				may(5), 
				jun(6), 
				jul(7), 
				aug(8), 
				sep(9), 
				oct(10), 
				nov(11), 
				dec(12)
		}
	MAX-ACCESS read-write
	STATUS current
	DESCRIPTION
		""
	::= { dayLightSavingEndTime 1 } 
	
	dayLightSavingEndWeek OBJECT-TYPE
	SYNTAX INTEGER {
        		first(1), 
				second(2), 
				third(3), 
				fourth(4), 
				last(5)
		}
	MAX-ACCESS read-write
	STATUS current
	DESCRIPTION
		""
	::= { dayLightSavingEndTime 2 } 
	
	dayLightSavingEndWday OBJECT-TYPE
	SYNTAX INTEGER {
        		sun(1), 
				mon(2), 
				tus(3), 
				wed(4), 
				thu(5), 
				fri(6), 
				sat(7)
		}
	MAX-ACCESS read-write
	STATUS current
	DESCRIPTION
		""
	::= { dayLightSavingEndTime 3 } 
	
	dayLightSavingEndHour OBJECT-TYPE
	SYNTAX INTEGER (1..24)
	MAX-ACCESS read-write
	STATUS current
	DESCRIPTION
		"1: 01:00,
		2: 02:00
		3: 03:00
		4: 04:00
		5: 05:00
		6: 06:00
		7: 07:00
		8: 08:00
		9: 09:00
		10: 10:00
		11: 11:00
		12: 12:00
		13: 13:00
		14: 14:00
		15: 15:00
		16: 16:00
		17: 17:00
		18: 18:00
		19: 19:00
		20: 20:00
		21: 21:00
		22: 22:00
		23: 23:00
		24: 00:00"
	::= { dayLightSavingEndTime 4 }


	timeServerInetAddrType OBJECT-TYPE
    SYNTAX InetAddressType
	MAX-ACCESS read-write
	STATUS current
	DESCRIPTION
		"The IP Address type."
	::= { timeSetup 8 }	
	
	timeServerInetAddr OBJECT-TYPE
    SYNTAX InetAddress
	MAX-ACCESS read-write
	STATUS current
	DESCRIPTION
		"The IP Address of Time Server."
	::= { timeSetup 9 }
--------------------	
-- Access Control
--------------------

-- Access Control Table
	
        accessCtrlTable OBJECT-TYPE
        SYNTAX SEQUENCE OF AccessCtrlEntry
        MAX-ACCESS not-accessible
        STATUS current
        DESCRIPTION
		"A table that contains information about service access control."
        ::= { accessCtrl 1 }

        accessCtrlEntry OBJECT-TYPE
        SYNTAX AccessCtrlEntry
        MAX-ACCESS not-accessible
        STATUS current
        DESCRIPTION
		"A list of access control entry."
        INDEX { accessCtrlService }
        ::= { accessCtrlTable 1 }

        AccessCtrlEntry ::=
        	SEQUENCE {
        		accessCtrlService	INTEGER,
			accessCtrlEnable	INTEGER,
			accessCtrlPort		INTEGER
           	}

        accessCtrlService OBJECT-TYPE
        SYNTAX  INTEGER {
			telnet(1),
			ftp(2),
			web(3),
			icmp(4),
			ssh(5),
			snmp(6),
			https(7)
		}
        MAX-ACCESS read-only
        STATUS current
        DESCRIPTION
		"The service type of the access control entry."
        ::= { accessCtrlEntry 1 }

        accessCtrlEnable OBJECT-TYPE
        SYNTAX  INTEGER {
			enable(1),
			disable(2)
		}
        MAX-ACCESS read-write
        STATUS current
        DESCRIPTION
		"Enable/disable the service."
        ::= { accessCtrlEntry 2 }

        accessCtrlPort OBJECT-TYPE
        SYNTAX INTEGER
        MAX-ACCESS read-write
        STATUS current
        DESCRIPTION
        	"The port number which the service uses."
        ::= { accessCtrlEntry 3 }

-- Secured Client Table

        securedClientTable OBJECT-TYPE
        SYNTAX SEQUENCE OF SecuredClientEntry
        MAX-ACCESS not-accessible
        STATUS current
        DESCRIPTION
		"A table that contains information about secured clients."
        ::= { accessCtrl 2 }

        securedClientEntry OBJECT-TYPE
        SYNTAX SecuredClientEntry
        MAX-ACCESS not-accessible
        STATUS current
        DESCRIPTION
        	"A list of secured client entry."
        INDEX { securedClientIndex }
        ::= { securedClientTable 1 }

        SecuredClientEntry ::=
        	SEQUENCE {
        		securedClientIndex	INTEGER,
        		securedClientStartIp	IpAddress,
			securedClientEndIp	IpAddress,
			securedClientService	INTEGER,
			securedClientEnable	INTEGER				
           	}

        securedClientIndex OBJECT-TYPE
        SYNTAX INTEGER
        MAX-ACCESS read-only
        STATUS current
        DESCRIPTION
		"The index of the entry."
        ::= { securedClientEntry 1 }
        
        securedClientStartIp OBJECT-TYPE
        SYNTAX IpAddress
        MAX-ACCESS read-write
        STATUS current
        DESCRIPTION
		"The starting IP address of the secured client set."
        ::= { securedClientEntry 2 }

        securedClientEndIp OBJECT-TYPE
        SYNTAX IpAddress
        MAX-ACCESS read-write
        STATUS current
        DESCRIPTION
		"The ending IP address of the secured client set."
        ::= { securedClientEntry 3 }

        securedClientService OBJECT-TYPE
        SYNTAX INTEGER
        MAX-ACCESS read-write
        STATUS current
        DESCRIPTION
		"Each bit corresponds to a service. The bit is set to 1 if the
		service is enabled, and set to 0 if the service is disabled.
		The various bit positions are:
		BIT 1: telnet
		BIT 2: ftp
		BIT 3: web
		BIT 4: icmp
		BIT 5: ssh
		BIT 6: snmp
		BIT 7: https."
        ::= { securedClientEntry 4 }

        securedClientEnable OBJECT-TYPE
        SYNTAX INTEGER {
        	enable(1),
        	disable(2)
        }
        MAX-ACCESS read-write
        STATUS current
        DESCRIPTION
		"Enable/disable the entry."
        ::= { securedClientEntry 5 }  

-- Secured Client Inet Table

        securedClientInetTable OBJECT-TYPE
        SYNTAX SEQUENCE OF SecuredClientInetEntry
        MAX-ACCESS not-accessible
        STATUS current
        DESCRIPTION
		"A table that contains information about secured clients."
        ::= { accessCtrl 3 }

        securedClientInetEntry OBJECT-TYPE
        SYNTAX SecuredClientInetEntry
        MAX-ACCESS not-accessible
        STATUS current
        DESCRIPTION
        	"A list of secured client inet entry."
        INDEX { securedClientInetIndex }
        ::= { securedClientInetTable 1 }

        SecuredClientInetEntry ::=
        	SEQUENCE {
        		securedClientInetIndex		INTEGER,
        		securedClientInetAddrType	InetAddressType,	
        		securedClientInetAddr		InetAddress,
				securedClientInetMask		INTEGER,
				securedClientInetService	INTEGER,
				securedClientInetEnable		INTEGER				
           	}

        securedClientInetIndex OBJECT-TYPE
        SYNTAX INTEGER
        MAX-ACCESS read-only
        STATUS current
        DESCRIPTION
		"The index of the entry."
        ::= { securedClientInetEntry 1 }
        
        securedClientInetAddrType OBJECT-TYPE
        SYNTAX InetAddressType
        MAX-ACCESS read-write
        STATUS current
        DESCRIPTION
		""
        ::= { securedClientInetEntry 2 }

        securedClientInetAddr OBJECT-TYPE
        SYNTAX InetAddress
        MAX-ACCESS read-write
        STATUS current
        DESCRIPTION
		""
        ::= { securedClientInetEntry 3 } 
        
        securedClientInetMask OBJECT-TYPE
        SYNTAX INTEGER
        MAX-ACCESS read-write
        STATUS current
        DESCRIPTION
		""
        ::= { securedClientInetEntry 4 }

        securedClientInetService OBJECT-TYPE
        SYNTAX INTEGER
        MAX-ACCESS read-write
        STATUS current
        DESCRIPTION
		"Each bit corresponds to a service. The bit is set to 1 if the
		service is enabled, and set to 0 if the service is disabled.
		The various bit positions are:
		BIT 1: telnet
		BIT 2: ftp
		BIT 3: web
		BIT 4: icmp
		BIT 5: ssh
		BIT 6: snmp
		BIT 7: https."
        ::= { securedClientInetEntry 5 } 
        
        securedClientInetEnable OBJECT-TYPE
        SYNTAX INTEGER {
        	enable(1),
        	disable(2)
        }
        MAX-ACCESS read-write
        STATUS current
        DESCRIPTION
		"Enable/disable the entry."
        ::= { securedClientInetEntry 6 }
                
--------------------
-- syslog
--------------------

        syslogEnable OBJECT-TYPE
        SYNTAX INTEGER {
        	enable(1),
        	disable(2)
        }
        MAX-ACCESS read-write
        STATUS current
        DESCRIPTION
		"Enable/disable syslog function."
        ::= { syslog 1 }

        syslogTable OBJECT-TYPE
        SYNTAX SEQUENCE OF SyslogEntry
        MAX-ACCESS not-accessible
        STATUS current
        DESCRIPTION
		"A table that contains syslog configuration."
        ::= { syslog 2 }

        syslogEntry OBJECT-TYPE
        SYNTAX SyslogEntry
        MAX-ACCESS not-accessible
        STATUS current
        DESCRIPTION
        	"A list of syslog entry."
        INDEX { syslogFacility }
        ::= { syslogTable 1 }

        SyslogEntry ::=
        	SEQUENCE {
        		syslogFacility	INTEGER,
        		syslogServer	IpAddress,
        		syslogServerInetAddrType	InetAddressType,
       			syslogServerInetAddr		InetAddress 			
           	}
           	
        syslogFacility OBJECT-TYPE
        SYNTAX INTEGER {
		local0(0),        
		local1(1),
		local2(2),
		local3(3),
		local4(4),
		local5(5),
		local6(6),
		local7(7)
	}
        MAX-ACCESS read-only
        STATUS current
        DESCRIPTION
		"Log facility."
        ::= { syslogEntry 1 }
                
        syslogServer OBJECT-TYPE
        SYNTAX IpAddress
        MAX-ACCESS read-write
        STATUS current
        DESCRIPTION
		"IP address of the syslog server."
        ::= { syslogEntry 2 }  
        
        syslogServerInetAddrType OBJECT-TYPE
        SYNTAX InetAddressType
        MAX-ACCESS read-write
        STATUS current
        DESCRIPTION
		"The IP Address type."
        ::= { syslogEntry 3 }
        
        syslogServerInetAddr OBJECT-TYPE
        SYNTAX InetAddress
        MAX-ACCESS read-write
        STATUS current
        DESCRIPTION
		"IP address of the syslog server."
        ::= { syslogEntry 4 }

--------------------
-- SNMP Setup
--------------------

-- trapDestTable
	
	trapDestTable OBJECT-TYPE
    	SYNTAX SEQUENCE OF TrapDestEntry
    	MAX-ACCESS not-accessible
    	STATUS current
    	DESCRIPTION
                "A table that contains SNMP trap destination information."
    	::= { snmp 1 }

    	trapDestEntry OBJECT-TYPE
        SYNTAX TrapDestEntry
        MAX-ACCESS not-accessible
        STATUS current
        DESCRIPTION
        	"The entry of SNMP trap destination table."
        INDEX { trapDestIndex }
        ::= { trapDestTable 1 }

   	TrapDestEntry ::=
        	SEQUENCE {
        		trapDestIndex		INTEGER,
            		trapDestIp		IpAddress,
            		trapDestPort		INTEGER,
            		trapDestSnmpVersion	INTEGER,
            		trapDestUserName	DisplayString,
            		trapDestInetAddrType	InetAddressType,
            		trapDestInetAddr		InetAddress
    	   	} 

	trapDestIndex OBJECT-TYPE
	SYNTAX INTEGER
	MAX-ACCESS read-only
	STATUS current
	DESCRIPTION
		"The index of the entry."
	::= { trapDestEntry 1 }
	           	
	trapDestIp OBJECT-TYPE
	SYNTAX IpAddress
	MAX-ACCESS read-write
	STATUS current
	DESCRIPTION
		"The IP address of the trap destination."
	::= { trapDestEntry 2 }

	trapDestPort OBJECT-TYPE
	SYNTAX INTEGER
	MAX-ACCESS read-write
	STATUS current
	DESCRIPTION
		"The UDP port of the trap destination."
	::= { trapDestEntry 3 }

	trapDestSnmpVersion OBJECT-TYPE
	SYNTAX  INTEGER {
			v1(1),
			v2c(2),
			v3(3)
		}
	MAX-ACCESS read-write
	STATUS current
	DESCRIPTION
		"The SNMP protocol version to send traps."
	::= { trapDestEntry 4 }
	
	trapDestUserName OBJECT-TYPE
	SYNTAX DisplayString
	MAX-ACCESS read-write
	STATUS current
	DESCRIPTION
		"The user name for sending SNMPv3 traps."
	::= { trapDestEntry 5 } 
	
	trapDestInetAddrType OBJECT-TYPE
	SYNTAX InetAddressType
	MAX-ACCESS read-write
	STATUS current
	DESCRIPTION
		"The IP Address type."
	::= { trapDestEntry 6 }
	
	trapDestInetAddr OBJECT-TYPE
	SYNTAX InetAddress
	MAX-ACCESS read-write
	STATUS current
	DESCRIPTION
		"The IP address of the trap destination."
	::= { trapDestEntry 7 }
	
				
	snmpGetCommunity OBJECT-TYPE
	SYNTAX DisplayString (SIZE (1..31))
	MAX-ACCESS read-write
	STATUS current
	DESCRIPTION
		"The SNMP get community."
	::= { snmp 2 }

	snmpSetCommunity OBJECT-TYPE
	SYNTAX DisplayString (SIZE (1..31))
	MAX-ACCESS read-write
	STATUS current
	DESCRIPTION
		"The SNMP set community."
	::= { snmp 3 }
	
	snmpTrapCommunity OBJECT-TYPE
	SYNTAX DisplayString (SIZE(1..31))
	MAX-ACCESS read-write
	STATUS current
	DESCRIPTION
		"The SNMP trap community."
	::= { snmp 4 }

-- snmpUserTable
	
	snmpUserTable OBJECT-TYPE
    	SYNTAX SEQUENCE OF SnmpUserEntry
    	MAX-ACCESS not-accessible
    	STATUS current
    	DESCRIPTION
                "A table that contains SNMPv3 user information."
    	::= { snmp 5 }

    	snmpUserEntry OBJECT-TYPE
        SYNTAX SnmpUserEntry
        MAX-ACCESS not-accessible
        STATUS current
        DESCRIPTION
        	"An entry of snmpUserTable."
        INDEX { IMPLIED snmpUserName }
        ::= { snmpUserTable 1 }

   	SnmpUserEntry ::=
        	SEQUENCE {
            		snmpUserName		DisplayString,
            		snmpUserSecurityLevel	INTEGER,
            		snmpUserAuthProtocol	INTEGER,
            		snmpUserPrivProtocol	INTEGER
    	   	} 

	snmpUserName OBJECT-TYPE
	SYNTAX DisplayString
	MAX-ACCESS read-only
	STATUS current
	DESCRIPTION
		"The user name."
	::= { snmpUserEntry 1 }

	snmpUserSecurityLevel OBJECT-TYPE
	SYNTAX  INTEGER {
			noAuthNoPriv(1),
			authNoPriv(2),
			authPriv(3)
		}
	MAX-ACCESS read-write
	STATUS current
	DESCRIPTION
		"The level of security at which SNMP messages can be sent or 
		with which operations are being processed."
	::= { snmpUserEntry 2 }	

	snmpUserAuthProtocol OBJECT-TYPE
	SYNTAX  INTEGER {
			md5(1),
			sha(2)
		}
	MAX-ACCESS read-write
	STATUS current
	DESCRIPTION
		"The type of authentication protocol to be used."
	::= { snmpUserEntry 3 }

	snmpUserPrivProtocol OBJECT-TYPE
	SYNTAX 	INTEGER {
			des(1),
			aes(2)
		}
	MAX-ACCESS read-write
	STATUS current
	DESCRIPTION
		"The type of privacy protocol to be used."
	::= { snmpUserEntry 4 }

	snmpVersion OBJECT-TYPE
	SYNTAX 	INTEGER {
			v2c(1),
			v3(2),
			v3v2c(3)
		}
	MAX-ACCESS read-write
	STATUS current
	DESCRIPTION
		"The SNMP version to be used. v3v2c means that the manager 
		can get/set by SNMPv3 and can get by SNMPv2c."
	::= { snmp 6 }
	
--------------------
-- User Management
--------------------

-- userTable
	
	userTable OBJECT-TYPE
    	SYNTAX SEQUENCE OF UserEntry
    	MAX-ACCESS not-accessible
    	STATUS current
    	DESCRIPTION
                "A table that contains user information."
    	::= { user 5 }

    	userEntry OBJECT-TYPE
        SYNTAX UserEntry
        MAX-ACCESS not-accessible
        STATUS current
        DESCRIPTION
        	"An entry of userTable."
        INDEX { IMPLIED userName }
        ::= { userTable 1 }

   	UserEntry ::=
        	SEQUENCE {
            		userName		DisplayString,
            		userPassword		DisplayString,
            		userPriviledge		INTEGER,
            		userRowStatus		RowStatus
    	   	} 

	userName OBJECT-TYPE
	SYNTAX DisplayString
	MAX-ACCESS read-only
	STATUS current
	DESCRIPTION
		"The user name."
	::= { userEntry 1 }

	userPassword OBJECT-TYPE
	SYNTAX DisplayString
	MAX-ACCESS read-create
	STATUS current
	DESCRIPTION
		"The user password."
	::= { userEntry 2 }
	
	userPriviledge OBJECT-TYPE
	SYNTAX  INTEGER (1..14)
	MAX-ACCESS read-create
	STATUS current
	DESCRIPTION
		"The user privilege to decide what operation the user can and cannot do."
	::= { userEntry 3 }
	
	userRowStatus OBJECT-TYPE
	SYNTAX RowStatus
	MAX-ACCESS read-create
	STATUS current
	DESCRIPTION
		"The row status used to create or delete a user."
	::= { userEntry 4 }

--------------------
-- AAA
--------------------
auth			OBJECT IDENTIFIER ::= { aaa 1 }
acct			OBJECT IDENTIFIER ::= { aaa 2 } 
radius			OBJECT IDENTIFIER ::= { aaa 3 } 
tacacsplus		OBJECT IDENTIFIER ::= { aaa 4 } 
author			OBJECT IDENTIFIER ::= { aaa 5 } 

-- auth

	loginMethod1 OBJECT-TYPE
		SYNTAX  INTEGER {
				local(1),
				radius(2),
				tacacsplus(3)
			}
		MAX-ACCESS read-write
		STATUS current
		DESCRIPTION
			""
		::= { auth 1 }   

	loginMethod2 OBJECT-TYPE
		SYNTAX  INTEGER {
				none(0),
				local(1),
				radius(2),
				tacacsplus(3)
			}
		MAX-ACCESS read-write
		STATUS current
		DESCRIPTION
			""
		::= { auth 2 }  
		
	loginMethod3 OBJECT-TYPE
		SYNTAX  INTEGER {
				none(0),
				local(1),
				radius(2),
				tacacsplus(3)
			}
		MAX-ACCESS read-write
		STATUS current
		DESCRIPTION
			""
		::= { auth 3 }     
		
	enableMethod1 OBJECT-TYPE
		SYNTAX  INTEGER {
				enable(1),
				tacacsplus(2)
			}
		MAX-ACCESS read-write
		STATUS current
		DESCRIPTION
			"The first method of enable authentication.
			This MIB object is supported by R5.06 and later versions."
		::= { auth 4 }

	enableMethod2 OBJECT-TYPE
		SYNTAX  INTEGER {
				none(0),
				enable(1),
				tacacsplus(2)
			}
		MAX-ACCESS read-write
		STATUS current
		DESCRIPTION
			"The second method of enable authentication.
			This MIB object is supported by R5.06 and later versions."
		::= { auth 5 }

	loginTryCont OBJECT-TYPE
		SYNTAX  INTEGER {
				off(1),
				on(2)
			}
		MAX-ACCESS read-write
		STATUS current
		DESCRIPTION
			"Set to '1' so that the system try next login method only when previous method is not available.
			Set to '2' so that the system will try next login method when previous method does not authenticate the user."
		::= { auth 6 }

-- acct
	systemActive OBJECT-TYPE
		SYNTAX  INTEGER {
				enable(1),
				disable(2)
			}
		MAX-ACCESS read-write
		STATUS current
		DESCRIPTION
			""
		::= { acct 1 }

	systemMethod OBJECT-TYPE
		SYNTAX  INTEGER {
				radius(1),
				tacacsplus(2)
			}
		MAX-ACCESS read-write
		STATUS current
		DESCRIPTION
			""
		::= { acct 2 } 
		
	systemBroadcast OBJECT-TYPE
		SYNTAX  INTEGER {
				enable(1),
				disable(2)
			}
		MAX-ACCESS read-write
		STATUS current
		DESCRIPTION
			""
		::= { acct 3 } 

	execActive OBJECT-TYPE
		SYNTAX  INTEGER {
				enable(1),
				disable(2)
			}
		MAX-ACCESS read-write
		STATUS current
		DESCRIPTION
			""
		::= { acct 4 }
		
	execMethod OBJECT-TYPE
		SYNTAX  INTEGER {
				radius(1),
				tacacsplus(2)
			}
		MAX-ACCESS read-write
		STATUS current
		DESCRIPTION
			""
		::= { acct 5 }

	execMode OBJECT-TYPE
		SYNTAX  INTEGER {
				start-stop(1),
				stop-only(2)
			}
		MAX-ACCESS read-write
		STATUS current
		DESCRIPTION
			""
		::= { acct 6 }

	execBroadcast OBJECT-TYPE
		SYNTAX  INTEGER {
				enable(1),
				disable(2)
			}
		MAX-ACCESS read-write
		STATUS current
		DESCRIPTION
			""
		::= { acct 7 } 

	commandsActive OBJECT-TYPE
		SYNTAX  INTEGER {
				enable(1),
				disable(2)
			}
		MAX-ACCESS read-write
		STATUS current
		DESCRIPTION
			""
		::= { acct 8 }   
		
	commandsPrivilege OBJECT-TYPE
		SYNTAX  INTEGER (1..14)
		MAX-ACCESS read-write
		STATUS current
		DESCRIPTION
			"1~14"
		::= { acct 9 } 
		
	commandsBroadcast OBJECT-TYPE
		SYNTAX  INTEGER {
				enable(1),
				disable(2)
			}
		MAX-ACCESS read-write
		STATUS current
		DESCRIPTION
			""
		::= { acct 10 }

	updatePeriod OBJECT-TYPE
		SYNTAX  Unsigned32 (1..2147483647) 
		MAX-ACCESS read-write
		STATUS current
		DESCRIPTION
			"1~2147483647 minutes"
		::= { acct 11 }

-- radius
radiusAuth			OBJECT IDENTIFIER ::= { radius 1 }
radiusAcct			OBJECT IDENTIFIER ::= { radius 2 } 
	
	-- radiusAuth
	radiusAuthRedundantMode OBJECT-TYPE
		SYNTAX  INTEGER {
				index-priority(1),
				round-robin(2)
			}
		MAX-ACCESS read-write
		STATUS current
		DESCRIPTION
			""
		::= { radiusAuth 1 } 
		
	radiusAuthTimeoutPeriod OBJECT-TYPE
		SYNTAX  INTEGER (1..1000)
		MAX-ACCESS read-write
		STATUS current
		DESCRIPTION
			"1~1000 seconds"
		::= { radiusAuth 2 } 
		
	radiusAuthServerTable OBJECT-TYPE
    	SYNTAX SEQUENCE OF RadiusAuthServerEntry
    	MAX-ACCESS not-accessible
    	STATUS current
    	DESCRIPTION
                ""
    	::= { radiusAuth 3 }

    	radiusAuthServerEntry OBJECT-TYPE
        SYNTAX RadiusAuthServerEntry
        MAX-ACCESS not-accessible
        STATUS current
        DESCRIPTION
        	"An entry of radiusAuthServerTable."
        INDEX { radiusAuthServerIndex  }
        ::= { radiusAuthServerTable 1 }

   	RadiusAuthServerEntry ::=
        	SEQUENCE {
            		radiusAuthServerIndex		INTEGER,
            		radiusAuthServerIP			IpAddress,
            		radiusAuthServerPort		INTEGER,
            		radiusAuthServerSecret		DisplayString
    	   	} 

	radiusAuthServerIndex OBJECT-TYPE
	SYNTAX INTEGER (1..2)
	MAX-ACCESS read-only
	STATUS current
	DESCRIPTION
		""
	::= { radiusAuthServerEntry 1 }

	radiusAuthServerIP OBJECT-TYPE
	SYNTAX IpAddress
	MAX-ACCESS read-write
	STATUS current
	DESCRIPTION
		""
	::= { radiusAuthServerEntry 2 }  
	
	radiusAuthServerPort OBJECT-TYPE
	SYNTAX INTEGER
	MAX-ACCESS read-write
	STATUS current
	DESCRIPTION
		""
	::= { radiusAuthServerEntry 3 }  
	
	radiusAuthServerSecret OBJECT-TYPE
	SYNTAX DisplayString
	MAX-ACCESS read-write
	STATUS current
	DESCRIPTION
		""
	::= { radiusAuthServerEntry 4 }

	-- radiusAcct
	radiusAcctTimeoutPeriod OBJECT-TYPE
		SYNTAX  INTEGER (1..1000)
		MAX-ACCESS read-write
		STATUS current
		DESCRIPTION
			"1~1000 seconds"
		::= { radiusAcct 1 }

	radiusAcctServerTable OBJECT-TYPE
    	SYNTAX SEQUENCE OF RadiusAcctServerEntry
    	MAX-ACCESS not-accessible
    	STATUS current
    	DESCRIPTION
                ""
    	::= { radiusAcct 2 }

    	radiusAcctServerEntry OBJECT-TYPE
        SYNTAX RadiusAcctServerEntry
        MAX-ACCESS not-accessible
        STATUS current
        DESCRIPTION
        	"An entry of radiusAcctServerTable."
        INDEX { radiusAcctServerIndex  }
        ::= { radiusAcctServerTable 1 }

   	RadiusAcctServerEntry ::=
        	SEQUENCE {
            		radiusAcctServerIndex		INTEGER,
            		radiusAcctServerIP			IpAddress,
            		radiusAcctServerPort		INTEGER,
            		radiusAcctServerSecret		DisplayString
    	   	} 

	radiusAcctServerIndex OBJECT-TYPE
	SYNTAX INTEGER (1..2)
	MAX-ACCESS read-only
	STATUS current
	DESCRIPTION
		""
	::= { radiusAcctServerEntry 1 }

	radiusAcctServerIP OBJECT-TYPE
	SYNTAX IpAddress
	MAX-ACCESS read-write
	STATUS current
	DESCRIPTION
		""
	::= { radiusAcctServerEntry 2 }  
	
	radiusAcctServerPort OBJECT-TYPE
	SYNTAX INTEGER
	MAX-ACCESS read-write
	STATUS current
	DESCRIPTION
		""
	::= { radiusAcctServerEntry 3 }  
	
	radiusAcctServerSecret OBJECT-TYPE
	SYNTAX DisplayString
	MAX-ACCESS read-write
	STATUS current
	DESCRIPTION
		""
	::= { radiusAcctServerEntry 4 }	
	
	radiusAcctRedundantMode OBJECT-TYPE
		SYNTAX  INTEGER {
				index-priority(1),
				round-robin(2)
			} 
		MAX-ACCESS read-write
		STATUS current
		DESCRIPTION
			"Redundant mode of accounting via RADIUS.
			This MIB object is supported by R5.06 and later versions"
		::= { radiusAcct 3 }
					
-- tacacsplus
tacacsplusAuth			OBJECT IDENTIFIER ::= { tacacsplus 1 }
tacacsplusAcct			OBJECT IDENTIFIER ::= { tacacsplus 2 }
tacacsplusAuthor		OBJECT IDENTIFIER ::= { tacacsplus 3 } 
	
	-- tacacsplusAuth
	tacacsplusAuthRedundantMode OBJECT-TYPE
		SYNTAX  INTEGER {
				index-priority(1),
				round-robin(2)
			}
		MAX-ACCESS read-write
		STATUS current
		DESCRIPTION
			""
		::= { tacacsplusAuth 1 } 
		
	tacacsplusAuthTimeoutPeriod OBJECT-TYPE
		SYNTAX  INTEGER (1..1000)
		MAX-ACCESS read-write
		STATUS current
		DESCRIPTION
			"1~1000 seconds"
		::= { tacacsplusAuth 2 } 
		
	tacacsplusAuthServerTable OBJECT-TYPE
    	SYNTAX SEQUENCE OF TacacsplusAuthServerEntry
    	MAX-ACCESS not-accessible
    	STATUS current
    	DESCRIPTION
                ""
    	::= { tacacsplusAuth 3 }

    	tacacsplusAuthServerEntry OBJECT-TYPE
        SYNTAX TacacsplusAuthServerEntry
        MAX-ACCESS not-accessible
        STATUS current
        DESCRIPTION
        	"An entry of tacacsplusAuthServerTable."
        INDEX { tacscsplusAuthServerIndex   }
        ::= { tacacsplusAuthServerTable 1 }

   	TacacsplusAuthServerEntry ::=
        	SEQUENCE {
            		tacscsplusAuthServerIndex		INTEGER,
            		tacscsplusAuthServerIP			IpAddress,
            		tacscsplusAuthServerPort		INTEGER,
            		tacscsplusAuthServerSecret		DisplayString
    	   	} 

	tacscsplusAuthServerIndex OBJECT-TYPE
	SYNTAX INTEGER (1..2)
	MAX-ACCESS read-only
	STATUS current
	DESCRIPTION
		""
	::= { tacacsplusAuthServerEntry 1 }

	tacscsplusAuthServerIP OBJECT-TYPE
	SYNTAX IpAddress
	MAX-ACCESS read-write
	STATUS current
	DESCRIPTION
		""
	::= { tacacsplusAuthServerEntry 2 }  
	
	tacscsplusAuthServerPort OBJECT-TYPE
	SYNTAX INTEGER
	MAX-ACCESS read-write
	STATUS current
	DESCRIPTION
		""
	::= { tacacsplusAuthServerEntry 3 }  
	
	tacscsplusAuthServerSecret OBJECT-TYPE
	SYNTAX DisplayString
	MAX-ACCESS read-write
	STATUS current
	DESCRIPTION
		""
	::= { tacacsplusAuthServerEntry 4 }

	-- tacacsplusAcct 
	tacacsplusAcctTimeoutPeriod OBJECT-TYPE
		SYNTAX  INTEGER (1..1000)
		MAX-ACCESS read-write
		STATUS current
		DESCRIPTION
			"1~1000 seconds."
		::= { tacacsplusAcct 1 }

	tacacsplusAcctServerTable OBJECT-TYPE
    	SYNTAX SEQUENCE OF TacacsplusAcctServerEntry
    	MAX-ACCESS not-accessible
    	STATUS current
    	DESCRIPTION
                ""
    	::= { tacacsplusAcct 2 }

    	tacacsplusAcctServerEntry OBJECT-TYPE
        SYNTAX TacacsplusAcctServerEntry
        MAX-ACCESS not-accessible
        STATUS current
        DESCRIPTION
        	"An entry of tacacsplusAcctServerTable."
        INDEX { tacacsplusAcctServerIndex  }
        ::= { tacacsplusAcctServerTable 1 }

   	TacacsplusAcctServerEntry ::=
        	SEQUENCE {
            		tacacsplusAcctServerIndex		INTEGER,
            		tacacsplusAcctServerIP			IpAddress,
            		tacacsplusAcctServerPort		INTEGER,
            		tacacsplusAcctServerSecret		DisplayString
    	   	} 

	tacacsplusAcctServerIndex OBJECT-TYPE
	SYNTAX INTEGER (1..2)
	MAX-ACCESS read-only
	STATUS current
	DESCRIPTION
		""
	::= { tacacsplusAcctServerEntry 1 }

	tacacsplusAcctServerIP OBJECT-TYPE
	SYNTAX IpAddress
	MAX-ACCESS read-write
	STATUS current
	DESCRIPTION
		""
	::= { tacacsplusAcctServerEntry 2 }  
	
	tacacsplusAcctServerPort OBJECT-TYPE
	SYNTAX INTEGER
	MAX-ACCESS read-write
	STATUS current
	DESCRIPTION
		""
	::= { tacacsplusAcctServerEntry 3 }  
	
	tacacsplusAcctServerSecret OBJECT-TYPE
	SYNTAX DisplayString
	MAX-ACCESS read-write
	STATUS current
	DESCRIPTION
		""
	::= { tacacsplusAcctServerEntry 4 }	
	
	tacacsplusAcctRedundantMode OBJECT-TYPE
		SYNTAX  INTEGER {
				index-priority(1),
				round-robin(2)
			}
		MAX-ACCESS read-write
		STATUS current
		DESCRIPTION
			"Redundant mode of accounting via TACACS+. 
			This MIB object is supported by R5.06 and later versions."
		::= { tacacsplusAcct 3 }

	-- tacacsplusAuthor This table is supported by R5.06 and later versions.
	tacacsplusAuthorRedundantMode OBJECT-TYPE
		SYNTAX  INTEGER {
				index-priority(1),
				round-robin(2)
			}
		MAX-ACCESS read-write
		STATUS current
		DESCRIPTION
			"Redundant mode of command authorization via TACACS+
			This MIB Object is supported by R5.06 and later versions."
		::= { tacacsplusAuthor 1 } 
		
	tacacsplusAuthorTimeoutPeriod OBJECT-TYPE
		SYNTAX  INTEGER (1..1000)
		MAX-ACCESS read-write
		STATUS current
		DESCRIPTION
			"Timeout period (second) of command authorization via TACACS+. 1~1000 seconds
			This MIB Object is supported by R5.06 and later versions."
		::= { tacacsplusAuthor 2 } 
		
	tacacsplusAuthorServerTable OBJECT-TYPE
    	SYNTAX SEQUENCE OF TacacsplusAuthorServerEntry
    	MAX-ACCESS not-accessible
    	STATUS current
    	DESCRIPTION
                "This table is supported by R5.06 and later versions."
    	::= { tacacsplusAuthor 3 }

    	tacacsplusAuthorServerEntry OBJECT-TYPE
        SYNTAX TacacsplusAuthorServerEntry
        MAX-ACCESS not-accessible
        STATUS current
        DESCRIPTION
        	"An entry of tacacsplusAuthorServerEntry.
        	This table is supported by R5.06 and later versions."
        INDEX { tacscsplusAuthorServerIndex   }
        ::= { tacacsplusAuthorServerTable 1 }

   	TacacsplusAuthorServerEntry ::=
        	SEQUENCE {
            		tacscsplusAuthorServerIndex		INTEGER,
            		tacscsplusAuthorServerIP		IpAddress,
            		tacscsplusAuthorServerPort		INTEGER,
            		tacscsplusAuthorServerSecret	DisplayString
    	   	} 

	tacscsplusAuthorServerIndex OBJECT-TYPE
	SYNTAX INTEGER (1..2)
	MAX-ACCESS read-only
	STATUS current
	DESCRIPTION
		""
	::= { tacacsplusAuthorServerEntry 1 }

	tacscsplusAuthorServerIP OBJECT-TYPE
	SYNTAX IpAddress
	MAX-ACCESS read-write
	STATUS current
	DESCRIPTION
		"TACACS+ server IP for command authorization."
	::= { tacacsplusAuthorServerEntry 2 }  
	
	tacscsplusAuthorServerPort OBJECT-TYPE
	SYNTAX INTEGER
	MAX-ACCESS read-write
	STATUS current
	DESCRIPTION
		"TACACS+ server port for command authorization."
	::= { tacacsplusAuthorServerEntry 3 }  
	
	tacscsplusAuthorServerSecret OBJECT-TYPE
	SYNTAX DisplayString
	MAX-ACCESS read-write
	STATUS current
	DESCRIPTION
		"TACACS+ server secret key for command authorization."
	::= { tacacsplusAuthorServerEntry 4 } 

-- author This table is supported by R5.06 and later versions.
	authorCmdMethodTable OBJECT-TYPE
    	SYNTAX SEQUENCE OF AuthorCmdMethodEntry
    	MAX-ACCESS not-accessible
    	STATUS current
    	DESCRIPTION
                "This table is supported by R5.06 and later versions."
    	::= { author 1 }

    	authorCmdMethodEntry OBJECT-TYPE
        SYNTAX AuthorCmdMethodEntry
        MAX-ACCESS not-accessible
        STATUS current
        DESCRIPTION
        	"An entry of authorCmdMethodEntry."
        INDEX { ifIndex   }
        ::= { authorCmdMethodTable 1 }

   	AuthorCmdMethodEntry ::=
        	SEQUENCE {
            		authorCmdMethod		INTEGER
    	   	} 

	authorCmdMethod OBJECT-TYPE
	SYNTAX INTEGER {
				none(1),
				local(2),
				tacacsPlus(3),
				tacacsPlus-then-none(4),
				tacacsPlus-then-local(5)
			}
	MAX-ACCESS read-write
	STATUS current
	DESCRIPTION
		"Method mode of command authorization in each privilege level."
	::= { authorCmdMethodEntry 1 }
	

	authorExec OBJECT-TYPE
		SYNTAX  INTEGER {
				disable(0),
				enable(1)
			}
		MAX-ACCESS read-write
		STATUS current
		DESCRIPTION
			"enable:
				1. User login via Web GUI:  
					1.1. Tacacs+ account with privilege 14, get the privilege as 14.
					1.2. Tacacs+ account with privilege lower than 14, get the privilege as 1.
				
				2. User login via SSH, telnet or console:
					1.1. Whether Tacacs+ account privilege is (1-14), get the same privilege as Tacacs+ server.
				
			 disable:
				1. Whether user login via SSH, telnet, web GUI or console, get the privilege as 1.
					(no matter what the Tacacs+ account privilege is)
				"
		::= { author 2 } 
--------------------
-- session
--------------------

	sessionTimeOut OBJECT-TYPE
        SYNTAX INTEGER
	MAX-ACCESS read-write
	STATUS current
	DESCRIPTION
		"Configurable Web, telnet and SSH session timeout."
	::= { session 1 }

	sessionLoginMessage OBJECT-TYPE
        SYNTAX DisplayString
	MAX-ACCESS read-write
	STATUS current
	DESCRIPTION
		"Login message in 128 characters."
	::= { session 2 }	

--------------------
-- bootimage
--------------------
	sysBootImage OBJECT-TYPE
	SYNTAX	INTEGER {
			image1(1),
			image2(2)
		}
	MAX-ACCESS read-write
	STATUS current
	DESCRIPTION
		"Boot from the first image or the second image."
	::= { bootimage 1 }
		
----------------------------------------
-- statistics
----------------------------------------

	dhcpStats		OBJECT IDENTIFIER ::= { statistics 1 }
	igmpStats		OBJECT IDENTIFIER ::= { statistics 2 }
	macStats		OBJECT IDENTIFIER ::= { statistics 3 }
	adslStats		OBJECT IDENTIFIER ::= { statistics 4 }
	shdslStats		OBJECT IDENTIFIER ::= { statistics 5 }
	ipStats			OBJECT IDENTIFIER ::= { statistics 6 }
	mstpStats		OBJECT IDENTIFIER ::= { statistics 7 }
	vdslStats		OBJECT IDENTIFIER ::= { statistics 8 }
	paepvcStats		OBJECT IDENTIFIER ::= { statistics 9 }
	vlanMacStats		OBJECT IDENTIFIER ::= { statistics 10 }
	ipbpvcStats		OBJECT IDENTIFIER ::= { statistics 11 }
	voipStats		OBJECT IDENTIFIER ::= { statistics 12 }
	enetStats		OBJECT IDENTIFIER ::= { statistics 13 }
	ifStats			OBJECT IDENTIFIER ::= { statistics 14 }	
	imaStats		OBJECT IDENTIFIER ::= { statistics 15 }	
	e1Stats		OBJECT IDENTIFIER ::= { statistics 16 }	
	loopguardStats		OBJECT IDENTIFIER ::= { statistics 18 }
	stpStats	OBJECT IDENTIFIER ::= { statistics 19 }
	gbondStats	OBJECT IDENTIFIER ::= { statistics 20 }
	vdsl2Stats 	OBJECT IDENTIFIER ::= { statistics 21 }
	mldStats 	OBJECT IDENTIFIER ::= { statistics 22 }
	macFFStats 	OBJECT IDENTIFIER ::= { statistics 23 } 
	imageStats	OBJECT IDENTIFIER ::= { statistics 24 }
	
--------------------
-- DHCP
--------------------

-- dhcpSnoopIpTable

        dhcpSnoopIpTable OBJECT-TYPE
        SYNTAX SEQUENCE OF DhcpSnoopIpEntry
        MAX-ACCESS not-accessible
        STATUS current
        DESCRIPTION
        	"This table shows the IP addresses and netmasks offered by the DHCP server.
        	This table is supported by R1.02 and later versions."
        ::= { dhcpStats 1 }

	dhcpSnoopIpEntry OBJECT-TYPE
        SYNTAX DhcpSnoopIpEntry
        MAX-ACCESS not-accessible
        STATUS current
        DESCRIPTION
		"An entry of dhcpSnoopIpTable."
        INDEX { ifIndex, dhcpSnoopIp }
        ::= { dhcpSnoopIpTable 1 }

        DhcpSnoopIpEntry ::=
        	SEQUENCE {
			dhcpSnoopIp		IpAddress,
			dhcpSnoopMac		PhysAddress,
			dhcpSnoopVid		VlanIndex
           	}

        dhcpSnoopIp OBJECT-TYPE
        SYNTAX IpAddress
        MAX-ACCESS read-only
        STATUS current
        DESCRIPTION
                "The snooped IP address."
        ::= { dhcpSnoopIpEntry 1 }

        dhcpSnoopMac OBJECT-TYPE
        SYNTAX PhysAddress
        MAX-ACCESS read-only
        STATUS current
        DESCRIPTION
                "The snooped MAC address."
        ::= { dhcpSnoopIpEntry 2 }
         
        dhcpSnoopVid OBJECT-TYPE
        SYNTAX VlanIndex
        MAX-ACCESS read-only
        STATUS current
        DESCRIPTION
                "The snooped VLAN ID."
        ::= { dhcpSnoopIpEntry 3 }

-- dhcpSnoopCounterTable

        dhcpSnoopCounterTable OBJECT-TYPE
        SYNTAX SEQUENCE OF DhcpSnoopCounterEntry
        MAX-ACCESS not-accessible
        STATUS current
        DESCRIPTION
        	"This table shows the DHCP statistics.
        	This table is supported by R1.02 and later versions."
        ::= { dhcpStats 2 }

	dhcpSnoopCounterEntry OBJECT-TYPE
        SYNTAX DhcpSnoopCounterEntry
        MAX-ACCESS not-accessible
        STATUS current
        DESCRIPTION
		"An entry of dhcpSnoopCounterTable."
        INDEX { ifIndex }
        ::= { dhcpSnoopCounterTable 1 }

        DhcpSnoopCounterEntry ::=
        	SEQUENCE {
			dhcpDiscovery				Counter64,
			dhcpOffer					Counter64,
			dhcpRequest					Counter64,
			dhcpAck						Counter64,
			dhcpAckBySnoopFull			Counter64,
			dhcpv6Solicit				Counter64,
			dhcpv6Advertise				Counter64,
			dhcpv6Request				Counter64,
			dhcpv6Reply					Counter64,
			dhcpv6Renew					Counter64,
			dhcpv6Rebind				Counter64,
			dhcpv6Release				Counter64,
			dhcpv6RelayFwd				Counter64,
			dhcpv6RelayReply			Counter64
           	}

        dhcpDiscovery OBJECT-TYPE
        SYNTAX Counter64
        MAX-ACCESS read-only
        STATUS current
        DESCRIPTION
                "The total number of received DHCP server discovery packets."
         ::= { dhcpSnoopCounterEntry 1 }

        dhcpOffer OBJECT-TYPE
        SYNTAX Counter64
        MAX-ACCESS read-only
        STATUS current
        DESCRIPTION
                "The total number of received DHCP server offer packets."
         ::= { dhcpSnoopCounterEntry 2 }

        dhcpRequest OBJECT-TYPE
        SYNTAX Counter64
        MAX-ACCESS read-only
        STATUS current
        DESCRIPTION
                "The total number of received DHCP IP request packets."
         ::= { dhcpSnoopCounterEntry 3 }
         
        dhcpAck OBJECT-TYPE
        SYNTAX Counter64
        MAX-ACCESS read-only
        STATUS current
        DESCRIPTION
                "The total number of received DHCP IP acknowledge packets."
         ::= { dhcpSnoopCounterEntry 4 }
         
        dhcpAckBySnoopFull OBJECT-TYPE
        SYNTAX Counter64
        MAX-ACCESS read-only
        STATUS current
        DESCRIPTION
                "The total number of received DHCP IP acknowledge packets that replace the oldest snooping
                entry in snooping table due to table full."
         ::= { dhcpSnoopCounterEntry 5 }
         
        dhcpv6Solicit OBJECT-TYPE
        SYNTAX Counter64
        MAX-ACCESS read-only
        STATUS current
        DESCRIPTION
                "The total number of received DHCPv6 solicit packets."
        ::= { dhcpSnoopCounterEntry 6 }
        
        dhcpv6Advertise OBJECT-TYPE
        SYNTAX Counter64
        MAX-ACCESS read-only
        STATUS current
        DESCRIPTION
                "The total number of received DHCPv6 advertise packets."
        ::= { dhcpSnoopCounterEntry 7 } 
        
        dhcpv6Request OBJECT-TYPE
        SYNTAX Counter64
        MAX-ACCESS read-only
        STATUS current
        DESCRIPTION
                "The total number of received DHCPv6 request packets."
        ::= { dhcpSnoopCounterEntry 8 }
        
        dhcpv6Reply OBJECT-TYPE
        SYNTAX Counter64
        MAX-ACCESS read-only
        STATUS current
        DESCRIPTION
                "The total number of received DHCPv6 reply packets."
        ::= { dhcpSnoopCounterEntry 9 } 
        
        dhcpv6Renew OBJECT-TYPE
        SYNTAX Counter64
        MAX-ACCESS read-only
        STATUS current
        DESCRIPTION
                "The total number of received DHCPv6 renew packets."
        ::= { dhcpSnoopCounterEntry 10 } 
        
        dhcpv6Rebind OBJECT-TYPE
        SYNTAX Counter64
        MAX-ACCESS read-only
        STATUS current
        DESCRIPTION
                "The total number of received DHCPv6 rebind packets."
        ::= { dhcpSnoopCounterEntry 11 }
        
        dhcpv6Release OBJECT-TYPE
        SYNTAX Counter64
        MAX-ACCESS read-only
        STATUS current
        DESCRIPTION
                "The total number of received DHCPv6 release packets."
        ::= { dhcpSnoopCounterEntry 12 }
        
        dhcpv6RelayFwd OBJECT-TYPE
        SYNTAX Counter64
        MAX-ACCESS read-only
        STATUS current
        DESCRIPTION
                "The total number of received DHCPv6 relay-forward packets."
        ::= { dhcpSnoopCounterEntry 13 }
        
        dhcpv6RelayReply OBJECT-TYPE
        SYNTAX Counter64
        MAX-ACCESS read-only
        STATUS current
        DESCRIPTION
                "The total number of received DHCPv6 relay-reply packets."
        ::= { dhcpSnoopCounterEntry 14 }

-- dhcpv6SnoopIpTable

        dhcpv6SnoopIpTable OBJECT-TYPE
        SYNTAX SEQUENCE OF Dhcpv6SnoopIpEntry
        MAX-ACCESS not-accessible
        STATUS current
        DESCRIPTION
        	"This table shows LDRA statistics."
        ::= { dhcpStats 3 }

	dhcpv6SnoopIpEntry OBJECT-TYPE
        SYNTAX Dhcpv6SnoopIpEntry
        MAX-ACCESS not-accessible
        STATUS current
        DESCRIPTION
		"An entry of dhcpv6SnoopIpTable."
        INDEX { ifIndex, dhcpv6SnoopInetAddrType, dhcpv6SnoopInetAddr }
        ::= { dhcpv6SnoopIpTable 1 }

        Dhcpv6SnoopIpEntry ::=
        	SEQUENCE {
			dhcpv6SnoopInetAddrType		InetAddressType,
			dhcpv6SnoopInetAddr			InetAddress,
			dhcpv6SnoopMac				PhysAddress,
			dhcpv6SnoopVid				VlanIndex
           	}

        dhcpv6SnoopInetAddrType OBJECT-TYPE
        SYNTAX InetAddressType
        MAX-ACCESS read-only
        STATUS current
        DESCRIPTION
                "The snooped IP address type."
        ::= { dhcpv6SnoopIpEntry 1 }
         
        dhcpv6SnoopInetAddr OBJECT-TYPE
        SYNTAX InetAddress
        MAX-ACCESS read-only
        STATUS current
        DESCRIPTION
                "The snooped IP address."
        ::= { dhcpv6SnoopIpEntry 2 }
         
        dhcpv6SnoopMac OBJECT-TYPE
        SYNTAX PhysAddress
        MAX-ACCESS read-only
        STATUS current
        DESCRIPTION
                "The snooped MAC address."
        ::= { dhcpv6SnoopIpEntry 3 }
        
        dhcpv6SnoopVid OBJECT-TYPE
        SYNTAX VlanIndex
        MAX-ACCESS read-only
        STATUS current
        DESCRIPTION
                "The snooped VLAN ID."
        ::= { dhcpv6SnoopIpEntry 4 }
--------------------
--  IGMP
--------------------
		
	igmpQueryCntTotal OBJECT-TYPE
	SYNTAX Counter32
	MAX-ACCESS read-only
	STATUS current
	DESCRIPTION
		"The total number of IGMP query messages received.
		This object is supported by R1.02 and later versions."
	::= { igmpStats 1 }
	
	igmpReportCntTotal OBJECT-TYPE
	SYNTAX Counter32
	MAX-ACCESS read-only
	STATUS current
	DESCRIPTION
		"The total number of IGMP report messages received.
		This object is supported by R1.02 and later versions."
	::= { igmpStats 2 }
	
	igmpLeaveCntTotal OBJECT-TYPE
	SYNTAX Counter32
	MAX-ACCESS read-only
	STATUS current
	DESCRIPTION
		"The total number of IGMP leave messages received.
		This object is supported by R1.02 and later versions."
	::= { igmpStats 3 }
	
	igmpNumOfActiveGroups OBJECT-TYPE
	SYNTAX INTEGER
	MAX-ACCESS read-only
	STATUS current
	DESCRIPTION
		"The total number of IGMP learned groups.
		This object is supported by R1.02 and later versions."
	::= { igmpStats 4 }

-- igmpGroupTable

	igmpGroupTable OBJECT-TYPE
        SYNTAX SEQUENCE OF IgmpGroupEntry
        MAX-ACCESS not-accessible
        STATUS current
        DESCRIPTION
                "A table that displays IGMP learned group member information.
                This table is supported by R1.02 and later versions."
        ::= { igmpStats 5 }

        igmpGroupEntry OBJECT-TYPE
        SYNTAX IgmpGroupEntry
        MAX-ACCESS not-accessible
        STATUS current
        DESCRIPTION
        	"An entry of igmpGroupTable."
        INDEX { igmpGroupVid, igmpGroupIp }
        ::= { igmpGroupTable 1 }

        IgmpGroupEntry ::=
        	SEQUENCE {
        		igmpGroupVid		VlanIndex,
        		igmpGroupIp		IpAddress,
        		igmpGroupNumOfMembers	INTEGER,
        		igmpGroupMemberPorts	PortList	
           	}

	igmpGroupVid OBJECT-TYPE
	SYNTAX VlanIndex
	MAX-ACCESS read-only
	STATUS current
	DESCRIPTION
		"The IGMP group VLAN ID."
	::= { igmpGroupEntry 1 }
		
	igmpGroupIp OBJECT-TYPE
	SYNTAX IpAddress
	MAX-ACCESS read-only
	STATUS current
	DESCRIPTION
		"The multicast IP address."
	::= { igmpGroupEntry 2 }
	
	igmpGroupNumOfMembers OBJECT-TYPE
	SYNTAX INTEGER
	MAX-ACCESS read-only
	STATUS current
	DESCRIPTION
		"The number of member ports in the group."
	::= { igmpGroupEntry 3 }
	
	igmpGroupMemberPorts OBJECT-TYPE
	SYNTAX PortList
	MAX-ACCESS read-only
	STATUS current
	DESCRIPTION
		"The member port list of the group."
	::= { igmpGroupEntry 4 }		

-- igmpGroupPortTable

	igmpGroupPortTable OBJECT-TYPE
        SYNTAX SEQUENCE OF IgmpGroupPortEntry
        MAX-ACCESS not-accessible
        STATUS current
        DESCRIPTION
                "A table that displays IGMP joined groups in this port.
                This table is supported by R1.02 and later versions."
        ::= { igmpStats 6 }

        igmpGroupPortEntry OBJECT-TYPE
        SYNTAX IgmpGroupPortEntry
        MAX-ACCESS not-accessible
        STATUS current
        DESCRIPTION
        	"An entry of igmpGroupPortTable."
        INDEX { ifIndex, igmpGroupPortVid, igmpGroupPortIp, igmpGroupPortSourceIp }
        ::= { igmpGroupPortTable 1 }

        IgmpGroupPortEntry ::=
        	SEQUENCE {
        		igmpGroupPortVid	VlanIndex,
        		igmpGroupPortIp		IpAddress,
        		igmpGroupPortSourceIp	IpAddress
           	}

	igmpGroupPortVid OBJECT-TYPE
	SYNTAX VlanIndex
	MAX-ACCESS read-only
	STATUS current
	DESCRIPTION
		"The IGMP group VLAN ID."
	::= { igmpGroupPortEntry 1 }
		
	igmpGroupPortIp OBJECT-TYPE
	SYNTAX IpAddress
	MAX-ACCESS read-only
	STATUS current
	DESCRIPTION
		"The multicast IP address."
	::= { igmpGroupPortEntry 2 }

	igmpGroupPortSourceIp OBJECT-TYPE
	SYNTAX IpAddress
	MAX-ACCESS read-only
	STATUS current
	DESCRIPTION
		"The source IP address that joins the IGMP group."
	::= { igmpGroupPortEntry 3 }
	
-- igmpPortCtrlPduTable

	igmpPortCtrlPduTable OBJECT-TYPE
        SYNTAX SEQUENCE OF IgmpPortCtrlPduEntry
        MAX-ACCESS not-accessible
        STATUS current
        DESCRIPTION
                "A table that displays IGMP related counter values in this port.
                This table is supported by R1.02 and later versions."
        ::= { igmpStats 7 }

        igmpPortCtrlPduEntry OBJECT-TYPE
        SYNTAX IgmpPortCtrlPduEntry
        MAX-ACCESS not-accessible
        STATUS current
        DESCRIPTION
        	"An entry of igmpPortCtrlPduTable."
        INDEX { ifIndex }
        ::= { igmpPortCtrlPduTable 1 }

        IgmpPortCtrlPduEntry ::=
        	SEQUENCE {
        		igmpPortCtrlPduQueryCnt		Counter32,
        		igmpPortCtrlPduReportCnt	Counter32,
        		igmpPortCtrlPduLeaveCnt		Counter32,
        		igmpPortNumOfActiveGroups	INTEGER,
        		igmpPortCtrlPduV2SuccessJoinCnt		Counter32,
        		igmpPortCtrlPduV2UnsuccJoinCnt		Counter32,
        		igmpPortCtrlPduGenQryCnt		Counter32,
        		igmpPortCtrlPduSpecQryCnt		Counter32,
        		igmpPortCtrlPduV3SuccessReportCnt		Counter32,
        		igmpPortCtrlPduV3UnsuccReportCnt		Counter32,
        		igmpPortCtrlPduInvalidCnt		Counter32
           	}
	
	igmpPortCtrlPduQueryCnt OBJECT-TYPE
	SYNTAX Counter32
	MAX-ACCESS read-only
	STATUS current
	DESCRIPTION
		"The total number of IGMP query messages received in this port."
	::= { igmpPortCtrlPduEntry 1 }

	igmpPortCtrlPduReportCnt OBJECT-TYPE
	SYNTAX Counter32
	MAX-ACCESS read-only
	STATUS current
	DESCRIPTION
		"The total number of IGMP report messages received in this port."
	::= { igmpPortCtrlPduEntry 2 }
	
	igmpPortCtrlPduLeaveCnt OBJECT-TYPE
	SYNTAX Counter32
	MAX-ACCESS read-only
	STATUS current
	DESCRIPTION
		"The total number of IGMP leave messages received in this port."
	::= { igmpPortCtrlPduEntry 3 }
	
	igmpPortNumOfActiveGroups OBJECT-TYPE
	SYNTAX INTEGER
	MAX-ACCESS read-only
	STATUS current
	DESCRIPTION
		"The total number of active IGMP groups in this port."
	::= { igmpPortCtrlPduEntry 4 }
	
	igmpPortCtrlPduV2SuccessJoinCnt OBJECT-TYPE
	SYNTAX Counter32
	MAX-ACCESS read-only
	STATUS current
	DESCRIPTION
		"The total number of IGMP V2 success joins in this port. 
		This MIB object is supported by R5.05 and later versions."
	::= { igmpPortCtrlPduEntry 5 }
	
	igmpPortCtrlPduV2UnsuccJoinCnt OBJECT-TYPE
	SYNTAX Counter32
	MAX-ACCESS read-only
	STATUS current
	DESCRIPTION
		"The total number of IGMP V2 unsuccess  joins in this port. 
		This MIB object is supported by R5.05 and later versions."
	::= { igmpPortCtrlPduEntry 6 }
	
	igmpPortCtrlPduGenQryCnt OBJECT-TYPE
	SYNTAX Counter32
	MAX-ACCESS read-only
	STATUS current
	DESCRIPTION
		"The total number of IGMP general queries in this port. 
		This MIB object is supported by R5.05 and later versions."
	::= { igmpPortCtrlPduEntry 7 }
	
	igmpPortCtrlPduSpecQryCnt OBJECT-TYPE
	SYNTAX Counter32
	MAX-ACCESS read-only
	STATUS current
	DESCRIPTION
		"The total number of IGMP specific queries in this port. 
		This MIB object is supported by R5.05 and later versions."
	::= { igmpPortCtrlPduEntry 8 }
		
	igmpPortCtrlPduV3SuccessReportCnt OBJECT-TYPE
	SYNTAX Counter32
	MAX-ACCESS read-only
	STATUS current
	DESCRIPTION
		"The total number of IGMP V3 success joins in this port. 
		This MIB object is supported by R5.05 and later versions."
	::= { igmpPortCtrlPduEntry 9 }
	
	igmpPortCtrlPduV3UnsuccReportCnt OBJECT-TYPE
	SYNTAX Counter32
	MAX-ACCESS read-only
	STATUS current
	DESCRIPTION
		"The total number of IGMP V3 unsuccess  joins in this port. 
		This MIB object is supported by R5.05 and later versions."
	::= { igmpPortCtrlPduEntry 10 }
	
	igmpPortCtrlPduInvalidCnt OBJECT-TYPE
	SYNTAX Counter32
	MAX-ACCESS read-only
	STATUS current
	DESCRIPTION
		"The total number of IGMP invalid in this port. 
		This MIB object is supported by R5.05 and later versions."
	::= { igmpPortCtrlPduEntry 11 }

-- igmpVlanStatsTable

	igmpVlanStatsTable OBJECT-TYPE
        SYNTAX SEQUENCE OF IgmpVlanStatsEntry
        MAX-ACCESS not-accessible
        STATUS current
        DESCRIPTION
                "A table that displays IGMP related counter values per VLAN."
        ::= { igmpStats 8 }

        igmpVlanStatsEntry OBJECT-TYPE
        SYNTAX IgmpVlanStatsEntry
        MAX-ACCESS not-accessible
        STATUS current
        DESCRIPTION
        	"An entry of igmpVlanStatsTable."
        INDEX { igmpVlanStatsVlanIndex }
        ::= { igmpVlanStatsTable 1 }

        IgmpVlanStatsEntry ::=
        	SEQUENCE {
        		igmpVlanStatsVlanIndex				VlanIndex,
        		igmpVlanStatsQueryCnt				Counter32,
        		igmpVlanStatsReportCnt				Counter32,
        		igmpVlanStatsLeaveCnt				Counter32,
        		igmpVlanStatsNumOfActiveGroups		INTEGER,
        		igmpVlanStatsQueryPort	    		INTEGER,
        		igmpVlanStatsQuerierIp      		IpAddress,
        		igmpVlanStatsUnsuccessReportCnt 	Counter32,
        		igmpVlanStatsSuccessReportCnt 		Counter32,
        		igmpVlanStatsGeneralQueryInCnt 		Counter32,
        		igmpVlanStatsGeneralQueryOutCnt 	Counter32,
        		igmpVlanStatsSpecificQueryInCnt 	Counter32,
        		igmpVlanStatsSpecificQueryOutCnt 	Counter32
           	}
	
	igmpVlanStatsVlanIndex OBJECT-TYPE
	SYNTAX VlanIndex
	MAX-ACCESS read-only
	STATUS current
	DESCRIPTION
		"VLAN ID."
	::= { igmpVlanStatsEntry 1 }
	
	igmpVlanStatsQueryCnt OBJECT-TYPE
	SYNTAX Counter32
	MAX-ACCESS read-only
	STATUS current
	DESCRIPTION
		"The total number of IGMP query messages received in this VLAN."
	::= { igmpVlanStatsEntry 2 }

	igmpVlanStatsReportCnt OBJECT-TYPE
	SYNTAX Counter32
	MAX-ACCESS read-only
	STATUS current
	DESCRIPTION
		"The total number of IGMP report messages received in this VLAN."
	::= { igmpVlanStatsEntry 3 }
	
	igmpVlanStatsLeaveCnt OBJECT-TYPE
	SYNTAX Counter32
	MAX-ACCESS read-only
	STATUS current
	DESCRIPTION
		"The total number of IGMP leave messages received in this VLAN."
	::= { igmpVlanStatsEntry 4 }
	
	igmpVlanStatsNumOfActiveGroups OBJECT-TYPE
	SYNTAX INTEGER
	MAX-ACCESS read-only
	STATUS current
	DESCRIPTION
		"The total number of active IGMP groups in this VLAN."
	::= { igmpVlanStatsEntry 5 }  
	
	igmpVlanStatsQueryPort OBJECT-TYPE
	SYNTAX INTEGER
	MAX-ACCESS read-only
	STATUS current
	DESCRIPTION
		"The received Port of IGMP Router"
	::= { igmpVlanStatsEntry 6 }
	
	igmpVlanStatsQuerierIp OBJECT-TYPE
	SYNTAX IpAddress
	MAX-ACCESS read-only
	STATUS current
	DESCRIPTION
		"The IP address of IGMP Router"
	::= { igmpVlanStatsEntry 7 }  
	
	igmpVlanStatsUnsuccessReportCnt OBJECT-TYPE
	SYNTAX Counter32
	MAX-ACCESS read-only
	STATUS current
	DESCRIPTION
		"Total number of successful joins from users.
		This MIB object is supported by R5.05 and later versions."
	::= { igmpVlanStatsEntry 8 }
	
	igmpVlanStatsSuccessReportCnt OBJECT-TYPE
	SYNTAX Counter32
	MAX-ACCESS read-only
	STATUS current
	DESCRIPTION
		"Total number of unsuccessful joins from users.
		This MIB object is supported by R5.05 and later versions."
	::= { igmpVlanStatsEntry 9 }
	
	igmpVlanStatsGeneralQueryInCnt OBJECT-TYPE
	SYNTAX Counter32
	MAX-ACCESS read-only
	STATUS current
	DESCRIPTION
		"Total number of general queries sent to users.
		This MIB object is supported by R5.05 and later versions."
	::= { igmpVlanStatsEntry 10 }
	
	igmpVlanStatsGeneralQueryOutCnt OBJECT-TYPE
	SYNTAX Counter32
	MAX-ACCESS read-only
	STATUS current
	DESCRIPTION
		"Total number of general queries received from network.
		This MIB object is supported by R5.05 and later versions."
	::= { igmpVlanStatsEntry 11 }
	
	igmpVlanStatsSpecificQueryInCnt OBJECT-TYPE
	SYNTAX Counter32
	MAX-ACCESS read-only
	STATUS current
	DESCRIPTION
		"Total number of specific queries sent to users.
		This MIB object is supported by R5.05 and later versions."
	::= { igmpVlanStatsEntry 12 }
	
	igmpVlanStatsSpecificQueryOutCnt OBJECT-TYPE
	SYNTAX Counter32
	MAX-ACCESS read-only
	STATUS current
	DESCRIPTION
		"Total number of specific queries received from network.
		This MIB object is supported by R5.05 and later versions."
	::= { igmpVlanStatsEntry 13 } 
		
	igmpQueryOutCnt OBJECT-TYPE
	SYNTAX Counter32
	MAX-ACCESS read-only
	STATUS current
	DESCRIPTION
		"The total number of IGMP query messages transmitted."
	::= { igmpStats 9 }
	
	igmpReportOutCnt OBJECT-TYPE
	SYNTAX Counter32
	MAX-ACCESS read-only
	STATUS current
	DESCRIPTION
		"The total number of IGMP report messages transmitted."
	::= { igmpStats 10 }
	
	igmpLeaveOutCnt OBJECT-TYPE
	SYNTAX Counter32
	MAX-ACCESS read-only
	STATUS current
	DESCRIPTION
		"The total number of IGMP leave messages transmitted."
	::= { igmpStats 11 }
	
	igmpQueryDropCnt OBJECT-TYPE
	SYNTAX Counter32
	MAX-ACCESS read-only
	STATUS current
	DESCRIPTION
		"The total number of IGMP query messages dropped."
	::= { igmpStats 12 }
	
	igmpReportDropCnt OBJECT-TYPE
	SYNTAX Counter32
	MAX-ACCESS read-only
	STATUS current
	DESCRIPTION
		"The total number of IGMP report messages dropped."
	::= { igmpStats 13 }
	
	igmpLeaveDropCnt OBJECT-TYPE
	SYNTAX Counter32
	MAX-ACCESS read-only
	STATUS current
	DESCRIPTION
		"The total number of IGMP leave messages dropped."
	::= { igmpStats 14 }
--------------------
--  MAC
--------------------
		
	macDisplayTarget OBJECT-TYPE
	SYNTAX INTEGER
	MAX-ACCESS read-write
	STATUS current
	DESCRIPTION
		"This managed object is a filter used for identify the target from which 
		the MAC addresses are learned in macTable. Ifindex is used to specify a specific
		interface of which the MAC addresses are displayed. Some values are reserved for
		special purpose, they are:
		0: All interfaces 
		50: All uplink ports"
	::= { macStats 1 }

-- macTable
	
        macTable OBJECT-TYPE
        SYNTAX SEQUENCE OF MacEntry
        MAX-ACCESS not-accessible
        STATUS current
        DESCRIPTION
        	"A table that contains information about unicast
                entries for which the bridge has forwarding and/or
                filtering information. This information is used
                by the transparent bridging function in
                determining how to propagate a received frame."
        ::= { macStats 2 }

        macEntry OBJECT-TYPE
        SYNTAX MacEntry
        MAX-ACCESS not-accessible
        STATUS current
        DESCRIPTION
        	"An entry of macTable."
        INDEX { macAddress }
        ::= { macTable 1 }

        MacEntry ::=
        	SEQUENCE {
                  	macAddress	MacAddress,
                  	macPort		INTEGER,
                  	macStatus	INTEGER
              	}

        macAddress OBJECT-TYPE
        SYNTAX MacAddress
        MAX-ACCESS read-only
        STATUS current
        DESCRIPTION
        	"A unicast MAC address for which the bridge has
                forwarding and/or filtering information."
        ::= { macEntry 1 }

        macPort OBJECT-TYPE
        SYNTAX INTEGER
        MAX-ACCESS read-only
        STATUS current
        DESCRIPTION
        	"The port from which the mac address has been learned."
        ::= { macEntry 2 }

        macStatus OBJECT-TYPE
        SYNTAX  INTEGER {
                          other(1),
                          invalid(2),
                          learned(3),
                          self(4),
                          mgmt(5)
        	}
        MAX-ACCESS read-only
        STATUS current
        DESCRIPTION
        	"The status of this entry."
	::= { macEntry 3 }
	
	macFlush OBJECT-TYPE
        SYNTAX INTEGER
        MAX-ACCESS read-write
        STATUS current
        DESCRIPTION
        	"Set the object to 1 to flush mac table."
        ::= { macStats 3 }
                      
--------------------
--  ADSL
--------------------

	adslLineStatsAtucNumOfSubcarriersPerPort OBJECT-TYPE
	SYNTAX INTEGER
	MAX-ACCESS read-only
	STATUS current
	DESCRIPTION
		"The number of subcarriers per port for ATU-C."
	::= { adslStats 1 }

	adslLineStatsAturNumOfSubcarriersPerPort OBJECT-TYPE
	SYNTAX INTEGER
	MAX-ACCESS read-only
	STATUS current
	DESCRIPTION
		"The number of subcarriers per port for ATU-R."
	::= { adslStats 2 }
	
-- adslLineStatsTable

        adslLineStatsTable OBJECT-TYPE
        SYNTAX SEQUENCE OF AdslLineStatsEntry
        MAX-ACCESS not-accessible
        STATUS current
        DESCRIPTION
        	"The table displays ADSL line subcarrier status.
        	This table is supported by R1.02 and later versions."
        ::= { adslStats 3 }

        adslLineStatsEntry OBJECT-TYPE
        SYNTAX AdslLineStatsEntry
        MAX-ACCESS not-accessible
        STATUS current
        DESCRIPTION
        	"An entry of adslLineStatsTable."
        INDEX { ifIndex }
        ::= { adslLineStatsTable 1 }

        AdslLineStatsEntry ::=
        	SEQUENCE {
                  	adslLineStatsAtucHlog1		OCTET STRING,
			adslLineStatsAtucHlog2		OCTET STRING,
			adslLineStatsAturHlog		OCTET STRING,
			adslLineStatsAtucQln1		OCTET STRING,
			adslLineStatsAtucQln2		OCTET STRING,
			adslLineStatsAturQln		OCTET STRING,
			adslLineStatsAtucTssi1		OCTET STRING,
			adslLineStatsAtucTssi2		OCTET STRING,
			adslLineStatsAturTssi		OCTET STRING,
			adslLineStatsAtucGain1		OCTET STRING,
			adslLineStatsAtucGain2		OCTET STRING,
			adslLineStatsAturGain		OCTET STRING,
			adslLineStatsAtucBits1		OCTET STRING,
			adslLineStatsAtucBits2		OCTET STRING,
			adslLineStatsAturBits		OCTET STRING
              	}
              	
	adslLineStatsAtucHlog1 OBJECT-TYPE
	SYNTAX OCTET STRING
	MAX-ACCESS read-only
	STATUS current
	DESCRIPTION
		"The object provides Hlog for the ATU-C first 256 subcarriers.
		Each subcarrier takes two octets to store the value.
		A special value -32768 indicates that no measurement could 
		be done for the sub-carrier group."
	::= { adslLineStatsEntry 1 }

	adslLineStatsAtucHlog2 OBJECT-TYPE
	SYNTAX OCTET STRING
	MAX-ACCESS read-only
	STATUS current
	DESCRIPTION
		"The object provides Hlog for the ATU-C last 256 subcarriers.
		Each subcarrier takes two octets to store the value.
		A special value -32768 indicates that no measurement could 
		be done for the sub-carrier group."
	::= { adslLineStatsEntry 2 }

	adslLineStatsAturHlog OBJECT-TYPE
	SYNTAX OCTET STRING
	MAX-ACCESS read-only
	STATUS current
	DESCRIPTION
		"The object provides Hlog for the ATU-R subcarriers.
		Each subcarrier takes two octets to store the value.
		A special value -32768 indicates that no measurement could 
		be done for the sub-carrier group."
	::= { adslLineStatsEntry 3 }

	adslLineStatsAtucQln1 OBJECT-TYPE
	SYNTAX OCTET STRING
	MAX-ACCESS read-only
	STATUS current
	DESCRIPTION
		"The object provides QLN for the ATU-C first 256 subcarriers.
		Each subcarrier takes two octets to store the value.
		A special value 0 indicates that no measurement could be done 
		for the sub-carrier group."
	::= { adslLineStatsEntry 4 }

	adslLineStatsAtucQln2 OBJECT-TYPE
	SYNTAX OCTET STRING
	MAX-ACCESS read-only
	STATUS current
	DESCRIPTION
		"The object provides QLN for the ATU-C last 256 subcarriers.
		Each subcarrier takes two octets to store the value.
		A special value 0 indicates that no measurement could be done 
		for the sub-carrier group."
	::= { adslLineStatsEntry 5 }

	adslLineStatsAturQln OBJECT-TYPE
	SYNTAX OCTET STRING
	MAX-ACCESS read-only
	STATUS current
	DESCRIPTION
		"The object provides QLN for the ATU-R subcarriers.
		Each subcarrier takes two octets to store the value.
		A special value 0 indicates that no measurement could be done 
		for the sub-carrier group."
	::= { adslLineStatsEntry 6 }

	adslLineStatsAtucTssi1 OBJECT-TYPE
	SYNTAX OCTET STRING
	MAX-ACCESS read-only
	STATUS current
	DESCRIPTION
		"The object provides TSSI for the ATU-C first 256 subcarriers.
		Each subcarrier takes two octets to store the value."
	::= { adslLineStatsEntry 7 }

	adslLineStatsAtucTssi2 OBJECT-TYPE
	SYNTAX OCTET STRING
	MAX-ACCESS read-only
	STATUS current
	DESCRIPTION
		"The object provides TSSI for the ATU-C last 256 subcarriers.
		Each subcarrier takes two octets to store the value."
	::= { adslLineStatsEntry 8 }

	adslLineStatsAturTssi OBJECT-TYPE
	SYNTAX OCTET STRING
	MAX-ACCESS read-only
	STATUS current
	DESCRIPTION
		"The object provides TSSI for the ATU-R subcarriers.
		Each subcarrier takes two octets to store the value."
	::= { adslLineStatsEntry 9 }

	adslLineStatsAtucGain1 OBJECT-TYPE
	SYNTAX OCTET STRING
	MAX-ACCESS read-only
	STATUS current
	DESCRIPTION
		"The object provides GAIN for the ATU-C first 256 subcarriers.
		Each subcarrier takes two octets to store the value."
	::= { adslLineStatsEntry 10 }

	adslLineStatsAtucGain2 OBJECT-TYPE
	SYNTAX OCTET STRING
	MAX-ACCESS read-only
	STATUS current
	DESCRIPTION
		"The object provides GAIN for the ATU-C last 256 subcarriers.
		Each subcarrier takes two octets to store the value."
	::= { adslLineStatsEntry 11 }

	adslLineStatsAturGain OBJECT-TYPE
	SYNTAX OCTET STRING
	MAX-ACCESS read-only
	STATUS current
	DESCRIPTION
		"The object provides GAIN for the ATU-R subcarriers.
		Each subcarrier takes two octets to store the value."
	::= { adslLineStatsEntry 12 }

	adslLineStatsAtucBits1 OBJECT-TYPE
	SYNTAX OCTET STRING
	MAX-ACCESS read-only
	STATUS current
	DESCRIPTION
		"The object provides BITS for the ATU-C first 256 subcarriers.
		Each subcarrier takes two octets to store the value."
	::= { adslLineStatsEntry 13 }

	adslLineStatsAtucBits2 OBJECT-TYPE
	SYNTAX OCTET STRING
	MAX-ACCESS read-only
	STATUS current
	DESCRIPTION
		"The object provides BITS for the ATU-C last 256 subcarriers.
		Each subcarrier takes two octets to store the value."
	::= { adslLineStatsEntry 14 }

	adslLineStatsAturBits OBJECT-TYPE
	SYNTAX OCTET STRING
	MAX-ACCESS read-only
	STATUS current
	DESCRIPTION
		"The object provides BITS for the ATU-R subcarriers.
		Each subcarrier takes two octets to store the value."
	::= { adslLineStatsEntry 15 }
	
-- adslLinePerfTable

        adslLinePerfTable OBJECT-TYPE
        SYNTAX SEQUENCE OF AdslLinePerfEntry
        MAX-ACCESS not-accessible
        STATUS current
        DESCRIPTION
        	"The table displays ADSL line performance."
        ::= { adslStats 4 }

        adslLinePerfEntry OBJECT-TYPE
        SYNTAX AdslLinePerfEntry
        MAX-ACCESS not-accessible
        STATUS current
        DESCRIPTION
        	"An entry of adslLinePerfTable."
        INDEX { ifIndex }
        ::= { adslLinePerfTable 1 }

        AdslLinePerfEntry ::=
        	SEQUENCE {
                  	adslLinePerfAtucCrcFast		Counter32,
			adslLinePerfAturCrcFast		Counter32,
			adslLinePerfAtucFecFast		Counter32,
			adslLinePerfAturFecFast		Counter32,
			adslLinePerfAtucCrcInterleave	Counter32,
			adslLinePerfAturCrcInterleave	Counter32,
			adslLinePerfAtucFecInterleave	Counter32,
			adslLinePerfAturFecInterleave	Counter32,
			adslLinePerfAtucEs		Counter32,
			adslLinePerfAturEs		Counter32,
			adslLinePerfAtucSes		Counter32,
			adslLinePerfAturSes		Counter32,
			adslLinePerfAtucUas		Counter32,
			adslLinePerfAturUas		Counter32,
			adslLinePerfAtucLofs		Counter32,
			adslLinePerfAturLofs		Counter32,
			adslLinePerfAtucLoss		Counter32,
			adslLinePerfAturLoss		Counter32,
			adslLinePerfAtucLprs		Counter32,
			adslLinePerfAturLprs		Counter32
              	}
              	
	adslLinePerfAtucCrcFast OBJECT-TYPE
	SYNTAX Counter32
	MAX-ACCESS read-only
	STATUS current
	DESCRIPTION
		"The total number of CRC errors in fast mode."
	::= { adslLinePerfEntry 1 }
	
	adslLinePerfAturCrcFast OBJECT-TYPE
	SYNTAX Counter32
	MAX-ACCESS read-only
	STATUS current
	DESCRIPTION
		"The total number of CRC errors in fast mode."
	::= { adslLinePerfEntry 2 }
	
	adslLinePerfAtucFecFast OBJECT-TYPE
	SYNTAX Counter32
	MAX-ACCESS read-only
	STATUS current
	DESCRIPTION
		"The total number of FEC errors in fast mode."
	::= { adslLinePerfEntry 3 }
	
	adslLinePerfAturFecFast OBJECT-TYPE
	SYNTAX Counter32
	MAX-ACCESS read-only
	STATUS current
	DESCRIPTION
		"The total number of FEC errors in fast mode."
	::= { adslLinePerfEntry 4 }
	
	adslLinePerfAtucCrcInterleave OBJECT-TYPE
	SYNTAX Counter32
	MAX-ACCESS read-only
	STATUS current
	DESCRIPTION
		"The total number of CRC errors in interleave mode."
	::= { adslLinePerfEntry 5 }
	
	adslLinePerfAturCrcInterleave OBJECT-TYPE
	SYNTAX Counter32
	MAX-ACCESS read-only
	STATUS current
	DESCRIPTION
		"The total number of CRC errors in interleave mode."
	::= { adslLinePerfEntry 6 }
	
	adslLinePerfAtucFecInterleave OBJECT-TYPE
	SYNTAX Counter32
	MAX-ACCESS read-only
	STATUS current
	DESCRIPTION
		"The total number of FEC errors in interleave mode."
	::= { adslLinePerfEntry 7 }
	
	adslLinePerfAturFecInterleave OBJECT-TYPE
	SYNTAX Counter32
	MAX-ACCESS read-only
	STATUS current
	DESCRIPTION
		"The total number of FEC errors in interleave mode."
	::= { adslLinePerfEntry 8 }
					
        adslLinePerfAtucEs OBJECT-TYPE
	SYNTAX Counter32
	MAX-ACCESS read-only
	STATUS current
	DESCRIPTION
		"Count of the number of Errored Seconds since link up."
	::= { adslLinePerfEntry 9 }
	
	adslLinePerfAturEs OBJECT-TYPE
	SYNTAX Counter32
	MAX-ACCESS read-only
	STATUS current
	DESCRIPTION
		"Count of the number of Errored Seconds since link up."
	::= { adslLinePerfEntry 10 }
	
	adslLinePerfAtucSes OBJECT-TYPE
	SYNTAX Counter32
	MAX-ACCESS read-only
	STATUS current
	DESCRIPTION
		"Count of the number of Severely Errored Seconds since link up."
	::= { adslLinePerfEntry 11 }
	
	adslLinePerfAturSes OBJECT-TYPE
	SYNTAX Counter32
	MAX-ACCESS read-only
	STATUS current
	DESCRIPTION
		"Count of the number of Severely Errored Seconds since link up."
	::= { adslLinePerfEntry 12 }
	
	adslLinePerfAtucUas OBJECT-TYPE
	SYNTAX Counter32
	MAX-ACCESS read-only
	STATUS current
	DESCRIPTION
		"Count of the number of Unavailable Seconds since link up."
	::= { adslLinePerfEntry 13 }
	
	adslLinePerfAturUas OBJECT-TYPE
	SYNTAX Counter32
	MAX-ACCESS read-only
	STATUS current
	DESCRIPTION
		"Count of the number of Unavailable Seconds since link up."
	::= { adslLinePerfEntry 14 }
	
	adslLinePerfAtucLofs OBJECT-TYPE
	SYNTAX Counter32
	MAX-ACCESS read-only
	STATUS current
	DESCRIPTION
		"Count of the number of Loss of Framing failures since link up."
	::= { adslLinePerfEntry 15 }
	
	adslLinePerfAturLofs OBJECT-TYPE
	SYNTAX Counter32
	MAX-ACCESS read-only
	STATUS current
	DESCRIPTION
		"Count of the number of Loss of Framing failures since link up."
	::= { adslLinePerfEntry 16 }
	
	adslLinePerfAtucLoss OBJECT-TYPE
	SYNTAX Counter32
	MAX-ACCESS read-only
	STATUS current
	DESCRIPTION
		"Count of the number of Loss of Signal failures since link up."
	::= { adslLinePerfEntry 17 }
	
	adslLinePerfAturLoss OBJECT-TYPE
	SYNTAX Counter32
	MAX-ACCESS read-only
	STATUS current
	DESCRIPTION
		"Count of the number of Loss of Signal failures since link up."
	::= { adslLinePerfEntry 18 }
	
	adslLinePerfAtucLprs OBJECT-TYPE
	SYNTAX Counter32
	MAX-ACCESS read-only
	STATUS current
	DESCRIPTION
		"Count of the number of Loss of Power failures since link up."
	::= { adslLinePerfEntry 19 }
	
	adslLinePerfAturLprs OBJECT-TYPE
	SYNTAX Counter32
	MAX-ACCESS read-only
	STATUS current
	DESCRIPTION
		"Count of the number of Loss of Power failures since link up."
	::= { adslLinePerfEntry 20 }

--------------------
--  SHDSL
--------------------

-- shdslLinePerfTable

    shdslLinePerfTable OBJECT-TYPE
    SYNTAX SEQUENCE OF ShdslLinePerfEntry
    MAX-ACCESS not-accessible
    STATUS current
    DESCRIPTION
    "The table displays SHDSL line performance."
    ::= { shdslStats 1 }

    shdslLinePerfEntry OBJECT-TYPE
    SYNTAX ShdslLinePerfEntry
    MAX-ACCESS not-accessible
    STATUS current
    DESCRIPTION
    "An entry of shdslLinePerfTable."
    INDEX { ifIndex }
    ::= { shdslLinePerfTable 1 }

    ShdslLinePerfEntry ::=
    SEQUENCE {
        shdslLinePerfEs			Counter32,
        shdslLinePerfSes		Counter32,
		shdslLinePerfCrc		Counter32,
		shdslLinePerfLosws		Counter32,
		shdslLinePerfUas		Counter32,
		shdslLinePerfSegmentAnomalies	Counter32,
		shdslLinePerfSegmentDefect	Counter32
    }
              	
	shdslLinePerfEs OBJECT-TYPE
	SYNTAX Counter32
	MAX-ACCESS read-only
	STATUS current
	DESCRIPTION
		"Count of Errored Seconds (ES) on this endpoint since link up."
	::= { shdslLinePerfEntry 1 }
	
	shdslLinePerfSes OBJECT-TYPE
	SYNTAX Counter32
	MAX-ACCESS read-only
	STATUS current
	DESCRIPTION
		"Count of Severely Errored Seconds (SES) on this endpoint since link up."
	::= { shdslLinePerfEntry 2 }
	
	shdslLinePerfCrc OBJECT-TYPE
	SYNTAX Counter32
	MAX-ACCESS read-only
	STATUS current
	DESCRIPTION
		"Count of CRC anomalies on this endpoint since link up."
	::= { shdslLinePerfEntry 3 }
	
	shdslLinePerfLosws OBJECT-TYPE
	SYNTAX Counter32
	MAX-ACCESS read-only
	STATUS current
	DESCRIPTION
		"Count of Loss of Sync Word (LOSW) Seconds on this endpoint since link up."
	::= { shdslLinePerfEntry 4 }
	
	shdslLinePerfUas OBJECT-TYPE
	SYNTAX Counter32
	MAX-ACCESS read-only
	STATUS current
	DESCRIPTION
		"Count of Unavailable Seconds (UAS) on this endpoint since link up."
	::= { shdslLinePerfEntry 5 }
	
	shdslLinePerfSegmentAnomalies OBJECT-TYPE
	SYNTAX Counter32
	MAX-ACCESS read-only
	STATUS current
	DESCRIPTION
		"Count of Segment Anomalies on this endpoint since link up."
	::= { shdslLinePerfEntry 6 }
	
	shdslLinePerfSegmentDefect OBJECT-TYPE
	SYNTAX Counter32
	MAX-ACCESS read-only
	STATUS current
	DESCRIPTION
		"Count of Segment Defects on this endpoint since link up."
	::= { shdslLinePerfEntry 7 }

-- shdslPerfCurrTable

    shdslPerfCurrTable OBJECT-TYPE
    SYNTAX SEQUENCE OF ShdslPerfCurrEntry
    MAX-ACCESS not-accessible
    STATUS current
    DESCRIPTION
    "The table displays SHDSL current performance. This table is supported by R5.05 and later versions."
    ::= { shdslStats 2 }

    shdslPerfCurrEntry OBJECT-TYPE
    SYNTAX ShdslPerfCurrEntry
    MAX-ACCESS not-accessible
    STATUS current
    DESCRIPTION
    "An entry of shdslPerfCurrTable."
    INDEX { ifIndex }
    ::= { shdslPerfCurrTable 1 }

    ShdslPerfCurrEntry ::=
    SEQUENCE {
        shdslPerfCurrSturLPR			Counter32
    }
              	
	shdslPerfCurrSturLPR OBJECT-TYPE
	SYNTAX Counter32
	MAX-ACCESS read-only
	STATUS current
	DESCRIPTION
		"Count of the number of Loss of Power failures since agent reset."
	::= { shdslPerfCurrEntry 1 }

--------------------
--  IP
--------------------

-- ipInterfaceTable

        ipInterfaceTable OBJECT-TYPE
        SYNTAX SEQUENCE OF IpInterfaceEntry
        MAX-ACCESS not-accessible
        STATUS current
        DESCRIPTION
        	"The table displays IP interface statistics."
        ::= { ipStats 1 }

        ipInterfaceEntry OBJECT-TYPE
        SYNTAX IpInterfaceEntry
        MAX-ACCESS not-accessible
        STATUS current
        DESCRIPTION
        	"An entry of ipInterfaceTable."
        INDEX { ipInterface }
        ::= { ipInterfaceTable 1 }

        IpInterfaceEntry ::=
        	SEQUENCE {
                  	ipInterface		INTEGER,
			ipAddress		IpAddress,
			ipNetmask		IpAddress,
			ipBroadcast		IpAddress,
			ipMtu			INTEGER,
			ipVid			VlanIndex,
			ipInOctet		Counter32,
			ipInUnicast		Counter32,
			ipInMulticast		Counter32,
			ipInDiscard		Counter32,
			ipInError		Counter32,
			ipInUnknown		Counter32,
			ipOutOctet		Counter32,
			ipOutUnicast		Counter32,
			ipOutMulticast		Counter32,
			ipOutDiscard		Counter32,
			ipOutError		Counter32
              	}
              	
	ipInterface OBJECT-TYPE
	SYNTAX INTEGER
	MAX-ACCESS read-only
	STATUS current
	DESCRIPTION
		"The IP inband/outband interface."
	::= { ipInterfaceEntry 1 }

	ipAddress OBJECT-TYPE
	SYNTAX IpAddress
	MAX-ACCESS read-only
	STATUS current
	DESCRIPTION
		"IP address of the interface."
	::= { ipInterfaceEntry 2 }		

	ipNetmask OBJECT-TYPE
	SYNTAX IpAddress
	MAX-ACCESS read-only
	STATUS current
	DESCRIPTION
		"Netmask of the interface."
	::= { ipInterfaceEntry 3 }
	
	ipBroadcast OBJECT-TYPE
	SYNTAX IpAddress
	MAX-ACCESS read-only
	STATUS current
	DESCRIPTION
		"Broadcast address of the interface."
	::= { ipInterfaceEntry 4 }
	
	ipMtu OBJECT-TYPE
	SYNTAX INTEGER
	MAX-ACCESS read-only
	STATUS current
	DESCRIPTION
		"The size of the largest datagram which can be sent/received on the interface,
		specified in octets."
	::= { ipInterfaceEntry 5 }
	
	ipVid OBJECT-TYPE
	SYNTAX VlanIndex
	MAX-ACCESS read-only
	STATUS current
	DESCRIPTION
		"Management VLAN ID of the interface."
	::= { ipInterfaceEntry 6 }
	
	ipInOctet OBJECT-TYPE
	SYNTAX Counter32
	MAX-ACCESS read-only
	STATUS current
	DESCRIPTION
		"The total number of octets received on the interface."
	::= { ipInterfaceEntry 7 }
	
	ipInUnicast OBJECT-TYPE
	SYNTAX Counter32
	MAX-ACCESS read-only
	STATUS current
	DESCRIPTION
		"The number of subnetwork-unicast packets delivered to a higher-layer protocol."
	::= { ipInterfaceEntry 8 }
	
	ipInMulticast OBJECT-TYPE
	SYNTAX Counter32
	MAX-ACCESS read-only
	STATUS current
	DESCRIPTION
		"The number of subnetwork-multicast packets delivered to a higher-layer protocol."
	::= { ipInterfaceEntry 9 }
	
	ipInDiscard OBJECT-TYPE
	SYNTAX Counter32
	MAX-ACCESS read-only
	STATUS current
	DESCRIPTION
		"The number of inbound packets which were chosen to be discarded 
		even though no errors had been detected to prevent their being deliverable to a
 		higher-layer protocol."
	::= { ipInterfaceEntry 10 }
	
	ipInError OBJECT-TYPE
	SYNTAX Counter32
	MAX-ACCESS read-only
	STATUS current
	DESCRIPTION
		"The number of inbound packets that contained errors preventing them from 
		being deliverable to a higher-layer protocol."
	::= { ipInterfaceEntry 11 }
	
	ipInUnknown OBJECT-TYPE
	SYNTAX Counter32
	MAX-ACCESS read-only
	STATUS current
	DESCRIPTION
		"The number of packets received via the interface which were discarded 
		because of an unknown or unsupported protocol."
	::= { ipInterfaceEntry 12 }

	ipOutOctet OBJECT-TYPE
	SYNTAX Counter32
	MAX-ACCESS read-only
	STATUS current
	DESCRIPTION
		"The total number of octets transmitted out of the interface."
	::= { ipInterfaceEntry 13 }
	
	ipOutUnicast OBJECT-TYPE
	SYNTAX Counter32
	MAX-ACCESS read-only
	STATUS current
	DESCRIPTION
		"The total number of packets that higher-level protocols requested be 
		transmitted to a subnetwork-unicast address, including those that
 		were discarded or not sent."
	::= { ipInterfaceEntry 14 }
	
	ipOutMulticast OBJECT-TYPE
	SYNTAX Counter32
	MAX-ACCESS read-only
	STATUS current
	DESCRIPTION
		"The total number of packets that higher-level protocols requested be 
		transmitted to a subnetwork-multicast address, including those that
 		were discarded or not sent."
	::= { ipInterfaceEntry 15 }
	
	ipOutDiscard OBJECT-TYPE
	SYNTAX Counter32
	MAX-ACCESS read-only
	STATUS current
	DESCRIPTION
		"The number of outbound packets which were chosen to be discarded even though 
		no errors had been detected to prevent their being transmitted."
	::= { ipInterfaceEntry 16 }
	
	ipOutError OBJECT-TYPE
	SYNTAX Counter32
	MAX-ACCESS read-only
	STATUS current
	DESCRIPTION
		"The number of outbound packets that could not be transmitted because of errors."
	::= { ipInterfaceEntry 17 }

--------------------
--  MSTP
--------------------

	mstpExternalRootId OBJECT-TYPE
        SYNTAX BridgeId
        MAX-ACCESS read-only
        STATUS current
        DESCRIPTION
        	"The bridge identifier of the root of the spanning tree as determined by 
        	the Spanning Tree Protocol as executed by this node. This value is used as
                the Root Identifier parameter in all Configuration Bridge PDUs originated by this node.
                This object is supported by R1.02 and later versions."
        ::= { mstpStats 1 }

	mstpExternalRootCost OBJECT-TYPE
        SYNTAX INTEGER
        MAX-ACCESS read-only
        STATUS current
        DESCRIPTION
        	"The cost of the path to the root as seen from this bridge.
        	This object is supported by R1.02 and later versions."
        ::= { mstpStats 2 }
                                 
	mstpExternalRootPortId OBJECT-TYPE
        SYNTAX OCTET STRING
        MAX-ACCESS read-only
        STATUS current
        DESCRIPTION
        	"The port number of the port which offers the lowest cost path from 
        	this bridge to the root bridge.
        	This object is supported by R1.02 and later versions."
        ::= { mstpStats 3 }
              	
	mstpExternalRootMaxAge OBJECT-TYPE
        SYNTAX Timeout
        MAX-ACCESS read-only
        STATUS current
        DESCRIPTION
        	"The maximum age of Spanning Tree Protocol information learned from 
        	the network on any port before it is discarded, in units of hundredths of
                a second.  This is the actual value that this bridge is currently using.
                This object is supported by R1.02 and later versions."
        ::= { mstpStats 4 }
        
        mstpExternalRootHelloTime OBJECT-TYPE
        SYNTAX Timeout
        MAX-ACCESS read-only
        STATUS current
        DESCRIPTION
        	"The amount of time between the transmission of Configuration bridge PDUs 
        	by this node on any port when it is the root of the spanning tree or trying
                to become so, in units of hundredths of a second. This is the actual value that 
                this bridge is currently using.
                This object is supported by R1.02 and later versions."
        ::= { mstpStats 5 }
        
        mstpExternalRootForwardDelay OBJECT-TYPE
        SYNTAX Timeout
        MAX-ACCESS read-only
        STATUS current
        DESCRIPTION
        	"This time value, measured in units of hundredths of a second, controls
        	how fast a port changes its spanning state when moving towards the Forwarding
                state. The value determines how long the port stays in each of the Listening
                and Learning states, which precede the Forwarding state. This value is also used,
                when a topology change has been detected and is underway, to age all dynamic
                entries in the Forwarding Database.
                This object is supported by R1.02 and later versions."
        ::= { mstpStats 6 }

-- mstpPortStatsTable

	mstpPortStatsTable OBJECT-TYPE
    	SYNTAX SEQUENCE OF MstpPortStatsEntry
    	MAX-ACCESS not-accessible
    	STATUS current
    	DESCRIPTION
        	"A table that contains port-specific MSTP statistics.
        	This table is supported by R1.02 and later versions."
    	::= { mstpStats 7 }

	mstpPortStatsEntry OBJECT-TYPE
    	SYNTAX MstpPortStatsEntry
    	MAX-ACCESS not-accessible
    	STATUS current
    	DESCRIPTION
        	"A list of MSTP statistics maintained by each port."
    	INDEX { dot1dBasePort }
    	::= { mstpPortStatsTable 1 }

	MstpPortStatsEntry ::=
    		SEQUENCE {
    			mstpPortStatsExternalRootId	BridgeId,
    			mstpPortStatsExternalRootCost	INTEGER,
    			mstpPortStatsExternalPortCost	INTEGER,
    			mstpPortStatsOperEdgePort	INTEGER,
    			mstpPortStatsOperPoint2Point	INTEGER,
    			mstpPortStatsMACOperational	INTEGER,
    			mstpPortStatsRecvInternal	INTEGER,
    			mstpPortStatsRxStpCfgBPDU	Counter32,
    			mstpPortStatsRxStpTcnBPDU	Counter32,
    			mstpPortStatsRxRstpBPDU		Counter32,
    			mstpPortStatsRxMstpBPDU		Counter32
    		}

	mstpPortStatsExternalRootId OBJECT-TYPE
        SYNTAX BridgeId
        MAX-ACCESS read-only
        STATUS current
        DESCRIPTION
        	"The unique Bridge Identifier of the Bridge recorded as the Root 
        	in the Configuration BPDUs transmitted by the Designated Bridge for the
                segment to which the port is attached."
        ::= { mstpPortStatsEntry 1 }
              
	mstpPortStatsExternalRootCost OBJECT-TYPE
        SYNTAX INTEGER
        MAX-ACCESS read-only
        STATUS current
        DESCRIPTION
        	"The path cost of the Designated Port of the segment connected to this port.
        	This value is compared to the Root Path Cost field in received bridge PDUs."
        ::= { mstpPortStatsEntry 2 }
        
        mstpPortStatsExternalPortCost OBJECT-TYPE
        SYNTAX INTEGER
        MAX-ACCESS read-only
        STATUS current
        DESCRIPTION
        	""
        ::= { mstpPortStatsEntry 3 }
        
        mstpPortStatsOperEdgePort OBJECT-TYPE
        SYNTAX 	INTEGER {
        		true(1),
        		false(2)
        	}
        MAX-ACCESS read-only
        STATUS current
        DESCRIPTION
        	"The operational value of the Edge Port parameter."
        ::= { mstpPortStatsEntry 4 }
        
        mstpPortStatsOperPoint2Point OBJECT-TYPE
        SYNTAX 	INTEGER {
        		true(1),
        		false(2)
        	}
        MAX-ACCESS read-only
        STATUS current
        DESCRIPTION
        	"The operational point-to-point status of the LAN segment attached to this port.
        	It indicates whether a port is considered to have a point-to-point connection or not."
        ::= { mstpPortStatsEntry 5 }
        
        mstpPortStatsMACOperational OBJECT-TYPE
        SYNTAX 	INTEGER {
        		true(1),
        		false(2)
        	}
        MAX-ACCESS read-only
        STATUS current
        DESCRIPTION
        	""
        ::= { mstpPortStatsEntry 6 }
        
        mstpPortStatsRecvInternal OBJECT-TYPE
        SYNTAX 	INTEGER {
        		true(1),
        		false(2)
        	}
        MAX-ACCESS read-only
        STATUS current
        DESCRIPTION
        	""
        ::= { mstpPortStatsEntry 7 }
        
        mstpPortStatsRxStpCfgBPDU OBJECT-TYPE
        SYNTAX Counter32
        MAX-ACCESS read-only
        STATUS current
        DESCRIPTION
        	"The total number of received Configuration BPDUs."
        ::= { mstpPortStatsEntry 8 }
        
        mstpPortStatsRxStpTcnBPDU OBJECT-TYPE
        SYNTAX Counter32
        MAX-ACCESS read-only
        STATUS current
        DESCRIPTION
        	"The total number of received Topology Change Notification (TCN) Messages."
        ::= { mstpPortStatsEntry 9 }
        
        mstpPortStatsRxRstpBPDU OBJECT-TYPE
        SYNTAX Counter32
        MAX-ACCESS read-only
        STATUS current
        DESCRIPTION
        	"The total number of received RST BPDUs."
        ::= { mstpPortStatsEntry 10 }
        
        mstpPortStatsRxMstpBPDU OBJECT-TYPE
        SYNTAX Counter32
        MAX-ACCESS read-only
        STATUS current
        DESCRIPTION
        	"The total number of received MST BPDUs."
        ::= { mstpPortStatsEntry 11 }

-- mstpXstStatsTable

	mstpXstStatsTable OBJECT-TYPE
    	SYNTAX SEQUENCE OF MstpXstStatsEntry
    	MAX-ACCESS not-accessible
    	STATUS current
    	DESCRIPTION
        	"A table that contains MSTP statistics for multiple spanning trees.
        	This table is supported by R1.02 and later versions."
    	::= { mstpStats 8 }

	mstpXstStatsEntry OBJECT-TYPE
    	SYNTAX MstpXstStatsEntry
    	MAX-ACCESS not-accessible
    	STATUS current
    	DESCRIPTION
        	"An entry of mstpXstStatsTable."
    	INDEX { mstpXstId }
    	::= { mstpXstStatsTable 1 }

	MstpXstStatsEntry ::=
    		SEQUENCE {
    			mstpXstStatsBridgeId			BridgeId,
    			mstpXstStatsTimeSinceTopologyChange	TimeTicks,
    			mstpXstStatsTopologyChangesCount	Counter32,
    			mstpXstStatsInternalRootPortId		OCTET STRING,
    			mstpXstStatsInternalRootId		BridgeId,
    			mstpXstStatsInternalRootCost		INTEGER
    		}
    		
	mstpXstStatsBridgeId OBJECT-TYPE
        SYNTAX BridgeId
        MAX-ACCESS read-only
        STATUS current
        DESCRIPTION
        	""
        ::= { mstpXstStatsEntry 1 }
    	
    	mstpXstStatsTimeSinceTopologyChange OBJECT-TYPE
        SYNTAX TimeTicks
        MAX-ACCESS read-only
        STATUS current
        DESCRIPTION
        	""
        ::= { mstpXstStatsEntry 2 }
        
        mstpXstStatsTopologyChangesCount OBJECT-TYPE
        SYNTAX Counter32
        MAX-ACCESS read-only
        STATUS current
        DESCRIPTION
        	""
        ::= { mstpXstStatsEntry 3 }
        
        mstpXstStatsInternalRootPortId OBJECT-TYPE
        SYNTAX OCTET STRING
        MAX-ACCESS read-only
        STATUS current
        DESCRIPTION
        	""
        ::= { mstpXstStatsEntry 4 }
        
        mstpXstStatsInternalRootId OBJECT-TYPE
        SYNTAX BridgeId
        MAX-ACCESS read-only
        STATUS current
        DESCRIPTION
        	""
        ::= { mstpXstStatsEntry 5 }
        
        mstpXstStatsInternalRootCost OBJECT-TYPE
        SYNTAX INTEGER
        MAX-ACCESS read-only
        STATUS current
        DESCRIPTION
        	""
        ::= { mstpXstStatsEntry 6 }
        	
-- mstpXstPortStatsTable

	mstpXstPortStatsTable OBJECT-TYPE
    	SYNTAX SEQUENCE OF MstpXstPortStatsEntry
    	MAX-ACCESS not-accessible
    	STATUS current
    	DESCRIPTION
        	"A table that contains MSTP port statistics for multiple spanning trees.
        	This table is supported by R1.02 and later versions."
    	::= { mstpStats 9 }

	mstpXstPortStatsEntry OBJECT-TYPE
    	SYNTAX MstpXstPortStatsEntry
    	MAX-ACCESS not-accessible
    	STATUS current
    	DESCRIPTION
        	"An entry of mstpXstPortStatsTable."
    	INDEX { mstpXstId, mstpXstPortIndex }
    	::= { mstpXstPortStatsTable 1 }

	MstpXstPortStatsEntry ::=
    		SEQUENCE {
    			mstpXstPortStatsUptime			TimeTicks,
    			mstpXstPortStatsPortId			OCTET STRING,
    			mstpXstPortStatsState			INTEGER,
    			mstpXstPortStatsDesignatedBridgeId	BridgeId,
    			mstpXstPortStatsDesignatedPortId	OCTET STRING,
    			mstpXstPortStatsInternalPortCost	INTEGER,
    			mstpXstPortStatsInternalRootId		BridgeId
    		}
    		
    	mstpXstPortStatsUptime OBJECT-TYPE
        SYNTAX TimeTicks
        MAX-ACCESS read-only
        STATUS current
        DESCRIPTION
        	""
        ::= { mstpXstPortStatsEntry 1 }
        
        mstpXstPortStatsPortId OBJECT-TYPE
        SYNTAX OCTET STRING
        MAX-ACCESS read-only
        STATUS current
        DESCRIPTION
        	""
        ::= { mstpXstPortStatsEntry 2 }
        
        mstpXstPortStatsState OBJECT-TYPE
        SYNTAX 	INTEGER {
        		disabled(1),
        		discarding(2),
        		learning(3),
        		forwarding(4),
        		unknown(5)
        	}
        MAX-ACCESS read-only
        STATUS current
        DESCRIPTION
        	"The port's current state."
        ::= { mstpXstPortStatsEntry 3 }
        
        mstpXstPortStatsDesignatedBridgeId OBJECT-TYPE
        SYNTAX BridgeId
        MAX-ACCESS read-only
        STATUS current
        DESCRIPTION
        	"The Bridge Identifier of the bridge which this port considers to be 
        	the Designated Bridge for this port's segment."
        ::= { mstpXstPortStatsEntry 4 }
        
        mstpXstPortStatsDesignatedPortId OBJECT-TYPE
        SYNTAX OCTET STRING
        MAX-ACCESS read-only
        STATUS current
        DESCRIPTION
        	"The Port Identifier of the port on the Designated Bridge for this port's segment."
        ::= { mstpXstPortStatsEntry 5 }
        
        mstpXstPortStatsInternalPortCost OBJECT-TYPE
        SYNTAX INTEGER
        MAX-ACCESS read-only
        STATUS current
        DESCRIPTION
        	"The path cost of the Designated Port of the segment connected to this port.
        	This value is compared to the Root Path Cost field in received bridge PDUs."
        ::= { mstpXstPortStatsEntry 6 }
        
        mstpXstPortStatsInternalRootId OBJECT-TYPE
        SYNTAX BridgeId
        MAX-ACCESS read-only
        STATUS current
        DESCRIPTION
        	""
        ::= { mstpXstPortStatsEntry 7 }

--------------------
--  VDSL
--------------------

-- vdslLinePerfTable

        vdslLinePerfTable OBJECT-TYPE
        SYNTAX SEQUENCE OF VdslLinePerfEntry
        MAX-ACCESS not-accessible
        STATUS current
        DESCRIPTION
        	"The table displays VDSL line performance. This table is supported by R2.00 and later versions."
        ::= { vdslStats 1 }

        vdslLinePerfEntry OBJECT-TYPE
        SYNTAX VdslLinePerfEntry
        MAX-ACCESS not-accessible
        STATUS current
        DESCRIPTION
        	"An entry of vdslLinePerfTable."
        INDEX { ifIndex }
        ::= { vdslLinePerfTable 1 }

        VdslLinePerfEntry ::=
        	SEQUENCE {
                  	vdslLinePerfVtucCrc		Counter32,
			vdslLinePerfVturCrc		Counter32,
			vdslLinePerfVtucFec		Counter32,
			vdslLinePerfVturFec		Counter32,
			vdslLinePerfVtucLofs		Counter32,
			vdslLinePerfVturLofs		Counter32,
			vdslLinePerfVtucLoss		Counter32,
			vdslLinePerfVturLoss		Counter32,
			vdslLinePerfVtucLprs		Counter32,
			vdslLinePerfVturLprs		Counter32,
			vdslLinePerfVtucLols		Counter32,
			vdslLinePerfVturLols		Counter32,
			vdslLinePerfVtucESs		Counter32,
			vdslLinePerfVturESs		Counter32,
			vdslLinePerfVtucSESs		Counter32,
			vdslLinePerfVturSESs		Counter32,
			vdslLinePerfVtucUASs		Counter32,
			vdslLinePerfVturUASs		Counter32,
			vdslLinePerfInmVtucEqInp		Counter32,
			vdslLinePerfInmVturEqInp		Counter32,
			vdslLinePerfInmVtucIAT		Counter32,
			vdslLinePerfInmVturIAT		Counter32,
			vdslLinePerfInmVtucME		Counter32,
			vdslLinePerfInmVturME		Counter32,
			vdslLinePerfVtucRx		Unsigned32,
			vdslLinePerfVturRx		Unsigned32,
			vdslLinePerfVtucRxCorrected		Unsigned32,
			vdslLinePerfVturRxCorrected		Unsigned32,
			vdslLinePerfVtucRxUncorrected		Unsigned32,
			vdslLinePerfVturRxUncorrected		Unsigned32,
			vdslLinePerfVtucLEFTRs		Unsigned32,
			vdslLinePerfVturLEFTRs		Unsigned32,
			vdslLinePerfVtucErrFreeBits		Unsigned32,
			vdslLinePerfVturErrFreeBits		Unsigned32,
			vdslLinePerfVtucMinEftr		Counter32,
			vdslLinePerfVturMinEftr		Counter32		
              	}
              	
	vdslLinePerfVtucCrc OBJECT-TYPE
	SYNTAX Counter32
	MAX-ACCESS read-only
	STATUS current
	DESCRIPTION
		"The number of CRC errors since link up."
	::= { vdslLinePerfEntry 1 }
	
	vdslLinePerfVturCrc OBJECT-TYPE
	SYNTAX Counter32
	MAX-ACCESS read-only
	STATUS current
	DESCRIPTION
		"The number of CRC errors since link up."
	::= { vdslLinePerfEntry 2 }
	
	vdslLinePerfVtucFec OBJECT-TYPE
	SYNTAX Counter32
	MAX-ACCESS read-only
	STATUS current
	DESCRIPTION
		"The number of FEC errors since link up."
	::= { vdslLinePerfEntry 3 }
	
	vdslLinePerfVturFec OBJECT-TYPE
	SYNTAX Counter32
	MAX-ACCESS read-only
	STATUS current
	DESCRIPTION
		"The number of FEC errors since link up."
	::= { vdslLinePerfEntry 4 }
	
	vdslLinePerfVtucLofs OBJECT-TYPE
	SYNTAX Counter32
	MAX-ACCESS read-only
	STATUS current
	DESCRIPTION
		"Count of the number of Loss of Framing failures since link up."
	::= { vdslLinePerfEntry 5 }
	
	vdslLinePerfVturLofs OBJECT-TYPE
	SYNTAX Counter32
	MAX-ACCESS read-only
	STATUS current
	DESCRIPTION
		"Count of the number of Loss of Framing failures since link up."
	::= { vdslLinePerfEntry 6 }
	
	vdslLinePerfVtucLoss OBJECT-TYPE
	SYNTAX Counter32
	MAX-ACCESS read-only
	STATUS current
	DESCRIPTION
		"Count of the number of Loss of Signal failures since link up."
	::= { vdslLinePerfEntry 7 }
	
	vdslLinePerfVturLoss OBJECT-TYPE
	SYNTAX Counter32
	MAX-ACCESS read-only
	STATUS current
	DESCRIPTION
		"Count of the number of Loss of Signal failures since link up."
	::= { vdslLinePerfEntry 8 }
	
	vdslLinePerfVtucLprs OBJECT-TYPE
	SYNTAX Counter32
	MAX-ACCESS read-only
	STATUS current
	DESCRIPTION
		"Count of the number of Loss of Power failures since link up."
	::= { vdslLinePerfEntry 9 }
	
	vdslLinePerfVturLprs OBJECT-TYPE
	SYNTAX Counter32
	MAX-ACCESS read-only
	STATUS current
	DESCRIPTION
		"Count of the number of Loss of Power failures since link up."
	::= { vdslLinePerfEntry 10 }
	
	vdslLinePerfVtucLols OBJECT-TYPE
	SYNTAX Counter32
	MAX-ACCESS read-only
	STATUS current
	DESCRIPTION
		"Count of the number of Loss of Link failures since link up."
	::= { vdslLinePerfEntry 11 }
	
	vdslLinePerfVturLols OBJECT-TYPE
	SYNTAX Counter32
	MAX-ACCESS read-only
	STATUS current
	DESCRIPTION
		"Count of the number of Loss of Link failures since link up."
	::= { vdslLinePerfEntry 12 }
	
	vdslLinePerfVtucESs OBJECT-TYPE
	SYNTAX Counter32
	MAX-ACCESS read-only
	STATUS current
	DESCRIPTION
		"Count of the number of Errored Seconds since link up."
	::= { vdslLinePerfEntry 13 }
	
	vdslLinePerfVturESs OBJECT-TYPE
	SYNTAX Counter32
	MAX-ACCESS read-only
	STATUS current
	DESCRIPTION
		"Count of the number of Errored Seconds since link up."
	::= { vdslLinePerfEntry 14 }
	
	vdslLinePerfVtucSESs OBJECT-TYPE
	SYNTAX Counter32
	MAX-ACCESS read-only
	STATUS current
	DESCRIPTION
		"Count of the number of Severely Errored Seconds since link up."
	::= { vdslLinePerfEntry 15 }
	
	vdslLinePerfVturSESs OBJECT-TYPE
	SYNTAX Counter32
	MAX-ACCESS read-only
	STATUS current
	DESCRIPTION
		"Count of the number of Severely Errored Seconds since link up."
	::= { vdslLinePerfEntry 16 }
	
	vdslLinePerfVtucUASs OBJECT-TYPE
	SYNTAX Counter32
	MAX-ACCESS read-only
	STATUS current
	DESCRIPTION
		"Count of the number of Unavailable Seconds since link up."
	::= { vdslLinePerfEntry 17 }
	
	vdslLinePerfVturUASs OBJECT-TYPE
	SYNTAX Counter32
	MAX-ACCESS read-only
	STATUS current
	DESCRIPTION
		"Count of the number of Unavailable Seconds since link up."
	::= { vdslLinePerfEntry 18 }
	
	vdslLinePerfInmVtucEqInp OBJECT-TYPE
	SYNTAX Counter32
	MAX-ACCESS read-only
	STATUS current
	DESCRIPTION
		"The INM Equivalent Inp histogram since last link up. An array of 68 octets 
		(each 4 octets means amount of a bin of histogram), designed for supporting 
		from 1 to 17 bins of the histogram. The particular index of the bin incremented 
		by an impulse noise event is equal to the computed value of equivalent INP, 
		except the 17th of anomaly INPEQ, which logs all equivalent INPs greater than 16. 
		Each bin has a value in the range 0x0 to 0xFFFFFFFF"
	::= { vdslLinePerfEntry 19 }
	
	vdslLinePerfInmVturEqInp OBJECT-TYPE
	SYNTAX Counter32
	MAX-ACCESS read-only
	STATUS current
	DESCRIPTION
		"The INM Equivalent Inp histogram since last link up. An array of 68 octets 
		(each 4 octets means amount of a bin of histogram), designed for supporting 
		from 1 to 17 bins of the histogram. The particular index of the bin incremented 
		by an impulse noise event is equal to the computed value of equivalent INP, 
		except the 17th of anomaly INPEQ, which logs all equivalent INPs greater than 16. 
		Each bin has a value in the range 0x0 to 0xFFFFFFFF"
	::= { vdslLinePerfEntry 20 }
	
	vdslLinePerfInmVtucIAT OBJECT-TYPE
	SYNTAX Counter32
	MAX-ACCESS read-only
	STATUS current
	DESCRIPTION
		"The INM Inter Arrival Time histogram since last link up. An array of 32 octets 
		(each 4 octets means amount of a bin of histogram), designed for supporting 
		from 0 to 7 bins of the histogram. The index of the particular bin incremented 
		by an complete  impulse noise event is determained from the following INMControl parameters. 
		Each bin has a value in the range 0x0 to 0xFFFFFFFF."
	::= { vdslLinePerfEntry 21 }
	
	vdslLinePerfInmVturIAT OBJECT-TYPE
	SYNTAX Counter32
	MAX-ACCESS read-only
	STATUS current
	DESCRIPTION
		"The INM Inter Arrival Time histogram since last link up. An array of 32 octets 
		(each 4 octets means amount of a bin of histogram), designed for supporting 
		from 0 to 7 bins of the histogram. The index of the particular bin incremented 
		by an complete  impulse noise event is determained from the following INMControl parameters. 
		Each bin has a value in the range 0x0 to 0xFFFFFFFF."
	::= { vdslLinePerfEntry 22 }
	
	vdslLinePerfInmVtucME OBJECT-TYPE
	SYNTAX Counter32
	MAX-ACCESS read-only
	STATUS current
	DESCRIPTION
		"The INM total measurement since last link up. This indication occurs every time a data symbol 
		is processed by the Impulse Noise Sensor. The range of the value is from 0x0 to 0xFFFFFFFF."
	::= { vdslLinePerfEntry 23 }
	
	vdslLinePerfInmVturME OBJECT-TYPE
	SYNTAX Counter32
	MAX-ACCESS read-only
	STATUS current
	DESCRIPTION
		"The INM total measurement since last link up. This indication occurs every time a data symbol 
		is processed by the Impulse Noise Sensor. The range of the value is from 0x0 to 0xFFFFFFFF."
	::= { vdslLinePerfEntry 24 }
	
	vdslLinePerfVtucRx OBJECT-TYPE
	SYNTAX Unsigned32
	MAX-ACCESS read-only
	STATUS current
	DESCRIPTION
		"Number of codewords retransmitted since last link up."
	::= { vdslLinePerfEntry 25 }
	
	vdslLinePerfVturRx OBJECT-TYPE
	SYNTAX Unsigned32
	MAX-ACCESS read-only
	STATUS current
	DESCRIPTION
		"Number of codewords retransmitted since last link up."
	::= { vdslLinePerfEntry 26 }
	
	vdslLinePerfVtucRxCorrected OBJECT-TYPE
	SYNTAX Unsigned32
	MAX-ACCESS read-only
	STATUS current
	DESCRIPTION
		"Number of codewords corrected through retransmission since last link up."
	::= { vdslLinePerfEntry 27 }
	
	vdslLinePerfVturRxCorrected OBJECT-TYPE
	SYNTAX Unsigned32
	MAX-ACCESS read-only
	STATUS current
	DESCRIPTION
		"Number of codewords corrected through retransmission since last link up."
	::= { vdslLinePerfEntry 28 }
	
	vdslLinePerfVtucRxUncorrected OBJECT-TYPE
	SYNTAX Unsigned32
	MAX-ACCESS read-only
	STATUS current
	DESCRIPTION
		"Number of codewords left uncorrected after retransmission since last link up."
	::= { vdslLinePerfEntry 29 }
	
	vdslLinePerfVturRxUncorrected OBJECT-TYPE
	SYNTAX Unsigned32
	MAX-ACCESS read-only
	STATUS current
	DESCRIPTION
		"Number of codewords left uncorrected after retransmission since last link up."
	::= { vdslLinePerfEntry 30 }
	
	vdslLinePerfVtucLEFTRs OBJECT-TYPE
	SYNTAX Unsigned32
	MAX-ACCESS read-only
	STATUS current
	DESCRIPTION
		"Low Error-Free Throughput Rate Seconds since last link up."
	::= { vdslLinePerfEntry 31 }
	
	vdslLinePerfVturLEFTRs OBJECT-TYPE
	SYNTAX Unsigned32
	MAX-ACCESS read-only
	STATUS current
	DESCRIPTION
		"Low Error-Free Throughput Rate Seconds since last link up."
	::= { vdslLinePerfEntry 32 }
	
	vdslLinePerfVtucErrFreeBits OBJECT-TYPE
	SYNTAX Unsigned32
	MAX-ACCESS read-only
	STATUS current
	DESCRIPTION
		"The number of bits belonging to correct DTUs leaving the Rx PMS-TC x 2(-16) since last link up."
	::= { vdslLinePerfEntry 33 }
	
	vdslLinePerfVturErrFreeBits OBJECT-TYPE
	SYNTAX Unsigned32
	MAX-ACCESS read-only
	STATUS current
	DESCRIPTION
		"The number of bits belonging to correct DTUs leaving the Rx PMS-TC x 2(-16) since last link up."
	::= { vdslLinePerfEntry 34 } 
	
	vdslLinePerfVtucMinEftr OBJECT-TYPE
	SYNTAX Counter32
	MAX-ACCESS read-only
	STATUS current
	DESCRIPTION
		"Lowest EFTR of VTU-C observed since last link up."
	::= { vdslLinePerfEntry 35 }
    
    vdslLinePerfVturMinEftr OBJECT-TYPE
	SYNTAX Counter32
	MAX-ACCESS read-only
	STATUS current
	DESCRIPTION
		"Lowest EFTR of VTU-R observed since last link up."
	::= { vdslLinePerfEntry 36 }

-- vdslLineStatsTable

        vdslLineStatsTable OBJECT-TYPE
        SYNTAX SEQUENCE OF VdslLineStatsEntry
        MAX-ACCESS not-accessible
        STATUS current
        DESCRIPTION
        	"The table displays VDSL line statistics. This table is supported by R5.01 and later versions."
        ::= { vdslStats 2 }

        vdslLineStatsEntry OBJECT-TYPE
        SYNTAX VdslLineStatsEntry
        MAX-ACCESS not-accessible
        STATUS current
        DESCRIPTION
        	"An entry of vdslLineStatsTable."
        INDEX { ifIndex }
        ::= { vdslLineStatsTable 1 }

        VdslLineStatsEntry ::=
        	SEQUENCE {
                  	vdslLineStatsVtucBits1		OCTET STRING,
			vdslLineStatsVtucBits2		OCTET STRING,
			vdslLineStatsVtucBits3		OCTET STRING,
			vdslLineStatsVtucBits4		OCTET STRING,
			vdslLineStatsVturBits1		OCTET STRING,
			vdslLineStatsVturBits2		OCTET STRING,
			vdslLineStatsVturBits3		OCTET STRING,
			vdslLineStatsVturBits4		OCTET STRING,
			vdslLineStatsVtucGain1		OCTET STRING,
			vdslLineStatsVtucGain2		OCTET STRING,
			vdslLineStatsVtucGain3		OCTET STRING,
			vdslLineStatsVtucGain4		OCTET STRING,
			vdslLineStatsVtucGain5		OCTET STRING,
			vdslLineStatsVtucGain6		OCTET STRING,
			vdslLineStatsVtucGain7		OCTET STRING,
			vdslLineStatsVtucGain8		OCTET STRING,
			vdslLineStatsVturGain1		OCTET STRING,
			vdslLineStatsVturGain2		OCTET STRING,
			vdslLineStatsVturGain3		OCTET STRING,
			vdslLineStatsVturGain4		OCTET STRING,
			vdslLineStatsVturGain5		OCTET STRING,
			vdslLineStatsVturGain6		OCTET STRING,
			vdslLineStatsVturGain7		OCTET STRING,
			vdslLineStatsVturGain8		OCTET STRING,
			vdslLineStatsVtucHlog		OCTET STRING,
			vdslLineStatsVturHlog		OCTET STRING,
			vdslLineStatsVtucQln		OCTET STRING,
			vdslLineStatsVturQln		OCTET STRING,
			vdslLineStatsVtucSnr		OCTET STRING,
			vdslLineStatsVturSnr		OCTET STRING,
			vdslLineStatsVtucTssi		OCTET STRING,
			vdslLineStatsVturTssi		OCTET STRING,
			vdslLineStatsProtocol		INTEGER,
			vdslLineStatsUsCodingMode	INTEGER,
			vdslLineStatsDsCodingMode	INTEGER,
			vdslLineStatsVtucHlogGroupSize	INTEGER,
			vdslLineStatsVturHlogGroupSize	INTEGER,
			vdslLineStatsVtucQlnGroupSize	INTEGER,
			vdslLineStatsVturQlnGroupSize	INTEGER,
			vdslLineStatsVtucSnrGroupSize	INTEGER,
			vdslLineStatsVturSnrGroupSize	INTEGER,
			vdslLineStatsVtucRxPower		INTEGER,
			vdslLineStatsVturRxPower		INTEGER,
			vdslLineStatsVtucSnrMargin		INTEGER,
			vdslLineStatsVturSnrMargin		INTEGER,
			vdslLineStatsVtucSigAtten		INTEGER,
			vdslLineStatsVturSigAtten		INTEGER,
			vdslLineStatsVtucLineAtten		INTEGER,
			vdslLineStatsVturLineAtten		INTEGER
              	}
              	
	vdslLineStatsVtucBits1 OBJECT-TYPE
	SYNTAX OCTET STRING
	MAX-ACCESS read-only
	STATUS current
	DESCRIPTION
		"The object provides Bits for the VTU-C 1024 subcarriers.
		Each subcarrier takes two octets to store the value.
		The value is in the range 0 to 15."
	::= { vdslLineStatsEntry 1 }
	
	vdslLineStatsVtucBits2 OBJECT-TYPE
	SYNTAX OCTET STRING
	MAX-ACCESS read-only
	STATUS current
	DESCRIPTION
		"The object provides Bits for the VTU-C 1024 subcarriers.
		Each subcarrier takes two octets to store the value.
		The value is in the range 0 to 15."
	::= { vdslLineStatsEntry 2 }
	
	vdslLineStatsVtucBits3 OBJECT-TYPE
	SYNTAX OCTET STRING
	MAX-ACCESS read-only
	STATUS current
	DESCRIPTION
		"The object provides Bits for the VTU-C 1024 subcarriers.
		Each subcarrier takes two octets to store the value.
		The value is in the range 0 to 15."
	::= { vdslLineStatsEntry 3 }
	
	vdslLineStatsVtucBits4 OBJECT-TYPE
	SYNTAX OCTET STRING
	MAX-ACCESS read-only
	STATUS current
	DESCRIPTION
		"The object provides Bits for the VTU-C 1024 subcarriers.
		Each subcarrier takes two octets to store the value.
		The value is in the range 0 to 15."
	::= { vdslLineStatsEntry 4 }
	
	vdslLineStatsVturBits1 OBJECT-TYPE
	SYNTAX OCTET STRING
	MAX-ACCESS read-only
	STATUS current
	DESCRIPTION
		"The object provides Bits for the VTU-R 1024 subcarriers.
		Each subcarrier takes two octets to store the value.
		The value is in the range 0 to 15."
	::= { vdslLineStatsEntry 5 }
	
	vdslLineStatsVturBits2 OBJECT-TYPE
	SYNTAX OCTET STRING
	MAX-ACCESS read-only
	STATUS current
	DESCRIPTION
		"The object provides Bits for the VTU-R 1024 subcarriers.
		Each subcarrier takes two octets to store the value.
		The value is in the range 0 to 15."
	::= { vdslLineStatsEntry 6 }
	
	vdslLineStatsVturBits3 OBJECT-TYPE
	SYNTAX OCTET STRING
	MAX-ACCESS read-only
	STATUS current
	DESCRIPTION
		"The object provides Bits for the VTU-R 1024 subcarriers.
		Each subcarrier takes two octets to store the value.
		The value is in the range 0 to 15."
	::= { vdslLineStatsEntry 7 }
	
	vdslLineStatsVturBits4 OBJECT-TYPE
	SYNTAX OCTET STRING
	MAX-ACCESS read-only
	STATUS current
	DESCRIPTION
		"The object provides Bits for the VTU-R 1024 subcarriers.
		Each subcarrier takes two octets to store the value.
		The value is in the range 0 to 15."
	::= { vdslLineStatsEntry 8 }
	
	vdslLineStatsVtucGain1 OBJECT-TYPE
	SYNTAX OCTET STRING
	MAX-ACCESS read-only
	STATUS current
	DESCRIPTION
		"The object provides Gain for the VTU-C 512 subcarriers.
		Each subcarrier takes two octets to store the value.
		The value is in the range 0 to 4093. Each value in this array is 16 bits wide.
		The gain value is represented as a multiple of 1/512 on linear scale."
	::= { vdslLineStatsEntry 9 }
	
	vdslLineStatsVtucGain2 OBJECT-TYPE
	SYNTAX OCTET STRING
	MAX-ACCESS read-only
	STATUS current
	DESCRIPTION
		"The object provides Gain for the VTU-C 512 subcarriers.
		Each subcarrier takes two octets to store the value.
		The value is in the range 0 to 4093. Each value in this array is 16 bits wide.
		The gain value is represented as a multiple of 1/512 on linear scale."
	::= { vdslLineStatsEntry 10 }
	
	vdslLineStatsVtucGain3 OBJECT-TYPE
	SYNTAX OCTET STRING
	MAX-ACCESS read-only
	STATUS current
	DESCRIPTION
		"The object provides Gain for the VTU-C 512 subcarriers.
		Each subcarrier takes two octets to store the value.
		The value is in the range 0 to 4093. Each value in this array is 16 bits wide.
		The gain value is represented as a multiple of 1/512 on linear scale."
	::= { vdslLineStatsEntry 11 }
	
	vdslLineStatsVtucGain4 OBJECT-TYPE
	SYNTAX OCTET STRING
	MAX-ACCESS read-only
	STATUS current
	DESCRIPTION
		"The object provides Gain for the VTU-C 512 subcarriers.
		Each subcarrier takes two octets to store the value.
		The value is in the range 0 to 4093. Each value in this array is 16 bits wide.
		The gain value is represented as a multiple of 1/512 on linear scale."
	::= { vdslLineStatsEntry 12 }
	
	vdslLineStatsVtucGain5 OBJECT-TYPE
	SYNTAX OCTET STRING
	MAX-ACCESS read-only
	STATUS current
	DESCRIPTION
		"The object provides Gain for the VTU-C 512 subcarriers.
		Each subcarrier takes two octets to store the value.
		The value is in the range 0 to 4093. Each value in this array is 16 bits wide.
		The gain value is represented as a multiple of 1/512 on linear scale."
	::= { vdslLineStatsEntry 13 }
	
	vdslLineStatsVtucGain6 OBJECT-TYPE
	SYNTAX OCTET STRING
	MAX-ACCESS read-only
	STATUS current
	DESCRIPTION
		"The object provides Gain for the VTU-C 512 subcarriers.
		Each subcarrier takes two octets to store the value.
		The value is in the range 0 to 4093. Each value in this array is 16 bits wide.
		The gain value is represented as a multiple of 1/512 on linear scale."
	::= { vdslLineStatsEntry 14 }
	
	vdslLineStatsVtucGain7 OBJECT-TYPE
	SYNTAX OCTET STRING
	MAX-ACCESS read-only
	STATUS current
	DESCRIPTION
		"The object provides Gain for the VTU-C 512 subcarriers.
		Each subcarrier takes two octets to store the value.
		The value is in the range 0 to 4093. Each value in this array is 16 bits wide.
		The gain value is represented as a multiple of 1/512 on linear scale."
	::= { vdslLineStatsEntry 15 }
	
	vdslLineStatsVtucGain8 OBJECT-TYPE
	SYNTAX OCTET STRING
	MAX-ACCESS read-only
	STATUS current
	DESCRIPTION
		"The object provides Gain for the VTU-C 512 subcarriers.
		Each subcarrier takes two octets to store the value.
		The value is in the range 0 to 4093. Each value in this array is 16 bits wide.
		The gain value is represented as a multiple of 1/512 on linear scale."
	::= { vdslLineStatsEntry 16 }
	
	vdslLineStatsVturGain1 OBJECT-TYPE
	SYNTAX OCTET STRING
	MAX-ACCESS read-only
	STATUS current
	DESCRIPTION
		"The object provides Gain for the VTU-R 512 subcarriers.
		Each subcarrier takes two octets to store the value.
		The value is in the range 0 to 4093. Each value in this array is 16 bits wide.
		The gain value is represented as a multiple of 1/512 on linear scale."
	::= { vdslLineStatsEntry 17 }
	
	vdslLineStatsVturGain2 OBJECT-TYPE
	SYNTAX OCTET STRING
	MAX-ACCESS read-only
	STATUS current
	DESCRIPTION
		"The object provides Gain for the VTU-R 512 subcarriers.
		Each subcarrier takes two octets to store the value.
		The value is in the range 0 to 4093. Each value in this array is 16 bits wide.
		The gain value is represented as a multiple of 1/512 on linear scale."
	::= { vdslLineStatsEntry 18 }
	
	vdslLineStatsVturGain3 OBJECT-TYPE
	SYNTAX OCTET STRING
	MAX-ACCESS read-only
	STATUS current
	DESCRIPTION
		"The object provides Gain for the VTU-R 512 subcarriers.
		Each subcarrier takes two octets to store the value.
		The value is in the range 0 to 4093. Each value in this array is 16 bits wide.
		The gain value is represented as a multiple of 1/512 on linear scale."
	::= { vdslLineStatsEntry 19 }
	
	vdslLineStatsVturGain4 OBJECT-TYPE
	SYNTAX OCTET STRING
	MAX-ACCESS read-only
	STATUS current
	DESCRIPTION
		"The object provides Gain for the VTU-R 512 subcarriers.
		Each subcarrier takes two octets to store the value.
		The value is in the range 0 to 4093. Each value in this array is 16 bits wide.
		The gain value is represented as a multiple of 1/512 on linear scale."
	::= { vdslLineStatsEntry 20 }
	
	vdslLineStatsVturGain5 OBJECT-TYPE
	SYNTAX OCTET STRING
	MAX-ACCESS read-only
	STATUS current
	DESCRIPTION
		"The object provides Gain for the VTU-R 512 subcarriers.
		Each subcarrier takes two octets to store the value.
		The value is in the range 0 to 4093. Each value in this array is 16 bits wide.
		The gain value is represented as a multiple of 1/512 on linear scale."
	::= { vdslLineStatsEntry 21 }
	
	vdslLineStatsVturGain6 OBJECT-TYPE
	SYNTAX OCTET STRING
	MAX-ACCESS read-only
	STATUS current
	DESCRIPTION
		"The object provides Gain for the VTU-R 512 subcarriers.
		Each subcarrier takes two octets to store the value.
		The value is in the range 0 to 4093. Each value in this array is 16 bits wide.
		The gain value is represented as a multiple of 1/512 on linear scale."
	::= { vdslLineStatsEntry 22 }
	
	vdslLineStatsVturGain7 OBJECT-TYPE
	SYNTAX OCTET STRING
	MAX-ACCESS read-only
	STATUS current
	DESCRIPTION
		"The object provides Gain for the VTU-R 512 subcarriers.
		Each subcarrier takes two octets to store the value.
		The value is in the range 0 to 4093. Each value in this array is 16 bits wide.
		The gain value is represented as a multiple of 1/512 on linear scale."
	::= { vdslLineStatsEntry 23 }
	
	vdslLineStatsVturGain8 OBJECT-TYPE
	SYNTAX OCTET STRING
	MAX-ACCESS read-only
	STATUS current
	DESCRIPTION
		"The object provides Gain for the VTU-R 512 subcarriers.
		Each subcarrier takes two octets to store the value.
		The value is in the range 0 to 4093. Each value in this array is 16 bits wide.
		The gain value is represented as a multiple of 1/512 on linear scale."
	::= { vdslLineStatsEntry 24 }
	
	vdslLineStatsVtucHlog OBJECT-TYPE
	SYNTAX OCTET STRING
	MAX-ACCESS read-only
	STATUS current
	DESCRIPTION
		"The object provides Hlog for the VTU-C 512 subcarriers.
		Each subcarrier takes two octets to store the value.
		The real Hlog(f) value is represented as (6-m(i)/10), with m(i) in the range 0 to 1022.
		A special value m=1023 indicates that no measurement could be done for the 
		sub-carrier group becauseit is out of the passband or that the attenuation 
		is out of range to be represented. Each value in this array is 16 bits wide."
	::= { vdslLineStatsEntry 25 }
	
	vdslLineStatsVturHlog OBJECT-TYPE
	SYNTAX OCTET STRING
	MAX-ACCESS read-only
	STATUS current
	DESCRIPTION
		"The object provides Hlog for the VTU-R 512 subcarriers.
		Each subcarrier takes two octets to store the value.
		The real Hlog(f) value is represented as (6-m(i)/10), with m(i) in the range 0 to 1022.
		A special value m=1023 indicates that no measurement could be done for the
		sub-carrier group because it is out of the passband or that the attenuation
		is out ofrange to be represented. Each value in this array is 16 bits wide."
	::= { vdslLineStatsEntry 26 }
	
	vdslLineStatsVtucQln OBJECT-TYPE
	SYNTAX OCTET STRING
	MAX-ACCESS read-only
	STATUS current
	DESCRIPTION
		"The object provides Qln for the VTU-C 512 subcarriers.
		Each subcarrier takes two octets to store the value.
		The QLN(f) is represented as ( -23-n(i)/2), with n(i) in the range 0 to 254.
		A special value n(i)=255 indicates that no measurement could be done for the
		sub-carrier group. Each value in this array is 8 bits wide."
	::= { vdslLineStatsEntry 27 }
	
	vdslLineStatsVturQln OBJECT-TYPE
	SYNTAX OCTET STRING
	MAX-ACCESS read-only
	STATUS current
	DESCRIPTION
		"The object provides Qln for the VTU-R 512 subcarriers.
		Each subcarrier takes two octets to store the value.
		The QLN(f) is represented as ( -23-n(i)/2), with n(i) in the range 0 to 254.
		A special value n(i)=255 indicates that no measurement could be done for the
		sub-carrier group. Each value in this array is 8 bits wide."
	::= { vdslLineStatsEntry 28 }
	
	vdslLineStatsVtucSnr OBJECT-TYPE
	SYNTAX OCTET STRING
	MAX-ACCESS read-only
	STATUS current
	DESCRIPTION
		"The object provides Snr for the VTU-C 512 subcarriers.
		Each subcarrier takes one octets to store the value.
		Octet i is set to a value in the range 0 to 254 (-32 + vdslLineStatsVtucSnr (i)/2) in dB
		(i.e., -32 to 95dB). Each value in this array is 8 bits wide.
		A special value 255 indicates that no measurement could be done for the
		sub-carrier group."
	::= { vdslLineStatsEntry 29 }
	
	vdslLineStatsVturSnr OBJECT-TYPE
	SYNTAX OCTET STRING
	MAX-ACCESS read-only
	STATUS current
	DESCRIPTION
		"The object provides Snr for the VTU-R 512 subcarriers.
		Each subcarrier takes one octets to store the value.
		Octet i is set to a value in the range 0 to 254 (-32 + vdslLineStatsVturSnr (i)/2) in dB
		(i.e., -32 to 95dB). Each value in this array is 8 bits wide.
		A special value 255 indicates that no measurement could be done for the
		sub-carrier group."
	::= { vdslLineStatsEntry 30 }
	
	vdslLineStatsVtucTssi OBJECT-TYPE
	SYNTAX OCTET STRING
	MAX-ACCESS read-only
	STATUS current
	DESCRIPTION
		"The object provides Tssi for the VTU-C 512 subcarriers.
		Each subcarrier takes two octets to store the value.
		Each value in this array is 16 bits wide.
		The tssi value is represented as a multiple of 1/32768 on linear scale."
	::= { vdslLineStatsEntry 31 }
	
	vdslLineStatsVturTssi OBJECT-TYPE
	SYNTAX OCTET STRING
	MAX-ACCESS read-only
	STATUS current
	DESCRIPTION
		"The object provides Tssi for the VTU-R 512 subcarriers.
		Each subcarrier takes two octets to store the value.
		Each value in this array is 16 bits wide.
		The tssi value is represented as a multiple of 1/32768 on linear scale."
	::= { vdslLineStatsEntry 32 }
	
	vdslLineStatsProtocol OBJECT-TYPE
	SYNTAX INTEGER {
			none(1),
			vdsl-8a(2),
			vdsl-8b(3),
			vdsl-8c(4),
			vdsl-8d(5),
			vdsl-12a(6),
			vdsl-12b(7),
 			vdsl-17a(8),
 			vdsl-30a(9),
 			adsl2plus(10)
		}
	MAX-ACCESS read-only
	STATUS current
	DESCRIPTION
		"The actual line protocol."
	::= { vdslLineStatsEntry 33 }

	vdslLineStatsUsCodingMode OBJECT-TYPE
	SYNTAX INTEGER {
			none(1),
			trellis(2),
			reedSolomon(3),
			trellisAndReedSolomon(4)
		}
	MAX-ACCESS read-only
	STATUS current
	DESCRIPTION
		"The upstream coding mode of the line. This object is supported by R5.02 and later versions."
	::= { vdslLineStatsEntry 34 }

	vdslLineStatsDsCodingMode OBJECT-TYPE
	SYNTAX INTEGER {
			none(1),
			trellis(2),
			reedSolomon(3),
			trellisAndReedSolomon(4)
		}
	MAX-ACCESS read-only
	STATUS current
	DESCRIPTION
		"The downstream coding mode of the line. This object is supported by R5.02 and later versions."
	::= { vdslLineStatsEntry 35 }

	vdslLineStatsVtucHlogGroupSize OBJECT-TYPE
	SYNTAX INTEGER
	MAX-ACCESS read-only
	STATUS current
	DESCRIPTION
		"Number of sub-carriers per group used to report the H(f) linear representation values for the 
		respective transmission direction. The valid values are 1, 2, 4 and 8. 
		This object is supported by R5.02 and later versions."
	::= { vdslLineStatsEntry 36 }

	vdslLineStatsVturHlogGroupSize OBJECT-TYPE
	SYNTAX INTEGER
	MAX-ACCESS read-only
	STATUS current
	DESCRIPTION
		"Number of sub-carriers per group used to report the H(f) linear representation values for the 
		respective transmission direction. The valid values are 1, 2, 4 and 8. 
		This object is supported by R5.02 and later versions."
	::= { vdslLineStatsEntry 37 }

	vdslLineStatsVtucQlnGroupSize OBJECT-TYPE
	SYNTAX INTEGER
	MAX-ACCESS read-only
	STATUS current
	DESCRIPTION
		"Number of sub-carriers per group used to report the Quiet Line Noise values for the 
		respective transmission direction. The valid values are 1, 2, 4 and 8. 
		This object is supported by R5.02 and later versions."
	::= { vdslLineStatsEntry 38 }

	vdslLineStatsVturQlnGroupSize OBJECT-TYPE
	SYNTAX INTEGER
	MAX-ACCESS read-only
	STATUS current
	DESCRIPTION
		"Number of sub-carriers per group used to report the Quiet Line Noise values for the 
		respective transmission direction. The valid values are 1, 2, 4 and 8. 
		This object is supported by R5.02 and later versions."
	::= { vdslLineStatsEntry 39 }

	vdslLineStatsVtucSnrGroupSize OBJECT-TYPE
	SYNTAX INTEGER
	MAX-ACCESS read-only
	STATUS current
	DESCRIPTION
		"Number of sub-carriers per group used to report the SNR values on the 
		respective transmission direction. The valid values are 1, 2, 4 and 8. 
		This object is supported by R5.02 and later versions."
	::= { vdslLineStatsEntry 40 }

	vdslLineStatsVturSnrGroupSize OBJECT-TYPE
	SYNTAX INTEGER
	MAX-ACCESS read-only
	STATUS current
	DESCRIPTION
		"Number of sub-carriers per group used to report the SNR values on the 
		respective transmission direction. The valid values are 1, 2, 4 and 8. 
		This object is supported by R5.02 and later versions."
	::= { vdslLineStatsEntry 41 }
	
	vdslLineStatsVtucRxPower OBJECT-TYPE
	SYNTAX INTEGER
	MAX-ACCESS read-only
	STATUS current
	DESCRIPTION
		"Receive power of vtuc (in unit of 0.1 dBm)."
	::= { vdslLineStatsEntry 42 }
	
	vdslLineStatsVturRxPower OBJECT-TYPE
	SYNTAX INTEGER
	MAX-ACCESS read-only
	STATUS current
	DESCRIPTION
		"Receive power of vtur (in unit of 0.1 dBm)."
	::= { vdslLineStatsEntry 43 }
	
	vdslLineStatsVtucSnrMargin OBJECT-TYPE
	SYNTAX INTEGER
	MAX-ACCESS read-only
	STATUS current
	DESCRIPTION
		""
	::= { vdslLineStatsEntry 44 }
	
	vdslLineStatsVturSnrMargin OBJECT-TYPE
	SYNTAX INTEGER
	MAX-ACCESS read-only
	STATUS current
	DESCRIPTION
		""
	::= { vdslLineStatsEntry 45 } 
	
	vdslLineStatsVtucSigAtten OBJECT-TYPE
	SYNTAX INTEGER
	MAX-ACCESS read-only
	STATUS current
	DESCRIPTION
		""
	::= { vdslLineStatsEntry 46 }
	
	vdslLineStatsVturSigAtten OBJECT-TYPE
	SYNTAX INTEGER
	MAX-ACCESS read-only
	STATUS current
	DESCRIPTION
		""
	::= { vdslLineStatsEntry 47 }
	
	vdslLineStatsVtucLineAtten OBJECT-TYPE
	SYNTAX INTEGER
	MAX-ACCESS read-only
	STATUS current
	DESCRIPTION
		""
	::= { vdslLineStatsEntry 48 }
	
	vdslLineStatsVturLineAtten OBJECT-TYPE
	SYNTAX INTEGER
	MAX-ACCESS read-only
	STATUS current
	DESCRIPTION
		""
	::= { vdslLineStatsEntry 49 }

-- vdslLineUsBandPlanTable

        vdslLineUsBandPlanTable OBJECT-TYPE
        SYNTAX SEQUENCE OF VdslLineUsBandPlanEntry
        MAX-ACCESS not-accessible
        STATUS current
        DESCRIPTION
        	"The table displays VDSL line actual band plan. This table is supported by R5.01 and later versions."
        ::= { vdslStats 3 }

        vdslLineUsBandPlanEntry OBJECT-TYPE
        SYNTAX VdslLineUsBandPlanEntry
        MAX-ACCESS not-accessible
        STATUS current
        DESCRIPTION
        	"An entry of vdslLineUsBandPlanTable."
        INDEX { ifIndex, vdslLineUsBandId }
        ::= { vdslLineUsBandPlanTable 1 }

        VdslLineUsBandPlanEntry ::=
        	SEQUENCE {
                  	vdslLineUsBandId		INTEGER,
			vdslLineUsBandStartToneId	INTEGER,
			vdslLineUsBandStopToneId	INTEGER
              	}
              	
	vdslLineUsBandId OBJECT-TYPE
	SYNTAX INTEGER
	MAX-ACCESS read-only
	STATUS current
	DESCRIPTION
		"Ihe id of the upstream pass band, starting from 1."
	::= { vdslLineUsBandPlanEntry 1 }
	
	vdslLineUsBandStartToneId OBJECT-TYPE
	SYNTAX INTEGER
	MAX-ACCESS read-only
	STATUS current
	DESCRIPTION
		"The starting tone of the band."
	::= { vdslLineUsBandPlanEntry 2 }
	
	vdslLineUsBandStopToneId OBJECT-TYPE
	SYNTAX INTEGER
	MAX-ACCESS read-only
	STATUS current
	DESCRIPTION
		"The stopping tone of the band."
	::= { vdslLineUsBandPlanEntry 3 }

-- vdslLineDsBandPlanTable

        vdslLineDsBandPlanTable OBJECT-TYPE
        SYNTAX SEQUENCE OF VdslLineDsBandPlanEntry
        MAX-ACCESS not-accessible
        STATUS current
        DESCRIPTION
        	"The table displays VDSL line actual band plan. This table is supported by R5.01 and later versions."
        ::= { vdslStats 4 }

        vdslLineDsBandPlanEntry OBJECT-TYPE
        SYNTAX VdslLineDsBandPlanEntry
        MAX-ACCESS not-accessible
        STATUS current
        DESCRIPTION
        	"An entry of vdslLineDsBandPlanTable."
        INDEX { ifIndex, vdslLineDsBandId }
        ::= { vdslLineDsBandPlanTable 1 }

        VdslLineDsBandPlanEntry ::=
        	SEQUENCE {
                  	vdslLineDsBandId		INTEGER,
			vdslLineDsBandStartToneId	INTEGER,
			vdslLineDsBandStopToneId	INTEGER
              	}
              	
	vdslLineDsBandId OBJECT-TYPE
	SYNTAX INTEGER
	MAX-ACCESS read-only
	STATUS current
	DESCRIPTION
		"Ihe id of the downstream pass band, starting from 1."
	::= { vdslLineDsBandPlanEntry 1 }
	
	vdslLineDsBandStartToneId OBJECT-TYPE
	SYNTAX INTEGER
	MAX-ACCESS read-only
	STATUS current
	DESCRIPTION
		"The starting tone of the band."
	::= { vdslLineDsBandPlanEntry 2 }
	
	vdslLineDsBandStopToneId OBJECT-TYPE
	SYNTAX INTEGER
	MAX-ACCESS read-only
	STATUS current
	DESCRIPTION
		"The stopping tone of the band."
	::= { vdslLineDsBandPlanEntry 3 }

-- vdslLineUsResultMaskTable

        vdslLineUsResultMaskTable OBJECT-TYPE
        SYNTAX SEQUENCE OF VdslLineUsResultMaskEntry
        MAX-ACCESS not-accessible
        STATUS current
        DESCRIPTION
        	"The table displays VDSL line actual PSD mask. This table is supported by R5.01 and later versions."
        ::= { vdslStats 5 }

        vdslLineUsResultMaskEntry OBJECT-TYPE
        SYNTAX VdslLineUsResultMaskEntry
        MAX-ACCESS not-accessible
        STATUS current
        DESCRIPTION
        	"An entry of vdslLineUsResultMaskTable."
        INDEX { ifIndex, vdslLineUsMaskId }
        ::= { vdslLineUsResultMaskTable 1 }

        VdslLineUsResultMaskEntry ::=
        	SEQUENCE {
                  	vdslLineUsMaskId		INTEGER,
			vdslLineUsMaskTone		INTEGER,
			vdslLineUsMaskPsd		INTEGER
              	}
              	
	vdslLineUsMaskId OBJECT-TYPE
	SYNTAX INTEGER
	MAX-ACCESS read-only
	STATUS current
	DESCRIPTION
		"The id of the turning point of the mask, starting from 1."
	::= { vdslLineUsResultMaskEntry 1 }
	
	vdslLineUsMaskTone OBJECT-TYPE
	SYNTAX INTEGER
	MAX-ACCESS read-only
	STATUS current
	DESCRIPTION
		"The tone id."
	::= { vdslLineUsResultMaskEntry 2 }
	
	vdslLineUsMaskPsd OBJECT-TYPE
	SYNTAX INTEGER
	MAX-ACCESS read-only
	STATUS current
	DESCRIPTION
		"The psd, in 0.1 dBm/Hz."
	::= { vdslLineUsResultMaskEntry 3 }

-- vdslLineDsResultMaskTable

        vdslLineDsResultMaskTable OBJECT-TYPE
        SYNTAX SEQUENCE OF VdslLineDsResultMaskEntry
        MAX-ACCESS not-accessible
        STATUS current
        DESCRIPTION
        	"The table displays VDSL line actual PSD mask. This table is supported by R5.01 and later versions."
        ::= { vdslStats 6 }

        vdslLineDsResultMaskEntry OBJECT-TYPE
        SYNTAX VdslLineDsResultMaskEntry
        MAX-ACCESS not-accessible
        STATUS current
        DESCRIPTION
        	"An entry of vdslLineDsResultMaskTable."
        INDEX { ifIndex, vdslLineDsMaskId }
        ::= { vdslLineDsResultMaskTable 1 }

        VdslLineDsResultMaskEntry ::=
        	SEQUENCE {
                  	vdslLineDsMaskId		INTEGER,
			vdslLineDsMaskTone		INTEGER,
			vdslLineDsMaskPsd		INTEGER
              	}
              	
	vdslLineDsMaskId OBJECT-TYPE
	SYNTAX INTEGER
	MAX-ACCESS read-only
	STATUS current
	DESCRIPTION
		"The id of the turning point of the mask, starting from 1."
	::= { vdslLineDsResultMaskEntry 1 }
	
	vdslLineDsMaskTone OBJECT-TYPE
	SYNTAX INTEGER
	MAX-ACCESS read-only
	STATUS current
	DESCRIPTION
		"The tone id."
	::= { vdslLineDsResultMaskEntry 2 }
	
	vdslLineDsMaskPsd OBJECT-TYPE
	SYNTAX INTEGER
	MAX-ACCESS read-only
	STATUS current
	DESCRIPTION
		"The psd, in 0.1 dBm/Hz."
	::= { vdslLineDsResultMaskEntry 3 }

-- vdslLinePerfCurrTable

        vdslLinePerfCurrTable OBJECT-TYPE
        SYNTAX SEQUENCE OF VdslLinePerfCurrEntry
        MAX-ACCESS not-accessible
        STATUS current
        DESCRIPTION
        	"The table displays VDSL line current GINP/SOS/INM performance statistics."
        ::= { vdslStats 7 }

        vdslLinePerfCurrEntry OBJECT-TYPE
        SYNTAX VdslLinePerfCurrEntry
        MAX-ACCESS not-accessible
        STATUS current
        DESCRIPTION
        	"An entry of vdslLinePerfCurrTable."
        INDEX { ifIndex }
        ::= { vdslLinePerfCurrTable 1 }

        VdslLinePerfCurrEntry ::=
        	SEQUENCE {
                  	vdslLinePerfCurrInmVtucEqInp			Counter32,
					vdslLinePerfCurrInmVturEqInp			Counter32,
					vdslLinePerfCurr15MInmVtucEqInp			Counter32,
					vdslLinePerfCurr15MInmVturEqInp			Counter32,
					vdslLinePerfCurr1DayInmVtucEqInp		Counter32,
					vdslLinePerfCurr1DayInmVturEqInp		Counter32,
					vdslLinePerfCurrInmVtucIAT				Counter32,
					vdslLinePerfCurrInmVturIAT				Counter32,
					vdslLinePerfCurr15MInmVtucIAT			Counter32,
					vdslLinePerfCurr15MInmVturIAT			Counter32,
					vdslLinePerfCurr1DayInmVtucIAT			Counter32,
					vdslLinePerfCurr1DayInmVturIAT			Counter32,
					vdslLinePerfCurrInmVtucME				Counter32,
					vdslLinePerfCurrInmVturME				Counter32,
					vdslLinePerfCurr15MInmVtucME			Counter32,
					vdslLinePerfCurr15MInmVturME			Counter32,
					vdslLinePerfCurr1DayInmVtucME			Counter32,
					vdslLinePerfCurr1DayInmVturME			Counter32,
					vdslLinePerfCurrVtucRx					Unsigned32,
					vdslLinePerfCurrVturRx					Unsigned32,
					vdslLinePerfCurr15MVtucRx				Unsigned32,
					vdslLinePerfCurr15MVturRx				Unsigned32,
					vdslLinePerfCurr1DayVtucRx				Unsigned32,
					vdslLinePerfCurr1DayVturRx				Unsigned32,
					vdslLinePerfCurrVtucRxCorrected			Unsigned32,
					vdslLinePerfCurrVturRxCorrected			Unsigned32,
					vdslLinePerfCurr15MVtucRxCorrected		Unsigned32,
					vdslLinePerfCurr15MVturRxCorrected		Unsigned32,
					vdslLinePerfCurr1DayVtucRxCorrected		Unsigned32,
					vdslLinePerfCurr1DayVturRxCorrected		Unsigned32,
					vdslLinePerfCurrVtucRxUncorrected		Unsigned32,
					vdslLinePerfCurrVturRxUncorrected		Unsigned32,
					vdslLinePerfCurr15MVtucRxUncorrected	Unsigned32,
					vdslLinePerfCurr15MVturRxUncorrected	Unsigned32,
					vdslLinePerfCurr1DayVtucRxUncorrected	Unsigned32,
					vdslLinePerfCurr1DayVturRxUncorrected	Unsigned32,
					vdslLinePerfCurrVtucLEFTRs				Unsigned32,
					vdslLinePerfCurrVturLEFTRs				Unsigned32,
					vdslLinePerfCurr15MVtucLEFTRs			Unsigned32,
					vdslLinePerfCurr15MVturLEFTRs			Unsigned32,
					vdslLinePerfCurr1DayVtucLEFTRs			Unsigned32,
					vdslLinePerfCurr1DayVturLEFTRs			Unsigned32,
					vdslLinePerfCurrVtucErrFreeBits			Unsigned32,
					vdslLinePerfCurrVturErrFreeBits			Unsigned32,
					vdslLinePerfCurr15MVtucErrFreeBits		Unsigned32,
					vdslLinePerfCurr15MVturErrFreeBits		Unsigned32,
					vdslLinePerfCurr1DayVtucErrFreeBits		Unsigned32,
					vdslLinePerfCurr1DayVturErrFreeBits		Unsigned32,
					vdslLinePerfCurrVtucMinEftr				Counter32,
					vdslLinePerfCurrVturMinEftr				Counter32,
					vdslLinePerfCurr15MinVtucMinEftr		Counter32,
					vdslLinePerfCurr15MinVturMinEftr		Counter32,
					vdslLinePerfCurr1DayVtucMinEftr			Counter32,
					vdslLinePerfCurr1DayVturMinEftr			Counter32
              	}
              	
	vdslLinePerfCurrInmVtucEqInp OBJECT-TYPE
	SYNTAX Counter32
	MAX-ACCESS read-only
	STATUS current
	DESCRIPTION
		"The INM Equivalent Inp histogram since system boot up. An array of 68 octets 
		(each 4 octets means amount of a bin of histogram), designed for supporting 
		from 1 to 17 bins of the histogram. The particular index of the bin incremented 
		by an impulse noise event is equal to the computed value of equivalent INP, 
		except the 17th of anomaly INPEQ, which logs all equivalent INPs greater than 16. 
		Each bin has a value in the range 0x0 to 0xFFFFFFFF"
	::= { vdslLinePerfCurrEntry 1 }
	
	vdslLinePerfCurrInmVturEqInp OBJECT-TYPE
	SYNTAX Counter32
	MAX-ACCESS read-only
	STATUS current
	DESCRIPTION
		"The INM Equivalent Inp histogram since system boot up. An array of 68 octets 
		(each 4 octets means amount of a bin of histogram), designed for supporting 
		from 1 to 17 bins of the histogram. The particular index of the bin incremented 
		by an impulse noise event is equal to the computed value of equivalent INP, 
		except the 17th of anomaly INPEQ, which logs all equivalent INPs greater than 16. 
		Each bin has a value in the range 0x0 to 0xFFFFFFFF"
	::= { vdslLinePerfCurrEntry 2 }
	
	vdslLinePerfCurr15MInmVtucEqInp OBJECT-TYPE
	SYNTAX Counter32
	MAX-ACCESS read-only
	STATUS current
	DESCRIPTION
		"The INM Equivalent Inp histogram during this 15 minutes interval. An array of 68 octets 
		(each 4 octets means amount of a bin of histogram), designed for supporting from 1 to 17 
		bins of the histogram. The particular index of the bin incremented by an impulse noise event 
		is equal to the computed value of equivalent INP, except the 17th of anomaly INPEQ, which logs 
		all equivalent INPs greater than 16. Each bin has a value in the range 0x0 to 0xFFFFFFFF."
	::= { vdslLinePerfCurrEntry 3 }
	
	vdslLinePerfCurr15MInmVturEqInp OBJECT-TYPE
	SYNTAX Counter32
	MAX-ACCESS read-only
	STATUS current
	DESCRIPTION
		"The INM Equivalent Inp histogram during this 15 minutes interval. An array of 68 octets 
		(each 4 octets means amount of a bin of histogram), designed for supporting from 1 to 17 
		bins of the histogram. The particular index of the bin incremented by an impulse noise event 
		is equal to the computed value of equivalent INP, except the 17th of anomaly INPEQ, which logs 
		all equivalent INPs greater than 16. Each bin has a value in the range 0x0 to 0xFFFFFFFF."
	::= { vdslLinePerfCurrEntry 4 }
	
	vdslLinePerfCurr1DayInmVtucEqInp OBJECT-TYPE
	SYNTAX Counter32
	MAX-ACCESS read-only
	STATUS current
	DESCRIPTION
		"The INM Equivalent Inp histogram during this 1 day interval. An array of 68 octets 
		(each 4 octets means amount of a bin of histogram), designed for supporting from 1 to 17 
		bins of the histogram. The particular index of the bin incremented by an impulse noise event 
		is equal to the computed value of equivalent INP, except the 17th of anomaly INPEQ, which logs 
		all equivalent INPs greater than 16. Each bin has a value in the range 0x0 to 0xFFFFFFFF."
	::= { vdslLinePerfCurrEntry 5 }
	
	vdslLinePerfCurr1DayInmVturEqInp OBJECT-TYPE
	SYNTAX Counter32
	MAX-ACCESS read-only
	STATUS current
	DESCRIPTION
		"The INM Equivalent Inp histogram during this 1 day interval. An array of 68 octets 
		(each 4 octets means amount of a bin of histogram), designed for supporting from 1 to 17 
		bins of the histogram. The particular index of the bin incremented by an impulse noise event 
		is equal to the computed value of equivalent INP, except the 17th of anomaly INPEQ, which logs 
		all equivalent INPs greater than 16. Each bin has a value in the range 0x0 to 0xFFFFFFFF."
	::= { vdslLinePerfCurrEntry 6 }
	
	vdslLinePerfCurrInmVtucIAT OBJECT-TYPE
	SYNTAX Counter32
	MAX-ACCESS read-only
	STATUS current
	DESCRIPTION
		"The INM Inter Arrival Time histogram since system boot up. An array of 32 octets 
		(each 4 octets means amount of a bin of histogram), designed for supporting from 0 to 7 
		bins of the histogram. The index of the particular bin incremented by an complete  impulse noise event 
		is determained from the following INMControl parameters. Each bin has a value in the range 0x0 to 0xFFFFFFFF."
	::= { vdslLinePerfCurrEntry 7 }
	
	vdslLinePerfCurrInmVturIAT OBJECT-TYPE
	SYNTAX Counter32
	MAX-ACCESS read-only
	STATUS current
	DESCRIPTION
		"The INM Inter Arrival Time histogram since system boot up. An array of 32 octets 
		(each 4 octets means amount of a bin of histogram), designed for supporting from 0 to 7 
		bins of the histogram. The index of the particular bin incremented by an complete  impulse noise event 
		is determained from the following INMControl parameters. Each bin has a value in the range 0x0 to 0xFFFFFFFF."
	::= { vdslLinePerfCurrEntry 8 }
	
	vdslLinePerfCurr15MInmVtucIAT OBJECT-TYPE
	SYNTAX Counter32
	MAX-ACCESS read-only
	STATUS current
	DESCRIPTION
		"The INM Inter Arrival Time histogram during this 15 minutes interval. An array of 32 octets 
		(each 4 octets means amount of a bin of histogram), designed for supporting from 0 to 7 bins of the histogram. 
		The index of the particular bin incremented by an complete  impulse noise event is determained from the following 
		INMControl parameters. Each bin has a value in the range 0x0 to 0xFFFFFFFF."
	::= { vdslLinePerfCurrEntry 9 }
	
	vdslLinePerfCurr15MInmVturIAT OBJECT-TYPE
	SYNTAX Counter32
	MAX-ACCESS read-only
	STATUS current
	DESCRIPTION
		"The INM Inter Arrival Time histogram during this 15 minutes interval. An array of 32 octets 
		(each 4 octets means amount of a bin of histogram), designed for supporting from 0 to 7 bins of the histogram. 
		The index of the particular bin incremented by an complete  impulse noise event is determained from the following 
		INMControl parameters. Each bin has a value in the range 0x0 to 0xFFFFFFFF."
	::= { vdslLinePerfCurrEntry 10 }
	
	vdslLinePerfCurr1DayInmVtucIAT OBJECT-TYPE
	SYNTAX Counter32
	MAX-ACCESS read-only
	STATUS current
	DESCRIPTION
		"The INM Inter Arrival Time histogram during this 1 day interval. An array of 32 octets 
		(each 4 octets means amount of a bin of histogram), designed for supporting from 0 to 7 bins of the histogram. 
		The index of the particular bin incremented by an complete  impulse noise event is determained from the following 
		INMControl parameters. Each bin has a value in the range 0x0 to 0xFFFFFFFF."
	::= { vdslLinePerfCurrEntry 11 }
	
	vdslLinePerfCurr1DayInmVturIAT OBJECT-TYPE
	SYNTAX Counter32
	MAX-ACCESS read-only
	STATUS current
	DESCRIPTION
		"The INM Inter Arrival Time histogram during this 1 day interval. An array of 32 octets 
		(each 4 octets means amount of a bin of histogram), designed for supporting from 0 to 7 bins of the histogram. 
		The index of the particular bin incremented by an complete  impulse noise event is determained from the following 
		INMControl parameters. Each bin has a value in the range 0x0 to 0xFFFFFFFF."
	::= { vdslLinePerfCurrEntry 12 }
	
	vdslLinePerfCurrInmVtucME OBJECT-TYPE
	SYNTAX Counter32
	MAX-ACCESS read-only
	STATUS current
	DESCRIPTION
		"The INM total measurement since system boot up. This indication occurs every time 
		a data symbol is processed by the Impulse Noise Sensor. The range of the value is from 0x0 to 0xFFFFFFFF."
	::= { vdslLinePerfCurrEntry 13 }
	
	vdslLinePerfCurrInmVturME OBJECT-TYPE
	SYNTAX Counter32
	MAX-ACCESS read-only
	STATUS current
	DESCRIPTION
		"The INM total measurement since system boot up. This indication occurs every time 
		a data symbol is processed by the Impulse Noise Sensor. The range of the value is from 0x0 to 0xFFFFFFFF."
	::= { vdslLinePerfCurrEntry 14 }

	vdslLinePerfCurr15MInmVtucME OBJECT-TYPE
	SYNTAX Counter32
	MAX-ACCESS read-only
	STATUS current
	DESCRIPTION
		"The INM total measurement during this 15 minutes interval. This indication occurs every time 
		a data symbol is processed by the Impulse Noise Sensor. The range of the value is from 0x0 to 0xFFFFFFFF."
	::= { vdslLinePerfCurrEntry 15 }
	
	vdslLinePerfCurr15MInmVturME OBJECT-TYPE
	SYNTAX Counter32
	MAX-ACCESS read-only
	STATUS current
	DESCRIPTION
		"The INM total measurement during this 15 minutes interval. This indication occurs every time 
		a data symbol is processed by the Impulse Noise Sensor. The range of the value is from 0x0 to 0xFFFFFFFF."
	::= { vdslLinePerfCurrEntry 16 }
	
	vdslLinePerfCurr1DayInmVtucME OBJECT-TYPE
	SYNTAX Counter32
	MAX-ACCESS read-only
	STATUS current
	DESCRIPTION
		"The INM total measurement during this 1 day interval. This indication occurs every time 
		a data symbol is processed by the Impulse Noise Sensor. The range of the value is from 0x0 to 0xFFFFFFFF."
	::= { vdslLinePerfCurrEntry 17 } 
	
	vdslLinePerfCurr1DayInmVturME OBJECT-TYPE
	SYNTAX Counter32
	MAX-ACCESS read-only
	STATUS current
	DESCRIPTION
		"The INM total measurement during this 1 day interval. This indication occurs every time 
		a data symbol is processed by the Impulse Noise Sensor. The range of the value is from 0x0 to 0xFFFFFFFF."
	::= { vdslLinePerfCurrEntry 18 }
	
	vdslLinePerfCurrVtucRx OBJECT-TYPE
	SYNTAX Unsigned32
	MAX-ACCESS read-only
	STATUS current
	DESCRIPTION
		"Number of codewords retransmitted since system boot up."
	::= { vdslLinePerfCurrEntry 19 }
	
	vdslLinePerfCurrVturRx OBJECT-TYPE
	SYNTAX Unsigned32
	MAX-ACCESS read-only
	STATUS current
	DESCRIPTION
		"Number of codewords retransmitted since system boot up."
	::= { vdslLinePerfCurrEntry 20 }
	
	vdslLinePerfCurr15MVtucRx OBJECT-TYPE
	SYNTAX Unsigned32
	MAX-ACCESS read-only
	STATUS current
	DESCRIPTION
		"Number of codewords retransmitted during this 15 minutes interval."
	::= { vdslLinePerfCurrEntry 21 }
	
	vdslLinePerfCurr15MVturRx OBJECT-TYPE
	SYNTAX Unsigned32
	MAX-ACCESS read-only
	STATUS current
	DESCRIPTION
		"Number of codewords retransmitted during this 15 minutes interval."
	::= { vdslLinePerfCurrEntry 22 }
	
	vdslLinePerfCurr1DayVtucRx OBJECT-TYPE
	SYNTAX Unsigned32
	MAX-ACCESS read-only
	STATUS current
	DESCRIPTION
		"Number of codewords retransmitted during this 1 day interval."
	::= { vdslLinePerfCurrEntry 23 }
	
	vdslLinePerfCurr1DayVturRx OBJECT-TYPE
	SYNTAX Unsigned32
	MAX-ACCESS read-only
	STATUS current
	DESCRIPTION
		"Number of codewords retransmitted during this 1 day interval."
	::= { vdslLinePerfCurrEntry 24 }
	
	vdslLinePerfCurrVtucRxCorrected OBJECT-TYPE
	SYNTAX Unsigned32
	MAX-ACCESS read-only
	STATUS current
	DESCRIPTION
		"Number of codewords corrected through retransmission since system boot up."
	::= { vdslLinePerfCurrEntry 25 }
	
	vdslLinePerfCurrVturRxCorrected OBJECT-TYPE
	SYNTAX Unsigned32
	MAX-ACCESS read-only
	STATUS current
	DESCRIPTION
		"Number of codewords corrected through retransmission since system boot up."
	::= { vdslLinePerfCurrEntry 26 }
	
	vdslLinePerfCurr15MVtucRxCorrected OBJECT-TYPE
	SYNTAX Unsigned32
	MAX-ACCESS read-only
	STATUS current
	DESCRIPTION
		"Number of codewords corrected through retransmission during this 15 minutes interval."
	::= { vdslLinePerfCurrEntry 27 }
	
	vdslLinePerfCurr15MVturRxCorrected OBJECT-TYPE
	SYNTAX Unsigned32
	MAX-ACCESS read-only
	STATUS current
	DESCRIPTION
		"Number of codewords corrected through retransmission during this 15 minutes interval."
	::= { vdslLinePerfCurrEntry 28 }
	
	vdslLinePerfCurr1DayVtucRxCorrected OBJECT-TYPE
	SYNTAX Unsigned32
	MAX-ACCESS read-only
	STATUS current
	DESCRIPTION
		"Number of codewords corrected through retransmission during this 1 day interval."
	::= { vdslLinePerfCurrEntry 29 }
	
	vdslLinePerfCurr1DayVturRxCorrected OBJECT-TYPE
	SYNTAX Unsigned32
	MAX-ACCESS read-only
	STATUS current
	DESCRIPTION
		"Number of codewords corrected through retransmission during this 1 day interval."
	::= { vdslLinePerfCurrEntry 30 }
	
	vdslLinePerfCurrVtucRxUncorrected OBJECT-TYPE
	SYNTAX Unsigned32
	MAX-ACCESS read-only
	STATUS current
	DESCRIPTION
		"Number of codewords left uncorrected after retransmission since system boot up."
	::= { vdslLinePerfCurrEntry 31 }
	
	vdslLinePerfCurrVturRxUncorrected OBJECT-TYPE
	SYNTAX Unsigned32
	MAX-ACCESS read-only
	STATUS current
	DESCRIPTION
		"Number of codewords left uncorrected after retransmission since system boot up."
	::= { vdslLinePerfCurrEntry 32 }
	
	vdslLinePerfCurr15MVtucRxUncorrected OBJECT-TYPE
	SYNTAX Unsigned32
	MAX-ACCESS read-only
	STATUS current
	DESCRIPTION
		"Number of codewords left uncorrected after retransmission during this 15 minutes interval."
	::= { vdslLinePerfCurrEntry 33 }
	
	vdslLinePerfCurr15MVturRxUncorrected OBJECT-TYPE
	SYNTAX Unsigned32
	MAX-ACCESS read-only
	STATUS current
	DESCRIPTION
		"Number of codewords left uncorrected after retransmission during this 15 minutes interval."
	::= { vdslLinePerfCurrEntry 34 }
	
	vdslLinePerfCurr1DayVtucRxUncorrected OBJECT-TYPE
	SYNTAX Unsigned32
	MAX-ACCESS read-only
	STATUS current
	DESCRIPTION
		"Number of codewords left uncorrected after retransmission during this 1 day interval."
	::= { vdslLinePerfCurrEntry 35 }
	
	vdslLinePerfCurr1DayVturRxUncorrected OBJECT-TYPE
	SYNTAX Unsigned32
	MAX-ACCESS read-only
	STATUS current
	DESCRIPTION
		"Number of codewords left uncorrected after retransmission during this 1 day interval."
	::= { vdslLinePerfCurrEntry 36 }
	
	vdslLinePerfCurrVtucLEFTRs OBJECT-TYPE
	SYNTAX Unsigned32
	MAX-ACCESS read-only
	STATUS current
	DESCRIPTION
		"Low Error-Free Throughput Rate Seconds since system boot up."
	::= { vdslLinePerfCurrEntry 37 }
	
	vdslLinePerfCurrVturLEFTRs OBJECT-TYPE
	SYNTAX Unsigned32
	MAX-ACCESS read-only
	STATUS current
	DESCRIPTION
		"Low Error-Free Throughput Rate Seconds since system boot up."
	::= { vdslLinePerfCurrEntry 38 }
	
	vdslLinePerfCurr15MVtucLEFTRs OBJECT-TYPE
	SYNTAX Unsigned32
	MAX-ACCESS read-only
	STATUS current
	DESCRIPTION
		"Low Error-Free Throughput Rate Seconds during this 15 minutes interval."
	::= { vdslLinePerfCurrEntry 39 }
	
	vdslLinePerfCurr15MVturLEFTRs OBJECT-TYPE
	SYNTAX Unsigned32
	MAX-ACCESS read-only
	STATUS current
	DESCRIPTION
		"Low Error-Free Throughput Rate Seconds during this 15 minutes interval."
	::= { vdslLinePerfCurrEntry 40 }
	
	vdslLinePerfCurr1DayVtucLEFTRs OBJECT-TYPE
	SYNTAX Unsigned32
	MAX-ACCESS read-only
	STATUS current
	DESCRIPTION
		"Low Error-Free Throughput Rate Seconds during this 1 day interval."
	::= { vdslLinePerfCurrEntry 41 }
	
	vdslLinePerfCurr1DayVturLEFTRs OBJECT-TYPE
	SYNTAX Unsigned32
	MAX-ACCESS read-only
	STATUS current
	DESCRIPTION
		"Low Error-Free Throughput Rate Seconds during this 1 day interval."
	::= { vdslLinePerfCurrEntry 42 }

    vdslLinePerfCurrVtucErrFreeBits OBJECT-TYPE
	SYNTAX Unsigned32
	MAX-ACCESS read-only
	STATUS current
	DESCRIPTION
		"The number of bits belonging to correct DTUs leaving the Rx PMS-TC x 2(-16) since system boot up."
	::= { vdslLinePerfCurrEntry 43 }
	
	vdslLinePerfCurrVturErrFreeBits OBJECT-TYPE
	SYNTAX Unsigned32
	MAX-ACCESS read-only
	STATUS current
	DESCRIPTION
		"The number of bits belonging to correct DTUs leaving the Rx PMS-TC x 2(-16) since system boot up."
	::= { vdslLinePerfCurrEntry 44 }
	
	vdslLinePerfCurr15MVtucErrFreeBits OBJECT-TYPE
	SYNTAX Unsigned32
	MAX-ACCESS read-only
	STATUS current
	DESCRIPTION
		"The number of bits belonging to correct DTUs leaving the Rx PMS-TC x 2(-16) during this 15 minutes interval."
	::= { vdslLinePerfCurrEntry 45 }
	
	vdslLinePerfCurr15MVturErrFreeBits OBJECT-TYPE
	SYNTAX Unsigned32
	MAX-ACCESS read-only
	STATUS current
	DESCRIPTION
		"The number of bits belonging to correct DTUs leaving the Rx PMS-TC x 2(-16) during this 15 minutes interval."
	::= { vdslLinePerfCurrEntry 46 }
	
	vdslLinePerfCurr1DayVtucErrFreeBits OBJECT-TYPE
	SYNTAX Unsigned32
	MAX-ACCESS read-only
	STATUS current
	DESCRIPTION
		"The number of bits belonging to correct DTUs leaving the Rx PMS-TC x 2(-16) this 1 day interval."
	::= { vdslLinePerfCurrEntry 47 }
	
	vdslLinePerfCurr1DayVturErrFreeBits OBJECT-TYPE
	SYNTAX Unsigned32
	MAX-ACCESS read-only
	STATUS current
	DESCRIPTION
		"The number of bits belonging to correct DTUs leaving the Rx PMS-TC x 2(-16) this 1 day interval."
	::= { vdslLinePerfCurrEntry 48 } 
	
	vdslLinePerfCurrVtucMinEftr OBJECT-TYPE
	SYNTAX Counter32
	MAX-ACCESS read-only
	STATUS current
	DESCRIPTION
		"Lowest EFTR of VTU-C observed in the current interval."
	::= { vdslLinePerfCurrEntry 49 }
	
	vdslLinePerfCurrVturMinEftr OBJECT-TYPE
	SYNTAX Counter32
	MAX-ACCESS read-only
	STATUS current
	DESCRIPTION
		"Lowest EFTR of VTU-R observed in the current interval."
	::= { vdslLinePerfCurrEntry 50 }
	
	vdslLinePerfCurr15MinVtucMinEftr OBJECT-TYPE
	SYNTAX Counter32
	MAX-ACCESS read-only
	STATUS current
	DESCRIPTION
		"Lowest EFTR of VTU-C observed in the current 15 minutes interval."
	::= { vdslLinePerfCurrEntry 51 } 
	
	vdslLinePerfCurr15MinVturMinEftr OBJECT-TYPE
	SYNTAX Counter32
	MAX-ACCESS read-only
	STATUS current
	DESCRIPTION
		"Lowest EFTR of VTU-R observed in the current 15 minutes interval."
	::= { vdslLinePerfCurrEntry 52 }
	
	vdslLinePerfCurr1DayVtucMinEftr OBJECT-TYPE
	SYNTAX Counter32
	MAX-ACCESS read-only
	STATUS current
	DESCRIPTION
		"Lowest EFTR of VTU-C observed in the current 1 day interval."
	::= { vdslLinePerfCurrEntry 53 }
	
	vdslLinePerfCurr1DayVturMinEftr OBJECT-TYPE
	SYNTAX Counter32
	MAX-ACCESS read-only
	STATUS current
	DESCRIPTION
		"Lowest EFTR of VTU-R observed in the  current 1 day interval."
	::= { vdslLinePerfCurrEntry 54 }

-- vdslLinePerfHist15MinTable

        vdslLinePerfHist15MinTable OBJECT-TYPE
        SYNTAX SEQUENCE OF VdslLinePerfHist15MinEntry
        MAX-ACCESS not-accessible
        STATUS current
        DESCRIPTION
        	"The table displays VDSL line 15-Min SOS/GINP/INM performance stats."
        ::= { vdslStats 8 }

        vdslLinePerfHist15MinEntry OBJECT-TYPE
        SYNTAX VdslLinePerfHist15MinEntry
        MAX-ACCESS not-accessible
        STATUS current
        DESCRIPTION
        	"An entry of vdslLinePerfCurrTable."
        INDEX { ifIndex }
        ::= { vdslLinePerfHist15MinTable 1 }

        VdslLinePerfHist15MinEntry ::=
        	SEQUENCE {
                  	vdslLinePerfHist15MInmVtucEqInp			Counter32,
					vdslLinePerfHist15MInmVturEqInp			Counter32,
					vdslLinePerfHist15MInmVtucIAT			Counter32,
					vdslLinePerfHist15MInmVturIAT			Counter32,
					vdslLinePerfHist15MInmVtucME			Counter32,
					vdslLinePerfHist15MInmVturME			Counter32,
					vdslLinePerfHist15MVtucRtx				Unsigned32,
					vdslLinePerfHist15MVturRtx				Unsigned32,
					vdslLinePerfHist15MVtucRtxCorrected		Unsigned32,
					vdslLinePerfHist15MVturRtxCorrected		Unsigned32,
					vdslLinePerfHist15MVtucRtxUncorrected	Unsigned32,
					vdslLinePerfHist15MVturRtxUncorrected	Unsigned32,
					vdslLinePerfHist15MVtucLEFTRs			Unsigned32,
					vdslLinePerfHist15MVturLEFTRs			Unsigned32,
					vdslLinePerfHist15MVtucErrFreeBits		Unsigned32,
					vdslLinePerfHist15MVturErrFreeBits		Unsigned32,
					vdslLinePerfHist15MVtucMinEftr			Counter32,
					vdslLinePerfHist15MVturMinEftr			Counter32
              	}
              	
	vdslLinePerfHist15MInmVtucEqInp OBJECT-TYPE
	SYNTAX Counter32
	MAX-ACCESS read-only
	STATUS current
	DESCRIPTION
		"The INM Equivalent Inp histogram during 15min interval. An array of 68 octets 
		(each 4 octets means amount of a bin of histogram), designed for supporting from 
		1 to 17 bins of the histogram. The particular index of the bin incremented by an 
		impulse noise event is equal to the computed value of equivalent INP, except the 
		17th of anomaly INPEQ, which logs all equivalent INPs greater than 16. Each bin 
		has a value in the range 0x0 to 0xFFFFFFFF."
	::= { vdslLinePerfHist15MinEntry 1 }
	
	vdslLinePerfHist15MInmVturEqInp OBJECT-TYPE
	SYNTAX Counter32
	MAX-ACCESS read-only
	STATUS current
	DESCRIPTION
		"The INM Equivalent Inp histogram during 15min interval. An array of 68 octets 
		(each 4 octets means amount of a bin of histogram), designed for supporting from 
		1 to 17 bins of the histogram. The particular index of the bin incremented by an 
		impulse noise event is equal to the computed value of equivalent INP, except the 
		17th of anomaly INPEQ, which logs all equivalent INPs greater than 16. Each bin 
		has a value in the range 0x0 to 0xFFFFFFFF."
	::= { vdslLinePerfHist15MinEntry 2 }
	
	vdslLinePerfHist15MInmVtucIAT OBJECT-TYPE
	SYNTAX Counter32
	MAX-ACCESS read-only
	STATUS current
	DESCRIPTION
		"The INM Inter Arrival Time histogram during 15min interval. An array of 32 octets 
		(each 4 octets means amount of a bin of histogram), designed for supporting from 0 
		to 7 bins of the histogram. The index of the particular bin incremented by an complete 
		impulse noise event is determained from the following INMControl parameters. Each bin 
		has a value in the range 0x0 to 0xFFFFFFFF."
	::= { vdslLinePerfHist15MinEntry 3 }
	
	vdslLinePerfHist15MInmVturIAT OBJECT-TYPE
	SYNTAX Counter32
	MAX-ACCESS read-only
	STATUS current
	DESCRIPTION
		"The INM Inter Arrival Time histogram during 15min interval. An array of 32 octets 
		(each 4 octets means amount of a bin of histogram), designed for supporting from 0 
		to 7 bins of the histogram. The index of the particular bin incremented by an complete 
		impulse noise event is determained from the following INMControl parameters. Each bin 
		has a value in the range 0x0 to 0xFFFFFFFF."
	::= { vdslLinePerfHist15MinEntry 4 }
	
	vdslLinePerfHist15MInmVtucME OBJECT-TYPE
	SYNTAX Counter32
	MAX-ACCESS read-only
	STATUS current
	DESCRIPTION
		"The INM total measurement during 15min interval.This indication occurs every time 
		a data symbol is processed by the Impulse Noise Sensor. The range of the value is 
		from 0x0 to 0xFFFFFFFF."
	::= { vdslLinePerfHist15MinEntry 5 }
	
	vdslLinePerfHist15MInmVturME OBJECT-TYPE
	SYNTAX Counter32
	MAX-ACCESS read-only
	STATUS current
	DESCRIPTION
		"The INM total measurement during 15min interval.This indication occurs every time 
		a data symbol is processed by the Impulse Noise Sensor. The range of the value is 
		from 0x0 to 0xFFFFFFFF."
	::= { vdslLinePerfHist15MinEntry 6 }
	
	vdslLinePerfHist15MVtucRtx OBJECT-TYPE
	SYNTAX Unsigned32
	MAX-ACCESS read-only
	STATUS current
	DESCRIPTION
		"Number of codewords retransmitted during this interval."
	::= { vdslLinePerfHist15MinEntry 7 }
	
	vdslLinePerfHist15MVturRtx OBJECT-TYPE
	SYNTAX Unsigned32
	MAX-ACCESS read-only
	STATUS current
	DESCRIPTION
		"Number of codewords retransmitted during this interval."
	::= { vdslLinePerfHist15MinEntry 8 }
	
	vdslLinePerfHist15MVtucRtxCorrected OBJECT-TYPE
	SYNTAX Unsigned32
	MAX-ACCESS read-only
	STATUS current
	DESCRIPTION
		"Number of codewords corrected through retransmission during this interval."
	::= { vdslLinePerfHist15MinEntry 9 }
	
	vdslLinePerfHist15MVturRtxCorrected OBJECT-TYPE
	SYNTAX Unsigned32
	MAX-ACCESS read-only
	STATUS current
	DESCRIPTION
		"Number of codewords corrected through retransmission during this interval."
	::= { vdslLinePerfHist15MinEntry 10 }
	
	vdslLinePerfHist15MVtucRtxUncorrected OBJECT-TYPE
	SYNTAX Unsigned32
	MAX-ACCESS read-only
	STATUS current
	DESCRIPTION
		"Number of codewords left uncorrected after retransmission during this interval."
	::= { vdslLinePerfHist15MinEntry 11 }
	
	vdslLinePerfHist15MVturRtxUncorrected OBJECT-TYPE
	SYNTAX Unsigned32
	MAX-ACCESS read-only
	STATUS current
	DESCRIPTION
		"Number of codewords left uncorrected after retransmission during this interval."
	::= { vdslLinePerfHist15MinEntry 12 }
	
	vdslLinePerfHist15MVtucLEFTRs OBJECT-TYPE
	SYNTAX Unsigned32
	MAX-ACCESS read-only
	STATUS current
	DESCRIPTION
		"Low Error-Free Throughput Rate Seconds during this interval."
	::= { vdslLinePerfHist15MinEntry 13 }
	
	vdslLinePerfHist15MVturLEFTRs OBJECT-TYPE
	SYNTAX Unsigned32
	MAX-ACCESS read-only
	STATUS current
	DESCRIPTION
		"Low Error-Free Throughput Rate Seconds during this interval."
	::= { vdslLinePerfHist15MinEntry 14 }
		
	vdslLinePerfHist15MVtucErrFreeBits OBJECT-TYPE
	SYNTAX Unsigned32
	MAX-ACCESS read-only
	STATUS current
	DESCRIPTION
		"The number of bits belonging to correct DTUs leaving the Rx PMS-TC x 2(-16) during this interval."
	::= { vdslLinePerfHist15MinEntry 15 }
	
	vdslLinePerfHist15MVturErrFreeBits OBJECT-TYPE
	SYNTAX Unsigned32
	MAX-ACCESS read-only
	STATUS current
	DESCRIPTION
		"The number of bits belonging to correct DTUs leaving the Rx PMS-TC x 2(-16) during this interval."
	::= { vdslLinePerfHist15MinEntry 16 }
	
	vdslLinePerfHist15MVtucMinEftr OBJECT-TYPE
	SYNTAX Counter32
	MAX-ACCESS read-only
	STATUS current
	DESCRIPTION
		"Lowest EFTR of VTU-C observed during this interval."
	::= { vdslLinePerfHist15MinEntry 17 }
	
	vdslLinePerfHist15MVturMinEftr OBJECT-TYPE
	SYNTAX Counter32
	MAX-ACCESS read-only
	STATUS current
	DESCRIPTION
		"Lowest EFTR of VTU-R observed during this interval."
	::= { vdslLinePerfHist15MinEntry 18 }

-- vdslLinePerfHist1DayTable

        vdslLinePerfHist1DayTable OBJECT-TYPE
        SYNTAX SEQUENCE OF VdslLinePerfHist1DayEntry
        MAX-ACCESS not-accessible
        STATUS current
        DESCRIPTION
        	"The table displays VDSL line 1-Day SOS/GINP/INM performance stats."
        ::= { vdslStats 9 }

        vdslLinePerfHist1DayEntry OBJECT-TYPE
        SYNTAX VdslLinePerfHist1DayEntry
        MAX-ACCESS not-accessible
        STATUS current
        DESCRIPTION
        	"An entry of vdslLinePerfHist1DayTable."
        INDEX { ifIndex }
        ::= { vdslLinePerfHist1DayTable 1 }

        VdslLinePerfHist1DayEntry ::=
        	SEQUENCE {
                  	vdslLinePerfHist1DayInmVtucEqInp			Counter32,
					vdslLinePerfHist1DayInmVturEqInp			Counter32,
					vdslLinePerfHist1DayInmVtucIAT			Counter32,
					vdslLinePerfHist1DayInmVturIAT			Counter32,
					vdslLinePerfHist1DayInmVtucME			Counter32,
					vdslLinePerfHist1DayInmVturME			Counter32,
					vdslLinePerfHist1DayVtucRtx				Unsigned32,
					vdslLinePerfHist1DayVturRtx				Unsigned32,
					vdslLinePerfHist1DayVtucRtxCorrected		Unsigned32,
					vdslLinePerfHist1DayVturRtxCorrected		Unsigned32,
					vdslLinePerfHist1DayVtucRtxUncorrected	Unsigned32,
					vdslLinePerfHist1DayVturRtxUncorrected	Unsigned32,
					vdslLinePerfHist1DayVtucLEFTRs			Unsigned32,
					vdslLinePerfHist1DayVturLEFTRs			Unsigned32,
					vdslLinePerfHist1DayVtucErrFreeBits		Unsigned32,
					vdslLinePerfHist1DayVturErrFreeBits		Unsigned32,
					vdslLinePerfHist1DayVtucMinEftr			Counter32,
					vdslLinePerfHist1DayVturMinEftr			Counter32
              	}
              	
	vdslLinePerfHist1DayInmVtucEqInp OBJECT-TYPE
	SYNTAX Counter32
	MAX-ACCESS read-only
	STATUS current
	DESCRIPTION
		"The INM Equivalent Inp histogram during 1 day interval. An array of 68 octets 
		(each 4 octets means amount of a bin of histogram), designed for supporting from 
		1 to 17 bins of the histogram. The particular index of the bin incremented by an 
		impulse noise event is equal to the computed value of equivalent INP, except the 
		17th of anomaly INPEQ, which logs all equivalent INPs greater than 16. Each bin 
		has a value in the range 0x0 to 0xFFFFFFFF."
	::= { vdslLinePerfHist1DayEntry 1 }
	
	vdslLinePerfHist1DayInmVturEqInp OBJECT-TYPE
	SYNTAX Counter32
	MAX-ACCESS read-only
	STATUS current
	DESCRIPTION
		"The INM Equivalent Inp histogram during 1 day interval. An array of 68 octets 
		(each 4 octets means amount of a bin of histogram), designed for supporting from 
		1 to 17 bins of the histogram. The particular index of the bin incremented by an 
		impulse noise event is equal to the computed value of equivalent INP, except the 
		17th of anomaly INPEQ, which logs all equivalent INPs greater than 16. Each bin 
		has a value in the range 0x0 to 0xFFFFFFFF."
	::= { vdslLinePerfHist1DayEntry 2 }
	
	vdslLinePerfHist1DayInmVtucIAT OBJECT-TYPE
	SYNTAX Counter32
	MAX-ACCESS read-only
	STATUS current
	DESCRIPTION
		"The INM Inter Arrival Time histogram during 1 day interval. An array of 32 octets 
		(each 4 octets means amount of a bin of histogram), designed for supporting from 0 
		to 7 bins of the histogram. The index of the particular bin incremented by an complete 
		impulse noise event is determained from the following INMControl parameters. Each bin 
		has a value in the range 0x0 to 0xFFFFFFFF."
	::= { vdslLinePerfHist1DayEntry 3 }
	
	vdslLinePerfHist1DayInmVturIAT OBJECT-TYPE
	SYNTAX Counter32
	MAX-ACCESS read-only
	STATUS current
	DESCRIPTION
		"The INM Inter Arrival Time histogram during 1 day interval. An array of 32 octets 
		(each 4 octets means amount of a bin of histogram), designed for supporting from 0 
		to 7 bins of the histogram. The index of the particular bin incremented by an complete 
		impulse noise event is determained from the following INMControl parameters. Each bin 
		has a value in the range 0x0 to 0xFFFFFFFF."
	::= { vdslLinePerfHist1DayEntry 4 }
	
	vdslLinePerfHist1DayInmVtucME OBJECT-TYPE
	SYNTAX Counter32
	MAX-ACCESS read-only
	STATUS current
	DESCRIPTION
		"The INM total measurement during 1 day interval.This indication occurs every time 
		a data symbol is processed by the Impulse Noise Sensor. The range of the value is 
		from 0x0 to 0xFFFFFFFF."
	::= { vdslLinePerfHist1DayEntry 5 }
	
	vdslLinePerfHist1DayInmVturME OBJECT-TYPE
	SYNTAX Counter32
	MAX-ACCESS read-only
	STATUS current
	DESCRIPTION
		"The INM total measurement during 1 day interval.This indication occurs every time 
		a data symbol is processed by the Impulse Noise Sensor. The range of the value is 
		from 0x0 to 0xFFFFFFFF."
	::= { vdslLinePerfHist1DayEntry 6 }
	
	vdslLinePerfHist1DayVtucRtx OBJECT-TYPE
	SYNTAX Unsigned32
	MAX-ACCESS read-only
	STATUS current
	DESCRIPTION
		"Number of codewords retransmitted during this interval."
	::= { vdslLinePerfHist1DayEntry 7 }
	
	vdslLinePerfHist1DayVturRtx OBJECT-TYPE
	SYNTAX Unsigned32
	MAX-ACCESS read-only
	STATUS current
	DESCRIPTION
		"Number of codewords retransmitted during this interval."
	::= { vdslLinePerfHist1DayEntry 8 }
	
	vdslLinePerfHist1DayVtucRtxCorrected OBJECT-TYPE
	SYNTAX Unsigned32
	MAX-ACCESS read-only
	STATUS current
	DESCRIPTION
		"Number of codewords corrected through retransmission during this interval."
	::= { vdslLinePerfHist1DayEntry 9 }
	
	vdslLinePerfHist1DayVturRtxCorrected OBJECT-TYPE
	SYNTAX Unsigned32
	MAX-ACCESS read-only
	STATUS current
	DESCRIPTION
		"Number of codewords corrected through retransmission during this interval."
	::= { vdslLinePerfHist1DayEntry 10 }
	
	vdslLinePerfHist1DayVtucRtxUncorrected OBJECT-TYPE
	SYNTAX Unsigned32
	MAX-ACCESS read-only
	STATUS current
	DESCRIPTION
		"Number of codewords left uncorrected after retransmission during this interval."
	::= { vdslLinePerfHist1DayEntry 11 }
	
	vdslLinePerfHist1DayVturRtxUncorrected OBJECT-TYPE
	SYNTAX Unsigned32
	MAX-ACCESS read-only
	STATUS current
	DESCRIPTION
		"Number of codewords left uncorrected after retransmission during this interval."
	::= { vdslLinePerfHist1DayEntry 12 }
	
	vdslLinePerfHist1DayVtucLEFTRs OBJECT-TYPE
	SYNTAX Unsigned32
	MAX-ACCESS read-only
	STATUS current
	DESCRIPTION
		"Low Error-Free Throughput Rate Seconds during this interval."
	::= { vdslLinePerfHist1DayEntry 13 }
	
	vdslLinePerfHist1DayVturLEFTRs OBJECT-TYPE
	SYNTAX Unsigned32
	MAX-ACCESS read-only
	STATUS current
	DESCRIPTION
		"Low Error-Free Throughput Rate Seconds during this interval."
	::= { vdslLinePerfHist1DayEntry 14 }
		
	vdslLinePerfHist1DayVtucErrFreeBits OBJECT-TYPE
	SYNTAX Unsigned32
	MAX-ACCESS read-only
	STATUS current
	DESCRIPTION
		"The number of bits belonging to correct DTUs leaving the Rx PMS-TC x 2(-16) during this interval."
	::= { vdslLinePerfHist1DayEntry 15 }
	
	vdslLinePerfHist1DayVturErrFreeBits OBJECT-TYPE
	SYNTAX Unsigned32
	MAX-ACCESS read-only
	STATUS current
	DESCRIPTION
		"The number of bits belonging to correct DTUs leaving the Rx PMS-TC x 2(-16) during this interval."
	::= { vdslLinePerfHist1DayEntry 16 }
	
	vdslLinePerfHist1DayVtucMinEftr OBJECT-TYPE
	SYNTAX Counter32
	MAX-ACCESS read-only
	STATUS current
	DESCRIPTION
		"Lowest EFTR of VTU-C observed during this interval."
	::= { vdslLinePerfHist1DayEntry 17 }
	
	vdslLinePerfHist1DayVturMinEftr OBJECT-TYPE
	SYNTAX Counter32
	MAX-ACCESS read-only
	STATUS current
	DESCRIPTION
		"Lowest EFTR of VTU-R  observed during this interval."
	::= { vdslLinePerfHist1DayEntry 18 }

-- vdslChanStatsTable

    vdslChanStatsTable OBJECT-TYPE
    SYNTAX SEQUENCE OF VdslChanStatsEntry
    MAX-ACCESS not-accessible
    STATUS current
    DESCRIPTION
    	"The table displays VDSL channel Status."
    ::= { vdslStats 10 }

    vdslChanStatsEntry OBJECT-TYPE
    SYNTAX VdslChanStatsEntry
    MAX-ACCESS not-accessible
    STATUS current
    DESCRIPTION
    	"An entry of vdslChanStatsTable."
    INDEX { ifIndex }
    ::= { vdslChanStatsTable 1 }

    VdslChanStatsEntry ::=
   	SEQUENCE {
			vdslChanActualRaMode    						Xdsl2StatusActualRaMode,
			vdslChanRetransmissionMode    					Xdsl2StatusRtxMode,
			vdslChanRetransmissionOverhead    				Unsigned32
   	}
          	
	vdslChanActualRaMode  OBJECT-TYPE
    SYNTAX      Xdsl2StatusActualRaMode
    UNITS       ""
    MAX-ACCESS  read-only
    STATUS      current
    DESCRIPTION
     "The actual RA mode.
      The possible values are:
        fixedRateMode(1) - Fixed rate mode
        raInit(2)        - Adaptive rate mode at initialization
        dynamicRa(3)     - Dynamic rate adaptation
        sosEnabled(4)    - SOS enabled"
    ::= { vdslChanStatsEntry 2 }
    
    vdslChanRetransmissionMode  OBJECT-TYPE
    SYNTAX      Xdsl2StatusRtxMode
    UNITS       ""
    MAX-ACCESS  read-only
    STATUS      current
    DESCRIPTION
     "RTX-USED operational data parameter.
      The possible values are:
        rtxInUse(1)            - RTX in use.
        rtxForbidden(2)        - RTX not in use because RTX-MODE = FORBIDDEN.
        rtxNotSupportedXtuC(3) - RTX not in use because it is not supported by the XTU-C.
        rtxNotSupportedXtuR(4) - RTX not in use because it is not supported by the XTU-R.
        rtxNotSupportedBoth(5) - RTX not in use because it is not supported by the XTU-C and XTU-R."
    ::= { vdslChanStatsEntry 3 }
    
    vdslChanRetransmissionOverhead  OBJECT-TYPE
    SYNTAX      Unsigned32
    UNITS       "kbps"
    MAX-ACCESS  read-only
    STATUS      current
    DESCRIPTION
       "Expected retransmission overhead in G.inp due to REIN and SHINE noise. Unit is kbps."
    ::= { vdslChanStatsEntry 4 }
   

--------------------
--  PAEPVC
--------------------

-- paepvcSessionTable

        paepvcSessionTable OBJECT-TYPE
        SYNTAX SEQUENCE OF PaepvcSessionEntry
        MAX-ACCESS not-accessible
        STATUS current
        DESCRIPTION
        	"This table shows the paepvc session statistics.
        	This table is supported by R1.03 and later versions."
        ::= { paepvcStats 1 }

	paepvcSessionEntry OBJECT-TYPE
        SYNTAX PaepvcSessionEntry
        MAX-ACCESS not-accessible
        STATUS current
        DESCRIPTION
		"An entry of paepvcSessionTable."
        INDEX { ifIndex , paepvcSessionVpi, paepvcSessionVci }
        ::= { paepvcSessionTable 1 }

        PaepvcSessionEntry ::=
        	SEQUENCE {
			paepvcSessionVpi		INTEGER,
			paepvcSessionVci		INTEGER,
			paepvcSessionState		INTEGER,
			paepvcSessionId			INTEGER,
			paepvcSessionUpTime		Unsigned32,
			paepvcSessionAcName		DisplayString,
			paepvcSessionSrvcName		DisplayString
           	}

        paepvcSessionVpi OBJECT-TYPE
        SYNTAX INTEGER
        MAX-ACCESS read-only
        STATUS current
        DESCRIPTION
                "The PAEPVC VPI."
        ::= { paepvcSessionEntry 1 }

        paepvcSessionVci OBJECT-TYPE
        SYNTAX INTEGER
        MAX-ACCESS read-only
        STATUS current
        DESCRIPTION
                "The PAEPVC VCI."
        ::= { paepvcSessionEntry 2 }

        paepvcSessionState OBJECT-TYPE
        SYNTAX	INTEGER {
        		down(1),
        		pppoe(2),
			ppp(3),
			up(4)
        	}
        MAX-ACCESS read-only
        STATUS current
        DESCRIPTION
                "The PAEPVC status."
        ::= { paepvcSessionEntry 3 }

        paepvcSessionId OBJECT-TYPE
        SYNTAX INTEGER
        MAX-ACCESS read-only
        STATUS current
        DESCRIPTION
                "The PAEPVC session ID."
        ::= { paepvcSessionEntry 4 }

        paepvcSessionUpTime OBJECT-TYPE
        SYNTAX Unsigned32
        UNITS "second"
        MAX-ACCESS read-only
        STATUS current
        DESCRIPTION
                "The PAEPVC session uptime."
        ::= { paepvcSessionEntry 5 }

        paepvcSessionAcName OBJECT-TYPE
        SYNTAX DisplayString
        MAX-ACCESS read-only
        STATUS current
        DESCRIPTION
                "Access concentrator name."
        ::= { paepvcSessionEntry 6 }

        paepvcSessionSrvcName OBJECT-TYPE
        SYNTAX DisplayString
        MAX-ACCESS read-only
        STATUS current
        DESCRIPTION
                "Service name."
        ::= { paepvcSessionEntry 7 }


-- paepvcCountTable

        paepvcCountTable OBJECT-TYPE
        SYNTAX SEQUENCE OF PaepvcCountEntry
        MAX-ACCESS not-accessible
        STATUS current
        DESCRIPTION
        	"This table shows the paepvc counters.
        	This table is supported by R1.03 and later versions."
        ::= { paepvcStats 2 }

	paepvcCountEntry OBJECT-TYPE
        SYNTAX PaepvcCountEntry
        MAX-ACCESS not-accessible
        STATUS current
        DESCRIPTION
		"An entry of paepvcCountTable."
        INDEX { ifIndex , paepvcCountVpi, paepvcCountVci }
        ::= { paepvcCountTable 1 }

        PaepvcCountEntry ::=
        	SEQUENCE {
			paepvcCountVpi				INTEGER,
			paepvcCountVci				INTEGER,
			paepvcCountPppLcpCfgReqRx		Unsigned32,
			paepvcCountPppLcpEchoReqRx		Unsigned32,
			paepvcCountPppLcpEchoReplyRx		Unsigned32,
			paepvcCountPadiTx			Unsigned32,
			paepvcCountPadoRx			Unsigned32,
			paepvcCountPadrTx			Unsigned32,
			paepvcCountPadsRx			Unsigned32,
			paepvcCountPadtTx			Unsigned32,
			paepvcCountPadtRx			Unsigned32,
			paepvcCountSrvcnameErrRx		Unsigned32,
			paepvcCountAcnameErrRx			Unsigned32,
			paepvcCountGenericErrTx			Unsigned32,
			paepvcCountGenericErrRx			Unsigned32
           	}


        paepvcCountVpi OBJECT-TYPE
        SYNTAX INTEGER
        MAX-ACCESS read-only
        STATUS current
        DESCRIPTION
                "The PAEPVC VPI."
        ::= { paepvcCountEntry 1 }

        paepvcCountVci OBJECT-TYPE
        SYNTAX INTEGER
        MAX-ACCESS read-only
        STATUS current
        DESCRIPTION
                "The PAEPVC VCI."
        ::= { paepvcCountEntry 2 }

        paepvcCountPppLcpCfgReqRx OBJECT-TYPE
        SYNTAX Unsigned32
        MAX-ACCESS read-only
        STATUS current
        DESCRIPTION
                "The number of ppp lcp config-request received."
        ::= { paepvcCountEntry 3 }

        paepvcCountPppLcpEchoReqRx OBJECT-TYPE
        SYNTAX Unsigned32
        MAX-ACCESS read-only
        STATUS current
        DESCRIPTION
                "The number of ppp lcp echo-request received."
        ::= { paepvcCountEntry 4 }

        paepvcCountPppLcpEchoReplyRx OBJECT-TYPE
        SYNTAX Unsigned32
        MAX-ACCESS read-only
        STATUS current
        DESCRIPTION
                "The number of ppp lcp echo-reply received."
        ::= { paepvcCountEntry 5 }

        paepvcCountPadiTx OBJECT-TYPE
        SYNTAX Unsigned32
        MAX-ACCESS read-only
        STATUS current
        DESCRIPTION
                "The number of pppoe padi transfered."
        ::= { paepvcCountEntry 6 }

        paepvcCountPadoRx OBJECT-TYPE
        SYNTAX Unsigned32
        MAX-ACCESS read-only
        STATUS current
        DESCRIPTION
                "The number of pppoe pado received."
        ::= { paepvcCountEntry 7 }

        paepvcCountPadrTx OBJECT-TYPE
        SYNTAX Unsigned32
        MAX-ACCESS read-only
        STATUS current
        DESCRIPTION
                "The number of pppoe padr received."
        ::= { paepvcCountEntry 8 }

        paepvcCountPadsRx OBJECT-TYPE
        SYNTAX Unsigned32
        MAX-ACCESS read-only
        STATUS current
        DESCRIPTION
                "The number of pppoe pads received."
        ::= { paepvcCountEntry 9 }

        paepvcCountPadtTx OBJECT-TYPE
        SYNTAX Unsigned32
        MAX-ACCESS read-only
        STATUS current
        DESCRIPTION
                "The number of pppoe padt transfered."
        ::= { paepvcCountEntry 10 }

        paepvcCountPadtRx OBJECT-TYPE
        SYNTAX Unsigned32
        MAX-ACCESS read-only
        STATUS current
        DESCRIPTION
                "The number of pppoe padt received."
        ::= { paepvcCountEntry 11 }

        paepvcCountSrvcnameErrRx OBJECT-TYPE
        SYNTAX Unsigned32
        MAX-ACCESS read-only
        STATUS current
        DESCRIPTION
                "The number of pppoe service name error received."
        ::= { paepvcCountEntry 12 }

        paepvcCountAcnameErrRx OBJECT-TYPE
        SYNTAX Unsigned32
        MAX-ACCESS read-only
        STATUS current
        DESCRIPTION
                "The number of pppoe access concentrator name error received."
        ::= { paepvcCountEntry 13 }

        paepvcCountGenericErrTx OBJECT-TYPE
        SYNTAX Unsigned32
        MAX-ACCESS read-only
        STATUS current
        DESCRIPTION
                "The number of pppoe generic error transfered."
        ::= { paepvcCountEntry 14 }

        paepvcCountGenericErrRx OBJECT-TYPE
        SYNTAX Unsigned32
        MAX-ACCESS read-only
        STATUS current
        DESCRIPTION
                "The number of pppoe generic error received."
        ::= { paepvcCountEntry 15 }
	        
--------------------
--  VLAN MAC
--------------------
		
	vlanMacDisplayTarget OBJECT-TYPE
	SYNTAX INTEGER
	MAX-ACCESS read-write
	STATUS current
	DESCRIPTION
		"This managed object is a filter used for identify the target from which 
		the MAC addresses are learned in macTable. Ifindex is used to specify a specific
		interface of which the MAC addresses are displayed. Some values are reserved for
		special purpose, they are:
		0: All interfaces 
		50: All uplink ports"
	::= { vlanMacStats 1 }

	vlanMacDisplayVid OBJECT-TYPE
	SYNTAX VlanIndex
	MAX-ACCESS read-write
	STATUS current
	DESCRIPTION
		"This object is supported by R1.03 and later versions.
		This managed object is a filter used for identifying the target 
		from which the MAC addresses are learned in vlanMacTable. The value of zero
		means no filtering."
	::= { vlanMacStats 2 }
	
-- macTable
	
        vlanMacTable OBJECT-TYPE
        SYNTAX SEQUENCE OF VlanMacEntry
        MAX-ACCESS not-accessible
        STATUS current
        DESCRIPTION
        	"This table is supported by R1.03 and later versions.
        	A table that contains information about unicast
                entries for which the bridge has forwarding and/or
                filtering information. This information is used
                by the transparent bridging function in
                determining how to propagate a received frame."
        ::= { vlanMacStats 3 }
	
        vlanMacEntry OBJECT-TYPE
        SYNTAX VlanMacEntry
        MAX-ACCESS not-accessible
        STATUS current
        DESCRIPTION
        	"An entry of vlanMacTable."
        INDEX { dot1qVlanIndex, vlanMacAddress }
        ::= { vlanMacTable 1 }

        VlanMacEntry ::=
        	SEQUENCE {
                  	vlanMacAddress		MacAddress,
                  	vlanMacPort		INTEGER,
                  	vlanMacStatus		INTEGER
              	}

        vlanMacAddress OBJECT-TYPE
        SYNTAX MacAddress
        MAX-ACCESS read-only
        STATUS current
        DESCRIPTION
        	"A unicast MAC address for which the bridge has
                forwarding and/or filtering information."
        ::= { vlanMacEntry 1 }

        vlanMacPort OBJECT-TYPE
        SYNTAX INTEGER
        MAX-ACCESS read-only
        STATUS current
        DESCRIPTION
        	"The port from which the mac address has been learned."
        ::= { vlanMacEntry 2 }

        vlanMacStatus OBJECT-TYPE
        SYNTAX  INTEGER {
                          other(1),
                          invalid(2),
                          learned(3),
                          self(4),
                          mgmt(5)
        	}
        MAX-ACCESS read-only
        STATUS current
        DESCRIPTION
        	"The status of this entry."
	::= { vlanMacEntry 3 }

--------------------
--  ipbpvc
--------------------

-- arpproxyTable

        arpproxyTable OBJECT-TYPE
        SYNTAX SEQUENCE OF ArpproxyEntry
        MAX-ACCESS not-accessible
        STATUS current
        DESCRIPTION
        	"Display ARP table. This table is supported by R3.00 and later versions."
        ::= { ipbpvcStats 1 }
	
        arpproxyEntry OBJECT-TYPE
        SYNTAX ArpproxyEntry
        MAX-ACCESS not-accessible
        STATUS current
        DESCRIPTION
        	"An entry of arpproxyTable."
        INDEX { ipbpvcDomainName, arpproxyIp }
        ::= { arpproxyTable 1 }

        ArpproxyEntry ::=
        	SEQUENCE {
                  	arpproxyIp			IpAddress,
                  	arpproxyMac			MacAddress,
                  	arpproxyIfIndex			INTEGER,
                  	arpproxyVpi			INTEGER,
                  	arpproxyVci			INTEGER,
                  	arpproxyInterfaceIp		IpAddress,
                  	arpproxyInterfaceMask		INTEGER,
                  	arpproxyInterfaceVid		VlanIndex,
                  	arpproxyDhcpIp			INTEGER,
                  	arpproxyType			INTEGER
              	}

        arpproxyIp OBJECT-TYPE
        SYNTAX IpAddress
        MAX-ACCESS read-only
        STATUS current
        DESCRIPTION
        	""
        ::= { arpproxyEntry 1 }
        
	arpproxyMac OBJECT-TYPE
        SYNTAX MacAddress
        MAX-ACCESS read-only
        STATUS current
        DESCRIPTION
        	""
        ::= { arpproxyEntry 2 }
        
        arpproxyIfIndex OBJECT-TYPE
        SYNTAX INTEGER
        MAX-ACCESS read-only
        STATUS current
        DESCRIPTION
        	""
        ::= { arpproxyEntry 3 }
        
        arpproxyVpi OBJECT-TYPE
        SYNTAX INTEGER
        MAX-ACCESS read-only
        STATUS current
        DESCRIPTION
        	""
        ::= { arpproxyEntry 4 }
        
        arpproxyVci OBJECT-TYPE
        SYNTAX INTEGER
        MAX-ACCESS read-only
        STATUS current
        DESCRIPTION
        	""
        ::= { arpproxyEntry 5 }
        
        arpproxyInterfaceIp OBJECT-TYPE
        SYNTAX IpAddress
        MAX-ACCESS read-only
        STATUS current
        DESCRIPTION
        	""
        ::= { arpproxyEntry 6 }
        
        arpproxyInterfaceMask OBJECT-TYPE
        SYNTAX INTEGER
        MAX-ACCESS read-only
        STATUS current
        DESCRIPTION
        	""
        ::= { arpproxyEntry 7 }
        
        arpproxyInterfaceVid OBJECT-TYPE
        SYNTAX VlanIndex
        MAX-ACCESS read-only
        STATUS current
        DESCRIPTION
        	""
        ::= { arpproxyEntry 8 }
        
        arpproxyDhcpIp OBJECT-TYPE
        SYNTAX	INTEGER {
        		true(1),
        		false(2)
        	}
        MAX-ACCESS read-only
        STATUS current
        DESCRIPTION
        	""
        ::= { arpproxyEntry 9 }
        
        arpproxyType OBJECT-TYPE
        SYNTAX	INTEGER {
        		upstream(1),
        		downstream(2)
        	}
        MAX-ACCESS read-only
        STATUS current
        DESCRIPTION
        	""
        ::= { arpproxyEntry 10 }
        
-- ipbpvcIfDynamicTable

        ipbpvcIfDynamicTable OBJECT-TYPE
        SYNTAX SEQUENCE OF IpbpvcIfDynamicEntry
        MAX-ACCESS not-accessible
        STATUS current
        DESCRIPTION
        	"Display runtime interfaces. This table is supported by R3.00 and later versions."
        ::= { ipbpvcStats 2 }
	
        ipbpvcIfDynamicEntry OBJECT-TYPE
        SYNTAX IpbpvcIfDynamicEntry
        MAX-ACCESS not-accessible
        STATUS current
        DESCRIPTION
        	"An entry of ipbpvcIfDynamicTable."
        INDEX { ipbpvcDomainName, ipbpvcIfDynamicIp, ipbpvcIfDynamicMask, ipbpvcDomainVlanId }
        ::= { ipbpvcIfDynamicTable 1 }

        IpbpvcIfDynamicEntry ::=
        	SEQUENCE {
                  	ipbpvcIfDynamicIp			IpAddress,
                  	ipbpvcIfDynamicMask			INTEGER,
                  	ipbpvcIfDynamicIfIndex			INTEGER,
                  	ipbpvcIfDynamicVpi			INTEGER,
                  	ipbpvcIfDynamicVci			INTEGER
              	}

        ipbpvcIfDynamicIp OBJECT-TYPE
        SYNTAX IpAddress
        MAX-ACCESS read-only
        STATUS current
        DESCRIPTION
        	""
        ::= { ipbpvcIfDynamicEntry 1 }
        
        ipbpvcIfDynamicMask OBJECT-TYPE
        SYNTAX INTEGER
        MAX-ACCESS read-only
        STATUS current
        DESCRIPTION
        	""
        ::= { ipbpvcIfDynamicEntry 2 }
        
        ipbpvcIfDynamicIfIndex OBJECT-TYPE
        SYNTAX INTEGER
        MAX-ACCESS read-only
        STATUS current
        DESCRIPTION
        	""
        ::= { ipbpvcIfDynamicEntry 3 }
        
        ipbpvcIfDynamicVpi OBJECT-TYPE
        SYNTAX INTEGER
        MAX-ACCESS read-only
        STATUS current
        DESCRIPTION
        	""
        ::= { ipbpvcIfDynamicEntry 4 }
        
        ipbpvcIfDynamicVci OBJECT-TYPE
        SYNTAX INTEGER
        MAX-ACCESS read-only
        STATUS current
        DESCRIPTION
        	""
        ::= { ipbpvcIfDynamicEntry 5 }
        
-- ipbpvcRouteDynamicTable

        ipbpvcRouteDynamicTable OBJECT-TYPE
        SYNTAX SEQUENCE OF IpbpvcRouteDynamicEntry
        MAX-ACCESS not-accessible
        STATUS current
        DESCRIPTION
        	"Display runtime routing table. This table is supported by R3.00 and later versions."
        ::= { ipbpvcStats 3 }
	
        ipbpvcRouteDynamicEntry OBJECT-TYPE
        SYNTAX IpbpvcRouteDynamicEntry
        MAX-ACCESS not-accessible
        STATUS current
        DESCRIPTION
        	"An entry of ipbpvcRouteDynamicTable."
        INDEX { ipbpvcDomainName, ipbpvcRouteDynamicType, ipbpvcRouteDynamicIp, ipbpvcRouteDynamicMask, ipbpvcRouteDynamicNextHop }
        ::= { ipbpvcRouteDynamicTable 1 }

        IpbpvcRouteDynamicEntry ::=
        	SEQUENCE {
        		ipbpvcRouteDynamicType			INTEGER,
                  	ipbpvcRouteDynamicIp			IpAddress,
                  	ipbpvcRouteDynamicMask			INTEGER,
                  	ipbpvcRouteDynamicNextHop		IpAddress,
                  	ipbpvcRouteDynamicMetric		INTEGER,
                  	ipbpvcRouteDynamicPriority		INTEGER
              	}
	
	ipbpvcRouteDynamicType OBJECT-TYPE
        SYNTAX	INTEGER {
        		upstream(1),
        		downstream(2)
        	}
        MAX-ACCESS read-only
        STATUS current
        DESCRIPTION
        	""
        ::= { ipbpvcRouteDynamicEntry 1 }
        
        ipbpvcRouteDynamicIp OBJECT-TYPE
        SYNTAX IpAddress
        MAX-ACCESS read-only
        STATUS current
        DESCRIPTION
        	""
        ::= { ipbpvcRouteDynamicEntry 2 }
        
        ipbpvcRouteDynamicMask OBJECT-TYPE
        SYNTAX INTEGER
        MAX-ACCESS read-only
        STATUS current
        DESCRIPTION
        	""
        ::= { ipbpvcRouteDynamicEntry 3 }
        
        ipbpvcRouteDynamicNextHop OBJECT-TYPE
        SYNTAX IpAddress
        MAX-ACCESS read-only
        STATUS current
        DESCRIPTION
        	""
        ::= { ipbpvcRouteDynamicEntry 4 }
        
        ipbpvcRouteDynamicMetric OBJECT-TYPE
        SYNTAX INTEGER
        MAX-ACCESS read-only
        STATUS current
        DESCRIPTION
        	""
        ::= { ipbpvcRouteDynamicEntry 5 }
        
        ipbpvcRouteDynamicPriority OBJECT-TYPE
        SYNTAX INTEGER
        MAX-ACCESS read-only
        STATUS current
        DESCRIPTION
        	""
        ::= { ipbpvcRouteDynamicEntry 6 }

--------------------
--  VoIP
--------------------

-- voipLineStatusTable

        voipLineStatusTable OBJECT-TYPE
        SYNTAX SEQUENCE OF VoipLineStatusEntry
        MAX-ACCESS not-accessible
        STATUS current
        DESCRIPTION
        	"The table displays VoIP line status. This table is supported by R4.01 and later versions."
        ::= { voipStats 1 }

        voipLineStatusEntry OBJECT-TYPE
        SYNTAX VoipLineStatusEntry
        MAX-ACCESS not-accessible
        STATUS current
        DESCRIPTION
        	"An entry of voipLineStatusTable."
        INDEX { voipIfIndex }
        ::= { voipLineStatusTable 1 }

        VoipLineStatusEntry ::=
        	SEQUENCE {
                  	voipLineStatusFxsStatus			INTEGER,
                  	voipLineStatusServiceStatus		INTEGER			
              	}
              	
	voipLineStatusFxsStatus OBJECT-TYPE
	SYNTAX INTEGER {
			disabled(1),
			on-hook(2),
			off-hook(3),
			ringing(4),
			power-cut-down(5),
			testing(6),
			fault(7),
			bad(8),
			uninitialized(9)
		}
	MAX-ACCESS read-only
	STATUS current
	DESCRIPTION
		"FXS status of the line."
	::= { voipLineStatusEntry 1 }
	 
	voipLineStatusServiceStatus OBJECT-TYPE
	SYNTAX INTEGER {
			disabled(1),
			out-of-service(2),
			idle(3),
			waiting-for-dialing(4),
			dialing-out(5),
			ringing(6),
			conversation-caller(7),
			conversation-callee(8),
			fax-caller(9),
			fax-callee(10),
			modem-caller(11),
			modem-callee(12),
			waiting-for-on-hook(13),
			dialing-timeout(14),
			alerting-off-hook(15),
			power-cut-down(16)
		}
	MAX-ACCESS read-only
	STATUS current
	DESCRIPTION
		"Service status of the line."
	::= { voipLineStatusEntry 2 }

-- voipLineInfoTable

        voipLineInfoTable OBJECT-TYPE
        SYNTAX SEQUENCE OF VoipLineInfoEntry
        MAX-ACCESS not-accessible
        STATUS current
        DESCRIPTION
        	"The table displays VoIP line information. This table is supported by R4.01 and later versions."
        ::= { voipStats 2 }

        voipLineInfoEntry OBJECT-TYPE
        SYNTAX VoipLineInfoEntry
        MAX-ACCESS not-accessible
        STATUS current
        DESCRIPTION
        	"An entry of voipLineInfoTable."
        INDEX { voipIfIndex }
        ::= { voipLineInfoTable 1 }

        VoipLineInfoEntry ::=
        	SEQUENCE {
                  	voipLineInfoSipLocalUri			DisplayString,
                  	voipLineInfoSipRemoteUri		DisplayString,
                  	voipLineInfoRtpTxCodecType		DisplayString,
                  	voipLineInfoRtpRxCodecType		DisplayString,
                  	voipLineInfoRtpTxPt			INTEGER,
                  	voipLineInfoRtpRxPt			INTEGER,
                  	voipLineInfoRtpLocalIp			IpAddress,
                  	voipLineInfoRtpRemoteIp			IpAddress,
                  	voipLineInfoRtpLocalPort		INTEGER,
                  	voipLineInfoRtpRemotePort		INTEGER,
                  	voipLineInfoLastCidMode			INTEGER,
                  	voipLineInfoPlaySignalTel		INTEGER,
                  	voipLineInfoPlaySignalNet		INTEGER			
              	}
              	
	voipLineInfoSipLocalUri OBJECT-TYPE
	SYNTAX DisplayString
	MAX-ACCESS read-only
	STATUS current
	DESCRIPTION
		""
	::= { voipLineInfoEntry 1 }
	
	voipLineInfoSipRemoteUri OBJECT-TYPE
	SYNTAX DisplayString
	MAX-ACCESS read-only
	STATUS current
	DESCRIPTION
		""
	::= { voipLineInfoEntry 2 }
	
	voipLineInfoRtpTxCodecType OBJECT-TYPE
	SYNTAX DisplayString
	MAX-ACCESS read-only
	STATUS current
	DESCRIPTION
		""
	::= { voipLineInfoEntry 3 }
	
	voipLineInfoRtpRxCodecType OBJECT-TYPE
	SYNTAX DisplayString
	MAX-ACCESS read-only
	STATUS current
	DESCRIPTION
		""
	::= { voipLineInfoEntry 4 }
	
	voipLineInfoRtpTxPt OBJECT-TYPE
	SYNTAX INTEGER
	MAX-ACCESS read-only
	STATUS current
	DESCRIPTION
		"1: g711mu(0)
		2: g711a(8)
		3: g723(4)
		4: g729(18)
		5: g726-16(96)
		6: g726-24(97)
		7: g728-32(98)
		8: g728-40(99)"
	::= { voipLineInfoEntry 5 }
	
	voipLineInfoRtpRxPt OBJECT-TYPE
	SYNTAX INTEGER
	MAX-ACCESS read-only
	STATUS current
	DESCRIPTION
		"1: g711mu(0)
		2: g711a(8)
		3: g723(4)
		4: g729(18)
		5: g726-16(96)
		6: g726-24(97)
		7: g728-32(98)
		8: g728-40(99)"
	::= { voipLineInfoEntry 6 }
	
	voipLineInfoRtpLocalIp OBJECT-TYPE
	SYNTAX IpAddress
	MAX-ACCESS read-only
	STATUS current
	DESCRIPTION
		""
	::= { voipLineInfoEntry 7 }
	
	voipLineInfoRtpRemoteIp OBJECT-TYPE
	SYNTAX IpAddress
	MAX-ACCESS read-only
	STATUS current
	DESCRIPTION
		""
	::= { voipLineInfoEntry 8 }
	
	voipLineInfoRtpLocalPort OBJECT-TYPE
	SYNTAX INTEGER
	MAX-ACCESS read-only
	STATUS current
	DESCRIPTION
		""
	::= { voipLineInfoEntry 9 }
	
	voipLineInfoRtpRemotePort OBJECT-TYPE
	SYNTAX INTEGER
	MAX-ACCESS read-only
	STATUS current
	DESCRIPTION
		""
	::= { voipLineInfoEntry 10 }
	
	voipLineInfoLastCidMode OBJECT-TYPE
	SYNTAX INTEGER {
			none(0),
			fsk(1),
			dtmf(2)
		}
	MAX-ACCESS read-only
	STATUS current
	DESCRIPTION
		""
	::= { voipLineInfoEntry 11 }
	
	voipLineInfoPlaySignalTel OBJECT-TYPE
	SYNTAX INTEGER {
			none(0),
			dial-tone(1),
			ringback-tone(2),
			busy-tone(3),
			congestion-tone(4),
			special-dial-tone(5),
			warning-tone(6),
			beep-tone(7),
			call-waiting-tone1(8),
			howler-tone(9),
			confirmation-tone(10),
			holding-tone(11),
			mwi-tone(12),
			enable-dtmf-detect(13),
			disable-dtmf-detect(14),
			mute(15),
			call-waiting-tone2(16),
			dtmf-tone(17),
			recall-dial-tone(18),
			stop-ring(19),
			ring(20)
		}
	MAX-ACCESS read-only
	STATUS current
	DESCRIPTION
		""
	::= { voipLineInfoEntry 12 }
	
	voipLineInfoPlaySignalNet OBJECT-TYPE
	SYNTAX INTEGER {
			none(0),
			dial-tone(1),
			ringback-tone(2),
			busy-tone(3),
			congestion-tone(4),
			special-dial-tone(5),
			warning-tone(6),
			beep-tone(7),
			call-waiting-tone1(8),
			howler-tone(9),
			confirmation-tone(10),
			holding-tone(11),
			mwi-tone(12),
			enable-dtmf-detect(13),
			disable-dtmf-detect(14),
			mute(15),
			call-waiting-tone2(16),
			dtmf-tone(17),
			recall-dial-tone(18),
			stop-ring(19),
			ring(20)
		}
	MAX-ACCESS read-only
	STATUS current
	DESCRIPTION
		""
	::= { voipLineInfoEntry 13 }

-- voipH248StatTable

        voipH248StatTable OBJECT-TYPE
        SYNTAX SEQUENCE OF VoipH248StatEntry
        MAX-ACCESS not-accessible
        STATUS current
        DESCRIPTION
        	"The table displays registration status of media gateway.
        	This table is supported by R5.01 and later versions."
        ::= { voipStats 3 }

        voipH248StatEntry OBJECT-TYPE
        SYNTAX VoipH248StatEntry
        MAX-ACCESS not-accessible
        STATUS current
        DESCRIPTION
        	"An entry of voipH248StatTable."
        INDEX { voipH248StatSlot, voipH248StatMgName }
        ::= { voipH248StatTable 1 }

        VoipH248StatEntry ::=
        	SEQUENCE {
                  	voipH248StatSlot			INTEGER,
                  	voipH248StatMgName			DisplayString,
                  	voipH248StatMgState			INTEGER		
              	}
              	
	voipH248StatSlot OBJECT-TYPE
	SYNTAX INTEGER
	MAX-ACCESS read-only
	STATUS current
	DESCRIPTION
		"Line card slot number."
	::= { voipH248StatEntry 1 }
	
	voipH248StatMgName OBJECT-TYPE
	SYNTAX DisplayString
	MAX-ACCESS read-only
	STATUS current
	DESCRIPTION
		"MG name."
	::= { voipH248StatEntry 2 }		                

	voipH248StatMgState OBJECT-TYPE
	SYNTAX INTEGER {
			disabled(1),
    			registering(2),
    			registered(3),
    			unregistering(4),
    			unregistered(5),
    			inactivity-timeout(6),
    			activity-back(7),
    			disconnected(8),
    			disabled-by-mgc(9),
    			unknown(10)
		}
	MAX-ACCESS read-only
	STATUS current
	DESCRIPTION
		"MG state."
	::= { voipH248StatEntry 3 }
	
-- voipSipStatTable

        voipSipStatTable OBJECT-TYPE
        SYNTAX SEQUENCE OF VoipSipStatEntry
        MAX-ACCESS not-accessible
        STATUS current
        DESCRIPTION
        	"The table displays the status of SIP proxy server while oolocal calloo feature is enabled.
        	This table is supported by R5.01 and later versions."
        ::= { voipStats 4 }

        voipSipStatEntry OBJECT-TYPE
        SYNTAX VoipSipStatEntry
        MAX-ACCESS not-accessible
        STATUS current
        DESCRIPTION
        	"An entry of voipSipStatTable."
        INDEX { voipSipStatSlot, voipSipStatProxyIndex }
        ::= { voipSipStatTable 1 }

        VoipSipStatEntry ::=
        	SEQUENCE {
                  	voipSipStatSlot			INTEGER,
                  	voipSipStatProxyIndex		INTEGER,
                  	voipSipStatProxySvr		DisplayString,
                  	voipSipStatProxyPort		INTEGER,
                  	voipSipStatState		INTEGER		
              	}
              	
	voipSipStatSlot OBJECT-TYPE
	SYNTAX INTEGER
	MAX-ACCESS read-only
	STATUS current
	DESCRIPTION
		"Line card slot number."
	::= { voipSipStatEntry 1 }
	
	voipSipStatProxyIndex OBJECT-TYPE
	SYNTAX INTEGER
	MAX-ACCESS read-only
	STATUS current
	DESCRIPTION
		""
	::= { voipSipStatEntry 2 }
	
	voipSipStatProxySvr OBJECT-TYPE
	SYNTAX DisplayString
	MAX-ACCESS read-only
	STATUS current
	DESCRIPTION
		"Proxy server IP or proxy server doamin name."
	::= { voipSipStatEntry 3 }
	
	voipSipStatProxyPort OBJECT-TYPE
	SYNTAX INTEGER
	MAX-ACCESS read-only
	STATUS current
	DESCRIPTION
		"Proxy server port."
	::= { voipSipStatEntry 4 }
	
	voipSipStatState OBJECT-TYPE
	SYNTAX INTEGER {
			lost(1),
			alive(2),
			unknown(3)
		}
	MAX-ACCESS read-only
	STATUS current
	DESCRIPTION
		""
	::= { voipSipStatEntry 5 }

-- voipH248InterfaceStatTable 

        voipH248InterfaceStatTable OBJECT-TYPE
        SYNTAX SEQUENCE OF VoipH248InterfaceStatEntry
        MAX-ACCESS not-accessible
        STATUS current
        DESCRIPTION
        	""
        ::= { voipStats 5 }

        voipH248InterfaceStatEntry OBJECT-TYPE
        SYNTAX VoipH248InterfaceStatEntry
        MAX-ACCESS not-accessible
        STATUS current
        DESCRIPTION
        	"An entry of voipH248InterfaceStatTable."
        INDEX { voipH248InterfaceStatId }
        ::= { voipH248InterfaceStatTable 1 }

        VoipH248InterfaceStatEntry ::=
        	SEQUENCE {
                  	voipH248InterfaceStatId 			INTEGER,
                  	voipH248InterfaceStatMgState 		INTEGER,
                  	voipH248InterfaceStatPrimarySlot 		INTEGER,
                  	voipH248InterfaceStatSecondarySlot 		INTEGER,
                  	voipH248InterfaceStatPrimaryProtectionState 		INTEGER,
                  	voipH248InterfaceStatSecondaryProtectionState 		INTEGER,
                  	voipH248InterfaceStatRedundantState 		INTEGER		
              	}
              	
		voipH248InterfaceStatId OBJECT-TYPE
			SYNTAX INTEGER
			MAX-ACCESS read-only
			STATUS current
			DESCRIPTION
				"Line card slot number."
			::= { voipH248InterfaceStatEntry 1 }
						
		voipH248InterfaceStatMgState OBJECT-TYPE
			SYNTAX INTEGER {
					disable(1),
					registering(2),
					registered(3),     
					unregistering(4),
					unregistered(5),
					inactivity-timeout(6),
					activity-back(7),
					disconnected(8), 
					disabled-by-MGC(9)
			}
			MAX-ACCESS read-only
			STATUS current
			DESCRIPTION
				"Mg State"
			::= { voipH248InterfaceStatEntry 2 }
			
			voipH248InterfaceStatPrimarySlot OBJECT-TYPE
			SYNTAX INTEGER
			MAX-ACCESS read-only
			STATUS current
			DESCRIPTION
				"Primary Slot"
			::= { voipH248InterfaceStatEntry 3 }
			
			voipH248InterfaceStatSecondarySlot OBJECT-TYPE
			SYNTAX INTEGER
			MAX-ACCESS read-only
			STATUS current
			DESCRIPTION
				"Secondary Slot"
			::= { voipH248InterfaceStatEntry 4 }
			   	    
		voipH248InterfaceStatPrimaryProtectionState  OBJECT-TYPE
			SYNTAX INTEGER {
					invalid(1),
					active(2),
					standby(3)
			}
			MAX-ACCESS read-only
			STATUS current
			DESCRIPTION
				"Primary Protection State"
			::= { voipH248InterfaceStatEntry 5 }
			
			voipH248InterfaceStatSecondaryProtectionState  OBJECT-TYPE
			SYNTAX INTEGER {
					invalid(1),
					active(2),
					standby(3)
			}
			MAX-ACCESS read-only
			STATUS current
			DESCRIPTION
				"Secondary Protection State"
			::= { voipH248InterfaceStatEntry 6 }
		
		voipH248InterfaceStatRedundantState   OBJECT-TYPE
			SYNTAX INTEGER {
					out-of-sync(1),
					authorization(2),
					synchronizing(3),
					in-service(4)
			}
			MAX-ACCESS read-only
			STATUS current
			DESCRIPTION
				"Redundant State"
			::= { voipH248InterfaceStatEntry 7}

-- voipH248MediaStatTable  

        voipH248MediaStatTable OBJECT-TYPE
        SYNTAX SEQUENCE OF VoipH248MediaStatEntry
        MAX-ACCESS not-accessible
        STATUS current
        DESCRIPTION
        	""
        ::= { voipStats 6 }

        voipH248MediaStatEntry OBJECT-TYPE
        SYNTAX VoipH248MediaStatEntry
        MAX-ACCESS not-accessible
        STATUS current
        DESCRIPTION
        	"An entry of voipH248MediaStatTable."
        INDEX { voipH248MediaStatInterfaceId, voipH248MediaStatSlaveId }
        ::= { voipH248MediaStatTable 1 }

        VoipH248MediaStatEntry ::=
        	SEQUENCE {
                  	voipH248MediaStatInterfaceId	INTEGER,
                	voipH248MediaStatSlaveId  	INTEGER,
               		voipH248MediaStatSlaveIp   	INTEGER,
               		voipH248MediaStatMgmtInbandIp   INTEGER,
               		voipH248MediaStatMgmtOutbandIp  INTEGER,
               		voipH248MediaStatSlotId    	INTEGER,
               		voipH248MediaStatPortCount    	INTEGER,
               		voipH248MediaStatState   	INTEGER
              	}
              	
		voipH248MediaStatInterfaceId  OBJECT-TYPE
			SYNTAX INTEGER
			MAX-ACCESS read-only
			STATUS current
			DESCRIPTION
				"Interface ID."
			::= { voipH248MediaStatEntry 1 }
						
		voipH248MediaStatSlaveId  OBJECT-TYPE
			SYNTAX INTEGER
			MAX-ACCESS read-only
			STATUS current
			DESCRIPTION
				"Media ID"
			::= { voipH248MediaStatEntry 2 }
			   	    
		voipH248MediaStatSlaveIp   OBJECT-TYPE
			SYNTAX INTEGER
			MAX-ACCESS read-only
			STATUS current
			DESCRIPTION
				"Media Ip"
			::= { voipH248MediaStatEntry 3 }
		
		voipH248MediaStatMgmtInbandIp    OBJECT-TYPE
			SYNTAX INTEGER
			MAX-ACCESS read-only
			STATUS current
			DESCRIPTION
				"Management Inband Ip"
			::= { voipH248MediaStatEntry 4 }

		voipH248MediaStatMgmtOutbandIp    OBJECT-TYPE
			SYNTAX INTEGER
			MAX-ACCESS read-only
			STATUS current
			DESCRIPTION
				"Management Onband Ip"
			::= { voipH248MediaStatEntry 5 }

		voipH248MediaStatSlotId    OBJECT-TYPE
			SYNTAX INTEGER
			MAX-ACCESS read-only
			STATUS current
			DESCRIPTION
				"slot id"
			::= { voipH248MediaStatEntry 6 }
 
 		voipH248MediaStatPortCount    OBJECT-TYPE
			SYNTAX INTEGER
			MAX-ACCESS read-only
			STATUS current
			DESCRIPTION
				"port count"
			::= { voipH248MediaStatEntry 7 }   
			

		voipH248MediaStatState     OBJECT-TYPE
			SYNTAX INTEGER
			{
				unregistered(1),
				registered(2),
				invalid(3),
				unknown(4)
			}
			MAX-ACCESS read-only
			STATUS current
			DESCRIPTION
				"state"
			::= { voipH248MediaStatEntry 8 }   
	
	
-- voipH248TerminationStatTable  
        
voipH248TerminationStatTable OBJECT-TYPE
        SYNTAX SEQUENCE OF VoipH248TerminationStatEntry
        MAX-ACCESS not-accessible
        STATUS current
        DESCRIPTION
        	""
        ::= { voipStats 7 }
        
        voipH248TerminationStatEntry OBJECT-TYPE
        SYNTAX VoipH248TerminationStatEntry  
        MAX-ACCESS not-accessible
        STATUS current
        DESCRIPTION
        	"An entry of voipH248TerminationStatStateTable."
        INDEX { voipH248TerminationStatStateId,voipH248TerminationStatStateMediaId,voipH248TerminationStatStatePortNumber }
        ::= { voipH248TerminationStatTable 1 }

        VoipH248TerminationStatEntry ::=
        SEQUENCE {
                voipH248TerminationStatStateId           INTEGER,
                voipH248TerminationStatStateMediaId      INTEGER,
                voipH248TerminationStatStatePortNumber   INTEGER, 
               	voipH248TerminationStatName 			DisplayString,
              	voipH248TerminationStatPhoneState   		INTEGER,
        	voipH248TerminationStatCallServiceState    	INTEGER
        }

	voipH248TerminationStatStateId OBJECT-TYPE
	SYNTAX INTEGER
	MAX-ACCESS read-only
	STATUS current
	DESCRIPTION
	    "Interface Id of the termination."
	::= { voipH248TerminationStatEntry 1 }
	
	voipH248TerminationStatStateMediaId OBJECT-TYPE
	SYNTAX INTEGER
	MAX-ACCESS read-only
	STATUS current
	DESCRIPTION
	    "Media Card Id of the termination."
	::= { voipH248TerminationStatEntry 2 }
	
	voipH248TerminationStatStatePortNumber OBJECT-TYPE
	SYNTAX INTEGER
	MAX-ACCESS read-only
	STATUS current
	DESCRIPTION
	    "Port number the termination."
	::= { voipH248TerminationStatEntry 3 }

              	
	voipH248TerminationStatName  OBJECT-TYPE
	SYNTAX DisplayString
	MAX-ACCESS read-only
	STATUS current
	DESCRIPTION
		"Termination Name."
	::= { voipH248TerminationStatEntry 4 }
						
	voipH248TerminationStatPhoneState  OBJECT-TYPE
	SYNTAX INTEGER{
			disabled(1),
			on-hook(2),
			off-hook(3),						
			ringing(4),					
			testing(5),
			power-cut-down(6),
			fault(7),						
			bad(8),					
			uninitialized(9),						
			unknown(10)
	}
	MAX-ACCESS read-only
	STATUS current
	DESCRIPTION
		"Phone State"
	::= { voipH248TerminationStatEntry 5 }
			   	                                 
	voipH248TerminationStatCallServiceState   OBJECT-TYPE
	SYNTAX INTEGER{
			disabled(1),
			out-of-service(2),
			idle(3),
			waiting-for-dialing(4),
			dialing-out(5),
			ringing(6),
			conversation-caller(7),
			conversation-callee(8),
			fax-modem-caller(9),
			fax-modem-callee(10),
			waiting-for-on-hook(13),
			dialing-timeout(14),
			alerting-off-hook(15),
			power-cut-down(16),
			unknown(17)
	}
	MAX-ACCESS read-only
	STATUS current
	DESCRIPTION
		"Call Service State"
	::= { voipH248TerminationStatEntry 6 }

-- voipH248TerminationStatQuery		
	voipH248TerminationStatQuery	OBJECT IDENTIFIER ::= { voipStats 8 }
       
        voipH248TerminationStatQueryInterfaceId OBJECT-TYPE
        SYNTAX INTEGER
        MAX-ACCESS read-write
        STATUS current
        DESCRIPTION
				"Interface Id"
        ::= { voipH248TerminationStatQuery 1 }
        
        voipH248TerminationStatQueryTerminationName OBJECT-TYPE
        SYNTAX DisplayString (SIZE(1..31))
        MAX-ACCESS read-write
        STATUS current
        DESCRIPTION
				"Termination Name"
        ::= { voipH248TerminationStatQuery 2 }
        
        voipH248TerminationStatQuerySlaveId OBJECT-TYPE
        SYNTAX INTEGER
        MAX-ACCESS read-only
        STATUS current
        DESCRIPTION
        "Slave Id"
        ::= { voipH248TerminationStatQuery 3 }

        voipH248TerminationStatQuerySlaveIp OBJECT-TYPE
        SYNTAX IpAddress
        MAX-ACCESS read-only
       	STATUS current
        DESCRIPTION
       	"Slave Ip"
        ::= { voipH248TerminationStatQuery 4 }
               		
        voipH248TerminationStatQueryMgmtInbandIp OBJECT-TYPE
        SYNTAX IpAddress
        MAX-ACCESS read-only
       	STATUS current
        DESCRIPTION
        "Management Inband Ip"
        ::= { voipH248TerminationStatQuery 5 }
        
        voipH248TerminationStatQueryMgmtOutbandIp OBJECT-TYPE
        SYNTAX IpAddress
        MAX-ACCESS read-only
       	STATUS current
        DESCRIPTION
        "Management Outband Ip"
        ::= { voipH248TerminationStatQuery 6 }
	
	     voipH248TerminationStatQuerySlotId OBJECT-TYPE
        SYNTAX INTEGER
        MAX-ACCESS read-only
        STATUS current
        DESCRIPTION
        "Slot Id"
        ::= { voipH248TerminationStatQuery 7 }
        
        voipH248TerminationStatQueryPortCount OBJECT-TYPE
        SYNTAX INTEGER
        MAX-ACCESS read-only
        STATUS current
        DESCRIPTION
        "Port Count"
        ::= { voipH248TerminationStatQuery 8 }
        
        voipH248TerminationStatQueryState OBJECT-TYPE
        SYNTAX INTEGER{
			unregistered(1),
			registered(2),
			invalid(3),
			unknown(4)
		}
        MAX-ACCESS read-only
        STATUS current
        DESCRIPTION
      	"State"
        ::= { voipH248TerminationStatQuery 9 }
        
        voipH248TerminationStatQueryPortNumber OBJECT-TYPE
        SYNTAX INTEGER
        MAX-ACCESS read-only
        STATUS current
        DESCRIPTION
        "Port Number"
        ::= { voipH248TerminationStatQuery 10 }
        
        voipH248TerminationStatQueryPhoneState OBJECT-TYPE
       	SYNTAX INTEGER{
					disabled(1),
					on-hook(2),
					off-hook(3),						
					ringing(4),					
					testing(5),
					power-cut-down(6),
					fault(7),						
					bad(8),					
					uninitialized(9),						
					unknown(10)
			}
        MAX-ACCESS read-only
        STATUS current
        DESCRIPTION
        "Phone State"
        ::= { voipH248TerminationStatQuery 11 }
        
       	voipH248TerminationStatQueryCallServiceState OBJECT-TYPE
        	SYNTAX INTEGER{
					disabled(1),
					out-of-service(2),
					idle(3),						
					waiting-for-dialing(4),					
					ringing(5),
					conversation-caller(6),
					conversation-callee(7),						
					fax-modem-caller(8),
					fax-modem-callee(9),
					waiting-for-on-hook(12),
					dialing-timeout(13),					
					alerting-off-hook(14),
					power-cut-down(15)
			}
		MAX-ACCESS read-only
        STATUS current
        DESCRIPTION
        "CallService State"
        ::= { voipH248TerminationStatQuery 12 }
 	

-- voipRtpStatTable  
        
voipRtpStatTable OBJECT-TYPE
        SYNTAX SEQUENCE OF VoipRtpStatEntry
        MAX-ACCESS not-accessible
        STATUS current
        DESCRIPTION
        	""
        ::= { voipStats 9 }
        
        voipRtpStatEntry OBJECT-TYPE
        SYNTAX VoipRtpStatEntry  
        MAX-ACCESS not-accessible
        STATUS current
        DESCRIPTION
        	"An entry of voipRtpStatTable."
        INDEX { voipIfIndex }
        ::= { voipRtpStatTable 1 }

        VoipRtpStatEntry ::=
        SEQUENCE {
                voipRtpStatTxRate           INTEGER,
                voipRtpStatRxRate      		INTEGER,
                voipRtpStatTxPktCnt   		Counter64, 
               	voipRtpStatRxPktCnt 		Counter64,
              	voipRtpStatTxFracLost   	INTEGER,
        		voipRtpStatRxFracLost    	INTEGER,
        		voipRtpStatTxJitter			Counter64,
        		voipRtpStatRxJitter			Counter64,
        		voipRtpStatTxAvgDelay		Counter64,
        		voipRtpStatRxAvgDelay		Counter64
        }

	voipRtpStatTxRate OBJECT-TYPE
	SYNTAX INTEGER
	MAX-ACCESS read-only
	STATUS current
	DESCRIPTION
	    "real-time RTP tx packet rate in bps."
	::= { voipRtpStatEntry 1 }
	
	voipRtpStatRxRate OBJECT-TYPE
	SYNTAX INTEGER
	MAX-ACCESS read-only
	STATUS current
	DESCRIPTION
	    "real-time RTP rx packet rate in bps."
	::= { voipRtpStatEntry 2 }
	
	voipRtpStatTxPktCnt OBJECT-TYPE
	SYNTAX Counter64
	MAX-ACCESS read-only
	STATUS current
	DESCRIPTION
	    "total RTP tx packet counter for current/last call."
	::= { voipRtpStatEntry 3 }

              	
	voipRtpStatRxPktCnt  OBJECT-TYPE
	SYNTAX Counter64
	MAX-ACCESS read-only
	STATUS current
	DESCRIPTION
		"total RTP rx packet counter for current/last call."
	::= { voipRtpStatEntry 4 }
						
	voipRtpStatTxFracLost  OBJECT-TYPE
	SYNTAX INTEGER
	MAX-ACCESS read-only
	STATUS current
	DESCRIPTION
		"RTP Tx packet lost in percentage"
	::= { voipRtpStatEntry 5 }
			   	                                 
	voipRtpStatRxFracLost   OBJECT-TYPE
	SYNTAX INTEGER
	MAX-ACCESS read-only
	STATUS current
	DESCRIPTION
		"RTP Rx packet lost in percentage"
	::= { voipRtpStatEntry 6 }	
	
	voipRtpStatTxJitter   OBJECT-TYPE
	SYNTAX Counter64
	MAX-ACCESS read-only
	STATUS current
	DESCRIPTION
		"TX jitter in micro-second"
	::= { voipRtpStatEntry 7 }
	
	voipRtpStatRxJitter   OBJECT-TYPE
	SYNTAX Counter64
	MAX-ACCESS read-only
	STATUS current
	DESCRIPTION
		"Rx jitter in micro-second"
	::= { voipRtpStatEntry 8 }
	
	voipRtpStatTxAvgDelay   OBJECT-TYPE
	SYNTAX Counter64
	MAX-ACCESS read-only
	STATUS current
	DESCRIPTION
		"Average Tx delay in ms"
	::= { voipRtpStatEntry 9 }
	
	voipRtpStatRxAvgDelay   OBJECT-TYPE
	SYNTAX Counter64
	MAX-ACCESS read-only
	STATUS current
	DESCRIPTION
		"Average Rx delay in ms"
	::= { voipRtpStatEntry 10 }	
	
-- voipCdrStat
	voipCdrStat	OBJECT IDENTIFIER ::= { voipStats 10 }

-- voipCdrStatFilter	
	voipCdrStatFilter	OBJECT IDENTIFIER ::= { voipCdrStat 1 }		       
        
    voipCdrStatFilterInterface OBJECT-TYPE
    SYNTAX INTEGER
    MAX-ACCESS read-write
    STATUS current
    DESCRIPTION
		"Interface id."
    ::= { voipCdrStatFilter 1 }
    
    voipCdrStatFilterIndexEnable OBJECT-TYPE
    SYNTAX INTEGER
    MAX-ACCESS read-write
    STATUS current
    DESCRIPTION
		"Set 0 to clear voipCdrStatFilterIndex. 
		It will show 1 if voipCdrStatFilterIndex had been set before."
    ::= { voipCdrStatFilter 2 }
    
    voipCdrStatFilterIndex OBJECT-TYPE
    SYNTAX INTEGER
    MAX-ACCESS read-write
    STATUS current
    DESCRIPTION
		"Index filter."
    ::= { voipCdrStatFilter 3 }
    
    voipCdrStatFilterSlotPortEnable OBJECT-TYPE
    SYNTAX INTEGER
    MAX-ACCESS read-write
    STATUS current
    DESCRIPTION
		"Set 0 to clear voipCdrStatFilterSlot and voipCdrStatFilterPort. 
		It will show 1 if voipCdrStatFilterSlot and voipCdrStatFilterPort had been set before."
    ::= { voipCdrStatFilter 4 } 
    
    voipCdrStatFilterSlot OBJECT-TYPE
    SYNTAX INTEGER
    MAX-ACCESS read-write
    STATUS current
    DESCRIPTION
		"Slot filter."
    ::= { voipCdrStatFilter 5 }
    
    voipCdrStatFilterPort OBJECT-TYPE
    SYNTAX INTEGER
    MAX-ACCESS read-write
    STATUS current
    DESCRIPTION
		"Port filter, 0 mean select all port"
    ::= { voipCdrStatFilter 6 }
    
    voipCdrStatFilterRtpElpasedTimeEnable OBJECT-TYPE
    SYNTAX INTEGER
    MAX-ACCESS read-write
    STATUS current
    DESCRIPTION
		"Set 0 to clear voipCdrStatFilterRtpElpasedTimeMin and voipCdrStatFilterRtpElpasedTimeMax. It will show 1 if any of them had been set before."
    ::= { voipCdrStatFilter 7 }
    
    voipCdrStatFilterRtpElpasedTimeMin OBJECT-TYPE
    SYNTAX INTEGER
    MAX-ACCESS read-write
    STATUS current
    DESCRIPTION
		"in unit of second"
    ::= { voipCdrStatFilter 8 }
    
    voipCdrStatFilterRtpElpasedTimeMax OBJECT-TYPE
    SYNTAX INTEGER
    MAX-ACCESS read-write
    STATUS current
    DESCRIPTION
		"in unit of second"
    ::= { voipCdrStatFilter 9 }
    
    voipCdrStatFilterTelEnable OBJECT-TYPE
    SYNTAX INTEGER
    MAX-ACCESS read-write
    STATUS current
    DESCRIPTION
		"Set 0 to clear voipCdrStatFilterTel. It will show 1 if voipCdrStatFilterTel had been set before."
    ::= { voipCdrStatFilter 10 }
    
    voipCdrStatFilterTel OBJECT-TYPE
    SYNTAX DisplayString
    MAX-ACCESS read-write
    STATUS current
    DESCRIPTION
		"Telephone number filter, max length is 24."
    ::= { voipCdrStatFilter 11 }
    
    voipCdrStatFilterOffhookEnable OBJECT-TYPE
    SYNTAX INTEGER
    MAX-ACCESS read-write
    STATUS current
    DESCRIPTION
		"Set 0 to clear voipCdrStatFilterOffhookDateMin, voipCdrStatFilterOffhookTimeMin, voipCdrStatFilterOffhookDateMax,
		and voipCdrStatFilterOffhookDateMax . It will show 1 if any of them had been set before."
    ::= { voipCdrStatFilter 12 }
    
    voipCdrStatFilterOffhookDateMin OBJECT-TYPE
    SYNTAX INTEGER
    MAX-ACCESS read-write
    STATUS current
    DESCRIPTION
		"Minimum offhook date filter, format example:20120101"
    ::= { voipCdrStatFilter 13 }
    
    voipCdrStatFilterOffhookTimeMin OBJECT-TYPE
    SYNTAX INTEGER
    MAX-ACCESS read-write
    STATUS current
    DESCRIPTION
		"Minimum offhook time filter, format example:235959"
    ::= { voipCdrStatFilter 14 }
    
    voipCdrStatFilterOffhookDateMax OBJECT-TYPE
    SYNTAX INTEGER
    MAX-ACCESS read-write
    STATUS current
    DESCRIPTION
		"Maximum offhook date filter, format example:20120101"
    ::= { voipCdrStatFilter 15 }
    
    voipCdrStatFilterOffhookTimeMax OBJECT-TYPE
    SYNTAX INTEGER
    MAX-ACCESS read-write
    STATUS current
    DESCRIPTION
		"Maximum offhook time filter, format example:235959"
    ::= { voipCdrStatFilter 16 }
    
    voipCdrStatFilterCodeEnable OBJECT-TYPE
    SYNTAX INTEGER
    MAX-ACCESS read-write
    STATUS current
    DESCRIPTION
		"Set 0 to clear voipCdrStatFilterCode. It will show 1 if voipCdrStatFilterCode had been set before."
    ::= { voipCdrStatFilter 17 }
    
    voipCdrStatFilterCode OBJECT-TYPE
    SYNTAX INTEGER
    MAX-ACCESS read-write
    STATUS current
    DESCRIPTION
		"Code filter. It is a bit map of the call state record.
		bit 6(0x20): offhook
		bit 5(0x10): remote ringback tone
		bit 4(0x08): local ringback tone
		bit 3(0x04): dial tone
		bit 2(0x02): ring
		bit 1(0x01): rtp"
    ::= { voipCdrStatFilter 18 } 
    
    voipCdrStatFilterErrCodeEnable OBJECT-TYPE
    SYNTAX INTEGER
    MAX-ACCESS read-write
    STATUS current
    DESCRIPTION
		"Set 1 to ebable H.248 errcode filter. Set 0 to disable it."
    ::= { voipCdrStatFilter 19 }
    
-- voipCdrStatResultTable	
	voipCdrStatResultTable OBJECT-TYPE
    SYNTAX SEQUENCE OF VoipCdrStatResultEntry
    MAX-ACCESS not-accessible
    STATUS current
    DESCRIPTION
        ""
    ::= { voipCdrStat 2 }
        
    voipCdrStatResultEntry OBJECT-TYPE
    SYNTAX VoipCdrStatResultEntry  
    MAX-ACCESS not-accessible
    STATUS current
    DESCRIPTION
      "An entry of voipCdrStatResultTable."
    INDEX { voipCdrStatResultIndex }
      ::= { voipCdrStatResultTable 1 }

    VoipCdrStatResultEntry ::=
    SEQUENCE {
            voipCdrStatResultIndex           		INTEGER,
            voipCdrStatResultSlot					INTEGER,
            voipCdrStatResultPort      				INTEGER,
            voipCdrStatResultTermName   			DisplayString, 
            voipCdrStatResultLineDirection 			INTEGER,
            voipCdrStatResultLocalNumber   			DisplayString,
        	voipCdrStatResultRemoteNumber    		DisplayString,
        	voipCdrStatResultOffHookDatetime		DisplayString,
        	voipCdrStatResultOnHookDatetime			DisplayString,
        	voipCdrStatResultRingStartDatetime		DisplayString,
        	voipCdrStatResultRingStopDatetime		DisplayString,
        	voipCdrStatResultRtpStartDatetime		DisplayString,
        	voipCdrStatResultRtpStopDatetime		DisplayString,
        	 voipCdrStatResultRtpElapsedTime		INTEGER,
        	voipCdrStatResultTxRate					INTEGER,
        	voipCdrStatResultRxRate					INTEGER,
        	voipCdrStatResultTxPktCnt				Counter64,
        	voipCdrStatResultRxPktCnt				Counter64,
        	voipCdrStatResultTxFracLost				INTEGER,
        	voipCdrStatResultRxFracLost				INTEGER,
        	voipCdrStatResultTxJitter				Counter64,
        	voipCdrStatResultRxJitter				Counter64,
        	voipCdrStatResultTxAvgDelay				Counter64,
        	voipCdrStatResultRxAvgDelay				Counter64,
        	voipCdrStatResultCode					INTEGER,
        	voipCdrStatResultErrCode				INTEGER,
        	voipCdrStatResultTerminationCause		DisplayString
    }

	voipCdrStatResultIndex OBJECT-TYPE
	SYNTAX INTEGER
	MAX-ACCESS read-only
	STATUS current
	DESCRIPTION
	    "Index of record. Index of the newest record will show first."
	::= { voipCdrStatResultEntry 1 }
	
	voipCdrStatResultSlot OBJECT-TYPE
	SYNTAX INTEGER
	MAX-ACCESS read-only
	STATUS current
	DESCRIPTION
	    "Record Slot"
	::= { voipCdrStatResultEntry 2 } 
	
	voipCdrStatResultPort OBJECT-TYPE
	SYNTAX INTEGER
	MAX-ACCESS read-only
	STATUS current
	DESCRIPTION
	    "Record port"
	::= { voipCdrStatResultEntry 3 }
	
	voipCdrStatResultTermName OBJECT-TYPE
	SYNTAX DisplayString
	MAX-ACCESS read-only
	STATUS current
	DESCRIPTION
	    "The termination name used for this record."
	::= { voipCdrStatResultEntry 4 }

	voipCdrStatResultLineDirection OBJECT-TYPE
	SYNTAX INTEGER
	MAX-ACCESS read-only
	STATUS current
	DESCRIPTION
	    "1: Call in
	    2: Dial out"
	::= { voipCdrStatResultEntry 5 } 
	
	voipCdrStatResultLocalNumber OBJECT-TYPE
	SYNTAX DisplayString
	MAX-ACCESS read-only
	STATUS current
	DESCRIPTION
	    "The local phone number set by manager and use for localcall"
	::= { voipCdrStatResultEntry 6 } 
	
	voipCdrStatResultRemoteNumber OBJECT-TYPE
	SYNTAX DisplayString
	MAX-ACCESS read-only
	STATUS current
	DESCRIPTION
	    "The remote phone number which assigned by mgc"
	::= { voipCdrStatResultEntry 7 }
	
	voipCdrStatResultOffHookDatetime OBJECT-TYPE
	SYNTAX DisplayString
	MAX-ACCESS read-only
	STATUS current
	DESCRIPTION
	    "In format YYYYMMDDhhmmss"
	::= { voipCdrStatResultEntry 8 }
	
	voipCdrStatResultOnHookDatetime OBJECT-TYPE
	SYNTAX DisplayString
	MAX-ACCESS read-only
	STATUS current
	DESCRIPTION
	    "In format YYYYMMDDhhmmss"
	::= { voipCdrStatResultEntry 9 }
	
	voipCdrStatResultRingStartDatetime OBJECT-TYPE
	SYNTAX DisplayString
	MAX-ACCESS read-only
	STATUS current
	DESCRIPTION
	    "In format YYYYMMDDhhmmss"
	::= { voipCdrStatResultEntry 10 } 
	
	voipCdrStatResultRingStopDatetime OBJECT-TYPE
	SYNTAX DisplayString
	MAX-ACCESS read-only
	STATUS current
	DESCRIPTION
	    "In format YYYYMMDDhhmmss"
	::= { voipCdrStatResultEntry 11 }
	
	voipCdrStatResultRtpStartDatetime OBJECT-TYPE
	SYNTAX DisplayString
	MAX-ACCESS read-only
	STATUS current
	DESCRIPTION
	    "In format YYYYMMDDhhmmss"
	::= { voipCdrStatResultEntry 12 }
	
	voipCdrStatResultRtpStopDatetime OBJECT-TYPE
	SYNTAX DisplayString
	MAX-ACCESS read-only
	STATUS current
	DESCRIPTION
	    "In format YYYYMMDDhhmmss"
	::= { voipCdrStatResultEntry 13 } 
	
	 voipCdrStatResultRtpElapsedTime OBJECT-TYPE
	SYNTAX INTEGER
	MAX-ACCESS read-only
	STATUS current
	DESCRIPTION
	    "In unit of second"
	::= { voipCdrStatResultEntry 14 } 
	
	voipCdrStatResultTxRate OBJECT-TYPE
	SYNTAX INTEGER
	MAX-ACCESS read-only
	STATUS current
	DESCRIPTION
	    "real-time RTP tx packet rate in bps"
	::= { voipCdrStatResultEntry 15 }
	
	voipCdrStatResultRxRate OBJECT-TYPE
	SYNTAX INTEGER
	MAX-ACCESS read-only
	STATUS current
	DESCRIPTION
	    "real-time RTP rx packet rate in bps"
	::= { voipCdrStatResultEntry 16 }
	
	voipCdrStatResultTxPktCnt OBJECT-TYPE
	SYNTAX Counter64
	MAX-ACCESS read-only
	STATUS current
	DESCRIPTION
	    "total RTP tx packet counter"
	::= { voipCdrStatResultEntry 17 }
	
	voipCdrStatResultRxPktCnt OBJECT-TYPE
	SYNTAX Counter64
	MAX-ACCESS read-only
	STATUS current
	DESCRIPTION
	    "total RTP rx packet counter"
	::= { voipCdrStatResultEntry 18 }
	
	voipCdrStatResultTxFracLost OBJECT-TYPE
	SYNTAX INTEGER
	MAX-ACCESS read-only
	STATUS current
	DESCRIPTION
	    "RTP tx packet lost in percentage"
	::= { voipCdrStatResultEntry 19 } 
	
	voipCdrStatResultRxFracLost OBJECT-TYPE
	SYNTAX INTEGER
	MAX-ACCESS read-only
	STATUS current
	DESCRIPTION
	    "RTP rx packet lost in percentage"
	::= { voipCdrStatResultEntry 20 }
	
	voipCdrStatResultTxJitter OBJECT-TYPE
	SYNTAX Counter64
	MAX-ACCESS read-only
	STATUS current
	DESCRIPTION
	    "Tx Jitter in micro-second"
	::= { voipCdrStatResultEntry 21 } 
	
	voipCdrStatResultRxJitter OBJECT-TYPE
	SYNTAX Counter64
	MAX-ACCESS read-only
	STATUS current
	DESCRIPTION
	    "Rx Jitter in micro-second"
	::= { voipCdrStatResultEntry 22 } 
	
	voipCdrStatResultTxAvgDelay OBJECT-TYPE
	SYNTAX Counter64
	MAX-ACCESS read-only
	STATUS current
	DESCRIPTION
	    "Average tx delay in ms"
	::= { voipCdrStatResultEntry 23 } 
	
	voipCdrStatResultRxAvgDelay OBJECT-TYPE
	SYNTAX Counter64
	MAX-ACCESS read-only
	STATUS current
	DESCRIPTION
	    "Average rx delay in ms"
	::= { voipCdrStatResultEntry 24 } 
	
	voipCdrStatResultCode OBJECT-TYPE
	SYNTAX INTEGER
	MAX-ACCESS read-only
	STATUS current
	DESCRIPTION
	    "Bit map of the call state record.
	    bit 6(0x20): offhook
	    bit 5(0x10): remote ringback tone
	    bit 4(0x08): local ringback tone
	    bit 3(0x04): dial tone
	    bit 2(0x02): ring
	    bit 1(0x01): rtp"
	::= { voipCdrStatResultEntry 25 }

    voipCdrStatResultErrCode OBJECT-TYPE
	SYNTAX INTEGER
	MAX-ACCESS read-only
	STATUS current
	DESCRIPTION
	    "Errcode of H.248 protocol. 0 mean no error."
	::= { voipCdrStatResultEntry 26 }
	
	voipCdrStatResultTerminationCause OBJECT-TYPE
	SYNTAX DisplayString
	MAX-ACCESS read-only
	STATUS current
	DESCRIPTION
	    "Termination Cause"
	::= { voipCdrStatResultEntry 27 }  
	
	
-- voipProtocolStatTable
voipH248Statistics	OBJECT IDENTIFIER ::= { voipStats 11 }  
        
	voipH248StatisticsInterface OBJECT-TYPE
	SYNTAX INTEGER
	MAX-ACCESS read-write
	STATUS current
	DESCRIPTION
	    "Interface id."
	::= { voipH248Statistics 1 }

	voipH248StatisticsMsgSent OBJECT-TYPE
	SYNTAX Unsigned64
	MAX-ACCESS read-only
	STATUS current
	DESCRIPTION
	    "Number of sent protocol message, include reset and error."
	::= { voipH248Statistics 2 }
	
	voipH248StatisticsMsgRecv OBJECT-TYPE
	SYNTAX Unsigned64
	MAX-ACCESS read-only
	STATUS current
	DESCRIPTION
	    "Number of received message."
	::= { voipH248Statistics 3 }
	
	voipH248StatisticsMsgLost OBJECT-TYPE
	SYNTAX Unsigned32
	MAX-ACCESS read-only
	STATUS current
	DESCRIPTION
	    "Number of message without reply."
	::= { voipH248Statistics 4 }

              	
	voipH248StatisticsMsgResent  OBJECT-TYPE
	SYNTAX Unsigned32
	MAX-ACCESS read-only
	STATUS current
	DESCRIPTION
		"Number of resent message."
	::= { voipH248Statistics 5 } 
	
	voipH248StatisticsErrorMsg  OBJECT-TYPE
	SYNTAX Unsigned32
	MAX-ACCESS read-only
	STATUS current
	DESCRIPTION
		"Number of error message sent."
	::= { voipH248Statistics 6 }


	voipH248StatisticsUnIdentifiedMsg  OBJECT-TYPE
	SYNTAX Unsigned32
	MAX-ACCESS read-only
	STATUS current
	DESCRIPTION
		"Number of parse fail message."
	::= { voipH248Statistics 7 }

						
--------------------
--  Ethernet Port
--------------------
-- enetPortStatusTable
	enetPortStatusTable OBJECT-TYPE
        SYNTAX SEQUENCE OF EnetPortStatusEntry
        MAX-ACCESS not-accessible
        STATUS current
        DESCRIPTION
        	"The table displays ethernet port status."
        ::= { enetStats 1 }

        enetPortStatusEntry OBJECT-TYPE
        SYNTAX EnetPortStatusEntry
        MAX-ACCESS not-accessible
        STATUS current
        DESCRIPTION
        	"An entry of enetPortStatusTable."
        INDEX { ifIndex }
        ::= { enetPortStatusTable 1 }

        EnetPortStatusEntry ::=
        	SEQUENCE {
                  	enetPortStatusLinkUpType	INTEGER,
                  	enetPortStatusLinkUpTime	Unsigned32,
                  	enetPortStatusLinkSpeed		Unsigned32,
                  	enetPortStatusLinkDuplex	INTEGER,
                  	enetPortStatusDataRateTx	Unsigned32,
                  	enetPortStatusDataRateRx	Unsigned32,
                  	enetPortStatusDataUtilTx	INTEGER,		
                  	enetPortStatusDataUtilRx	INTEGER
              	}
              	
	enetPortStatusLinkUpType OBJECT-TYPE
	SYNTAX INTEGER {
			down(0),
        		copper(1),
        		fiber(2)
        	}
	MAX-ACCESS read-only
	STATUS current
	DESCRIPTION
		""
	::= { enetPortStatusEntry 1 }

	enetPortStatusLinkUpTime OBJECT-TYPE
	SYNTAX Unsigned32
	MAX-ACCESS read-only
	STATUS current
	DESCRIPTION
		"The time since the enet port up."
	::= { enetPortStatusEntry 2 } 
	
	enetPortStatusLinkSpeed OBJECT-TYPE
	SYNTAX Unsigned32
	MAX-ACCESS read-only
	STATUS current
	DESCRIPTION
		"Link speed in Mbps."
	::= { enetPortStatusEntry 3 } 
	
	enetPortStatusLinkDuplex OBJECT-TYPE
	SYNTAX INTEGER { 
		full(1), 
		half(2) 
	}
	MAX-ACCESS read-only
	STATUS current
	DESCRIPTION
		"Link full/half duplex."
	::= { enetPortStatusEntry 4 } 
	
    enetPortStatusDataRateTx OBJECT-TYPE
	SYNTAX Unsigned32
	MAX-ACCESS read-only
	STATUS current
	DESCRIPTION
		"TX data rate in kbps."
	::= { enetPortStatusEntry 5 } 
	
	enetPortStatusDataRateRx OBJECT-TYPE
	SYNTAX Unsigned32
	MAX-ACCESS read-only
	STATUS current
	DESCRIPTION
		"RX data rate in kbps."
	::= { enetPortStatusEntry 6 } 
	
	enetPortStatusDataUtilTx OBJECT-TYPE
	SYNTAX INTEGER ( 0.. 100 )
	MAX-ACCESS read-only
	STATUS current
	DESCRIPTION
		"TX throughput utilization in percentage."
	::= { enetPortStatusEntry 7 } 
	
	enetPortStatusDataUtilRx OBJECT-TYPE
	SYNTAX INTEGER ( 0.. 100 )
	MAX-ACCESS read-only
	STATUS current
	DESCRIPTION
		"RX throughput utilization in percentage."
	::= { enetPortStatusEntry 8 }

-- sfpPortStatusTable
	sfpPortStatusTable OBJECT-TYPE
        SYNTAX SEQUENCE OF SfpPortStatusEntry
        MAX-ACCESS not-accessible
        STATUS current
        DESCRIPTION
        	"The table displays SFP ethernet port status. This table is supported by R5.02 and later versions."
        ::= { enetStats 2 }

        sfpPortStatusEntry OBJECT-TYPE
        SYNTAX SfpPortStatusEntry
        MAX-ACCESS not-accessible
        STATUS current
        DESCRIPTION
        	"An entry of sfpPortStatusTable."
        INDEX { ifIndex }
        ::= { sfpPortStatusTable 1 }

        SfpPortStatusEntry ::=
        	SEQUENCE {
            sfpId					DisplayString,
			sfpConnector			DisplayString,
			sfpTransceiver			DisplayString,
			sfpEncoding				DisplayString,
			sfpName					DisplayString,
			sfpPartNumber			DisplayString,
			sfpRevision				DisplayString,
			sfpSerialNumber			DisplayString,
			sfpTemperature			Unsigned32,
			sfpSupplyVoltage		Unsigned32,
			sfpTxBiasCurrent		Unsigned32,
			sfpTxPower				Unsigned32,
			sfpRxPower				Unsigned32
              	}
              	
	sfpId OBJECT-TYPE
	SYNTAX DisplayString
	MAX-ACCESS read-only
	STATUS current
	DESCRIPTION
		""
	::= { sfpPortStatusEntry 1 }

	sfpConnector OBJECT-TYPE
	SYNTAX DisplayString
	MAX-ACCESS read-only
	STATUS current
	DESCRIPTION
		""
	::= { sfpPortStatusEntry 2 }

	sfpTransceiver OBJECT-TYPE
	SYNTAX DisplayString
	MAX-ACCESS read-only
	STATUS current
	DESCRIPTION
		""
	::= { sfpPortStatusEntry 3 }

	sfpEncoding OBJECT-TYPE
	SYNTAX DisplayString
	MAX-ACCESS read-only
	STATUS current
	DESCRIPTION
		""
	::= { sfpPortStatusEntry 4 }

	sfpName OBJECT-TYPE
	SYNTAX DisplayString
	MAX-ACCESS read-only
	STATUS current
	DESCRIPTION
		""
	::= { sfpPortStatusEntry 5 }

	sfpPartNumber OBJECT-TYPE
	SYNTAX DisplayString
	MAX-ACCESS read-only
	STATUS current
	DESCRIPTION
		""
	::= { sfpPortStatusEntry 6 }

	sfpRevision OBJECT-TYPE
	SYNTAX DisplayString
	MAX-ACCESS read-only
	STATUS current
	DESCRIPTION
		""
	::= { sfpPortStatusEntry 7 }

	sfpSerialNumber OBJECT-TYPE
	SYNTAX DisplayString
	MAX-ACCESS read-only
	STATUS current
	DESCRIPTION
		""
	::= { sfpPortStatusEntry 8 }   
	
	sfpTemperature OBJECT-TYPE
	SYNTAX Unsigned32
	MAX-ACCESS read-only
	STATUS current
	DESCRIPTION
		""
	::= { sfpPortStatusEntry 9 }  
	
	sfpSupplyVoltage OBJECT-TYPE
	SYNTAX Unsigned32
	MAX-ACCESS read-only
	STATUS current
	DESCRIPTION
		""
	::= { sfpPortStatusEntry 10 }

	sfpTxBiasCurrent OBJECT-TYPE
	SYNTAX Unsigned32
	MAX-ACCESS read-only
	STATUS current
	DESCRIPTION
		""
	::= { sfpPortStatusEntry 11 }

	sfpTxPower OBJECT-TYPE
	SYNTAX Unsigned32
	MAX-ACCESS read-only
	STATUS current
	DESCRIPTION
		""
	::= { sfpPortStatusEntry 12 }

	sfpRxPower OBJECT-TYPE
	SYNTAX Unsigned32
	MAX-ACCESS read-only
	STATUS current
	DESCRIPTION
		""
	::= { sfpPortStatusEntry 13 }


--------------------
--  Interface Status Table
--------------------

	ifStatusTable OBJECT-TYPE
        SYNTAX SEQUENCE OF IfStatusEntry
        MAX-ACCESS not-accessible
        STATUS current
        DESCRIPTION
        	"The table displays port interface status. This table is supported by R5.02 and later versions."
        ::= { ifStats 1 }

        ifStatusEntry OBJECT-TYPE
        SYNTAX IfStatusEntry
        MAX-ACCESS not-accessible
        STATUS current
        DESCRIPTION
        	"An entry of ifStatusTable."
        INDEX { ifIndex }
        ::= { ifStatusTable 1 }

        IfStatusEntry ::=
        	SEQUENCE {
                  	ifInRate	Counter32,
			ifOutRate	Counter32,
					ifCurrentStatus		INTEGER,
					ifUpTime			Unsigned32
              	}
              	
	ifInRate OBJECT-TYPE
	SYNTAX Counter32
	MAX-ACCESS read-only
	STATUS current
	DESCRIPTION
		""
	::= { ifStatusEntry 1 }

	ifOutRate OBJECT-TYPE
	SYNTAX Counter32
	MAX-ACCESS read-only
	STATUS current
	DESCRIPTION
		""
	::= { ifStatusEntry 2 }

	ifCurrentStatus OBJECT-TYPE
        SYNTAX INTEGER {
        		up(1),
        		down(2),
        		testing(3),
        		unknown(4),
        		blocked(5)
        	}
	MAX-ACCESS read-only
	STATUS current
	DESCRIPTION
		"Current status of an interface"  
	::= { ifStatusEntry 3 }  
	
	ifUpTime OBJECT-TYPE
	SYNTAX Unsigned32
	MAX-ACCESS read-only
	STATUS current
	DESCRIPTION
		"The time since the line link up."
	::= { ifStatusEntry 4 }  
	
--------------------
--  IMA Status Table
--------------------

-- imaPvcStatsTable
	imaPvcStatsTable OBJECT-TYPE
        SYNTAX SEQUENCE OF ImaPvcStatsEntry
        MAX-ACCESS not-accessible
        STATUS current
        DESCRIPTION
        	"The table displays IMA Group PVC status. This table is supported by R5.03 and later versions."
        ::= { imaStats 1 }

        imaPvcStatsEntry OBJECT-TYPE
        SYNTAX ImaPvcStatsEntry
        MAX-ACCESS not-accessible
        STATUS current
        DESCRIPTION
        	"An entry of imaPvcStatsTable."
        INDEX { imaPvcStatsGroupIndex , imaPvcStatsVpi , imaPvcStatsVci }
        ::= { imaPvcStatsTable 1 }

        ImaPvcStatsEntry ::=
        	SEQUENCE {
            imaPvcStatsGroupIndex	INTEGER,
			imaPvcStatsVpi	INTEGER,
			imaPvcStatsVci	INTEGER,
			imaPvcStatsTxPackets	Counter64,
			imaPvcStatsRxPackets	Counter64,
			imaPvcStatsTxUnicast	Counter64,
			imaPvcStatsRxUnicast	Counter64,
			imaPvcStatsTxMulticast	Counter64,
			imaPvcStatsRxMulticast	Counter64,
			imaPvcStatsTxBroadcast	Counter64,
			imaPvcStatsRxBroadcast	Counter64,
			imaPvcStatsTxDiscard	Counter64,
            imaPvcStatsRxDiscard	Counter64
           }
              	
	imaPvcStatsGroupIndex OBJECT-TYPE
	SYNTAX INTEGER
	MAX-ACCESS read-only
	STATUS current
	DESCRIPTION
		""
	::= { imaPvcStatsEntry 1 } 
	
	imaPvcStatsVpi OBJECT-TYPE
	SYNTAX INTEGER
	MAX-ACCESS read-only
	STATUS current
	DESCRIPTION
		""
	::= { imaPvcStatsEntry 2 }


	imaPvcStatsVci OBJECT-TYPE
	SYNTAX INTEGER
	MAX-ACCESS read-only
	STATUS current
	DESCRIPTION
		""
	::= { imaPvcStatsEntry 3 }


	imaPvcStatsTxPackets OBJECT-TYPE
	SYNTAX Counter64
	MAX-ACCESS read-only
	STATUS current
	DESCRIPTION
		""
	::= { imaPvcStatsEntry 4 }   
	
	imaPvcStatsRxPackets OBJECT-TYPE
	SYNTAX Counter64
	MAX-ACCESS read-only
	STATUS current
	DESCRIPTION
		""
	::= { imaPvcStatsEntry 5 }
	
	imaPvcStatsTxUnicast OBJECT-TYPE
	SYNTAX Counter64
	MAX-ACCESS read-only
	STATUS current
	DESCRIPTION
		""
	::= { imaPvcStatsEntry 6 }
	
	imaPvcStatsRxUnicast OBJECT-TYPE
	SYNTAX Counter64
	MAX-ACCESS read-only
	STATUS current
	DESCRIPTION
		""
	::= { imaPvcStatsEntry 7 }
	
	imaPvcStatsTxMulticast OBJECT-TYPE
	SYNTAX Counter64
	MAX-ACCESS read-only
	STATUS current
	DESCRIPTION
		""
	::= { imaPvcStatsEntry 8 }
	
	imaPvcStatsRxMulticast OBJECT-TYPE
	SYNTAX Counter64
	MAX-ACCESS read-only
	STATUS current
	DESCRIPTION
		""
	::= { imaPvcStatsEntry 9 }
	
	imaPvcStatsTxBroadcast OBJECT-TYPE
	SYNTAX Counter64
	MAX-ACCESS read-only
	STATUS current
	DESCRIPTION
		""
	::= { imaPvcStatsEntry 10 }
	
	imaPvcStatsRxBroadcast OBJECT-TYPE
	SYNTAX Counter64
	MAX-ACCESS read-only
	STATUS current
	DESCRIPTION
		""
	::= { imaPvcStatsEntry 11 }
	
	imaPvcStatsTxDiscard OBJECT-TYPE
	SYNTAX Counter64
	MAX-ACCESS read-only
	STATUS current
	DESCRIPTION
		""
	::= { imaPvcStatsEntry 12 }
	
	imaPvcStatsRxDiscard OBJECT-TYPE
	SYNTAX Counter64
	MAX-ACCESS read-only
	STATUS current
	DESCRIPTION
		""
	::= { imaPvcStatsEntry 13 }
	
-- imaGroupStatsTable
	imaGroupStatsTable OBJECT-TYPE
        SYNTAX SEQUENCE OF ImaGroupStatsEntry
        MAX-ACCESS not-accessible
        STATUS current
        DESCRIPTION
        	"The table displays IMA Group status. This table is supported by R5.03 and later versions."
        ::= { imaStats 2 }

        imaGroupStatsEntry OBJECT-TYPE
        SYNTAX ImaGroupStatsEntry
        MAX-ACCESS not-accessible
        STATUS current
        DESCRIPTION
        	"An entry of imaGroupStatsTable."
        INDEX { imaGroupStatsGroupIndex }
        ::= { imaGroupStatsTable 1 }

        ImaGroupStatsEntry ::=
        	SEQUENCE {
            imaGroupStatsGroupIndex	INTEGER,
			imaGroupStatsTxCells	Counter64,
			imaGroupStatsRxCells	Counter64,
			imaGroupStatsTxRate		INTEGER,
			imaGroupStatsRxRate		INTEGER,
			imaGroupStatsCrcErr		Counter64
           }
              	
	imaGroupStatsGroupIndex OBJECT-TYPE
	SYNTAX INTEGER
	MAX-ACCESS read-only
	STATUS current
	DESCRIPTION
		""
	::= { imaGroupStatsEntry 1 } 
	

	imaGroupStatsTxCells OBJECT-TYPE
	SYNTAX Counter64
	MAX-ACCESS read-only
	STATUS current
	DESCRIPTION
		"Tx Cells since reset"
	::= { imaGroupStatsEntry 2 }   
	
	imaGroupStatsRxCells OBJECT-TYPE
	SYNTAX Counter64
	MAX-ACCESS read-only
	STATUS current
	DESCRIPTION
		"Rx Cells since reset"
	::= { imaGroupStatsEntry 3 }  
	
	imaGroupStatsTxRate OBJECT-TYPE
	SYNTAX INTEGER
	MAX-ACCESS read-only
	STATUS current
	DESCRIPTION
		"Tx data rate in Bytes/s"
	::= { imaGroupStatsEntry 4 }


	imaGroupStatsRxRate OBJECT-TYPE
	SYNTAX INTEGER
	MAX-ACCESS read-only
	STATUS current
	DESCRIPTION
		"Rx data rate in Bytes/s"
	::= { imaGroupStatsEntry 5 }     
	
	imaGroupStatsCrcErr OBJECT-TYPE
	SYNTAX Counter64
	MAX-ACCESS read-only
	STATUS current
	DESCRIPTION
		"CRC errors since reset"
	::= { imaGroupStatsEntry 6 }

-- imaGroupCurrDayTable
	imaGroupCurrDayTable OBJECT-TYPE
        SYNTAX SEQUENCE OF ImaGroupCurrDayEntry
        MAX-ACCESS not-accessible
        STATUS current
        DESCRIPTION
        	"The table displays IMA Group Current Day Counters. This table is supported by R5.03 and later versions."
        ::= { imaStats 3 }

        imaGroupCurrDayEntry OBJECT-TYPE
        SYNTAX ImaGroupCurrDayEntry
        MAX-ACCESS not-accessible
        STATUS current
        DESCRIPTION
        	"An entry of imaGroupCurrDayTable."
        INDEX { imaGroupCurrDayGroupIndex }
        ::= { imaGroupCurrDayTable 1 }

        ImaGroupCurrDayEntry ::=
        	SEQUENCE {
            imaGroupCurrDayGroupIndex	INTEGER,
			imaGroupCurrDayUnavailSecs	INTEGER,
			imaGroupCurrDayNeNumFailures	INTEGER,
			imaGroupCurrDayFeNumFailures	INTEGER
           }
              	
	imaGroupCurrDayGroupIndex OBJECT-TYPE
	SYNTAX INTEGER
	MAX-ACCESS read-only
	STATUS current
	DESCRIPTION
		""
	::= { imaGroupCurrDayEntry 1 } 
	
	imaGroupCurrDayUnavailSecs OBJECT-TYPE
	SYNTAX INTEGER
	MAX-ACCESS read-only
	STATUS current
	DESCRIPTION
		""
	::= { imaGroupCurrDayEntry 2 }


	imaGroupCurrDayNeNumFailures OBJECT-TYPE
	SYNTAX INTEGER
	MAX-ACCESS read-only
	STATUS current
	DESCRIPTION
		""
	::= { imaGroupCurrDayEntry 3 } 
	
	imaGroupCurrDayFeNumFailures OBJECT-TYPE
	SYNTAX INTEGER
	MAX-ACCESS read-only
	STATUS current
	DESCRIPTION
		""
	::= { imaGroupCurrDayEntry 4 }

-- imaLinkCurrDayTable
	imaLinkCurrDayTable OBJECT-TYPE
        SYNTAX SEQUENCE OF ImaLinkCurrDayEntry
        MAX-ACCESS not-accessible
        STATUS current
        DESCRIPTION
        	"The table displays IMA Link Current Day Counters. This table is supported by R5.03 and later versions."
        ::= { imaStats 4 }

        imaLinkCurrDayEntry OBJECT-TYPE
        SYNTAX ImaLinkCurrDayEntry
        MAX-ACCESS not-accessible
        STATUS current
        DESCRIPTION
        	"An entry of imaLinkCurrDayTable."
        INDEX { imaLinkCurrDayIfindex }
        ::= { imaLinkCurrDayTable 1 }

        ImaLinkCurrDayEntry ::=
        	SEQUENCE {
            imaLinkCurrDayIfindex	INTEGER,
			imaLinkCurrDayImaViolations	INTEGER,
			imaLinkCurrDayOifAnomalies	INTEGER,
			imaLinkCurrDayNeSevErroredSecs	INTEGER,
			imaLinkCurrDayFeSevErroredSecs	INTEGER,
			imaLinkCurrDayNeUnavailSecs	INTEGER,
			imaLinkCurrDayFeUnavailSecs	INTEGER,
			imaLinkCurrDayNeTxUnusableSecs	INTEGER,
			imaLinkCurrDayNeRxUnusableSecs	INTEGER,
			imaLinkCurrDayFeTxUnusableSecs	INTEGER,
			imaLinkCurrDayFeRxUnusableSecs	INTEGER,
			imaLinkCurrDayNeTxNumFailures	INTEGER,
			imaLinkCurrDayNeRxNumFailures	INTEGER,
			imaLinkCurrDayFeTxNumFailures	INTEGER,
			imaLinkCurrDayFeRxNumFailures	INTEGER,
			imaLinkCurrDayTxStuffs	INTEGER,
			imaLinkCurrDayRxStuffs	INTEGER
           }
              	
	imaLinkCurrDayIfindex OBJECT-TYPE
	SYNTAX INTEGER
	MAX-ACCESS read-only
	STATUS current
	DESCRIPTION
		""
	::= { imaLinkCurrDayEntry 1 } 
	
	imaLinkCurrDayImaViolations OBJECT-TYPE
	SYNTAX INTEGER
	MAX-ACCESS read-only
	STATUS current
	DESCRIPTION
		""
	::= { imaLinkCurrDayEntry 2 }


	imaLinkCurrDayOifAnomalies OBJECT-TYPE
	SYNTAX INTEGER
	MAX-ACCESS read-only
	STATUS current
	DESCRIPTION
		""
	::= { imaLinkCurrDayEntry 3 } 
	
	imaLinkCurrDayNeSevErroredSecs OBJECT-TYPE
	SYNTAX INTEGER
	MAX-ACCESS read-only
	STATUS current
	DESCRIPTION
		""
	::= { imaLinkCurrDayEntry 4 }     
	
	imaLinkCurrDayFeSevErroredSecs OBJECT-TYPE
	SYNTAX INTEGER
	MAX-ACCESS read-only
	STATUS current
	DESCRIPTION
		""
	::= { imaLinkCurrDayEntry 5 }


	imaLinkCurrDayNeUnavailSecs OBJECT-TYPE
	SYNTAX INTEGER
	MAX-ACCESS read-only
	STATUS current
	DESCRIPTION
		""
	::= { imaLinkCurrDayEntry 6 }  
	
	imaLinkCurrDayFeUnavailSecs OBJECT-TYPE
	SYNTAX INTEGER
	MAX-ACCESS read-only
	STATUS current
	DESCRIPTION
		""
	::= { imaLinkCurrDayEntry 7 }

	imaLinkCurrDayNeTxUnusableSecs OBJECT-TYPE
	SYNTAX INTEGER
	MAX-ACCESS read-only
	STATUS current
	DESCRIPTION
		""
	::= { imaLinkCurrDayEntry 8 }

	imaLinkCurrDayNeRxUnusableSecs OBJECT-TYPE
	SYNTAX INTEGER
	MAX-ACCESS read-only
	STATUS current
	DESCRIPTION
		""
	::= { imaLinkCurrDayEntry 9 }

	imaLinkCurrDayFeTxUnusableSecs OBJECT-TYPE
	SYNTAX INTEGER
	MAX-ACCESS read-only
	STATUS current
	DESCRIPTION
		""
	::= { imaLinkCurrDayEntry 10 }


	imaLinkCurrDayFeRxUnusableSecs OBJECT-TYPE
	SYNTAX INTEGER
	MAX-ACCESS read-only
	STATUS current
	DESCRIPTION
		""
	::= { imaLinkCurrDayEntry 11 }

	imaLinkCurrDayNeTxNumFailures OBJECT-TYPE
	SYNTAX INTEGER
	MAX-ACCESS read-only
	STATUS current
	DESCRIPTION
		""
	::= { imaLinkCurrDayEntry 12 }

	imaLinkCurrDayNeRxNumFailures OBJECT-TYPE
	SYNTAX INTEGER
	MAX-ACCESS read-only
	STATUS current
	DESCRIPTION
		""
	::= { imaLinkCurrDayEntry 13 }

	imaLinkCurrDayFeTxNumFailures OBJECT-TYPE
	SYNTAX INTEGER
	MAX-ACCESS read-only
	STATUS current
	DESCRIPTION
		""
	::= { imaLinkCurrDayEntry 14 }

	imaLinkCurrDayFeRxNumFailures OBJECT-TYPE
	SYNTAX INTEGER
	MAX-ACCESS read-only
	STATUS current
	DESCRIPTION
		""
	::= { imaLinkCurrDayEntry 15 }

	imaLinkCurrDayTxStuffs OBJECT-TYPE
	SYNTAX INTEGER
	MAX-ACCESS read-only
	STATUS current
	DESCRIPTION
		""
	::= { imaLinkCurrDayEntry 16 }

	imaLinkCurrDayRxStuffs OBJECT-TYPE
	SYNTAX INTEGER
	MAX-ACCESS read-only
	STATUS current
	DESCRIPTION
		""
	::= { imaLinkCurrDayEntry 17 }

-- imaGroupConfReadyTable
	imaGroupConfReadyTable OBJECT-TYPE
        SYNTAX SEQUENCE OF ImaGroupConfReadyEntry
        MAX-ACCESS not-accessible
        STATUS current
        DESCRIPTION
        	"The table displays IMA Group Configuration Ready status. This table is supported by R5.03 and later versions."
        ::= { imaStats 5 }

        imaGroupConfReadyEntry OBJECT-TYPE
        SYNTAX ImaGroupConfReadyEntry
        MAX-ACCESS not-accessible
        STATUS current
        DESCRIPTION
        	"An entry of imaGroupConfReadyTable."
        INDEX { imaGroupConfReadyIndex }
        ::= { imaGroupConfReadyTable 1 }

        ImaGroupConfReadyEntry ::=
        	SEQUENCE {
            imaGroupConfReadyIndex	INTEGER,
			imaGroupConfReadyState	INTEGER
           }
              	
	imaGroupConfReadyIndex OBJECT-TYPE
	SYNTAX INTEGER
	MAX-ACCESS read-only
	STATUS current
	DESCRIPTION
		""
	::= { imaGroupConfReadyEntry 1 } 
	
    imaGroupConfReadyState OBJECT-TYPE
    SYNTAX INTEGER {
        conf-ready(1),
        conf-forbidden(2)
    }
    MAX-ACCESS read-only
    STATUS current
    DESCRIPTION
            ""
    ::= { imaGroupConfReadyEntry 2 }  
    
-- imaGroupStatusTable
	imaGroupStatusTable OBJECT-TYPE
        SYNTAX SEQUENCE OF ImaGroupStatusEntry
        MAX-ACCESS not-accessible
        STATUS current
        DESCRIPTION
        	"The table displays IMA Group status. This table is supported by R5.03 and later versions."
        ::= { imaStats 6 }

        imaGroupStatusEntry OBJECT-TYPE
        SYNTAX ImaGroupStatusEntry
        MAX-ACCESS not-accessible
        STATUS current
        DESCRIPTION
        	"An entry of imaGroupConfReadyTable."
        INDEX { imaGroupStatusGroupIndex }
        ::= { imaGroupStatusTable 1 }

        ImaGroupStatusEntry ::=
        	SEQUENCE {
            imaGroupStatusGroupIndex	INTEGER,
						imaGroupStatusTxPayloadRate	INTEGER,
						imaGroupStatusRxPayloadRate INTEGER
           }
              	
	imaGroupStatusGroupIndex OBJECT-TYPE
	SYNTAX INTEGER
	MAX-ACCESS read-only
	STATUS current
	DESCRIPTION
		""
	::= { imaGroupStatusEntry 1 } 
	
    imaGroupStatusTxPayloadRate OBJECT-TYPE
    SYNTAX INTEGER
    MAX-ACCESS read-only
    STATUS current
    DESCRIPTION
            "Maximum tx data rate in kbps"
    ::= { imaGroupStatusEntry 2 }
    
    imaGroupStatusRxPayloadRate OBJECT-TYPE
    SYNTAX INTEGER
    MAX-ACCESS read-only
    STATUS current
    DESCRIPTION
            "Maximum rx data rate in kbps"
    ::= { imaGroupStatusEntry 3 }
	
--------------------
--  E1 Port Status Table
--------------------

-- e1CurrDayTable
	e1CurrDayTable OBJECT-TYPE
        SYNTAX SEQUENCE OF E1CurrDayEntry
        MAX-ACCESS not-accessible
        STATUS current
        DESCRIPTION
        	"The table displays E1 Port Current Day Counters. This table is supported by R5.03 and later versions."
        ::= { e1Stats 1 }

        e1CurrDayEntry OBJECT-TYPE
        SYNTAX E1CurrDayEntry
        MAX-ACCESS not-accessible
        STATUS current
        DESCRIPTION
        	"An entry of e1CurrDayTable."
        INDEX { e1CurrDayIfindex }
        ::= { e1CurrDayTable 1 }

        E1CurrDayEntry ::=
        	SEQUENCE {
            e1CurrDayIfindex	INTEGER,
			e1CurrDayLCVs	INTEGER,
			e1CurrDayPCVs	INTEGER,
			e1CurrDayESs	INTEGER,
			e1CurrDaySESs	INTEGER,
			e1CurrDayUASs	INTEGER
           }
              	
	e1CurrDayIfindex OBJECT-TYPE
	SYNTAX INTEGER
	MAX-ACCESS read-only
	STATUS current
	DESCRIPTION
		""
	::= { e1CurrDayEntry 1 } 
	
	e1CurrDayLCVs OBJECT-TYPE
	SYNTAX INTEGER
	MAX-ACCESS read-only
	STATUS current
	DESCRIPTION
		"Line Coding Violation"
	::= { e1CurrDayEntry 2 }


	e1CurrDayPCVs OBJECT-TYPE
	SYNTAX INTEGER
	MAX-ACCESS read-only
	STATUS current
	DESCRIPTION
		"Path Coding Violation, a.k.a. Error Blocks"
	::= { e1CurrDayEntry 3 }

    e1CurrDayESs OBJECT-TYPE
	SYNTAX INTEGER
	MAX-ACCESS read-only
	STATUS current
	DESCRIPTION
		""
	::= { e1CurrDayEntry 4 }
	
	e1CurrDaySESs OBJECT-TYPE
	SYNTAX INTEGER
	MAX-ACCESS read-only
	STATUS current
	DESCRIPTION
		""
	::= { e1CurrDayEntry 5 }
	
	e1CurrDayUASs OBJECT-TYPE
	SYNTAX INTEGER
	MAX-ACCESS read-only
	STATUS current
	DESCRIPTION
		""
	::= { e1CurrDayEntry 6 }
	
-- e1StatusTable
	e1StatusTable OBJECT-TYPE
        SYNTAX SEQUENCE OF E1StatusEntry
        MAX-ACCESS not-accessible
        STATUS current
        DESCRIPTION
        	"The table displays E1 Port Status. This table is supported by R5.03 and later versions."
        ::= { e1Stats 2 }

        e1StatusEntry OBJECT-TYPE
        SYNTAX E1StatusEntry
        MAX-ACCESS not-accessible
        STATUS current
        DESCRIPTION
        	"An entry of e1StatusTable."
        INDEX { e1StatusIfindex }
        ::= { e1StatusTable 1 }

        E1StatusEntry ::=
        	SEQUENCE {
            		e1StatusIfindex	INTEGER,
					e1StatusTxPayloadRate	INTEGER,
					e1StatusRxPayloadRate	INTEGER,
					e1StatusUpTime			Unsigned32					
           }
              	
	e1StatusIfindex OBJECT-TYPE
	SYNTAX INTEGER
	MAX-ACCESS read-only
	STATUS current
	DESCRIPTION
		""
	::= { e1StatusEntry 1 } 
	
	e1StatusTxPayloadRate OBJECT-TYPE
	SYNTAX INTEGER
	MAX-ACCESS read-only
	STATUS current
	DESCRIPTION
		"Maximum tx data rate in kbps"
	::= { e1StatusEntry 2 }


	e1StatusRxPayloadRate OBJECT-TYPE
	SYNTAX INTEGER
	MAX-ACCESS read-only
	STATUS current
	DESCRIPTION
		"Maximum rx data rate in kbps"
	::= { e1StatusEntry 3 } 
	
	e1StatusUpTime OBJECT-TYPE
	SYNTAX Unsigned32
	MAX-ACCESS read-only
	STATUS current
	DESCRIPTION
		"The uplink time."
	::= { e1StatusEntry 4 } 
	
--------------------
--  Loopguard Stats
--------------------

	loopguardStatsTable OBJECT-TYPE
        SYNTAX SEQUENCE OF LoopguardStatsEntry
        MAX-ACCESS not-accessible
        STATUS current
        DESCRIPTION
        	""
        ::= { loopguardStats 1 }

        loopguardStatsEntry OBJECT-TYPE
        SYNTAX LoopguardStatsEntry
        MAX-ACCESS not-accessible
        STATUS current
        DESCRIPTION
        	"An entry of loopguardStatsTable."
        INDEX { ifIndex }
        ::= { loopguardStatsTable 1 }

        LoopguardStatsEntry ::=
        	SEQUENCE {
	            loopguardStatsPort	INTEGER,
				loopguardStatsPortStatus	INTEGER,
				loopguardStatsLoopguardStatus	INTEGER,
				loopguardStatsTotalTxPackets	INTEGER,
				loopguardStatsTotalRxPackets	INTEGER,
				loopguardStatsBadPackets	INTEGER, 
				loopguardStatsShutdownTime	DisplayString
           }
              	
	loopguardStatsPort OBJECT-TYPE
	SYNTAX INTEGER
	MAX-ACCESS read-only
	STATUS current
	DESCRIPTION
		""
	::= { loopguardStatsEntry 1 } 
	
	loopguardStatsPortStatus OBJECT-TYPE
	SYNTAX INTEGER{
		link-down(0),
		link-up(1),
		blocked-by-loopguard(2)			
	}
	MAX-ACCESS read-only
	STATUS current
	DESCRIPTION
		""
	::= { loopguardStatsEntry 2 }


	loopguardStatsLoopguardStatus OBJECT-TYPE
	SYNTAX INTEGER{
		enable(1),
		disable(2)			
	}
	MAX-ACCESS read-only
	STATUS current
	DESCRIPTION
		""
	::= { loopguardStatsEntry 3 }
	
	loopguardStatsTotalTxPackets OBJECT-TYPE
	SYNTAX INTEGER
	MAX-ACCESS read-only
	STATUS current
	DESCRIPTION
		""
	::= { loopguardStatsEntry 4 }	
	
	loopguardStatsTotalRxPackets OBJECT-TYPE
	SYNTAX INTEGER
	MAX-ACCESS read-only
	STATUS current
	DESCRIPTION
		""
	::= { loopguardStatsEntry 5 }
	
	loopguardStatsBadPackets OBJECT-TYPE
	SYNTAX INTEGER
	MAX-ACCESS read-only
	STATUS current
	DESCRIPTION
		""
	::= { loopguardStatsEntry 6 }  
	
	loopguardStatsShutdownTime OBJECT-TYPE
	SYNTAX DisplayString
	MAX-ACCESS read-only
	STATUS current
	DESCRIPTION
		"seconds"
	::= { loopguardStatsEntry 7 } 

--------------------
--  Stp Stats Table
--------------------
-- stpPortStatsTable
	stpPortStatsTable OBJECT-TYPE
        SYNTAX SEQUENCE OF StpPortStatsEntry
        MAX-ACCESS not-accessible
        STATUS current
        DESCRIPTION
        	"The table displays STP Port Status. This table is supported by R5.03 and later versions."
        ::= { stpStats 1 }

        stpPortStatsEntry OBJECT-TYPE
        SYNTAX StpPortStatsEntry
        MAX-ACCESS not-accessible
        STATUS current
        DESCRIPTION
        	"An entry of stpPortStatsTable."
        INDEX { ifIndex }
        ::= { stpPortStatsTable 1 }

        StpPortStatsEntry ::=
        	SEQUENCE {
            stpPortStatus	INTEGER
           }
              	
	stpPortStatus OBJECT-TYPE
	SYNTAX INTEGER {
        discarding(1),
        learning(2),
        forwarding(3),
        down(4)
    }
	MAX-ACCESS read-only
	STATUS current
	DESCRIPTION
		""
	::= { stpPortStatsEntry 1 }   

	stpStatsPortNum		OBJECT IDENTIFIER ::= { stpStats 2 }	
	
	stpStatsPortNumForwarding OBJECT-TYPE
	SYNTAX INTEGER
	MAX-ACCESS read-only
	STATUS current
	DESCRIPTION
		"the number of forwarding ports.
		This MIB object is supported by R5.05 and later versions."
	::= { stpStatsPortNum 1 }

	stpStatsPortNumLearning OBJECT-TYPE
	SYNTAX INTEGER
	MAX-ACCESS read-only
	STATUS current
	DESCRIPTION
		"the number of learning ports.
		This MIB object is supported by R5.05 and later versions."
	::= { stpStatsPortNum 2 }		

	stpStatsPortNumDiscarding OBJECT-TYPE
	SYNTAX INTEGER
	MAX-ACCESS read-only
	STATUS current
	DESCRIPTION
		"the number of discarding ports.
		This MIB object is supported by R5.05 and later versions."
	::= { stpStatsPortNum 3 }

	stpStatsPortNumDown OBJECT-TYPE
	SYNTAX INTEGER
	MAX-ACCESS read-only
	STATUS current
	DESCRIPTION
		"the number of link-down ports.
		This MIB object is supported by R5.05 and later versions."
	::= { stpStatsPortNum 4 } 
	
--------------------
--  G.Bond Stats Table
--------------------
-- gbondStatsTable
	gbondStatsTable OBJECT-TYPE
        SYNTAX SEQUENCE OF GbondStatsEntry
        MAX-ACCESS not-accessible
        STATUS current
        DESCRIPTION
        	"The table displays G.Bond Status. This table is supported by R5.05 and later versions."
        ::= { gbondStats 1 }

        gbondStatsEntry OBJECT-TYPE
        SYNTAX GbondStatsEntry
        MAX-ACCESS not-accessible
        STATUS current
        DESCRIPTION
        	"An entry of gbondStatsTable."
        INDEX { slotId,  gbondStatsName}
        ::= { gbondStatsTable 1 }

        GbondStatsEntry ::=
        	SEQUENCE {
            gbondStatsName			DisplayString,
            gbondStatsUpRate        Unsigned32,
            gbondStatsDownRate      Unsigned32,
			gbondStatsMember        OCTET STRING,
            gbondStatslinkup        OCTET STRING,
            gbondStatsTx            OCTET STRING,
            gbondStatsRx            OCTET STRING,
            gbondStatslinkdown      OCTET STRING,
            gbondStatsTCMode		INTEGER,
            gbondStatsTxRate		Unsigned32,
            gbondStatsRxRate		Unsigned32
           }
              	
	gbondStatsName OBJECT-TYPE
	SYNTAX DisplayString
	MAX-ACCESS read-only
	STATUS current
	DESCRIPTION
		"An administratively assigned string, which identifies the bonding group."
	::= { gbondStatsEntry 1 } 
	
	gbondStatsUpRate OBJECT-TYPE
	SYNTAX Unsigned32
	MAX-ACCESS read-only
	STATUS current
	DESCRIPTION
		"The current up stream rate."
	::= { gbondStatsEntry 2 }
	
	gbondStatsDownRate OBJECT-TYPE
	SYNTAX Unsigned32
	MAX-ACCESS read-only
	STATUS current
	DESCRIPTION
		"The current down stream rate."
	::= { gbondStatsEntry 3 } 
	
	gbondStatsMember OBJECT-TYPE
	SYNTAX OCTET STRING
	MAX-ACCESS read-only
	STATUS current
	DESCRIPTION
		"Indicate if the port is a member port of the bonding group. Each bit in the octet specifies a port from MSB to LSB.
		for example: 32(hex) = 50(dec) = 00110010(bin) means the port 3, 4 and 7."
	::= { gbondStatsEntry 4 } 
	
	gbondStatslinkup OBJECT-TYPE
	SYNTAX OCTET STRING
	MAX-ACCESS read-only
	STATUS current
	DESCRIPTION
		"Indicate if the link status of port is bidirectional. Each bit in the octet specifies a port from MSB to LSB.
		for example: 32(hex) = 50(dec) = 00110010(bin) means the port 3, 4 and 7."
	::= { gbondStatsEntry 5 } 
	
	gbondStatsTx OBJECT-TYPE
	SYNTAX OCTET STRING
	MAX-ACCESS read-only
	STATUS current
	DESCRIPTION
		"Indicate if the link status of port is Tx only. Each bit in the octet specifies a port from MSB to LSB.
		for example: 32(hex) = 50(dec) = 00110010(bin) means the port 3, 4 and 7."
	::= { gbondStatsEntry 6 } 
	
	gbondStatsRx OBJECT-TYPE
	SYNTAX OCTET STRING
	MAX-ACCESS read-only
	STATUS current
	DESCRIPTION
		"Indicate if the link status of port is Rx only. Each bit in the octet specifies a port from MSB to LSB.
		for example: 32(hex) = 50(dec) = 00110010(bin) means the port 3, 4 and 7."
	::= { gbondStatsEntry 7 } 
	
	gbondStatslinkdown OBJECT-TYPE
	SYNTAX OCTET STRING
	MAX-ACCESS read-only
	STATUS current
	DESCRIPTION
		"Indicate if the link status of the port is down. Each bit in the octet specifies a port from MSB to LSB.
		for example: 32(hex) = 50(dec) = 00110010(bin) means the port 3, 4 and 7."
	::= { gbondStatsEntry 8 }
		
	gbondStatsTCMode OBJECT-TYPE
	SYNTAX 	INTEGER {
			atm(1),
			efm(2)
		}
	MAX-ACCESS read-only
	STATUS current
	DESCRIPTION
		"Transmission Convergence layer."
	::= { gbondStatsEntry 9 }
	
	gbondStatsTxRate OBJECT-TYPE
	SYNTAX Unsigned32
	MAX-ACCESS read-only
	STATUS current
	DESCRIPTION
		"The tx packet rate."
	::= { gbondStatsEntry 10 }
	
	gbondStatsRxRate OBJECT-TYPE
	SYNTAX Unsigned32
	MAX-ACCESS read-only
	STATUS current
	DESCRIPTION
		"The rx packet rate."
	::= { gbondStatsEntry 11 }     

--------------------
--  vdsl2 Stats Table
--------------------
-- vdslChanExtendedTable
	vdslChanExtendedTable OBJECT-TYPE
        SYNTAX SEQUENCE OF VdslChanExtendedEntry
        MAX-ACCESS not-accessible
        STATUS current
        DESCRIPTION
        	"The table displays VDSL2 channel Status. This table is supported by R5.06 and later versions."
        ::= { vdsl2Stats 1 }

        vdslChanExtendedEntry OBJECT-TYPE
        SYNTAX VdslChanExtendedEntry
        MAX-ACCESS not-accessible
        STATUS current
        DESCRIPTION
        	"An entry of vdslChanExtendedTable."
        INDEX { ifIndex,  vdslPhysSide }
        ::= { vdslChanExtendedTable 1 }

        VdslChanExtendedEntry ::=
        	SEQUENCE {
            vdslChanPrevTxRate								Gauge32,
            vdslChanActualRaMode    						Xdsl2StatusActualRaMode,
       		vdslChanRetransmissionMode    					Xdsl2StatusRtxMode,
       		vdslChanRetransmissionOverhead    				Unsigned32,
       		vdslChanGinpFramingType    						Unsigned32,
       		vdslChanActualInpAgainstREIN    				Unsigned32,
       		vdslChanReedSolomonCodeWordPerDtu    			Unsigned32
           }
              	
	vdslChanPrevTxRate OBJECT-TYPE
	SYNTAX Gauge32
	MAX-ACCESS read-only
	STATUS current
	DESCRIPTION
		"Units: kbps"
	::= { vdslChanExtendedEntry 1 } 
	
	vdslChanActualRaMode  OBJECT-TYPE
    SYNTAX      Xdsl2StatusActualRaMode
    UNITS       ""
    MAX-ACCESS  read-only
    STATUS      current
    DESCRIPTION
     "The actual RA mode.
      The possible values are:
        fixedRateMode(1) - Fixed rate mode
        raInit(2)        - Adaptive rate mode at initialization
        dynamicRa(3)     - Dynamic rate adaptation
        sosEnabled(4)    - SOS enabled"
    ::= { vdslChanExtendedEntry 2 }
    
    vdslChanRetransmissionMode  OBJECT-TYPE
    SYNTAX      Xdsl2StatusRtxMode
    UNITS       ""
    MAX-ACCESS  read-only
    STATUS      current
    DESCRIPTION
     "RTX-USED operational data parameter.
      The possible values are:
        rtxInUse(1)            - RTX in use.
        rtxForbidden(2)        - RTX not in use because RTX-MODE = FORBIDDEN.
        rtxNotSupportedXtuC(3) - RTX not in use because it is not supported by the XTU-C.
        rtxNotSupportedXtuR(4) - RTX not in use because it is not supported by the XTU-R.
        rtxNotSupportedBoth(5) - RTX not in use because it is not supported by the XTU-C and XTU-R."
    ::= { vdslChanExtendedEntry 3 }
    
    vdslChanRetransmissionOverhead  OBJECT-TYPE
    SYNTAX      Unsigned32
    UNITS       "kbps"
    MAX-ACCESS  read-only
    STATUS      current
    DESCRIPTION
       "Expected retransmission overhead in G.inp due to REIN and SHINE noise. Unit is kbps."
    ::= { vdslChanExtendedEntry 4 }
    
    vdslChanGinpFramingType  OBJECT-TYPE
    SYNTAX      Unsigned32
    UNITS       ""
    MAX-ACCESS  read-only
    STATUS      current
    DESCRIPTION
       "This parameter is equal to zero if G.inp is 
        not enabled. If G.inp is enabled, it reports 
        the framing type in use (1, 2, 3, or 4)."
    ::= { vdslChanExtendedEntry 5 }
    
    vdslChanActualInpAgainstREIN  OBJECT-TYPE
    SYNTAX      Unsigned32
    UNITS       "1/2 symbol"
    MAX-ACCESS  read-only
    STATUS      current
    DESCRIPTION
       "This parameter reports the actual INP against REIN noise. Unit is 1/2 symbol."
    ::= { vdslChanExtendedEntry 6 }
    
    vdslChanReedSolomonCodeWordPerDtu  OBJECT-TYPE
    SYNTAX      Unsigned32
    UNITS       ""
    MAX-ACCESS  read-only
    STATUS      current
    DESCRIPTION
       "This parameter reports the number of RS codewords per DTU.
        It is equal to D when PhyR is enabled."
    ::= { vdslChanExtendedEntry 7 }

-- vdslPerfDataExtendedTable
	vdslPerfDataExtendedTable OBJECT-TYPE
        SYNTAX SEQUENCE OF VdslPerfDataExtendedEntry
        MAX-ACCESS not-accessible
        STATUS current
        DESCRIPTION
        	"The table displays VDSL2 Performance Data. This table is supported by R5.06 and later versions."
        ::= { vdsl2Stats 2 }

        vdslPerfDataExtendedEntry OBJECT-TYPE
        SYNTAX VdslPerfDataExtendedEntry
        MAX-ACCESS not-accessible
        STATUS current
        DESCRIPTION
        	"An entry of vdslPerfDataExtendedTable."
        INDEX { ifIndex,  vdslPhysSide }
        ::= { vdslPerfDataExtendedTable 1 }

        VdslPerfDataExtendedEntry ::=
        	SEQUENCE {
            vdslPerfDataFECs			Unsigned32
           }
              	
	vdslPerfDataFECs OBJECT-TYPE
	SYNTAX Unsigned32
	MAX-ACCESS read-only
	STATUS current
	DESCRIPTION
		"Units: kbps"
	::= { vdslPerfDataExtendedEntry 1 }	

-- vdslChanPerfDataExtendedTable
	vdslChanPerfDataExtendedTable OBJECT-TYPE
        SYNTAX SEQUENCE OF VdslChanPerfDataExtendedEntry
        MAX-ACCESS not-accessible
        STATUS current
        DESCRIPTION
        	"The table displays VDSL2 Channel Performance Data. This table is supported by R5.06 and later versions."
        ::= { vdsl2Stats 3 }

        vdslChanPerfDataExtendedEntry OBJECT-TYPE
        SYNTAX VdslChanPerfDataExtendedEntry
        MAX-ACCESS not-accessible
        STATUS current
        DESCRIPTION
        	"An entry of vdslPerfDataExtendedTable."
        INDEX { ifIndex,  vdslPhysSide }
        ::= { vdslChanPerfDataExtendedTable 1 }

        VdslChanPerfDataExtendedEntry ::=
        	SEQUENCE {
            vdslChanPerfDataCorrectedBlks			Counter32,
            vdslChanPerfDataUncorrectBlks			Counter32,
            vdslChanPerfDataCodeViolations			Unsigned32
           }
              	
	vdslChanPerfDataCorrectedBlks OBJECT-TYPE
	SYNTAX Counter32
	MAX-ACCESS read-only
	STATUS current
	DESCRIPTION
		"Count of all blocks received with errors that were corrected since agent reset. 
		These blocks are passed on as good data. 
		Units:        blocks"
	::= { vdslChanPerfDataExtendedEntry 1 }	
	
	vdslChanPerfDataUncorrectBlks OBJECT-TYPE
	SYNTAX Counter32
	MAX-ACCESS read-only
	STATUS current
	DESCRIPTION
		"Count of all blocks received with uncorrectable errors since agent reset.
		Units:        blocks"
	::= { vdslChanPerfDataExtendedEntry 2 }
	
	vdslChanPerfDataCodeViolations OBJECT-TYPE
	SYNTAX Unsigned32
	MAX-ACCESS read-only
	STATUS current
	DESCRIPTION
		"Count of CRC-8 (FEBE for xTU-R) anomalies occurring in the
		channel during the interval.  This parameter is inhibited during
		UAS or SES.  If the CRC is applied over multiple channels, then
		each related CRC-8 (or FEBE) anomaly SHOULD increment each of the
		counters related to the individual channels."
	::= { vdslChanPerfDataExtendedEntry 3 }	

-- xdsl2PM	
xdsl2PMEx  		OBJECT IDENTIFIER ::= { vdsl2Stats 4 }

-- xdsl2PMLine
xdsl2PMLineEx  				OBJECT IDENTIFIER ::= { xdsl2PMEx 1 } 
xdsl2PMLineChannelEx		OBJECT IDENTIFIER ::= { xdsl2PMEx 2 }
xdsl2PMChannelEx 			OBJECT IDENTIFIER ::= { xdsl2PMEx 3 }


-- xdsl2PMLineCurrExtendedTable
	xdsl2PMLineCurrExtendedTable OBJECT-TYPE
        SYNTAX SEQUENCE OF Xdsl2PMLineCurrExtendedEntry
        MAX-ACCESS not-accessible
        STATUS current
        DESCRIPTION
        	"The table displays VDSL2 Line Current Performance Data. This table is supported by R5.06 and later versions."
        ::= { xdsl2PMLineEx 1 }

        xdsl2PMLineCurrExtendedEntry OBJECT-TYPE
        SYNTAX Xdsl2PMLineCurrExtendedEntry
        MAX-ACCESS not-accessible
        STATUS current
        DESCRIPTION
        	"An entry of xdsl2PMLineCurrExtendedEntry."
        INDEX { ifIndex,  xdsl2PMLCurrUnit }
        ::= { xdsl2PMLineCurrExtendedTable 1 }

        Xdsl2PMLineCurrExtendedEntry ::=
        	SEQUENCE {
            xdsl2PMLCurr15MMonitoredTime			INTEGER,
            xdsl2PMLCurr15MLofs						Counter32,
            xdsl2PMLCurr15MLols						Counter32,
            xdsl2PMLCurr15MLol						Counter32,
            xdsl2PMLCurr15MLprs						Counter32,
            xdsl2PMLCurr15MLpr						Counter32,
            xdsl2PMLCurr15MInits					Counter32,
            xdsl2PMLCurr1DayMonitoredTime			INTEGER,
            xdsl2PMLCurr1DayLofs					Counter32,
            xdsl2PMLCurr1DayLols					Counter32,
            xdsl2PMLCurr1DayLol						Counter32,
            xdsl2PMLCurr1DayLprs					Counter32,
            xdsl2PMLCurr1DayLpr						Counter32,
            xdsl2PMLCurr1DayInits					Counter32,
	       	xdsl2PMLSinceLinkInmEqInp				OCTET STRING,
	       	xdsl2PMLSinceLinkInmIAT					OCTET STRING,
	       	xdsl2PMLSinceLinkInmME					Counter32,
	       	xdsl2PMLCurr15MInmEqInp					OCTET STRING,
	       	xdsl2PMLCurr15MInmIAT					OCTET STRING,
	       	xdsl2PMLCurr15MInmME					Counter32,
	       	xdsl2PMLCurr1DayInmEqInp				OCTET STRING,
	       	xdsl2PMLCurr1DayInmIAT					OCTET STRING,
	       	xdsl2PMLCurr1DayInmME					Counter32,
	       	xdsl2PMLSinceInitLofs					Counter32,
	       	xdsl2PMLSinceInitLols					Counter32,
	       	xdsl2PMLSinceInitLol					Counter32,
	       	xdsl2PMLSinceInitLprs					Counter32,
	       	xdsl2PMLSinceInitLpr					Counter32,
	       	xdsl2PMLSinceInitInits					Counter32
           }
              	
	xdsl2PMLCurr15MMonitoredTime OBJECT-TYPE
	SYNTAX INTEGER
	MAX-ACCESS read-only
	STATUS current
	DESCRIPTION
		"Units: seconds"
	::= { xdsl2PMLineCurrExtendedEntry 1 }
	
	xdsl2PMLCurr15MLofs OBJECT-TYPE
	SYNTAX Counter32
	MAX-ACCESS read-only
	STATUS current
	DESCRIPTION
		"Count of the number of Loss of Framing failures since link up."
	::= { xdsl2PMLineCurrExtendedEntry 2 }
	
	xdsl2PMLCurr15MLols OBJECT-TYPE
	SYNTAX Counter32
	MAX-ACCESS read-only
	STATUS current
	DESCRIPTION
		"Count of the number of Loss of Link failures since link up."
	::= { xdsl2PMLineCurrExtendedEntry 3 }
	
	xdsl2PMLCurr15MLol OBJECT-TYPE
	SYNTAX Counter32
	MAX-ACCESS read-only
	STATUS current
	DESCRIPTION
		"Count of the number of Loss of Link failures."
	::= { xdsl2PMLineCurrExtendedEntry 4 }
	
	xdsl2PMLCurr15MLprs OBJECT-TYPE
	SYNTAX Counter32
	MAX-ACCESS read-only
	STATUS current
	DESCRIPTION
		"Count of the number of Loss of Power failures since link up."
	::= { xdsl2PMLineCurrExtendedEntry 5 }
	
	xdsl2PMLCurr15MLpr OBJECT-TYPE
	SYNTAX Counter32
	MAX-ACCESS read-only
	STATUS current
	DESCRIPTION
		"Count of the number of Loss of Power failures."
	::= { xdsl2PMLineCurrExtendedEntry 6 }
	
	xdsl2PMLCurr15MInits OBJECT-TYPE
	SYNTAX Counter32
	MAX-ACCESS read-only
	STATUS current
	DESCRIPTION
		"Count of the line initialization attempts since link up. Includes both successful and failed attempts."
	::= { xdsl2PMLineCurrExtendedEntry 7 }
	
	xdsl2PMLCurr1DayMonitoredTime OBJECT-TYPE
	SYNTAX INTEGER
	MAX-ACCESS read-only
	STATUS current
	DESCRIPTION
		"Units: seconds"
	::= { xdsl2PMLineCurrExtendedEntry 8 }
	
	xdsl2PMLCurr1DayLofs OBJECT-TYPE
	SYNTAX Counter32
	MAX-ACCESS read-only
	STATUS current
	DESCRIPTION
		"Count of the number of Loss of Framing failures since link up."
	::= { xdsl2PMLineCurrExtendedEntry 9 }
	
	xdsl2PMLCurr1DayLols OBJECT-TYPE
	SYNTAX Counter32
	MAX-ACCESS read-only
	STATUS current
	DESCRIPTION
		"Count of the number of Loss of Link failures since link up."
	::= { xdsl2PMLineCurrExtendedEntry 10 }
	
	xdsl2PMLCurr1DayLol OBJECT-TYPE
	SYNTAX Counter32
	MAX-ACCESS read-only
	STATUS current
	DESCRIPTION
		"Count of the number of Loss of Link failures."
	::= { xdsl2PMLineCurrExtendedEntry 11 }
	
	xdsl2PMLCurr1DayLprs OBJECT-TYPE
	SYNTAX Counter32
	MAX-ACCESS read-only
	STATUS current
	DESCRIPTION
		"Count of the number of Loss of Power failures since link up."
	::= { xdsl2PMLineCurrExtendedEntry 12 }
	
	xdsl2PMLCurr1DayLpr OBJECT-TYPE
	SYNTAX Counter32
	MAX-ACCESS read-only
	STATUS current
	DESCRIPTION
		"Count of the number of Loss of Power failures."
	::= { xdsl2PMLineCurrExtendedEntry 13 }
	
	xdsl2PMLCurr1DayInits OBJECT-TYPE
	SYNTAX Counter32
	MAX-ACCESS read-only
	STATUS current
	DESCRIPTION
		"Count of the line initialization attempts since link up. Includes both successful and failed attempts."
	::= { xdsl2PMLineCurrExtendedEntry 14 }	
	
	xdsl2PMLSinceLinkInmEqInp  OBJECT-TYPE
    SYNTAX      OCTET STRING
    MAX-ACCESS  read-only
    STATUS      current
    DESCRIPTION
       "The INM Equivalent Inp histogram since last link up. An 
    array of 68 octets (each 4 octets means amount of a bin of 
    histogram), designed for supporting from 1 to 17 bins of 
    the histogram. 
       The particular index of the bin incremented by an impulse
    noise event is equal to the computed value of equivalent INP,
    except the 17th of anomaly INPEQ, which logs all equivalent 
    INPs greater than 16.
       Each bin has a value in the range 0x0 to 0xFFFFFFFF"
    REFERENCE    "ITU-T G.993.2 Amd2, paragraph 11.4.2.2.1 (INM 
    			 procedure)"
    ::= { xdsl2PMLineCurrExtendedEntry 15 }    
    
    xdsl2PMLSinceLinkInmIAT  OBJECT-TYPE
    SYNTAX      OCTET STRING
    MAX-ACCESS  read-only
    STATUS      current
    DESCRIPTION
       "The INM Inter Arrival Time histogram since last link up. 
    An array of 32 octets (each 4 octets means amount of a bin 
    of histogram), designed for supporting from 0 to 7 bins of 
    the histogram. 
       The index of the particular bin incremented by an complete 
    impulse noise event is determained from the following 
    INMControl parameters.
       Each bin has a value in the range 0x0 to 0xFFFFFFFF"
    REFERENCE    "ITU-T G.993.2 Amd2, paragraph 11.4.2.2.1 (INM 
    			 procedure)"   
    ::= { xdsl2PMLineCurrExtendedEntry 16 }    
    
    xdsl2PMLSinceLinkInmME  OBJECT-TYPE
    SYNTAX      Counter32
    UNITS       "symbols"
    MAX-ACCESS  read-only
    STATUS      current
    DESCRIPTION
       "The INM total measurement since last link up. This 
    indication occurs every time a data symbol is processed by 
    the Impulse Noise Sensor.
       The range of the value is from 0x0 to 0xFFFFFFFF" 
    REFERENCE    "ITU-T G.993.2 Amd2, paragraph 11.4.2.2.1 (INM 
    			 procedure)"   
    ::= { xdsl2PMLineCurrExtendedEntry 17 }    
    
    xdsl2PMLCurr15MInmEqInp  OBJECT-TYPE
    SYNTAX      OCTET STRING
    MAX-ACCESS  read-only
    STATUS      current
    DESCRIPTION
       "The INM Equivalent Inp histogram during this 15min 
    interval. An array of 68 octets (each 4 octets means amount of
    a bin of histogram), designed for supporting from 1 to 17 bins
    of the histogram. 
       The particular index of the bin incremented by an impulse
    noise event is equal to the computed value of equivalent INP,
    except the 17th of anomaly INPEQ, which logs all equivalent 
    INPs greater than 16.
       Each bin has a value in the range 0x0 to 0xFFFFFFFF"
    REFERENCE    "ITU-T G.993.2 Amd2, paragraph 11.4.2.2.1 (INM 
    			 procedure)"   
    ::= { xdsl2PMLineCurrExtendedEntry 18 }    
    
    xdsl2PMLCurr15MInmIAT  OBJECT-TYPE
    SYNTAX      OCTET STRING
    MAX-ACCESS  read-only
    STATUS      current
    DESCRIPTION
       "The INM Inter Arrival Time histogram during this 15min 
    interval. An array of 32 octets (each 4 octets means amount of 
    a bin of histogram), designed for supporting from 0 to 7 bins 
    of the histogram. 
       The index of the particular bin incremented by an complete 
    impulse noise event is determained from the following 
    INMControl parameters.
       Each bin has a value in the range 0x0 to 0xFFFFFFFF"
    REFERENCE    "ITU-T G.993.2 Amd2, paragraph 11.4.2.2.1 (INM 
    			 procedure)"   
    ::= { xdsl2PMLineCurrExtendedEntry 19 }    
    
    xdsl2PMLCurr15MInmME  OBJECT-TYPE
    SYNTAX      Counter32
    MAX-ACCESS  read-only
    STATUS      current
    DESCRIPTION
       "The INM total measurement during this 15min interval. 
    This indication occurs every time a data symbol is processed 
    by the Impulse Noise Sensor.
       The range of the value is from 0x0 to 0xFFFFFFFF"
    REFERENCE    "ITU-T G.993.2 Amd2, paragraph 11.4.2.2.1 (INM 
    			 procedure)"   
    ::= { xdsl2PMLineCurrExtendedEntry 20 }    
    
    xdsl2PMLCurr1DayInmEqInp  OBJECT-TYPE
    SYNTAX      OCTET STRING
    MAX-ACCESS  read-only
    STATUS      current
    DESCRIPTION
       "The INM Equivalent Inp histogram during this 1Day interval. 
    An array of 68 octets (each 4 octets means amount of a bin of 
    histogram), designed for supporting from 1 to 17 bins of the 
    histogram. 
       The particular index of the bin incremented by an impulse
    noise event is equal to the computed value of equivalent INP,
    except the 17th of anomaly INPEQ, which logs all equivalent 
    INPs greater than 16.
       Each bin has a value in the range 0x0 to 0xFFFFFFFF"
    REFERENCE    "ITU-T G.993.2 Amd2, paragraph 11.4.2.2.1 (INM 
    			 procedure)"   
    ::= { xdsl2PMLineCurrExtendedEntry 21 }    
    
    xdsl2PMLCurr1DayInmIAT  OBJECT-TYPE
    SYNTAX      OCTET STRING
    MAX-ACCESS  read-only
    STATUS      current
    DESCRIPTION
       "The INM Inter Arrival Time histogram during this 1Day 
    interval. An array of 32 octets (each 4 octets means amount of 
    a bin of histogram), designed for supporting from 0 to 7 bins 
    of the histogram. 
       The index of the particular bin incremented by an complete 
    impulse noise event is determained from the following 
    INMControl parameters.
       Each bin has a value in the range 0x0 to 0xFFFFFFFF"
    REFERENCE    "ITU-T G.993.2 Amd2, paragraph 11.4.2.2.1 (INM 
    			 procedure)"   
    ::= { xdsl2PMLineCurrExtendedEntry 22 }    
    
    xdsl2PMLCurr1DayInmME  OBJECT-TYPE
    SYNTAX      Counter32
    MAX-ACCESS  read-only
    STATUS      current
    DESCRIPTION
       "The INM total measurement during this 1Day interval. 
    This indication occurs every time a data symbol is processed 
    by the Impulse Noise Sensor.
       The range of the value is from 0x0 to 0xFFFFFFFF"
    REFERENCE    "ITU-T G.993.2 Amd2, paragraph 11.4.2.2.1 (INM 
    			 procedure)"   
    ::= { xdsl2PMLineCurrExtendedEntry 23 }
    
    xdsl2PMLSinceInitLofs  OBJECT-TYPE
    SYNTAX      Counter32
    MAX-ACCESS  read-only
    STATUS      current
    DESCRIPTION
       "Count of seconds of Loss of Framing failures since initialized." 
    ::= { xdsl2PMLineCurrExtendedEntry 24 }
    
    xdsl2PMLSinceInitLols  OBJECT-TYPE
    SYNTAX      Counter32
    MAX-ACCESS  read-only
    STATUS      current
    DESCRIPTION
       "Count of seconds of Loss of Link failures since initialized." 
    ::= { xdsl2PMLineCurrExtendedEntry 25 }
    
    xdsl2PMLSinceInitLol  OBJECT-TYPE
    SYNTAX      Counter32
    MAX-ACCESS  read-only
    STATUS      current
    DESCRIPTION
       "Count of the number of Loss of Link failures since initialized." 
    ::= { xdsl2PMLineCurrExtendedEntry 26 }
    
    xdsl2PMLSinceInitLprs  OBJECT-TYPE
    SYNTAX      Counter32
    MAX-ACCESS  read-only
    STATUS      current
    DESCRIPTION
       "Count of seconds of Loss of Power failures since initialized." 
    ::= { xdsl2PMLineCurrExtendedEntry 27 }
    
    xdsl2PMLSinceInitLpr  OBJECT-TYPE
    SYNTAX      Counter32
    MAX-ACCESS  read-only
    STATUS      current
    DESCRIPTION
       "Count of the number of Loss of Power failures since initialized." 
    ::= { xdsl2PMLineCurrExtendedEntry 28 }
    
    xdsl2PMLSinceInitInits  OBJECT-TYPE
    SYNTAX      Counter32
    MAX-ACCESS  read-only
    STATUS      current
    DESCRIPTION
       "Count of the line initialization attempts since initialized. 
       Includes both successful and failed attempts." 
    ::= { xdsl2PMLineCurrExtendedEntry 29 }

 
 -- xdsl2PMLineHist15MinExtendedTable
	xdsl2PMLineHist15MinExtendedTable OBJECT-TYPE
        SYNTAX SEQUENCE OF Xdsl2PMLineHist15MinExtendedEntry
        MAX-ACCESS not-accessible
        STATUS current
        DESCRIPTION
        	"The table displays VDSL2 Line History 15 minute Performance Data. This table is supported by R5.06 and later versions."
        ::= { xdsl2PMLineEx 2 }

        xdsl2PMLineHist15MinExtendedEntry OBJECT-TYPE
        SYNTAX Xdsl2PMLineHist15MinExtendedEntry
        MAX-ACCESS not-accessible
        STATUS current
        DESCRIPTION
        	"An entry of xdsl2PMLineHist15MinExtendedEntry."
        INDEX { ifIndex,  xdsl2PMLHist15MUnit, xdsl2PMLHist15MInterval  }
        ::= { xdsl2PMLineHist15MinExtendedTable 1 }

        Xdsl2PMLineHist15MinExtendedEntry ::=
        	SEQUENCE {
            xdsl2PMLHist15MLofs						Counter32,
            xdsl2PMLHist15MLols						Counter32,
            xdsl2PMLHist15MLol						Counter32,
            xdsl2PMLHist15MLprs						Counter32,
            xdsl2PMLHist15MLpr						Counter32,
            xdsl2PMLHist15MInits					Counter32,
            xdsl2PMLHist15MInmEqInp		            OCTET STRING,
       		xdsl2PMLHist15MInmIAT         		    OCTET STRING,
       		xdsl2PMLHist15MInmME          	     	Counter32           
        }
              	
	xdsl2PMLHist15MLofs OBJECT-TYPE
	SYNTAX Counter32
	MAX-ACCESS read-only
	STATUS current
	DESCRIPTION
		"Count of the number of Loss of Framing failures since link up."
	::= { xdsl2PMLineHist15MinExtendedEntry 1 }
	
	xdsl2PMLHist15MLols OBJECT-TYPE
	SYNTAX Counter32
	MAX-ACCESS read-only
	STATUS current
	DESCRIPTION
		"Count of the number of Loss of Link failures since link up."
	::= { xdsl2PMLineHist15MinExtendedEntry 2 }
	
	xdsl2PMLHist15MLol OBJECT-TYPE
	SYNTAX Counter32
	MAX-ACCESS read-only
	STATUS current
	DESCRIPTION
		"Count of the number of Loss of Link failures."
	::= { xdsl2PMLineHist15MinExtendedEntry 3 }
	
	xdsl2PMLHist15MLprs OBJECT-TYPE
	SYNTAX Counter32
	MAX-ACCESS read-only
	STATUS current
	DESCRIPTION
		"Count of the number of Loss of Power failures since link up."
	::= { xdsl2PMLineHist15MinExtendedEntry 4 }
	
	xdsl2PMLHist15MLpr OBJECT-TYPE
	SYNTAX Counter32
	MAX-ACCESS read-only
	STATUS current
	DESCRIPTION
		"Count of the number of Loss of Power failures."
	::= { xdsl2PMLineHist15MinExtendedEntry 5 }
	
	xdsl2PMLHist15MInits OBJECT-TYPE
	SYNTAX Counter32
	MAX-ACCESS read-only
	STATUS current
	DESCRIPTION
		"Count of the line initialization attempts since link up. Includes both successful and failed attempts."
	::= { xdsl2PMLineHist15MinExtendedEntry 6 }  
	
	xdsl2PMLHist15MInmEqInp  OBJECT-TYPE
    SYNTAX      OCTET STRING
    MAX-ACCESS  read-only
    STATUS      current
    DESCRIPTION
       "The INM Equivalent Inp histogram during 15min interval. 
    An array of 68 octets (each 4 octets means amount of a bin of 
    histogram), designed for supporting from 1 to 17 bins of the 
    histogram. 
       The particular index of the bin incremented by an impulse
    noise event is equal to the computed value of equivalent INP,
    except the 17th of anomaly INPEQ, which logs all equivalent 
    INPs greater than 16.
       Each bin has a value in the range 0x0 to 0xFFFFFFFF"
    REFERENCE    "ITU-T G.993.2 Amd2, paragraph 11.4.2.2.1 (INM 
    			 procedure)"
    ::= { xdsl2PMLineHist15MinExtendedEntry 7 }
       
    xdsl2PMLHist15MInmIAT  OBJECT-TYPE
    SYNTAX      OCTET STRING
    MAX-ACCESS  read-only
    STATUS      current
    DESCRIPTION
       "The INM Inter Arrival Time histogram during 15min 
    interval. An array of 32 octets (each 4 octets means amount of 
    a bin of histogram), designed for supporting from 0 to 7 bins 
    of the histogram. 
       The index of the particular bin incremented by an complete 
    impulse noise event is determained from the following 
    INMControl parameters.
       Each bin has a value in the range 0x0 to 0xFFFFFFFF"
    REFERENCE    "ITU-T G.993.2 Amd2, paragraph 11.4.2.2.1 (INM 
    			 procedure)"
    ::= { xdsl2PMLineHist15MinExtendedEntry 8 }

    xdsl2PMLHist15MInmME  OBJECT-TYPE
    SYNTAX      Counter32
    MAX-ACCESS  read-only
    STATUS      current
    DESCRIPTION
       "The INM total measurement during 15min interval. 
    This indication occurs every time a data symbol is processed 
    by the Impulse Noise Sensor.
       The range of the value is from 0x0 to 0xFFFFFFFF"
    REFERENCE    "ITU-T G.993.2 Amd2, paragraph 11.4.2.2.1 (INM 
    			 procedure)"
    ::= { xdsl2PMLineHist15MinExtendedEntry 9 }
	
	-- xdsl2PMLineHist1DayExtendedTable
	xdsl2PMLineHist1DayExtendedTable OBJECT-TYPE
        SYNTAX SEQUENCE OF Xdsl2PMLineHist1DayExtendedEntry
        MAX-ACCESS not-accessible
        STATUS current
        DESCRIPTION
        	"The table displays VDSL2 Line History 1 day Performance Data. This table is supported by R5.06 and later versions."
        ::= { xdsl2PMLineEx 3 }

        xdsl2PMLineHist1DayExtendedEntry OBJECT-TYPE
        SYNTAX Xdsl2PMLineHist1DayExtendedEntry
        MAX-ACCESS not-accessible
        STATUS current
        DESCRIPTION
        	"An entry of xdsl2PMLineHist1DayExtendedTable."
        INDEX { ifIndex,  xdsl2PMLHist1DUnit , xdsl2PMLHist1DInterval  }
        ::= { xdsl2PMLineHist1DayExtendedTable 1 }

        Xdsl2PMLineHist1DayExtendedEntry ::=
        	SEQUENCE {
            xdsl2PMLHist1DLofs						Counter32,
            xdsl2PMLHist1DLols						Counter32,
            xdsl2PMLHist1DLol						Counter32,
            xdsl2PMLHist1DLprs						Counter32,
            xdsl2PMLHist1DLpr						Counter32,
            xdsl2PMLHist1DInits						Counter32,
     		xdsl2PMLHist1DInmEqInp         			OCTET STRING,
       		xdsl2PMLHist1DInmIAT           			OCTET STRING,
       		xdsl2PMLHist1DInmME            			Counter32           
        }
              	
	xdsl2PMLHist1DLofs OBJECT-TYPE
	SYNTAX Counter32
	MAX-ACCESS read-only
	STATUS current
	DESCRIPTION
		"Count of the number of Loss of Framing failures since link up."
	::= { xdsl2PMLineHist1DayExtendedEntry 1 }
	
	xdsl2PMLHist1DLols OBJECT-TYPE
	SYNTAX Counter32
	MAX-ACCESS read-only
	STATUS current
	DESCRIPTION
		"Count of the number of Loss of Link failures since link up."
	::= { xdsl2PMLineHist1DayExtendedEntry 2 }
	
	xdsl2PMLHist1DLol OBJECT-TYPE
	SYNTAX Counter32
	MAX-ACCESS read-only
	STATUS current
	DESCRIPTION
		"Count of the number of Loss of Link failures."
	::= { xdsl2PMLineHist1DayExtendedEntry 3 }
	
	xdsl2PMLHist1DLprs OBJECT-TYPE
	SYNTAX Counter32
	MAX-ACCESS read-only
	STATUS current
	DESCRIPTION
		"Count of the number of Loss of Power failures since link up."
	::= { xdsl2PMLineHist1DayExtendedEntry 4 }
	
	xdsl2PMLHist1DLpr OBJECT-TYPE
	SYNTAX Counter32
	MAX-ACCESS read-only
	STATUS current
	DESCRIPTION
		"Count of the number of Loss of Power failures."
	::= { xdsl2PMLineHist1DayExtendedEntry 5 }
	
	xdsl2PMLHist1DInits OBJECT-TYPE
	SYNTAX Counter32
	MAX-ACCESS read-only
	STATUS current
	DESCRIPTION
		"Count of the line initialization attempts since link up. Includes both successful and failed attempts."
	::= { xdsl2PMLineHist1DayExtendedEntry 6 } 
	
	xdsl2PMLHist1DInmEqInp  OBJECT-TYPE
    SYNTAX      OCTET STRING
    MAX-ACCESS  read-only
    STATUS      current
    DESCRIPTION
       "The INM Equivalent Inp histogram during 1Day interval. 
    An array of 68 octets (each 4 octets means amount of a bin of 
    histogram), designed for supporting from 1 to 17 bins of the 
    histogram. 
       The particular index of the bin incremented by an impulse
    noise event is equal to the computed value of equivalent INP,
    except the 17th of anomaly INPEQ, which logs all equivalent 
    INPs greater than 16.
       Each bin has a value in the range 0x0 to 0xFFFFFFFF"
    REFERENCE    "ITU-T G.993.2 Amd2, paragraph 11.4.2.2.1 (INM 
    			 procedure)"
    ::= { xdsl2PMLineHist1DayExtendedEntry 7 }    
    
    xdsl2PMLHist1DInmIAT  OBJECT-TYPE
    SYNTAX      OCTET STRING
    MAX-ACCESS  read-only
    STATUS      current
    DESCRIPTION
       "The INM Inter Arrival Time histogram during 1Day 
    interval. An array of 32 octets (each 4 octets means amount of 
    a bin of histogram), designed for supporting from 0 to 7 bins 
    of the histogram. 
       The index of the particular bin incremented by an complete 
    impulse noise event is determained from the following 
    INMControl parameters.
       Each bin has a value in the range 0x0 to 0xFFFFFFFF"
    REFERENCE    "ITU-T G.993.2 Amd2, paragraph 11.4.2.2.1 (INM 
    			 procedure)"
    ::= { xdsl2PMLineHist1DayExtendedEntry 8 }    
    
    xdsl2PMLHist1DInmME  OBJECT-TYPE
    SYNTAX      Counter32
    MAX-ACCESS  read-only
    STATUS      current
    DESCRIPTION
       "The INM total measurement during this 1Day interval. 
    This indication occurs every time a data symbol is processed 
    by the Impulse Noise Sensor.
       The range of the value is from 0x0 to 0xFFFFFFFF"
    REFERENCE    "ITU-T G.993.2 Amd2, paragraph 11.4.2.2.1 (INM 
    			 procedure)"
    ::= { xdsl2PMLineHist1DayExtendedEntry 9 }
		
	-- xdsl2PMChannel
-- xdsl2PMChCurrExtendedTable
	xdsl2PMChCurrExtendedTable OBJECT-TYPE
        SYNTAX SEQUENCE OF Xdsl2PMChCurrExtendedEntry
        MAX-ACCESS not-accessible
        STATUS current
        DESCRIPTION
        	"The table displays VDSL2 Channel Current Performance Data. This table is supported by R5.06 and later versions."
        ::= { xdsl2PMLineChannelEx 1 }

        xdsl2PMChCurrExtendedEntry OBJECT-TYPE
        SYNTAX Xdsl2PMChCurrExtendedEntry
        MAX-ACCESS not-accessible
        STATUS current
        DESCRIPTION
        	"An entry of xdsl2PMChHist15MinExtendedTable."
        INDEX { ifIndex,  xdsl2PMLCurrUnit }
        ::= { xdsl2PMChCurrExtendedTable 1 }

        Xdsl2PMChCurrExtendedEntry ::=
        	SEQUENCE {
            xdsl2PMChCurr15MUncorrectBlks		Counter32,
            xdsl2PMChCurr1DayUncorrectBlks		Counter32,
            xdsl2PMChSinceLinkRtx           	Unsigned32,
	       	xdsl2PMChCurr15MRtx              	Unsigned32,
	       	xdsl2PMChCurr1DayRtx             	Unsigned32,
	       	xdsl2PMChSinceLinkRtxCorrected  	Unsigned32,
	       	xdsl2PMChCurr15MRtxCorrected    	Unsigned32,
	       	xdsl2PMChCurr1DayRtxCorrected   	Unsigned32,
	       	xdsl2PMChSinceLinkRtxUncorrected	Unsigned32,
	       	xdsl2PMChCurr15MRtxUncorrected  	Unsigned32,
	       	xdsl2PMChCurr1DayRtxUncorrected 	Unsigned32,
	       	xdsl2PMChSinceLinkLEFTRs          	Unsigned32,
	       	xdsl2PMChCurr15MLEFTRs             	Unsigned32,
	       	xdsl2PMChCurr1DayLEFTRs            	Unsigned32,
	       	xdsl2PMChSinceLinkMinEFTR          	Unsigned32,
	       	xdsl2PMChCurr15MMinEFTR            	Unsigned32,
	       	xdsl2PMChCurr1DayMinEFTR           	Unsigned32,
	       	xdsl2PMChSinceLinkErrFreeBits      	Unsigned32,
	       	xdsl2PMChCurr15MErrFreeBits        	Unsigned32,
	       	xdsl2PMChCurr1DayErrFreeBits       	Unsigned32
           }
              	
	xdsl2PMChCurr15MUncorrectBlks OBJECT-TYPE
	SYNTAX Counter32
	MAX-ACCESS read-only
	STATUS current
	DESCRIPTION
		"Count of all blocks received with uncorrectable errors on this channel within the current 15 minute interval."
	::= { xdsl2PMChCurrExtendedEntry 1 }
	
	xdsl2PMChCurr1DayUncorrectBlks OBJECT-TYPE
	SYNTAX Counter32
	MAX-ACCESS read-only
	STATUS current
	DESCRIPTION
		"Count of all blocks received with uncorrectable errors on this channel within the current 7 day interval."
	::= { xdsl2PMChCurrExtendedEntry 2 }
	
	xdsl2PMChSinceLinkRtx  OBJECT-TYPE
    SYNTAX      Unsigned32
    MAX-ACCESS  read-only
    STATUS      current
    DESCRIPTION
       "Number of codewords retransmitted since last link up."
   ::= { xdsl2PMChCurrExtendedEntry 3 }

    xdsl2PMChCurr15MRtx OBJECT-TYPE
    SYNTAX      Unsigned32
    MAX-ACCESS  read-only
    STATUS      current
    DESCRIPTION
       "Number of codewords retransmitted during this interval."
   ::= { xdsl2PMChCurrExtendedEntry 4 }

    xdsl2PMChCurr1DayRtx OBJECT-TYPE
    SYNTAX      Unsigned32
    MAX-ACCESS  read-only
    STATUS      current
    DESCRIPTION
       "Number of codewords retransmitted during this interval."
   ::= { xdsl2PMChCurrExtendedEntry 5 }

    xdsl2PMChSinceLinkRtxCorrected OBJECT-TYPE
    SYNTAX      Unsigned32
    MAX-ACCESS  read-only
    STATUS      current
    DESCRIPTION
       "Number of codewords corrected through retransmission since last link up."
   ::= { xdsl2PMChCurrExtendedEntry 6 }

    xdsl2PMChCurr15MRtxCorrected OBJECT-TYPE
    SYNTAX      Unsigned32
    MAX-ACCESS  read-only
    STATUS      current
    DESCRIPTION
       "Number of codewords corrected through retransmission during this interval."
   ::= { xdsl2PMChCurrExtendedEntry 7 }

    xdsl2PMChCurr1DayRtxCorrected OBJECT-TYPE
    SYNTAX      Unsigned32
    MAX-ACCESS  read-only
    STATUS      current
    DESCRIPTION
       "Number of codewords corrected through retransmission during this interval."
   ::= { xdsl2PMChCurrExtendedEntry 8 }

    xdsl2PMChSinceLinkRtxUncorrected OBJECT-TYPE
    SYNTAX      Unsigned32
    MAX-ACCESS  read-only
    STATUS      current
    DESCRIPTION
       "Number of codewords left uncorrected after retransmission since last link up."
   ::= { xdsl2PMChCurrExtendedEntry 9 }

    xdsl2PMChCurr15MRtxUncorrected OBJECT-TYPE
    SYNTAX      Unsigned32
    MAX-ACCESS  read-only
    STATUS      current
    DESCRIPTION
       "Number of codewords left uncorrected after retransmission during this interval."
   ::= { xdsl2PMChCurrExtendedEntry 10 }

    xdsl2PMChCurr1DayRtxUncorrected OBJECT-TYPE
    SYNTAX      Unsigned32
    MAX-ACCESS  read-only
    STATUS      current
    DESCRIPTION
       "Number of codewords left uncorrected after retransmission during this interval."
   ::= { xdsl2PMChCurrExtendedEntry 11 }

    xdsl2PMChSinceLinkLEFTRs  OBJECT-TYPE
    SYNTAX      Unsigned32
    MAX-ACCESS  read-only
    STATUS      current
    DESCRIPTION
       "Low Error-Free Throughput Rate Seconds since last link up."
   ::= { xdsl2PMChCurrExtendedEntry 12 }

    xdsl2PMChCurr15MLEFTRs  OBJECT-TYPE
    SYNTAX      Unsigned32
    MAX-ACCESS  read-only
    STATUS      current
    DESCRIPTION
       "Low Error-Free Throughput Rate Seconds during this interval."
   ::= { xdsl2PMChCurrExtendedEntry 13 }

    xdsl2PMChCurr1DayLEFTRs  OBJECT-TYPE
    SYNTAX      Unsigned32
    MAX-ACCESS  read-only
    STATUS      current
    DESCRIPTION
       "Low Error-Free Throughput Rate Seconds during this interval."
   ::= { xdsl2PMChCurrExtendedEntry 14 }

    xdsl2PMChSinceLinkMinEFTR  OBJECT-TYPE
    SYNTAX      Unsigned32
    MAX-ACCESS  read-only
    STATUS      current
    DESCRIPTION
       "Lowest EFTR observed since last link up."
   ::= { xdsl2PMChCurrExtendedEntry 15 }

    xdsl2PMChCurr15MMinEFTR  OBJECT-TYPE
    SYNTAX      Unsigned32
    MAX-ACCESS  read-only
    STATUS      current
    DESCRIPTION
       "Lowest EFTR observed in the current interval."
   ::= { xdsl2PMChCurrExtendedEntry 16 }

    xdsl2PMChCurr1DayMinEFTR  OBJECT-TYPE
    SYNTAX      Unsigned32
    MAX-ACCESS  read-only
    STATUS      current
    DESCRIPTION
       "Lowest EFTR observed in the current interval."
   ::= { xdsl2PMChCurrExtendedEntry 17 }

    xdsl2PMChSinceLinkErrFreeBits  OBJECT-TYPE
    SYNTAX      Unsigned32
    MAX-ACCESS  read-only
    STATUS      current
    DESCRIPTION
       "The number of bits belonging to correct DTUs leaving the Rx PMS-TC oo 2(oV16) since last link up."
   ::= { xdsl2PMChCurrExtendedEntry 18 }

    xdsl2PMChCurr15MErrFreeBits  OBJECT-TYPE
    SYNTAX      Unsigned32
    MAX-ACCESS  read-only
    STATUS      current
    DESCRIPTION
       "The number of bits belonging to correct DTUs leaving the Rx PMS-TC oo 2(oV16) during this interval."
   ::= { xdsl2PMChCurrExtendedEntry 19 }

    xdsl2PMChCurr1DayErrFreeBits  OBJECT-TYPE
    SYNTAX      Unsigned32
    MAX-ACCESS  read-only
    STATUS      current
    DESCRIPTION
       "The number of bits belonging to correct DTUs leaving the Rx PMS-TC oo 2(oV16) during this interval."
   ::= { xdsl2PMChCurrExtendedEntry 20 }
	
-- xdsl2PMChHist15MinExtendedTable
	xdsl2PMChHist15MinExtendedTable OBJECT-TYPE
        SYNTAX SEQUENCE OF Xdsl2PMChHist15MinExtendedEntry
        MAX-ACCESS not-accessible
        STATUS current
        DESCRIPTION
        	"The table displays VDSL2 Channel History 15 minute Performance Data. This table is supported by R5.06 and later versions."
        ::= { xdsl2PMChannelEx 1 }

        xdsl2PMChHist15MinExtendedEntry OBJECT-TYPE
        SYNTAX Xdsl2PMChHist15MinExtendedEntry
        MAX-ACCESS not-accessible
        STATUS current
        DESCRIPTION
        	"An entry of xdsl2PMChHist15MinExtendedTable."
        INDEX { ifIndex,  xdsl2PMChHist15MUnit, xdsl2PMChHist15MInterval  }
        ::= { xdsl2PMChHist15MinExtendedTable 1 }

        Xdsl2PMChHist15MinExtendedEntry ::=
        	SEQUENCE {
            xdsl2PMChHist15MUncorrectBlks 			Counter32,
       		xdsl2PMChHist15MRtx						Unsigned32,
       		xdsl2PMChHist15MRtxCorrected			Unsigned32,
       		xdsl2PMChHist15MRtxUncorrected			Unsigned32,
       		xdsl2PMChHist15MLEFTRs                  Unsigned32,
       		xdsl2PMChHist15MMinEFTR                 Unsigned32,
       		xdsl2PMChHist15MErrFreeBits             Unsigned32
        }
              	
	xdsl2PMChHist15MUncorrectBlks OBJECT-TYPE
	SYNTAX Counter32
	MAX-ACCESS read-only
	STATUS current
	DESCRIPTION
		"Count of all blocks received with uncorrectable errors on this channel within the history 15 minute interval."
	::= { xdsl2PMChHist15MinExtendedEntry 1 }
	
	xdsl2PMChHist15MRtx OBJECT-TYPE
    SYNTAX      Unsigned32
    MAX-ACCESS  read-only
    STATUS      current
    DESCRIPTION
       "Number of codewords retransmitted during this interval."
    ::= { xdsl2PMChHist15MinExtendedEntry 2 }
    
    xdsl2PMChHist15MRtxCorrected OBJECT-TYPE
    SYNTAX      Unsigned32
    MAX-ACCESS  read-only
    STATUS      current
    DESCRIPTION
       "Number of codewords corrected through retransmission during this interval."
    ::= { xdsl2PMChHist15MinExtendedEntry 3 }
    
    xdsl2PMChHist15MRtxUncorrected OBJECT-TYPE
    SYNTAX      Unsigned32
    MAX-ACCESS  read-only
    STATUS      current
    DESCRIPTION
       "Number of codewords left uncorrected after retransmission during this interval."
    ::= { xdsl2PMChHist15MinExtendedEntry 4 }
    
    xdsl2PMChHist15MLEFTRs  OBJECT-TYPE
    SYNTAX      Unsigned32
    MAX-ACCESS  read-only
    STATUS      current
    DESCRIPTION
       "Low Error-Free Throughput Rate Seconds during this interval."
    ::= { xdsl2PMChHist15MinExtendedEntry 5 }
    
    xdsl2PMChHist15MMinEFTR  OBJECT-TYPE
    SYNTAX      Unsigned32
    MAX-ACCESS  read-only
    STATUS      current
    DESCRIPTION
       "Lowest EFTR observed in the current interval."
    ::= { xdsl2PMChHist15MinExtendedEntry 6 }
    
    xdsl2PMChHist15MErrFreeBits  OBJECT-TYPE
    SYNTAX      Unsigned32
    MAX-ACCESS  read-only
    STATUS      current
    DESCRIPTION
       "The number of bits belonging to correct DTUs leaving the Rx PMS-TC oo 2(oV16) during this interval."
    ::= { xdsl2PMChHist15MinExtendedEntry 7 } 
	
-- xdsl2PMChHist1DExtendedTable
	xdsl2PMChHist1DExtendedTable OBJECT-TYPE
        SYNTAX SEQUENCE OF Xdsl2PMChHist1DExtendedEntry
        MAX-ACCESS not-accessible
        STATUS current
        DESCRIPTION
        	"The table displays VDSL2 Channel History 1 day Performance Data. This table is supported by R5.06 and later versions."
        ::= { xdsl2PMChannelEx 2 }

        xdsl2PMChHist1DExtendedEntry OBJECT-TYPE
        SYNTAX Xdsl2PMChHist1DExtendedEntry
        MAX-ACCESS not-accessible
        STATUS current
        DESCRIPTION
        	"An entry of xdsl2PMChHist1DExtendedTable."
        INDEX { ifIndex,  xdsl2PMChHist1DUnit, xdsl2PMChHist1DInterval  }
        ::= { xdsl2PMChHist1DExtendedTable 1 }

        Xdsl2PMChHist1DExtendedEntry ::=
        	SEQUENCE {
            xdsl2PMChHist1DUncorrectBlks				Counter32,
            xdsl2PMChHist1DayRtx   		               	Unsigned32,
       		xdsl2PMChHist1DayRtxCorrected		        Unsigned32,
       		xdsl2PMChHist1DayRtxUncorrected		       	Unsigned32,
       		xdsl2PMChHist1DayLEFTRs                  	Unsigned32,
       		xdsl2PMChHist1DayMinEFTR                 	Unsigned32,
       		xdsl2PMChHist1DayErrFreeBits            	Unsigned32
        }
              	
	xdsl2PMChHist1DUncorrectBlks OBJECT-TYPE
	SYNTAX Counter32
	MAX-ACCESS read-only
	STATUS current
	DESCRIPTION
		"Count of all blocks received with uncorrectable errors on this channel within the history 1 day interval."
	::= { xdsl2PMChHist1DExtendedEntry 1 } 
	
	xdsl2PMChHist1DayRtx OBJECT-TYPE
    SYNTAX      Unsigned32
    MAX-ACCESS  read-only
    STATUS      current
    DESCRIPTION
       "Number of codewords retransmitted during this interval."
    ::= { xdsl2PMChHist1DExtendedEntry 2 }
    
    xdsl2PMChHist1DayRtxCorrected OBJECT-TYPE
    SYNTAX      Unsigned32
    MAX-ACCESS  read-only
    STATUS      current
    DESCRIPTION
       "Number of codewords corrected through retransmission during this interval."
    ::= { xdsl2PMChHist1DExtendedEntry 3 }
    
    xdsl2PMChHist1DayRtxUncorrected OBJECT-TYPE
    SYNTAX      Unsigned32
    MAX-ACCESS  read-only
    STATUS      current
    DESCRIPTION
       "Number of codewords left uncorrected after retransmission during this interval."
    ::= { xdsl2PMChHist1DExtendedEntry 4 }
    
    xdsl2PMChHist1DayLEFTRs  OBJECT-TYPE
    SYNTAX      Unsigned32
    MAX-ACCESS  read-only
    STATUS      current
    DESCRIPTION
       "Low Error-Free Throughput Rate Seconds during this interval."
    ::= { xdsl2PMChHist1DExtendedEntry 5 }
    
    xdsl2PMChHist1DayMinEFTR  OBJECT-TYPE
    SYNTAX      Unsigned32
    MAX-ACCESS  read-only
    STATUS      current
    DESCRIPTION
       "Lowest EFTR observed in the current interval."
    ::= { xdsl2PMChHist1DExtendedEntry 6 }
    
    xdsl2PMChHist1DayErrFreeBits  OBJECT-TYPE
    SYNTAX      Unsigned32
    MAX-ACCESS  read-only
    STATUS      current
    DESCRIPTION
       "The number of bits belonging to correct DTUs leaving the Rx PMS-TC oo 2(oV16) during this interval."
    ::= { xdsl2PMChHist1DExtendedEntry 7 }    
	
	-- xdsl2LineBandExtTable
	xdsl2LineBandExtTable OBJECT-TYPE
        SYNTAX SEQUENCE OF Xdsl2LineBandExtEntry
        MAX-ACCESS not-accessible
        STATUS current
        DESCRIPTION
        	" This table is supported by R5.06 and later versions."
        ::= { vdsl2Stats 5 }

        xdsl2LineBandExtEntry OBJECT-TYPE
        SYNTAX Xdsl2LineBandExtEntry
        MAX-ACCESS not-accessible
        STATUS current
        DESCRIPTION
        	"An entry of xdsl2LineBandExtTable."
        INDEX { ifIndex,  xdsl2LineBand }
        ::= { xdsl2LineBandExtTable 1 }

        Xdsl2LineBandExtEntry ::=
        	SEQUENCE {
            xdsl2LineBandTxPower			INTEGER,
            xdsl2LineBandRxPower			INTEGER
           }
              	
	xdsl2LineBandTxPower OBJECT-TYPE
	SYNTAX INTEGER
	MAX-ACCESS read-only
	STATUS current
	DESCRIPTION
		"Xdsl line band Tx power (in unit of 0.1 Dbm, -1280 indicates that power is empty)"
	::= { xdsl2LineBandExtEntry 1 }	

	xdsl2LineBandRxPower OBJECT-TYPE
	SYNTAX INTEGER
	MAX-ACCESS read-only
	STATUS current
	DESCRIPTION
		"Xdsl line band Rx power (in unit of 0.1 Dbm, -1280 indicates that power is empty)"
	::= { xdsl2LineBandExtEntry 2 }		

--------------------
--  MLD Stats Table
--------------------
	mldStatsV1QueryInCnt OBJECT-TYPE
	SYNTAX Counter32
	MAX-ACCESS read-only
	STATUS current
	DESCRIPTION
		""
	::= { mldStats 1 }
	
	mldStatsV1ReportInCnt OBJECT-TYPE
	SYNTAX Counter32
	MAX-ACCESS read-only
	STATUS current
	DESCRIPTION
		""
	::= { mldStats 2 }	
	
	mldStatsV1DoneInCnt OBJECT-TYPE
	SYNTAX Counter32
	MAX-ACCESS read-only
	STATUS current
	DESCRIPTION
		""
	::= { mldStats 3 }
	
	mldStatsV1QueryInDropCnt OBJECT-TYPE
	SYNTAX Counter32
	MAX-ACCESS read-only
	STATUS current
	DESCRIPTION
		""
	::= { mldStats 4 }
	
	mldStatsV1ReportInDropCnt OBJECT-TYPE
	SYNTAX Counter32
	MAX-ACCESS read-only
	STATUS current
	DESCRIPTION
		""
	::= { mldStats 5 }
	
	mldStatsV1DoneInDropCnt OBJECT-TYPE
	SYNTAX Counter32
	MAX-ACCESS read-only
	STATUS current
	DESCRIPTION
		""
	::= { mldStats 6 }
	
	mldStatsV1QueryOutCnt OBJECT-TYPE
	SYNTAX Counter32
	MAX-ACCESS read-only
	STATUS current
	DESCRIPTION
		""
	::= { mldStats 7 }
	
	mldStatsV1ReportOutCnt OBJECT-TYPE
	SYNTAX Counter32
	MAX-ACCESS read-only
	STATUS current
	DESCRIPTION
		""
	::= { mldStats 8 }	
	
	mldStatsV1DoneOutCnt OBJECT-TYPE
	SYNTAX Counter32
	MAX-ACCESS read-only
	STATUS current
	DESCRIPTION
		""
	::= { mldStats 9 }
	
	mldStatsV2QueryInCnt OBJECT-TYPE
	SYNTAX Counter32
	MAX-ACCESS read-only
	STATUS current
	DESCRIPTION
		""
	::= { mldStats 10 }	
	
	mldStatsV2ReportInCnt OBJECT-TYPE
	SYNTAX Counter32
	MAX-ACCESS read-only
	STATUS current
	DESCRIPTION
		""
	::= { mldStats 11 }	
	
	mldStatsV2QueryInDropCnt OBJECT-TYPE
	SYNTAX Counter32
	MAX-ACCESS read-only
	STATUS current
	DESCRIPTION
		""
	::= { mldStats 12 } 
	
	mldStatsV2ReportInDropCnt OBJECT-TYPE
	SYNTAX Counter32
	MAX-ACCESS read-only
	STATUS current
	DESCRIPTION
		""
	::= { mldStats 13 } 
	
	mldStatsV2QueryOutCnt OBJECT-TYPE
	SYNTAX Counter32
	MAX-ACCESS read-only
	STATUS current
	DESCRIPTION
		""
	::= { mldStats 14 }
	
	mldStatsV2ReportOutCnt OBJECT-TYPE
	SYNTAX Counter32
	MAX-ACCESS read-only
	STATUS current
	DESCRIPTION
		""
	::= { mldStats 15 } 
	
	mldNumOfActiveGroups OBJECT-TYPE
	SYNTAX INTEGER
	MAX-ACCESS read-only
	STATUS current
	DESCRIPTION
		""
	::= { mldStats 16 }

-- mldGroupTable
	mldGroupTable OBJECT-TYPE
        SYNTAX SEQUENCE OF MldGroupEntry
        MAX-ACCESS not-accessible
        STATUS current
        DESCRIPTION
        	" This table is supported by R5.06 and later versions."
        ::= { mldStats 17 }

        mldGroupEntry OBJECT-TYPE
        SYNTAX MldGroupEntry
        MAX-ACCESS not-accessible
        STATUS current
        DESCRIPTION
        	"An entry of mldGroupTable."
        INDEX {  mldGroupVid, mldGroupIp }
        ::= { mldGroupTable 1 }

        MldGroupEntry ::=
        	SEQUENCE {
            mldGroupVid				VlanIndex,
            mldGroupIp				InetAddress,
            mldGroupNumOfMembers	INTEGER,
         	mldGroupMemberPorts		PortList,
         	mldGroupNumOfActiveUsers	INTEGER	   	
           }
              	
	mldGroupVid OBJECT-TYPE
	SYNTAX VlanIndex
	MAX-ACCESS read-only
	STATUS current
	DESCRIPTION
		""
	::= { mldGroupEntry 1 }	
	
	mldGroupIp OBJECT-TYPE
	SYNTAX InetAddress
	MAX-ACCESS read-only
	STATUS current
	DESCRIPTION
		""
	::= { mldGroupEntry 2 }
	
	mldGroupNumOfMembers OBJECT-TYPE
	SYNTAX INTEGER
	MAX-ACCESS read-only
	STATUS current
	DESCRIPTION
		""
	::= { mldGroupEntry 3 }
	
	mldGroupMemberPorts OBJECT-TYPE
	SYNTAX PortList
	MAX-ACCESS read-only
	STATUS current
	DESCRIPTION
		""
	::= { mldGroupEntry 4 }
	
	mldGroupNumOfActiveUsers OBJECT-TYPE
	SYNTAX INTEGER
	MAX-ACCESS read-only
	STATUS current
	DESCRIPTION
		"Number of active users."
	::= { mldGroupEntry 5 }  
	
-- mldGroupPortTable
	mldGroupPortTable OBJECT-TYPE
        SYNTAX SEQUENCE OF MldGroupPortEntry
        MAX-ACCESS not-accessible
        STATUS current
        DESCRIPTION
        	" This table is supported by R5.06 and later versions."
        ::= { mldStats 18 }

        mldGroupPortEntry OBJECT-TYPE
        SYNTAX MldGroupPortEntry
        MAX-ACCESS not-accessible
        STATUS current
        DESCRIPTION
        	"An entry of mldGroupPortTable."
        INDEX {  ifIndex, mldGroupPortVid, mldGroupPortIp, mldGroupPortSourceIp }
        ::= { mldGroupPortTable 1 }

        MldGroupPortEntry ::=
        	SEQUENCE {
            mldGroupPortVid				VlanIndex,
            mldGroupPortIp				InetAddress,
            mldGroupPortSourceIp		InetAddress   	
           }
              	
	mldGroupPortVid OBJECT-TYPE
	SYNTAX VlanIndex
	MAX-ACCESS read-only
	STATUS current
	DESCRIPTION
		""
	::= { mldGroupPortEntry 1 }	
	
	mldGroupPortIp OBJECT-TYPE
	SYNTAX InetAddress
	MAX-ACCESS read-only
	STATUS current
	DESCRIPTION
		""
	::= { mldGroupPortEntry 2 }
	
	mldGroupPortSourceIp OBJECT-TYPE
	SYNTAX InetAddress
	MAX-ACCESS read-only
	STATUS current
	DESCRIPTION
		""
	::= { mldGroupPortEntry 3 }

-- mldPortCtrlPduTable
	mldPortCtrlPduTable OBJECT-TYPE
        SYNTAX SEQUENCE OF MldPortCtrlPduEntry
        MAX-ACCESS not-accessible
        STATUS current
        DESCRIPTION
        	" This table is supported by R5.06 and later versions."
        ::= { mldStats 19 }

        mldPortCtrlPduEntry OBJECT-TYPE
        SYNTAX MldPortCtrlPduEntry
        MAX-ACCESS not-accessible
        STATUS current
        DESCRIPTION
        	"An entry of mldPortCtrlPduTable."
        INDEX {  ifIndex }
        ::= { mldPortCtrlPduTable 1 }

        MldPortCtrlPduEntry ::=
        	SEQUENCE {
            mldPortCtrlPduQueryCnt					Counter32,
            mldPortCtrlPduReportCnt					Counter32,
            mldPortCtrlPduLeaveCnt					Counter32,
            mldPortNumOfActiveGroups				INTEGER,
            mldPortCtrlPduV1SuccessJoinCnt			Counter32,
            mldPortCtrlPduV1UnsuccJoinCnt			Counter32,
            mldPortCtrlPduGenQryCnt					Counter32,
            mldPortCtrlPduSpecQryCnt				Counter32,
            mldPortCtrlPduV2SuccessReportCnt		Counter32,
            mldPortCtrlPduV2UnsuccReportCnt			Counter32,
            mldPortCtrlPduInvalidCnt				Counter32   	
           }
              	
	mldPortCtrlPduQueryCnt OBJECT-TYPE
	SYNTAX Counter32
	MAX-ACCESS read-only
	STATUS current
	DESCRIPTION
		""
	::= { mldPortCtrlPduEntry 1 }	    
	
	mldPortCtrlPduReportCnt OBJECT-TYPE
	SYNTAX Counter32
	MAX-ACCESS read-only
	STATUS current
	DESCRIPTION
		""
	::= { mldPortCtrlPduEntry 2 }	

	mldPortCtrlPduLeaveCnt OBJECT-TYPE
	SYNTAX Counter32
	MAX-ACCESS read-only
	STATUS current
	DESCRIPTION
		""
	::= { mldPortCtrlPduEntry 3 }
	
	mldPortNumOfActiveGroups OBJECT-TYPE
	SYNTAX INTEGER
	MAX-ACCESS read-only
	STATUS current
	DESCRIPTION
		""
	::= { mldPortCtrlPduEntry 4 }
	
	mldPortCtrlPduV1SuccessJoinCnt OBJECT-TYPE
	SYNTAX Counter32
	MAX-ACCESS read-only
	STATUS current
	DESCRIPTION
		""
	::= { mldPortCtrlPduEntry 5 }
	
	mldPortCtrlPduV1UnsuccJoinCnt OBJECT-TYPE
	SYNTAX Counter32
	MAX-ACCESS read-only
	STATUS current
	DESCRIPTION
		""
	::= { mldPortCtrlPduEntry 6 }
	
	mldPortCtrlPduGenQryCnt OBJECT-TYPE
	SYNTAX Counter32
	MAX-ACCESS read-only
	STATUS current
	DESCRIPTION
		""
	::= { mldPortCtrlPduEntry 7 }
	
	mldPortCtrlPduSpecQryCnt OBJECT-TYPE
	SYNTAX Counter32
	MAX-ACCESS read-only
	STATUS current
	DESCRIPTION
		""
	::= { mldPortCtrlPduEntry 8 }
	
	mldPortCtrlPduV2SuccessReportCnt OBJECT-TYPE
	SYNTAX Counter32
	MAX-ACCESS read-only
	STATUS current
	DESCRIPTION
		""
	::= { mldPortCtrlPduEntry 9 }
	
	mldPortCtrlPduV2UnsuccReportCnt OBJECT-TYPE
	SYNTAX Counter32
	MAX-ACCESS read-only
	STATUS current
	DESCRIPTION
		""
	::= { mldPortCtrlPduEntry 10 }
	
	mldPortCtrlPduInvalidCnt OBJECT-TYPE
	SYNTAX Counter32
	MAX-ACCESS read-only
	STATUS current
	DESCRIPTION
		""
	::= { mldPortCtrlPduEntry 11 }	

-- mldVlanStatsTable
	mldVlanStatsTable OBJECT-TYPE
        SYNTAX SEQUENCE OF MldVlanStatsuEntry
        MAX-ACCESS not-accessible
        STATUS current
        DESCRIPTION
        	" This table is supported by R5.06 and later versions."
        ::= { mldStats 20 }

        mldVlanStatsuEntry OBJECT-TYPE
        SYNTAX MldVlanStatsuEntry
        MAX-ACCESS not-accessible
        STATUS current
        DESCRIPTION
        	"An entry of mldVlanStatsTable."
        INDEX {  mldVlanStatsVlanIndex }
        ::= { mldVlanStatsTable 1 }

        MldVlanStatsuEntry ::=
        	SEQUENCE {
            mldVlanStatsVlanIndex					VlanIndex,
            mldVlanStatsNumOfActiveGroups			INTEGER,
            mldVlanStatsQueryPort					INTEGER,
            mldVlanStatsQuerierIp					InetAddress,
            mldVlanStatsV1QueryInCnt				Counter32,
            mldVlanStatsV1ReportInCnt				Counter32,
            mldVlanStatsV1DoneInCnt					Counter32,
            mldVlanStatsV1QueryInDropCnt			Counter32,
            mldVlanStatsV1ReportInDropCnt			Counter32,
            mldVlanStatsV1DoneInDropCnt				Counter32,
            mldVlanStatsV1QueryOutCnt				Counter32,
            mldVlanStatsV1ReportOutCnt				Counter32,
            mldVlanStatsV1DoneOutCnt				Counter32,
            mldVlanStatsV2QueryInCnt				Counter32,
            mldVlanStatsV2ReportInCnt				Counter32,
            mldVlanStatsV2QueryInDropCnt			Counter32,
            mldVlanStatsV2ReportInDropCnt			Counter32,
            mldVlanStatsV2QueryOutCnt				Counter32,
            mldVlanStatsV2ReportOutCnt				Counter32   	
           }
              	
	mldVlanStatsVlanIndex OBJECT-TYPE
	SYNTAX VlanIndex
	MAX-ACCESS read-only
	STATUS current
	DESCRIPTION
		""
	::= { mldVlanStatsuEntry 1 }
	
	mldVlanStatsNumOfActiveGroups OBJECT-TYPE
	SYNTAX INTEGER
	MAX-ACCESS read-only
	STATUS current
	DESCRIPTION
		""
	::= { mldVlanStatsuEntry 2 }
	
	mldVlanStatsQueryPort OBJECT-TYPE
	SYNTAX INTEGER
	MAX-ACCESS read-only
	STATUS current
	DESCRIPTION
		""
	::= { mldVlanStatsuEntry 3 }	
	
	mldVlanStatsQuerierIp OBJECT-TYPE
	SYNTAX InetAddress
	MAX-ACCESS read-only
	STATUS current
	DESCRIPTION
		""
	::= { mldVlanStatsuEntry 4 } 
	
	mldVlanStatsV1QueryInCnt OBJECT-TYPE
	SYNTAX Counter32
	MAX-ACCESS read-only
	STATUS current
	DESCRIPTION
		""
	::= { mldVlanStatsuEntry 5 } 
	
	mldVlanStatsV1ReportInCnt OBJECT-TYPE
	SYNTAX Counter32
	MAX-ACCESS read-only
	STATUS current
	DESCRIPTION
		""
	::= { mldVlanStatsuEntry 6 }
	
	mldVlanStatsV1DoneInCnt OBJECT-TYPE
	SYNTAX Counter32
	MAX-ACCESS read-only
	STATUS current
	DESCRIPTION
		""
	::= { mldVlanStatsuEntry 7 }
	
	mldVlanStatsV1QueryInDropCnt OBJECT-TYPE
	SYNTAX Counter32
	MAX-ACCESS read-only
	STATUS current
	DESCRIPTION
		""
	::= { mldVlanStatsuEntry 8 }
	
	mldVlanStatsV1ReportInDropCnt OBJECT-TYPE
	SYNTAX Counter32
	MAX-ACCESS read-only
	STATUS current
	DESCRIPTION
		""
	::= { mldVlanStatsuEntry 9 } 
	
	mldVlanStatsV1DoneInDropCnt OBJECT-TYPE
	SYNTAX Counter32
	MAX-ACCESS read-only
	STATUS current
	DESCRIPTION
		""
	::= { mldVlanStatsuEntry 10 } 
	
	mldVlanStatsV1QueryOutCnt OBJECT-TYPE
	SYNTAX Counter32
	MAX-ACCESS read-only
	STATUS current
	DESCRIPTION
		""
	::= { mldVlanStatsuEntry 11 }
	
	mldVlanStatsV1ReportOutCnt OBJECT-TYPE
	SYNTAX Counter32
	MAX-ACCESS read-only
	STATUS current
	DESCRIPTION
		""
	::= { mldVlanStatsuEntry 12 } 
	
	mldVlanStatsV1DoneOutCnt OBJECT-TYPE
	SYNTAX Counter32
	MAX-ACCESS read-only
	STATUS current
	DESCRIPTION
		""
	::= { mldVlanStatsuEntry 13 }
	
	mldVlanStatsV2QueryInCnt OBJECT-TYPE
	SYNTAX Counter32
	MAX-ACCESS read-only
	STATUS current
	DESCRIPTION
		""
	::= { mldVlanStatsuEntry 14 } 
	
	mldVlanStatsV2ReportInCnt OBJECT-TYPE
	SYNTAX Counter32
	MAX-ACCESS read-only
	STATUS current
	DESCRIPTION
		""
	::= { mldVlanStatsuEntry 15 }
	
	mldVlanStatsV2QueryInDropCnt OBJECT-TYPE
	SYNTAX Counter32
	MAX-ACCESS read-only
	STATUS current
	DESCRIPTION
		""
	::= { mldVlanStatsuEntry 16 }
	
	mldVlanStatsV2ReportInDropCnt OBJECT-TYPE
	SYNTAX Counter32
	MAX-ACCESS read-only
	STATUS current
	DESCRIPTION
		""
	::= { mldVlanStatsuEntry 17 }
	
	mldVlanStatsV2QueryOutCnt OBJECT-TYPE
	SYNTAX Counter32
	MAX-ACCESS read-only
	STATUS current
	DESCRIPTION
		""
	::= { mldVlanStatsuEntry 18 }
	
	mldVlanStatsV2ReportOutCnt OBJECT-TYPE
	SYNTAX Counter32
	MAX-ACCESS read-only
	STATUS current
	DESCRIPTION
		""
	::= { mldVlanStatsuEntry 19 }

--------------------
--  macFFStats Table
--------------------
-- macFFArpStatusUplinkTable                
	macFFArpStatusUplinkTable OBJECT-TYPE
        SYNTAX SEQUENCE OF MacFFArpStatusUplinkEntry
        MAX-ACCESS not-accessible
        STATUS current
        DESCRIPTION
                ""
        ::= { macFFStats 1 }

        macFFArpStatusUplinkEntry OBJECT-TYPE
        SYNTAX MacFFArpStatusUplinkEntry
        MAX-ACCESS not-accessible
        STATUS current
        DESCRIPTION
        	"The entry of macFFArpStatusUplinkTable."
        INDEX  { slotId, macFFArpStatusUplinkMacVid , macFFArpStatusUplinkIpAddr  }
        ::= { macFFArpStatusUplinkTable 1 }

        MacFFArpStatusUplinkEntry ::=
        	SEQUENCE {
        		macFFArpStatusUplinkIpAddr		IpAddress,
        		macFFArpStatusUplinkMacAddr		PhysAddress,
        		macFFArpStatusUplinkMacVid		INTEGER		
           	}
        
        macFFArpStatusUplinkIpAddr OBJECT-TYPE
        SYNTAX  IpAddress
        MAX-ACCESS read-only
        STATUS current
        DESCRIPTION
		"macFF arp ip address from uplink"
        ::= { macFFArpStatusUplinkEntry 1 }
        
        macFFArpStatusUplinkMacAddr OBJECT-TYPE
        SYNTAX  PhysAddress
        MAX-ACCESS read-only
        STATUS current
        DESCRIPTION
		"macFF arp mac address from uplink"
        ::= { macFFArpStatusUplinkEntry 2 }
        
        macFFArpStatusUplinkMacVid OBJECT-TYPE
        SYNTAX  INTEGER(1..4094)
        MAX-ACCESS read-only
        STATUS current
        DESCRIPTION
		"macFF arp vid from uplink"
        ::= { macFFArpStatusUplinkEntry 3 }

-- macFFArpStatusSlotTable                
	macFFArpStatusSlotTable OBJECT-TYPE
        SYNTAX SEQUENCE OF MacFFArpStatusSlotEntry
        MAX-ACCESS not-accessible
        STATUS current
        DESCRIPTION
                ""
        ::= { macFFStats 2 }

        macFFArpStatusSlotEntry OBJECT-TYPE
        SYNTAX MacFFArpStatusSlotEntry
        MAX-ACCESS not-accessible
        STATUS current
        DESCRIPTION
        	"The entry of macFFArpStatusSlotTable."
        INDEX  { slotId, macFFArpStatusSlotMacVid , macFFArpStatusSlotIpAddr  }
        ::= { macFFArpStatusSlotTable 1 }

        MacFFArpStatusSlotEntry ::=
        	SEQUENCE {
        		macFFArpStatusSlotIpAddr		IpAddress,
        		macFFArpStatusSlotMacAddr		PhysAddress,
        		macFFArpStatusSlotMacVid		INTEGER,
        		macFFArpStatusSlotPort			INTEGER	        			
           	}
        
        macFFArpStatusSlotIpAddr OBJECT-TYPE
        SYNTAX  IpAddress
        MAX-ACCESS read-only
        STATUS current
        DESCRIPTION
		"macFF arp ip address from subscrib port"
        ::= { macFFArpStatusSlotEntry 1 }
        
        macFFArpStatusSlotMacAddr OBJECT-TYPE
        SYNTAX  PhysAddress
        MAX-ACCESS read-only
        STATUS current
        DESCRIPTION
		"macFF arp mac address from subscrib port"
        ::= { macFFArpStatusSlotEntry 2 }
        
        macFFArpStatusSlotMacVid OBJECT-TYPE
        SYNTAX  INTEGER(1..4094)
        MAX-ACCESS read-only
        STATUS current
        DESCRIPTION
		"macFF arp vid from subscrib port"
        ::= { macFFArpStatusSlotEntry 3 }
        
        macFFArpStatusSlotPort OBJECT-TYPE
        SYNTAX  INTEGER
        MAX-ACCESS read-only
        STATUS current
        DESCRIPTION
		"macFF arp learnt subscrib port"
        ::= { macFFArpStatusSlotEntry 4 }        

-- macFFArpCntUplinkTable                
	macFFArpCntUplinkTable OBJECT-TYPE
        SYNTAX SEQUENCE OF MacFFArpCntUplinkEntry
        MAX-ACCESS not-accessible
        STATUS current
        DESCRIPTION
                ""
        ::= { macFFStats 3 }

        macFFArpCntUplinkEntry OBJECT-TYPE
        SYNTAX MacFFArpCntUplinkEntry
        MAX-ACCESS not-accessible
        STATUS current
        DESCRIPTION
        	"The entry of macFFArpCntUplinkTable."
        INDEX  { slotId  }
        ::= { macFFArpCntUplinkTable 1 }

        MacFFArpCntUplinkEntry ::=
        	SEQUENCE {
        		macFFArpCntUplinkReqRx 			Unsigned32,
        		macFFArpCntUplinkReqTx 			Unsigned32,
        		macFFArpCntUplinkReqRxDrop		Unsigned32,
        		macFFArpCntUplinkRpyRx			Unsigned32,
        		macFFArpCntUplinkRpyTx			Unsigned32,
        		macFFArpCntUplinkRpyRxDrop		Unsigned32
           	}

		macFFArpCntUplinkReqRx OBJECT-TYPE
        SYNTAX  Unsigned32
        MAX-ACCESS read-only
        STATUS current
        DESCRIPTION
		"macFF arp request rx counter from uplink"
        ::= { macFFArpCntUplinkEntry 1 }
        
        macFFArpCntUplinkReqTx OBJECT-TYPE
        SYNTAX  Unsigned32
        MAX-ACCESS read-only
        STATUS current
        DESCRIPTION
		"macFF arp request tx counter from uplink"
        ::= { macFFArpCntUplinkEntry 2 }
        
        macFFArpCntUplinkReqRxDrop OBJECT-TYPE
        SYNTAX  Unsigned32
        MAX-ACCESS read-only
        STATUS current
        DESCRIPTION
		"macFF arp request rx drop counter from uplink"
        ::= { macFFArpCntUplinkEntry 3 }
        
        macFFArpCntUplinkRpyRx OBJECT-TYPE
        SYNTAX  Unsigned32
        MAX-ACCESS read-only
        STATUS current
        DESCRIPTION
		"macFF arp reply rx counter from uplink"
        ::= { macFFArpCntUplinkEntry 4 }
        
        macFFArpCntUplinkRpyTx OBJECT-TYPE
        SYNTAX  Unsigned32
        MAX-ACCESS read-only
        STATUS current
        DESCRIPTION
		"macFF arp reply tx counter from uplink"
        ::= { macFFArpCntUplinkEntry 5 } 
        
        macFFArpCntUplinkRpyRxDrop OBJECT-TYPE
        SYNTAX  Unsigned32
        MAX-ACCESS read-only
        STATUS current
        DESCRIPTION
		"macFF arp reply rx drop counter from uplink"
        ::= { macFFArpCntUplinkEntry 6 }

-- macFFArpCntPortTable                
	macFFArpCntPortTable OBJECT-TYPE
        SYNTAX SEQUENCE OF MacFFArpCntPortEntry
        MAX-ACCESS not-accessible
        STATUS current
        DESCRIPTION
                ""
        ::= { macFFStats 4 }

        macFFArpCntPortEntry OBJECT-TYPE
        SYNTAX MacFFArpCntPortEntry
        MAX-ACCESS not-accessible
        STATUS current
        DESCRIPTION
        	"The entry of macFFArpCntPortTable."
        INDEX  { ifIndex  }
        ::= { macFFArpCntPortTable 1 }

        MacFFArpCntPortEntry ::=
        	SEQUENCE {
        		macFFArpCntPortReqRx 			Unsigned32,
        		macFFArpCntPortReqTx 			Unsigned32,
        		macFFArpCntPortReqRxDrop		Unsigned32,
        		macFFArpCntPortRpyRx			Unsigned32,
        		macFFArpCntPortRpyTx			Unsigned32,
        		macFFArpCntPortRpyRxDrop		Unsigned32
           	}

		macFFArpCntPortReqRx OBJECT-TYPE
        SYNTAX  Unsigned32
        MAX-ACCESS read-only
        STATUS current
        DESCRIPTION
		"macFF arp request rx counter from subscrib port"
        ::= { macFFArpCntPortEntry 1 }
        
        macFFArpCntPortReqTx OBJECT-TYPE
        SYNTAX  Unsigned32
        MAX-ACCESS read-only
        STATUS current
        DESCRIPTION
		"macFF arp request tx counter from subscrib port"
        ::= { macFFArpCntPortEntry 2 }
        
        macFFArpCntPortReqRxDrop OBJECT-TYPE
        SYNTAX  Unsigned32
        MAX-ACCESS read-only
        STATUS current
        DESCRIPTION
		"macFF arp request rx drop counter from subscrib port"
        ::= { macFFArpCntPortEntry 3 }
        
        macFFArpCntPortRpyRx OBJECT-TYPE
        SYNTAX  Unsigned32
        MAX-ACCESS read-only
        STATUS current
        DESCRIPTION
		"macFF arp reply rx counter from subscrib port"
        ::= { macFFArpCntPortEntry 4 }
        
        macFFArpCntPortRpyTx OBJECT-TYPE
        SYNTAX  Unsigned32
        MAX-ACCESS read-only
        STATUS current
        DESCRIPTION
		"macFF arp reply tx counter from subscrib port"
        ::= { macFFArpCntPortEntry 5 } 
        
        macFFArpCntPortRpyRxDrop OBJECT-TYPE
        SYNTAX  Unsigned32
        MAX-ACCESS read-only
        STATUS current
        DESCRIPTION
		"macFF reply rx drop counter from subscrib port"
        ::= { macFFArpCntPortEntry 6 }                     	

--------------------
--  imageStats
--------------------
	sysBootUpFwIndex OBJECT-TYPE
		SYNTAX INTEGER
		MAX-ACCESS read-only
		STATUS current
		DESCRIPTION
			""
		::= { imageStats 1 }

    sysBootUpFwVersion OBJECT-TYPE
        SYNTAX  DisplayString
        ACCESS  read-only
        STATUS  current
        DESCRIPTION
        	""
        ::= { imageStats 2}
    
    sysFlashFwInfoTable OBJECT-TYPE
    	SYNTAX SEQUENCE OF SysFlashFwInfoEntry
        MAX-ACCESS not-accessible
        STATUS current
        DESCRIPTION
			""
        ::= { imageStats 3 }
   	
    sysFlashFwInfoEntry OBJECT-TYPE
    	SYNTAX SysFlashFwInfoEntry
    	MAX-ACCESS not-accessible
    	STATUS current
    	DESCRIPTION
    		""
        INDEX { sysFlashFwIndex }
        ::= { sysFlashFwInfoTable 1 }
 
        SysFlashFwInfoEntry ::=
           SEQUENCE {
				sysFlashFwIndex  INTEGER,
				sysFlashFwVersion	DisplayString
           }
    sysFlashFwIndex OBJECT-TYPE
    	SYNTAX INTEGER (1..2)
    	MAX-ACCESS not-accessible
    	STATUS current
    	DESCRIPTION
    		""
    	::= { sysFlashFwInfoEntry 1 }
    
    sysFlashFwVersion OBJECT-TYPE
    	SYNTAX DisplayString
    	MAX-ACCESS read-only
    	STATUS current
    	DESCRIPTION
    		""
    	::= { sysFlashFwInfoEntry 2 }        
  
----------------------------------------
-- clear
----------------------------------------

imaClear		OBJECT IDENTIFIER ::= { clear 5 }
voipClear		OBJECT IDENTIFIER ::= { clear 6 }

       	counterClearTarget OBJECT-TYPE
        SYNTAX OCTET STRING
        MAX-ACCESS read-write
        STATUS current
        DESCRIPTION
		"This object is supported by R1.02 and later versions.
		This managed object is used for identify the target on which 
		the counter would be cleared. The target is encoded as:
		Byte 1:   the octet specifies a set of eight chassis, chassis 0 through 7
		Byte 2~4: each octet specifies a set of eight slots, with the 
			  first octet specifying slots 1 through 8, and the second
		          octet specifying slots 9 through 16, and so on.
		Byte 5~:  each octet specifies a set of eight ports, with the first
		          octet specifying ports 1 through 8, etc."
        ::= { clear 1 }
        
        counterClearOps OBJECT-TYPE
        SYNTAX INTEGER
        MAX-ACCESS read-write
        STATUS current
        DESCRIPTION
		"This object is supported by R1.02 and later versions.
		The corresponding bit is set to 1 to start the operation.
		The various bit positions are:
		BIT 1: clear interface counters
		BIT 2: clear pvc packet counters
		BIT 3: clear port ATM counters
		BIT 4: clear pvc ATM counters
		BIT 5: clear DHCP counters
		BIT 6: clear IGMP counters
		BIT 7: clear IGMP port counters
		BIT 8: clear inband IP interface counters
		BIT 9: clear outband IP interface counters
		BIT10: clear line performance counters
		BIT11: clear performance current counters
		BIT12: clear performance current 15min counters
		BIT13: clear performance current 1day counters
		BIT14: clear macFF arp counters"
        ::= { clear 2 }
        
        counterClearVpi OBJECT-TYPE
        SYNTAX INTEGER (0..255)
        MAX-ACCESS read-write
        STATUS current
        DESCRIPTION
                "This object is supported by R1.02 and later versions.
                VPI of the pvc whose counters would be cleared."
        ::= { clear 3 }

        counterClearVci OBJECT-TYPE
        SYNTAX INTEGER (1..65535)
        MAX-ACCESS read-write
       	STATUS current
        DESCRIPTION
                "This object is supported by R1.02 and later versions.
                VCI of the pvc whose counters would be cleared."
        ::= { clear 4 }

--  imaClear
        
        imaClearOps OBJECT-TYPE
        SYNTAX INTEGER
        MAX-ACCESS read-write
        STATUS current
        DESCRIPTION
		"This object is supported by R5.03 and later versions.
		The corresponding bit is set to 1 to start the operation.
		The various bit positions are:
		BIT 0: clear pvc pkt counters
		BIT 1: clear group cell counters
		BIT 2: clear ima group performance current 15min counters
		BIT 3: clear ima group performance current 1day counters
		BIT 4: clear ima link performance current 15min counters
		BIT 5: clear ima link performance current 1day counters
		BIT 6: clear e1 performance current 15min counters
		BIT 7: clear e1 performance current 1day counters"
        ::= { imaClear 1 }
        
        imaClearTargetGroupIndex OBJECT-TYPE
        SYNTAX INTEGER
        MAX-ACCESS read-write
        STATUS current
        DESCRIPTION
                ""
        ::= { imaClear 2 } 
        
        imaClearTargetLinkIndex OBJECT-TYPE
        SYNTAX INTEGER
        MAX-ACCESS read-write
        STATUS current
        DESCRIPTION
                "1~8, link index in the group"
        ::= { imaClear 3 }
        
        imaClearTargetVpi OBJECT-TYPE
        SYNTAX INTEGER (0..255)
        MAX-ACCESS read-write
        STATUS current
        DESCRIPTION
                "This object is supported by R5.03 and later versions.
                VPI of the pvc whose counters would be cleared."
        ::= { imaClear 4 }

        imaClearTargetVci OBJECT-TYPE
        SYNTAX INTEGER (1..65535)
        MAX-ACCESS read-write
       	STATUS current
        DESCRIPTION
                "This object is supported by R5.03 and later versions.
                VCI of the pvc whose counters would be cleared."
        ::= { imaClear 5 }
        
        imaClearTargetIfindex OBJECT-TYPE
        SYNTAX INTEGER
        MAX-ACCESS read-write
       	STATUS current
        DESCRIPTION
                "This object is supported by R5.03 and later versions."
        ::= { imaClear 6 }

--  voipClear  

		voipClearOps OBJECT-TYPE
        SYNTAX INTEGER
        MAX-ACCESS read-write
       	STATUS current
        DESCRIPTION
        "The corresponding bit is set to 1 to start the operation.
		The various bit positions are:
		BIT 0: clear call detail records
		BIT 1: clear H248 statistics"
        ::= { voipClear 1 }
        
        voipClearH248TargetInterface OBJECT-TYPE
        SYNTAX INTEGER
        MAX-ACCESS read-write
       	STATUS current
        DESCRIPTION
                "Interface Id"
        ::= { voipClear 2 }
		       
----------------------------------------
-- cluster
----------------------------------------

	clusterEnable OBJECT-TYPE
        SYNTAX	INTEGER {
        		enableManager(1),
        		enableMember(2),
        		disable(3)
        	}
        MAX-ACCESS read-write
       	STATUS current
        DESCRIPTION
                "Enable/disable clustering. This object is supported by R3.00 and later versions."
        ::= { cluster 1 }

	clusterName OBJECT-TYPE
        SYNTAX DisplayString
        MAX-ACCESS read-write
       	STATUS current
        DESCRIPTION
                "Name of the cluster. This object is supported by R3.00 and later versions."
        ::= { cluster 2 }
       
        clusterMemberPassword  OBJECT-TYPE
        SYNTAX DisplayString
        MAX-ACCESS read-write
       	STATUS current
        DESCRIPTION
                "Password of the member. This object is supported by R3.00 and later versions."
        ::= { cluster 3 }
        
        clusterVlan OBJECT-TYPE
        SYNTAX VlanIndex
        MAX-ACCESS read-write
       	STATUS current
        DESCRIPTION
                "Setting cluster VLAN ID. This object is supported by R3.00 and later versions."
        ::= { cluster 4 }        


	clusterCandidate	OBJECT IDENTIFIER ::= { cluster 5 }

	clusterCandidateFlush OBJECT-TYPE
        SYNTAX INTEGER
        MAX-ACCESS read-write
       	STATUS current
        DESCRIPTION
                "Setting the object to be 1 to flush the candidate table and re-discover candidates.
                This object is supported by R3.00 and later versions."
        ::= { clusterCandidate 1 }
        
-- clusterCandidateTable

        clusterCandidateTable OBJECT-TYPE
        SYNTAX SEQUENCE OF ClusterCandidateEntry
        MAX-ACCESS not-accessible
        STATUS current
        DESCRIPTION
        	"A table that contains information about cluster candidates.
        	This table is supported by R3.00 and later versions."
        ::= { clusterCandidate 2 }
	
        clusterCandidateEntry OBJECT-TYPE
        SYNTAX ClusterCandidateEntry
        MAX-ACCESS not-accessible
        STATUS current
        DESCRIPTION
        	"An entry of clusterCandidateTable."
        INDEX { clusterCandidateMacAddr }
        ::= { clusterCandidateTable 1 }

        ClusterCandidateEntry ::=
        	SEQUENCE {
                  	clusterCandidateMacAddr		MacAddress,
			clusterCandidateHostName	DisplayString,
			clusterCandidateModelName	DisplayString,
			clusterCandidateDeviceType	INTEGER
              	}

        clusterCandidateMacAddr OBJECT-TYPE
        SYNTAX MacAddress
        MAX-ACCESS read-only
        STATUS current
        DESCRIPTION
        	"The MAC address of the candidate."
        ::= { clusterCandidateEntry 1 }
        
        clusterCandidateHostName OBJECT-TYPE
        SYNTAX DisplayString
        MAX-ACCESS read-only
        STATUS current
        DESCRIPTION
        	"The host name of the candidate."
        ::= { clusterCandidateEntry 2 }
        
        clusterCandidateModelName OBJECT-TYPE
        SYNTAX DisplayString
        MAX-ACCESS read-only
        STATUS current
        DESCRIPTION
        	"The model name of the candidate."
        ::= { clusterCandidateEntry 3 }
        
        clusterCandidateDeviceType OBJECT-TYPE
        SYNTAX	INTEGER {
        		unknown(1),
        		ies5000(2),
        		ies5005(3),
        		ies6000(4),
        		ies1248-71(101),
        		ies1248-73(102),
        		ies1248-51(103),
        		ies1248-53(104)
        	}
        MAX-ACCESS read-only
        STATUS current
        DESCRIPTION
        	"The device type of the candidate."
        ::= { clusterCandidateEntry 4 }
        
-- clusterMemberConfTable

        clusterMemberConfTable OBJECT-TYPE
        SYNTAX SEQUENCE OF ClusterMemberConfEntry
        MAX-ACCESS not-accessible
        STATUS current
        DESCRIPTION
        	"A table that contains configuration about cluster members.
        	This table is supported by R3.00 and later versions."
        ::= { cluster 6 }
	
        clusterMemberConfEntry OBJECT-TYPE
        SYNTAX ClusterMemberConfEntry
        MAX-ACCESS not-accessible
        STATUS current
        DESCRIPTION
        	"An entry of clusterMemberConfTable."
        INDEX { clusterMemberConfId }
        ::= { clusterMemberConfTable 1 }

        ClusterMemberConfEntry ::=
        	SEQUENCE {
        		clusterMemberConfId		INTEGER,
                  	clusterMemberConfMacAddr	MacAddress,
                  	clusterMemberConfPasswd		DisplayString
              	}

	clusterMemberConfId OBJECT-TYPE
        SYNTAX INTEGER
        MAX-ACCESS read-only
        STATUS current
        DESCRIPTION
        	"The identity of the entry."
        ::= { clusterMemberConfEntry 1 }
        
        clusterMemberConfMacAddr OBJECT-TYPE
        SYNTAX MacAddress
        MAX-ACCESS read-write
        STATUS current
        DESCRIPTION
        	"The MAC address of the member which will join the cluster."
        ::= { clusterMemberConfEntry 2 }
        
        clusterMemberConfPasswd OBJECT-TYPE
        SYNTAX DisplayString
        MAX-ACCESS read-write
        STATUS current
        DESCRIPTION
        	"The password of the member which will join the cluster."
        ::= { clusterMemberConfEntry 3 }
        
-- clusterMemberStatusTable

        clusterMemberStatusTable OBJECT-TYPE
        SYNTAX SEQUENCE OF ClusterMemberStatusEntry
        MAX-ACCESS not-accessible
        STATUS current
        DESCRIPTION
        	"A table that contains information about cluster members.
        	This table is supported by R3.00 and later versions."
        ::= { cluster 7 }
	
        clusterMemberStatusEntry OBJECT-TYPE
        SYNTAX ClusterMemberStatusEntry
        MAX-ACCESS not-accessible
        STATUS current
        DESCRIPTION
        	"An entry of clusterMemberStatusTable."
        INDEX { clusterMemberConfId }
        ::= { clusterMemberStatusTable 1 }

        ClusterMemberStatusEntry ::=
        	SEQUENCE {
        		clusterMemberStatusState		INTEGER,
        		clusterMemberStatusMacAddr		MacAddress,
        		clusterMemberStatusHostName		DisplayString,
        		clusterMemberStatusModelName		DisplayString,
        		clusterMemberStatusDeviceType		INTEGER,
        		clusterMemberStatusFWVersion		DisplayString,
        		clusterMemberStatusUpTime		TimeTicks
              	}

	clusterMemberStatusState OBJECT-TYPE
        SYNTAX	INTEGER {
        		waiting(1),
        		inactive(2),
        		active(3),
        		empty(4),
        		error(5)
        	}
        MAX-ACCESS read-only
        STATUS current
        DESCRIPTION
        	"The state of the member."
        ::= { clusterMemberStatusEntry 1 }
        
        clusterMemberStatusMacAddr OBJECT-TYPE
        SYNTAX MacAddress
        MAX-ACCESS read-only
        STATUS current
        DESCRIPTION
        	"The MAC address of the member."
        ::= { clusterMemberStatusEntry 2 }
        
        clusterMemberStatusHostName OBJECT-TYPE
        SYNTAX DisplayString
        MAX-ACCESS read-only
        STATUS current
        DESCRIPTION
        	"The host name of the member."
        ::= { clusterMemberStatusEntry 3 }
        
        clusterMemberStatusModelName OBJECT-TYPE
        SYNTAX DisplayString
        MAX-ACCESS read-only
        STATUS current
        DESCRIPTION
        	"The model name of the member."
        ::= { clusterMemberStatusEntry 4 }
        
        clusterMemberStatusDeviceType OBJECT-TYPE
        SYNTAX	INTEGER {
        		unknown(1),
        		ies5000(2),
        		ies5005(3),
        		ies6000(4),
        		ies1248-71(101),
        		ies1248-73(102),
        		ies1248-51(103),
        		ies1248-53(104)
        	}
        MAX-ACCESS read-only
        STATUS current
        DESCRIPTION
        	"The device type of the member."
        ::= { clusterMemberStatusEntry 5 }
        
        clusterMemberStatusFWVersion OBJECT-TYPE
        SYNTAX DisplayString
        MAX-ACCESS read-only
        STATUS current
        DESCRIPTION
        	"The F/W version of the member."
        ::= { clusterMemberStatusEntry 6 }
        
        clusterMemberStatusUpTime OBJECT-TYPE
        SYNTAX TimeTicks
        MAX-ACCESS read-only
        STATUS current
        DESCRIPTION
        	"The time since the member joined the cluster."
        ::= { clusterMemberStatusEntry 7 }


----------------------------------------
-- voip
----------------------------------------

	voipArp			OBJECT IDENTIFIER ::= { voip 1 }
	voipSip			OBJECT IDENTIFIER ::= { voip 2 }
	voipH248		OBJECT IDENTIFIER ::= { voip 10 }
	        
-- voipArpFlushOperation

        voipArpFlushTarget OBJECT-TYPE
        SYNTAX INTEGER
        MAX-ACCESS read-write
        STATUS current
        DESCRIPTION
		"Flush arp entries in the specified slot."
        ::= { voipArp 1 }
        
        voipArpFlushOps OBJECT-TYPE
        SYNTAX INTEGER
        MAX-ACCESS read-write
        STATUS current
        DESCRIPTION
		"Set the object to 1 to start flushing."
        ::= { voipArp 2 }

-- voipArpShowTable

        voipArpShowTable OBJECT-TYPE
        SYNTAX SEQUENCE OF VoipArpShowEntry
        MAX-ACCESS not-accessible
        STATUS current
        DESCRIPTION
        	"Display ARP entries learnt in specified slot."
        ::= { voipArp 3 }
	
        voipArpShowEntry OBJECT-TYPE
        SYNTAX VoipArpShowEntry
        MAX-ACCESS not-accessible
        STATUS current
        DESCRIPTION
        	"An entry of voipArpShowTable."
        INDEX { slotId, voipArpShowIp  }
        ::= { voipArpShowTable 1 }

        VoipArpShowEntry ::=
        	SEQUENCE {
        		voipArpShowIp			IpAddress,
        		voipArpShowMac			PhysAddress,
        		voipArpShowTimer		INTEGER
              	}

	voipArpShowIp OBJECT-TYPE
        SYNTAX IpAddress
        MAX-ACCESS read-only
        STATUS current
        DESCRIPTION
        	""
        ::= { voipArpShowEntry 1 }
        
        voipArpShowMac OBJECT-TYPE
        SYNTAX PhysAddress
        MAX-ACCESS read-only
        STATUS current
        DESCRIPTION
        	""
        ::= { voipArpShowEntry 2 }
        
        voipArpShowTimer OBJECT-TYPE
        SYNTAX INTEGER
        MAX-ACCESS read-only
        STATUS current
        DESCRIPTION
        	""
        ::= { voipArpShowEntry 3 }

-- voipNumberPlanTable

	maxNumOfVoipNumberPlan OBJECT-TYPE
        SYNTAX INTEGER
        MAX-ACCESS read-only
        STATUS current
        DESCRIPTION
        	"The maximum number of VoIP number plan supported by the system."
        ::= { voipSip 1 }
        
        voipNumberPlanTable OBJECT-TYPE
        SYNTAX SEQUENCE OF VoipNumberPlanEntry
        MAX-ACCESS not-accessible
        STATUS current
        DESCRIPTION
        	"Configure numbering plan entry of specified index in specified payphone charging table."
        ::= { voipSip 2 }
	
        voipNumberPlanEntry OBJECT-TYPE
        SYNTAX VoipNumberPlanEntry
        MAX-ACCESS not-accessible
        STATUS current
        DESCRIPTION
        	"An entry of voipNumberPlanTable."
        INDEX { voipNumberPlanName, voipNumberPlanIndex }
        ::= { voipNumberPlanTable 1 }

        VoipNumberPlanEntry ::=
        	SEQUENCE {
        		voipNumberPlanName		DisplayString,
        		voipNumberPlanIndex		INTEGER,
        		voipNumberPlanPattern		DisplayString,
        		voipNumberPlanRule		DisplayString,
        		voipNumberPlanRowStatus		RowStatus
              	}

	voipNumberPlanName OBJECT-TYPE
        SYNTAX DisplayString (SIZE (1..31))
        MAX-ACCESS read-only
        STATUS current
        DESCRIPTION
        	"Numbering plan table name."
        ::= { voipNumberPlanEntry 1 }
        
        voipNumberPlanIndex OBJECT-TYPE
        SYNTAX INTEGER (1..16)
        MAX-ACCESS read-only
        STATUS current
        DESCRIPTION
        	""
        ::= { voipNumberPlanEntry 2 }
        
        voipNumberPlanPattern OBJECT-TYPE
        SYNTAX DisplayString (SIZE(1..47))
        MAX-ACCESS read-create
        STATUS current
        DESCRIPTION
       	    "up to 47 characters, allow digit, '*', and '#' characters and 
        	meaning characters that include 'x', '.', '|' and range format 
        	characters that include '~', ',' and parenthesis '(', ')' 
        	and brackets '[', ']' and at most one parenthesis pair and
        	'T' for terminate are allowed and two quotation marks 
        	means a null pattern for hot dial, 
        	examples: '002(x.)', '0(x.)', and '(x.)'" 

        ::= { voipNumberPlanEntry 3 }
        
        voipNumberPlanRule OBJECT-TYPE
        SYNTAX DisplayString (SIZE(1..15))
        MAX-ACCESS read-create
        STATUS current
        DESCRIPTION
        	"Allowed characters are 0~9, and '\c' stand for country code, 
        	'\d' stand for national destination code, 
        	'\1' stand for matched string enclosed by the parenthesis pair,
        	and 'deny' stand for the pattern specified is not allowed and 
        	<tel> accept 1-15 digits includes '+', '*' and '#' for hot or 
        	speed dial application.
        	Examples: '\1', '\c\1', and '\c\d\1'."
        ::= { voipNumberPlanEntry 4 }
        
        voipNumberPlanRowStatus OBJECT-TYPE
        SYNTAX RowStatus
        MAX-ACCESS read-create
        STATUS current
        DESCRIPTION
        	"This object is used to create a new entry or delete an existing entry in this table."
        ::= { voipNumberPlanEntry 5 }

-- voipDialPlanTable

	maxNumOfVoipDialPlan OBJECT-TYPE
        SYNTAX INTEGER
        MAX-ACCESS read-only
        STATUS current
        DESCRIPTION
        	"The maximum number of VoIP dial plan supported by the system."
        ::= { voipSip 3 }
        
        voipDialPlanTable OBJECT-TYPE
        SYNTAX SEQUENCE OF VoipDialPlanEntry
        MAX-ACCESS not-accessible
        STATUS current
        DESCRIPTION
        	"Configure dial plan related configuration.
        	This table is supported by R5.01 and later versions."
        ::= { voipSip 4 }
	
        voipDialPlanEntry OBJECT-TYPE
        SYNTAX VoipDialPlanEntry
        MAX-ACCESS not-accessible
        STATUS current
        DESCRIPTION
        	"An entry of voipDialPlanTable."
        INDEX { IMPLIED voipDialPlanName }
        ::= { voipDialPlanTable 1 }

        VoipDialPlanEntry ::=
        	SEQUENCE {
        		voipDialPlanName		DisplayString,
        		voipDialPlanPattern		DisplayString,
        		voipDialPlanNumOfPrefixCut	INTEGER,
        		voipDialPlanSipServer		DisplayString,
        		voipDialPlanPrefixAddDigits	DisplayString,
        		voipDialPlanNumberOfInterdigit	INTEGER,
        		voipDialPlanInterdigitTimeout	INTEGER,
        		voipDialPlanRowStatus		RowStatus
              	}

	voipDialPlanName OBJECT-TYPE
        SYNTAX DisplayString (SIZE (1..31))
        MAX-ACCESS read-only
        STATUS current
        DESCRIPTION
        	"Dial plan table name."
        ::= { voipDialPlanEntry 1 }
        
        voipDialPlanPattern OBJECT-TYPE
        SYNTAX DisplayString (SIZE (0..63))
        MAX-ACCESS read-create
        STATUS current
        DESCRIPTION
        	"only 63 DTMF characters that include digits, '*', '#' and meaning characters that 
        	include 'x', '.', '|' and characters of range format that include '~', ',' and 
        	brackets ('[', ']') are allowed.
        	Note:
  			'x' represents any digit character
  			'.' represents one or more repetitions of character or range that precedes it, 
  			can't use in brackets
  			'!' represents the user-dialed number can be rejected by placing '!' at the end of the pattern
  			'|' to connect next sub-pattern
  			'[' and ']' must pair and nest brackets is illegal
  			'~' and ',' only show in brackets
  			'~' connected characters must be digit
  		User should make sure to create unique pattern for each SIP proxy server.
  		The VOP1248G-61 is not able to distinguish between dial plan tables if they
  		have the same pattern."
        ::= { voipDialPlanEntry 2 }
        
        voipDialPlanNumOfPrefixCut OBJECT-TYPE
        SYNTAX INTEGER (0..8)
        MAX-ACCESS read-create
        STATUS current
        DESCRIPTION
        	"The number of digits at the beginning of the dialed number that will be removed."
        ::= { voipDialPlanEntry 3 }
        
        voipDialPlanSipServer OBJECT-TYPE
        SYNTAX DisplayString (SIZE(0..31))
        MAX-ACCESS read-create
        STATUS current
        DESCRIPTION
        	"SIP profile name."
        ::= { voipDialPlanEntry 4 }
        
        voipDialPlanPrefixAddDigits OBJECT-TYPE
        SYNTAX DisplayString (SIZE(0..15))
        MAX-ACCESS read-create
        STATUS current
        DESCRIPTION
        	"Only digit characters are allowed or use two quotation mark to 
        	indicate no prefix added digits."
        ::= { voipDialPlanEntry 5 }
        
        voipDialPlanNumberOfInterdigit OBJECT-TYPE
        SYNTAX INTEGER (1..15)
        MAX-ACCESS read-create
        STATUS current
        DESCRIPTION
        	"The number of dialing digits."
        ::= { voipDialPlanEntry 6 }
        
        voipDialPlanInterdigitTimeout OBJECT-TYPE
        SYNTAX INTEGER (1..10)
        UNITS "second"
        MAX-ACCESS read-create
        STATUS current
        DESCRIPTION
        	"Inter-digit timeout in seconds."
        ::= { voipDialPlanEntry 7 }
        
        voipDialPlanRowStatus OBJECT-TYPE
        SYNTAX RowStatus
        MAX-ACCESS read-create
        STATUS current
        DESCRIPTION
        	"This object is used to create a new entry or delete an existing entry in this table."
        ::= { voipDialPlanEntry 8 }

-- voipKeyPatternTable

	maxNumOfVoipKeyPattern OBJECT-TYPE
        SYNTAX INTEGER
        MAX-ACCESS read-only
        STATUS current
        DESCRIPTION
        	"The maximum number of VoIP key patterns supported by the system."
        ::= { voipSip 5 }
        
        voipKeyPatternTable OBJECT-TYPE
        SYNTAX SEQUENCE OF VoipKeyPatternEntry
        MAX-ACCESS not-accessible
        STATUS current
        DESCRIPTION
        	"Configure key pattern related configuration.
        	This table is supported by R5.01 and later versions."
        ::= { voipSip 6 }
	
        voipKeyPatternEntry OBJECT-TYPE
        SYNTAX VoipKeyPatternEntry
        MAX-ACCESS not-accessible
        STATUS current
        DESCRIPTION
        	"An entry of voipKeyPatternTable."
        INDEX { voipKeyPatternName, voipKeyPatternServiceType }
        ::= { voipKeyPatternTable 1 }

        VoipKeyPatternEntry ::=
        	SEQUENCE {
        		voipKeyPatternName		DisplayString,
        		voipKeyPatternServiceType	INTEGER,
        		voipKeyPatternPattern		DisplayString,
        		voipKeyPatternRowStatus		RowStatus
              	}

	voipKeyPatternName OBJECT-TYPE
        SYNTAX DisplayString (SIZE (1..31))
        MAX-ACCESS read-only
        STATUS current
        DESCRIPTION
        	"Key pattern table name."
        ::= { voipKeyPatternEntry 1 }
        
        voipKeyPatternServiceType OBJECT-TYPE
        SYNTAX INTEGER {
        		callreturn(1),
			calltransfer(2),
			callwaitdisconn(3),
			callwaitoff(4),
			callwaiton(5),
			callwaitonhold(6),
			callwaitreject(7),
			clir(8),
			dndoff(9),
			dndon(10),
			callin(11)
		}
        MAX-ACCESS read-only
        STATUS current
        DESCRIPTION
        	""
        ::= { voipKeyPatternEntry 2 }
        
        voipKeyPatternPattern OBJECT-TYPE
        SYNTAX DisplayString (SIZE (0..7))
        MAX-ACCESS read-create
        STATUS current
        DESCRIPTION
        	"Allowed characters are 0~9, *, and #."
        ::= { voipKeyPatternEntry 3 }
        
        voipKeyPatternRowStatus OBJECT-TYPE
        SYNTAX RowStatus
        MAX-ACCESS read-create
        STATUS current
        DESCRIPTION
        	"This object is used to create a new entry or delete an existing entry in this table."
        ::= { voipKeyPatternEntry 4 }

-- voipLocalCall

	voipLocalCall		OBJECT IDENTIFIER ::= { voipSip 7 }
	
	voipLocalCallSync OBJECT-TYPE
        SYNTAX INTEGER
        MAX-ACCESS read-write
        STATUS current
        DESCRIPTION
        	"Set the object to 1 to synchronize msc local call file with SIP linecard."
        ::= { voipLocalCall 1 }
        
        voipLocalCallEnterTime OBJECT-TYPE
        SYNTAX INTEGER (1..60)
        UNITS "minute"
        MAX-ACCESS read-write
        STATUS current
        DESCRIPTION
        	""
        ::= { voipLocalCall 2 }
        
        voipLocalCallExitTime OBJECT-TYPE
        SYNTAX INTEGER (1..60)
        UNITS "minute"
        MAX-ACCESS read-write
        STATUS current
        DESCRIPTION
        	""
        ::= { voipLocalCall 3 }
	
-- voipLocalHelpTable

	maxNumOfVoipLocalHelp OBJECT-TYPE
        SYNTAX INTEGER
        MAX-ACCESS read-only
        STATUS current
        DESCRIPTION
        	"The maximum number of VoIP local help entries supported by the system."
        ::= { voipSip 8 }
        
	voipLocalHelpTable OBJECT-TYPE
        SYNTAX SEQUENCE OF VoipLocalHelpEntry
        MAX-ACCESS not-accessible
        STATUS current
        DESCRIPTION
        	"Configure telephone number of specified index in specified local help table.
        	This table is supported by R5.01 and later versions."
        ::= { voipSip 9 }
	
        voipLocalHelpEntry OBJECT-TYPE
        SYNTAX VoipLocalHelpEntry
        MAX-ACCESS not-accessible
        STATUS current
        DESCRIPTION
        	"An entry of voipLocalHelpTable."
        INDEX { voipLocalHelpName, voipLocalHelpIndex }
        ::= { voipLocalHelpTable 1 }

        VoipLocalHelpEntry ::=
        	SEQUENCE {
        		voipLocalHelpName		DisplayString,
        		voipLocalHelpIndex		INTEGER,
        		voipLocalHelpTelNumber		DisplayString,
        		voipLocalHelpRowStatus		RowStatus
              	}

	voipLocalHelpName OBJECT-TYPE
        SYNTAX DisplayString (SIZE (1..31))
        MAX-ACCESS read-only
        STATUS current
        DESCRIPTION
        	"Local help table name."
        ::= { voipLocalHelpEntry 1 }
        
        voipLocalHelpIndex OBJECT-TYPE
        SYNTAX INTEGER (1..16)
        MAX-ACCESS read-only
        STATUS current
        DESCRIPTION
        	"Index number."
        ::= { voipLocalHelpEntry 2 }
        
        voipLocalHelpTelNumber OBJECT-TYPE
        SYNTAX DisplayString (SIZE (1..15))
        MAX-ACCESS read-create
        STATUS current
        DESCRIPTION
        	"Only digits are allowed."
        ::= { voipLocalHelpEntry 3 }
        
        voipLocalHelpRowStatus OBJECT-TYPE
        SYNTAX RowStatus
        MAX-ACCESS read-create
        STATUS current
        DESCRIPTION
        	"This object is used to create a new entry or delete an existing entry in this table."
        ::= { voipLocalHelpEntry 4 }
                                                
-- voipIpSetTable

        voipIpSetTable OBJECT-TYPE
        SYNTAX SEQUENCE OF VoipIpSetEntry
        MAX-ACCESS not-accessible
        STATUS current
        DESCRIPTION
        	"Configure IP address and VLAN ID of specified slot."
        ::= { voip 3 }
	
        voipIpSetEntry OBJECT-TYPE
        SYNTAX VoipIpSetEntry
        MAX-ACCESS not-accessible
        STATUS current
        DESCRIPTION
        	"An entry of voipIpSetTable."
        INDEX { slotId }
        ::= { voipIpSetTable 1 }

        VoipIpSetEntry ::=
        	SEQUENCE {
        		voipIpSetIp			IpAddress,
        		voipIpSetVid			VlanIndex,
        		voipIpSetMask			INTEGER
              	}

        voipIpSetIp OBJECT-TYPE
        SYNTAX IpAddress
        MAX-ACCESS read-write
        STATUS current
        DESCRIPTION
        	"IP address."
        ::= { voipIpSetEntry 1 }
        
        voipIpSetVid OBJECT-TYPE
        SYNTAX VlanIndex
        MAX-ACCESS read-write
        STATUS current
        DESCRIPTION
        	""
        ::= { voipIpSetEntry 2 }
        
        voipIpSetMask OBJECT-TYPE
        SYNTAX INTEGER (0..32)
        MAX-ACCESS read-write
        STATUS current
        DESCRIPTION
        	"Network mask."
        ::= { voipIpSetEntry 3 }
        
-- voipDnsTable

        voipDnsTable OBJECT-TYPE
        SYNTAX SEQUENCE OF VoipDnsEntry
        MAX-ACCESS not-accessible
        STATUS current
        DESCRIPTION
        	"Configure DNS server IP of specified slot."
        ::= { voip 4 }
	
        voipDnsEntry OBJECT-TYPE
        SYNTAX VoipDnsEntry
        MAX-ACCESS not-accessible
        STATUS current
        DESCRIPTION
        	"An entry of voipDnsTable."
        INDEX { slotId }
        ::= { voipDnsTable 1 }

        VoipDnsEntry ::=
        	SEQUENCE {
        		voipDnsIp			IpAddress
              	}
              	
        voipDnsIp OBJECT-TYPE
        SYNTAX IpAddress
        MAX-ACCESS read-write
        STATUS current
        DESCRIPTION
        	"IP address."
        ::= { voipDnsEntry 1 }

-- voipRouteTable

	maxNumOfVoipRoute OBJECT-TYPE
        SYNTAX INTEGER
        MAX-ACCESS read-only
        STATUS current
        DESCRIPTION
        	"The maximum number of VoIP routing entries in a slot."
        ::= { voip 7 }
        
        voipRouteTable OBJECT-TYPE
        SYNTAX SEQUENCE OF VoipRouteEntry
        MAX-ACCESS not-accessible
        STATUS current
        DESCRIPTION
        	""
        ::= { voip 8 }
	
        voipRouteEntry OBJECT-TYPE
        SYNTAX VoipRouteEntry
        MAX-ACCESS not-accessible
        STATUS current
        DESCRIPTION
        	"An entry of voipRouteTable."
        INDEX { voipRouteSlot, voipRouteIp, voipRouteGateway, voipRouteMask }
        ::= { voipRouteTable 1 }

        VoipRouteEntry ::=
        	SEQUENCE {
        		voipRouteSlot			INTEGER,
        		voipRouteIp			IpAddress,
        		voipRouteGateway		IpAddress,
        		voipRouteMask			INTEGER,
        		voipRouteMetric			INTEGER,
        		voipRouteRowStatus		RowStatus
              	}

	voipRouteSlot OBJECT-TYPE
        SYNTAX INTEGER
        MAX-ACCESS read-only
        STATUS current
        DESCRIPTION
        	"Specified slot number."
        ::= { voipRouteEntry 1 }
        
        voipRouteIp OBJECT-TYPE
        SYNTAX IpAddress
        MAX-ACCESS read-only
        STATUS current
        DESCRIPTION
        	"IP address."
        ::= { voipRouteEntry 2 }
        
        voipRouteGateway OBJECT-TYPE
        SYNTAX IpAddress
        MAX-ACCESS read-only
        STATUS current
        DESCRIPTION
        	"Gateway IP."
        ::= { voipRouteEntry 3 }
        
        voipRouteMask OBJECT-TYPE
        SYNTAX INTEGER (0..32)
        MAX-ACCESS read-only
        STATUS current
        DESCRIPTION
        	"Network mask."
        ::= { voipRouteEntry 4 }
        
        voipRouteMetric OBJECT-TYPE
        SYNTAX INTEGER (1..15)
        MAX-ACCESS read-create
        STATUS current
        DESCRIPTION
        	"Metric number of the route."
        ::= { voipRouteEntry 5 }
        
        voipRouteRowStatus OBJECT-TYPE
        SYNTAX RowStatus
        MAX-ACCESS read-create
        STATUS current
        DESCRIPTION
        	"This object is used to create a new entry or delete an existing entry in this table."
        ::= { voipRouteEntry 6 }

-- voipCountryCode
        
        voipCountryCode OBJECT-TYPE
        SYNTAX INTEGER {
        		usa(1),
        		taiwan(2),
        		austria(3),
        		belgium(4),
        		denmark(5),
        		finland(6),
        		netherland(7),
        		norway(8),
        		spain(9),
        		sweden(10),
        		switzerland(11),
        		uk(12),
        		germany(13),
        		australia(14),
        		ireland(15),
        		czech(16),
        		italy(17),
        		japan(18),
        		new-zealand(19),
        		russia(20),
        		china(21),
        		vietnam(22),
        		brazil(23),
        		bulgaria(24), 
			france(25),
			hungary(26),
			iceland(27), 
			luxembourg(28),
			poland(29),
			portugal(30),
			slovakia(31),
			greece(32),
			hongkong(33),
			singapore(34),
			morocco(35),
			malaysia(36),
			thailand(37),
			israle(38),
			uae(39),
			ukraine(40),
			south-africa(41),
			south-korea(42),
			philippines(43),
			india(44),
			turkey(45),
			iran(46)
        	}	
        MAX-ACCESS read-write
        STATUS current
        DESCRIPTION
        	"Configure country code (information) for VoIP services."
        ::= { voip 9 }                
        
-- voipH248MgConfTable

        voipH248MgConfTable OBJECT-TYPE
        SYNTAX SEQUENCE OF VoipH248MgConfEntry
        MAX-ACCESS not-accessible
        STATUS current
        DESCRIPTION
		"This table is used to create MG instance at specified slot with specified MGC profile.
		This table is supported by R5.01 and later versions."
        ::= { voipH248 1 }

	voipH248MgConfEntry OBJECT-TYPE
        SYNTAX VoipH248MgConfEntry
        MAX-ACCESS not-accessible
        STATUS current
        DESCRIPTION
        	"An entry in voipH248MgConfTable."
        INDEX { voipH248MgConfSlot , voipH248MgConfName }
        ::= { voipH248MgConfTable 1 }

        VoipH248MgConfEntry ::=
           SEQUENCE {
		voipH248MgConfSlot		INTEGER,
		voipH248MgConfName		DisplayString,
		voipH248MgConfEnable		INTEGER,
		voipH248MgConfH248Profile	DisplayString,
		voipH248MgConfPort		INTEGER,
		voipH248MgConfRowStatus		RowStatus
           }

	voipH248MgConfSlot OBJECT-TYPE
        SYNTAX INTEGER
        MAX-ACCESS read-only
        STATUS current
        DESCRIPTION
		"Line card slot number."
        ::= { voipH248MgConfEntry 1 }
        
        voipH248MgConfName OBJECT-TYPE
        SYNTAX DisplayString (SIZE(1..31))
        MAX-ACCESS read-only
        STATUS current
        DESCRIPTION
		"MG name."
        ::= { voipH248MgConfEntry 2 }
        
        voipH248MgConfEnable OBJECT-TYPE
        SYNTAX INTEGER {
        		enable(1),
        		disable(2)
        	}
        MAX-ACCESS read-create
        STATUS current
        DESCRIPTION
		"Enable/disable MG."
        ::= { voipH248MgConfEntry 3 }
        
        voipH248MgConfH248Profile OBJECT-TYPE
        SYNTAX DisplayString (SIZE(1..31))
        MAX-ACCESS read-create
        STATUS current
        DESCRIPTION
		"H.248 profile name."
        ::= { voipH248MgConfEntry 4 }
        
        voipH248MgConfPort OBJECT-TYPE
        SYNTAX INTEGER (1025..65535)
        MAX-ACCESS read-create
        STATUS current
        DESCRIPTION
		"MG port number."
        ::= { voipH248MgConfEntry 5 }
        
        voipH248MgConfRowStatus OBJECT-TYPE
        SYNTAX RowStatus
        MAX-ACCESS read-create
        STATUS current
        DESCRIPTION
		"This object is used to create a new row or delete an existing row in this table.."
        ::= { voipH248MgConfEntry 6 }
        
-- voipH248InterfaceConfTable

        voipH248InterfaceConfTable OBJECT-TYPE
        SYNTAX SEQUENCE OF VoipH248InterfaceConfEntry
        MAX-ACCESS not-accessible
        STATUS current
        DESCRIPTION
		""
        ::= { voipH248 2 }

	voipH248InterfaceConfEntry OBJECT-TYPE
        SYNTAX VoipH248InterfaceConfEntry
        MAX-ACCESS not-accessible
        STATUS current
        DESCRIPTION
        	"An entry in voipH248InterfaceConfTable."
        INDEX { voipH248InterfaceConfId }
        ::= { voipH248InterfaceConfTable 1 }

        VoipH248InterfaceConfEntry ::=
           SEQUENCE {
		voipH248InterfaceConfId			INTEGER,
		voipH248InterfaceConfMgName		DisplayString,
		voipH248InterfaceConfMgEnable		INTEGER,
		voipH248InterfaceConfH248Profile	DisplayString,
		voipH248InterfaceConfPort		INTEGER,
		voipH248InterfaceConfIp			IpAddress,
		voipH248InterfaceConfMasklen		INTEGER,
		voipH248InterfaceConfVid		VlanIndex,
		voipH248InterfaceConfPrimary		INTEGER,
		voipH248InterfaceConfSecondary		INTEGER,
		voipH248InterfaceConfBhcaPeak		INTEGER,
		voipH248InterfaceConfBhcaAverage	INTEGER 
           }

	voipH248InterfaceConfId OBJECT-TYPE
        SYNTAX INTEGER
        MAX-ACCESS read-only
        STATUS current
        DESCRIPTION
		"Line card slot number."
        ::= { voipH248InterfaceConfEntry 1 }
        
        voipH248InterfaceConfMgName OBJECT-TYPE
        SYNTAX DisplayString (SIZE(1..31))
        MAX-ACCESS read-write
        STATUS current
        DESCRIPTION
		"MG name."
        ::= { voipH248InterfaceConfEntry 2 }
        
        voipH248InterfaceConfMgEnable OBJECT-TYPE
        SYNTAX INTEGER {
        		enable(1),
        		disable(2)
        	}
        MAX-ACCESS read-write
        STATUS current
        DESCRIPTION
		"Enable/disable MG."
        ::= { voipH248InterfaceConfEntry 3 }
        
        voipH248InterfaceConfH248Profile OBJECT-TYPE
        SYNTAX DisplayString (SIZE(1..31))
        MAX-ACCESS read-write
        STATUS current
        DESCRIPTION
		"H.248 profile name."
        ::= { voipH248InterfaceConfEntry 4 }
        
        voipH248InterfaceConfPort OBJECT-TYPE
        SYNTAX INTEGER (1025..65535)
        MAX-ACCESS read-write
        STATUS current
        DESCRIPTION
		"MG port number."
        ::= { voipH248InterfaceConfEntry 5 }
      
	voipH248InterfaceConfIp OBJECT-TYPE
        SYNTAX IpAddress
        MAX-ACCESS read-write
        STATUS current
        DESCRIPTION
		"Interface Ip"
        ::= { voipH248InterfaceConfEntry 6 }
          
	voipH248InterfaceConfMasklen   OBJECT-TYPE
        SYNTAX INTEGER
        MAX-ACCESS read-write
        STATUS current
        DESCRIPTION
		"network mask, 0~32"
        ::= { voipH248InterfaceConfEntry 7 }		
        
        voipH248InterfaceConfVid     OBJECT-TYPE
        SYNTAX VlanIndex
        MAX-ACCESS read-write
        STATUS current
        DESCRIPTION
     "1~4094"
        ::= { voipH248InterfaceConfEntry 8 }
        
        voipH248InterfaceConfPrimary    OBJECT-TYPE
        SYNTAX INTEGER
        MAX-ACCESS read-write
        STATUS current
        DESCRIPTION
     "slot id"
        ::= { voipH248InterfaceConfEntry 9 }
        
        voipH248InterfaceConfSecondary    OBJECT-TYPE
        SYNTAX INTEGER
        MAX-ACCESS read-write
        STATUS current
        DESCRIPTION
     "slot id"
        ::= { voipH248InterfaceConfEntry 10 }
        
        voipH248InterfaceConfBhcaPeak    OBJECT-TYPE
        SYNTAX INTEGER
        MAX-ACCESS read-write
        STATUS current
        DESCRIPTION
     "peak call attempt allowance in one second , 0~30"
        ::= { voipH248InterfaceConfEntry 11 }
        
        voipH248InterfaceConfBhcaAverage    OBJECT-TYPE
        SYNTAX INTEGER
        MAX-ACCESS read-write
        STATUS current
        DESCRIPTION
     "average call attempt allowance in one hour, 0~60000"
        ::= { voipH248InterfaceConfEntry 12 }
    
    
  -- voipH248SlotConfTable

        voipH248SlotConfTable OBJECT-TYPE
        SYNTAX SEQUENCE OF VoipH248SlotConfEntry
        MAX-ACCESS not-accessible
        STATUS current
        DESCRIPTION
		""
        ::= { voipH248 3 }

	voipH248SlotConfEntry OBJECT-TYPE
        SYNTAX VoipH248SlotConfEntry
        MAX-ACCESS not-accessible
        STATUS current
        DESCRIPTION
        	"An entry in voipH248ConfSlotTable."
        INDEX { voipH248SlotConfId }
        ::= { voipH248SlotConfTable 1 }

        VoipH248SlotConfEntry ::=
	SEQUENCE {
		voipH248SlotConfId			INTEGER,
		voipH248SlotConfMasterIp1		IpAddress,   
		voipH248SlotConfMasterIp2		IpAddress,   
		voipH248SlotConfOpmode			INTEGER,  
		voipH248SlotConf8021pPrio		INTEGER,   
		voipH248SlotConfPriorityDscp  		INTEGER
	}

	voipH248SlotConfId OBJECT-TYPE
        SYNTAX INTEGER
        MAX-ACCESS read-only
        STATUS current
        DESCRIPTION
		"Line card slot number."
        ::= { voipH248SlotConfEntry 1 }
        
    voipH248SlotConfMasterIp1 OBJECT-TYPE
        SYNTAX IpAddress
        MAX-ACCESS read-write
        STATUS current
        DESCRIPTION
		"Master Ip"
        ::= { voipH248SlotConfEntry 2 }
        
    voipH248SlotConfMasterIp2 OBJECT-TYPE
        SYNTAX IpAddress
        MAX-ACCESS read-write
        STATUS current
        DESCRIPTION
		"Master Ip"
        ::= { voipH248SlotConfEntry 3 }
                
    voipH248SlotConfOpmode OBJECT-TYPE
        SYNTAX INTEGER{
        		mc(1),
        		sc(2)
        	}
        MAX-ACCESS read-write
        STATUS current
        DESCRIPTION
		"Opmode"
        ::= { voipH248SlotConfEntry 4 }  
        
    voipH248SlotConf8021pPrio OBJECT-TYPE
        SYNTAX INTEGER
        MAX-ACCESS read-write
        STATUS current
        DESCRIPTION
		"802.1p bit for H.248 internal message packet, 0 ~ 7"
        ::= { voipH248SlotConfEntry 5 }     
        
     voipH248SlotConfPriorityDscp   OBJECT-TYPE
        SYNTAX INTEGER
        MAX-ACCESS read-write
        STATUS current
        DESCRIPTION
		"DSCP for H.248 internal message packet, 0 ~ 63"
        ::= { voipH248SlotConfEntry 6 }   
        
         
 -- voipH248SlaveConfTable  

    voipH248SlaveConfTable  OBJECT-TYPE
        SYNTAX SEQUENCE OF VoipH248SlaveConfEntry
        MAX-ACCESS not-accessible
        STATUS current
        DESCRIPTION
		""
        ::= { voipH248 4 }

	voipH248SlaveConfEntry OBJECT-TYPE
        SYNTAX VoipH248SlaveConfEntry
        MAX-ACCESS not-accessible
        STATUS current
        DESCRIPTION
        	"An entry in voipH248InterfaceSlaveTable."
        INDEX { voipH248SlaveConfInterfaceId ,voipH248SlaveConfSlaveId}
        ::= { voipH248SlaveConfTable 1 }      

        VoipH248SlaveConfEntry ::=
        SEQUENCE {
		voipH248SlaveConfInterfaceId  		INTEGER,
		voipH248SlaveConfSlaveId  		INTEGER,   
		voipH248SlaveConfSlaveIp    		IpAddress
	}

	voipH248SlaveConfInterfaceId OBJECT-TYPE
        SYNTAX INTEGER
        MAX-ACCESS read-only
        STATUS current
        DESCRIPTION
		"Line card slot number."
        ::= { voipH248SlaveConfEntry 1 }
        
     voipH248SlaveConfSlaveId OBJECT-TYPE
        SYNTAX INTEGER
        MAX-ACCESS read-write
        STATUS current
        DESCRIPTION
		"Slave Member"
        ::= { voipH248SlaveConfEntry 2 }     
        
     voipH248SlaveConfSlaveIp OBJECT-TYPE
        SYNTAX IpAddress
        MAX-ACCESS read-write
        STATUS current
        DESCRIPTION
		"Slave Ip"
        ::= { voipH248SlaveConfEntry 3 }

 voipH248Localcall		OBJECT IDENTIFIER ::= { voipH248 5 }
     
     voipH248LocalcallEnterTime OBJECT-TYPE
        SYNTAX INTEGER(1..60)
        MAX-ACCESS read-write
        STATUS current
        DESCRIPTION
		"The time to enter localcall utility after MGC missing.
		1~60, in unit of minutes"
        ::= { voipH248Localcall 1 }
        
     voipH248LocalcallExistTime OBJECT-TYPE
        SYNTAX INTEGER(1..60)
        MAX-ACCESS read-write
        STATUS current
        DESCRIPTION
		"The time to exist localcall utility after MGC reconnected.
		1~60, in unit of minutes"
        ::= { voipH248Localcall 2 }
 	  

-- VoIP Country Code

	voipCountryCodeParam		OBJECT IDENTIFIER ::= { voip 11 }
	
	law OBJECT-TYPE
        SYNTAX INTEGER {
        		alaw(0),
        		ulaw(1)
        	}
        MAX-ACCESS read-only
        STATUS current
        DESCRIPTION
		""
        ::= { voipCountryCodeParam 1 }
        
        impedance OBJECT-TYPE
        SYNTAX DisplayString
        MAX-ACCESS read-only
        STATUS current
        DESCRIPTION
		""
        ::= { voipCountryCodeParam 2 }
        
        loopCurrent OBJECT-TYPE
        SYNTAX INTEGER
        UNITS "mA"
        MAX-ACCESS read-only
        STATUS current
        DESCRIPTION
		""
        ::= { voipCountryCodeParam 3 }
        
        taxType OBJECT-TYPE
        SYNTAX DisplayString
        MAX-ACCESS read-only
        STATUS current
        DESCRIPTION
		""
        ::= { voipCountryCodeParam 4 }
        
        ringFrequency OBJECT-TYPE
        SYNTAX INTEGER
        UNITS "Hz"
        MAX-ACCESS read-only
        STATUS current
        DESCRIPTION
		""
        ::= { voipCountryCodeParam 5 }
        
        ringAmplitude OBJECT-TYPE
        SYNTAX INTEGER
        UNITS "Vrms"
        MAX-ACCESS read-only
        STATUS current
        DESCRIPTION
		""
        ::= { voipCountryCodeParam 6 }
        
        ringOnTime1 OBJECT-TYPE
        SYNTAX INTEGER
        UNITS "miniseconds"
        MAX-ACCESS read-only
        STATUS current
        DESCRIPTION
		""
        ::= { voipCountryCodeParam 7 }
        
        ringOffTime1 OBJECT-TYPE
        SYNTAX INTEGER
        UNITS "miniseconds"
        MAX-ACCESS read-only
        STATUS current
        DESCRIPTION
		""
        ::= { voipCountryCodeParam 8 }
        
        ringOnTime2 OBJECT-TYPE
        SYNTAX INTEGER
        UNITS "miniseconds"
        MAX-ACCESS read-only
        STATUS current
        DESCRIPTION
		""
        ::= { voipCountryCodeParam 9 }
        
        ringOffTime2 OBJECT-TYPE
        SYNTAX INTEGER
        UNITS "miniseconds"
        MAX-ACCESS read-only
        STATUS current
        DESCRIPTION
		""
        ::= { voipCountryCodeParam 10 }
        
        flashMin OBJECT-TYPE
        SYNTAX INTEGER
        UNITS "miniseconds"
        MAX-ACCESS read-only
        STATUS current
        DESCRIPTION
		""
        ::= { voipCountryCodeParam 11 }
        
        flashMax OBJECT-TYPE
        SYNTAX INTEGER
        UNITS "miniseconds"
        MAX-ACCESS read-only
        STATUS current
        DESCRIPTION
		""
        ::= { voipCountryCodeParam 12 }
        
        breakMin OBJECT-TYPE
        SYNTAX INTEGER
        UNITS "miniseconds"
        MAX-ACCESS read-only
        STATUS current
        DESCRIPTION
		""
        ::= { voipCountryCodeParam 13 }
        
        breakMax OBJECT-TYPE
        SYNTAX INTEGER
        UNITS "miniseconds"
        MAX-ACCESS read-only
        STATUS current
        DESCRIPTION
		""
        ::= { voipCountryCodeParam 14 }
        
        makeMin OBJECT-TYPE
        SYNTAX INTEGER
        UNITS "miniseconds"
        MAX-ACCESS read-only
        STATUS current
        DESCRIPTION
		""
        ::= { voipCountryCodeParam 15 }
        
        makeMax OBJECT-TYPE
        SYNTAX INTEGER
        UNITS "miniseconds"
        MAX-ACCESS read-only
        STATUS current
        DESCRIPTION
		""
        ::= { voipCountryCodeParam 16 }
        
        interDigitMin OBJECT-TYPE
        SYNTAX INTEGER
        UNITS "miniseconds"
        MAX-ACCESS read-only
        STATUS current
        DESCRIPTION
		""
        ::= { voipCountryCodeParam 17 }
        
        meterFrequency OBJECT-TYPE
        SYNTAX INTEGER
        UNITS "kHz"
        MAX-ACCESS read-only
        STATUS current
        DESCRIPTION
		""
        ::= { voipCountryCodeParam 18 }
        
        meterOnTime OBJECT-TYPE
        SYNTAX INTEGER
        UNITS "miniseconds"
        MAX-ACCESS read-only
        STATUS current
        DESCRIPTION
		""
        ::= { voipCountryCodeParam 19 }
        
        meterOffTime OBJECT-TYPE
        SYNTAX INTEGER
        UNITS "miniseconds"
        MAX-ACCESS read-only
        STATUS current
        DESCRIPTION
		""
        ::= { voipCountryCodeParam 20 }
        
        cidType OBJECT-TYPE
        SYNTAX INTEGER {
        		during-ring(0),
        		prior-ring(1)
        	}
        MAX-ACCESS read-only
        STATUS current
        DESCRIPTION
		""
        ::= { voipCountryCodeParam 21 }
        
        payloadType OBJECT-TYPE
        SYNTAX DisplayString
        MAX-ACCESS read-only
        STATUS current
        DESCRIPTION
		""
        ::= { voipCountryCodeParam 22 }
        
        firstTASType OBJECT-TYPE
        SYNTAX DisplayString
        MAX-ACCESS read-only
        STATUS current
        DESCRIPTION
		""
        ::= { voipCountryCodeParam 23 }
        
        secondTASType OBJECT-TYPE
        SYNTAX DisplayString
        MAX-ACCESS read-only
        STATUS current
        DESCRIPTION
		""
        ::= { voipCountryCodeParam 24 }
        
        firstTASInterval OBJECT-TYPE
        SYNTAX INTEGER
        UNITS "miniseconds"
        MAX-ACCESS read-only
        STATUS current
        DESCRIPTION
		""
        ::= { voipCountryCodeParam 25 }
        
        secondTASInterval OBJECT-TYPE
        SYNTAX INTEGER
        UNITS "miniseconds"
        MAX-ACCESS read-only
        STATUS current
        DESCRIPTION
		""
        ::= { voipCountryCodeParam 26 }
        
        startToRing OBJECT-TYPE
        SYNTAX INTEGER
        UNITS "miniseconds"
        MAX-ACCESS read-only
        STATUS current
        DESCRIPTION
		""
        ::= { voipCountryCodeParam 27 }
        
        dialTone OBJECT-TYPE
        SYNTAX DisplayString
        MAX-ACCESS read-only
        STATUS current
        DESCRIPTION
		""
        ::= { voipCountryCodeParam 28 }
        
        ringBackTone OBJECT-TYPE
        SYNTAX DisplayString
        MAX-ACCESS read-only
        STATUS current
        DESCRIPTION
		""
        ::= { voipCountryCodeParam 29 }
        
        busyTone OBJECT-TYPE
        SYNTAX DisplayString
        MAX-ACCESS read-only
        STATUS current
        DESCRIPTION
		""
        ::= { voipCountryCodeParam 30 }
        
        congestionTone OBJECT-TYPE
        SYNTAX DisplayString
        MAX-ACCESS read-only
        STATUS current
        DESCRIPTION
		""
        ::= { voipCountryCodeParam 31 }
        
        callWaitingTone1 OBJECT-TYPE
        SYNTAX DisplayString
        MAX-ACCESS read-only
        STATUS current
        DESCRIPTION
		""
        ::= { voipCountryCodeParam 32 }
        
        callWaitingTone2 OBJECT-TYPE
        SYNTAX DisplayString
        MAX-ACCESS read-only
        STATUS current
        DESCRIPTION
		""
        ::= { voipCountryCodeParam 33 }
        
        specialDialTone OBJECT-TYPE
        SYNTAX DisplayString
        MAX-ACCESS read-only
        STATUS current
        DESCRIPTION
		""
        ::= { voipCountryCodeParam 34 }
        
        howlerTone OBJECT-TYPE
        SYNTAX DisplayString
        MAX-ACCESS read-only
        STATUS current
        DESCRIPTION
		""
        ::= { voipCountryCodeParam 35 }
        
        warningTone OBJECT-TYPE
        SYNTAX DisplayString
        MAX-ACCESS read-only
        STATUS current
        DESCRIPTION
		""
        ::= { voipCountryCodeParam 36 }
        
        confirmationTone OBJECT-TYPE
        SYNTAX DisplayString
        MAX-ACCESS read-only
        STATUS current
        DESCRIPTION
		""
        ::= { voipCountryCodeParam 37 }
        
        holdingTone OBJECT-TYPE
        SYNTAX DisplayString
        MAX-ACCESS read-only
        STATUS current
        DESCRIPTION
		""
        ::= { voipCountryCodeParam 38 } 
        
        numberUnobtainableTone OBJECT-TYPE
        SYNTAX DisplayString
        MAX-ACCESS read-only
        STATUS current
        DESCRIPTION
		"This object is supported by R5.05 and later versions."
        ::= { voipCountryCodeParam 39 }

        recallDialTone OBJECT-TYPE
        SYNTAX DisplayString
        MAX-ACCESS read-only
        STATUS current
        DESCRIPTION
		""
        ::= { voipCountryCodeParam 40 }
        
        specialInformationTone OBJECT-TYPE
        SYNTAX DisplayString
        MAX-ACCESS read-only
        STATUS current
        DESCRIPTION
		""
        ::= { voipCountryCodeParam 41 }

 
 -- VoIP Pots

	voipPots		OBJECT IDENTIFIER ::= { voip 12 }
	voipPotsFlash	OBJECT IDENTIFIER ::= { voipPots 2 }
	
	
	voipPotsRingTable  OBJECT-TYPE
        SYNTAX SEQUENCE OF VoipPotsRingEntry
        MAX-ACCESS not-accessible
        STATUS current
        DESCRIPTION
		"This table is supported by R5.05 and later versions."
        ::= { voipPots 1 }

	voipPotsRingEntry OBJECT-TYPE
        SYNTAX VoipPotsRingEntry
        MAX-ACCESS not-accessible
        STATUS current
        DESCRIPTION
        	"An entry in voipPotsRingEntry. "
        INDEX { voipPotsRingConfId}
        ::= { voipPotsRingTable 1 }      

        VoipPotsRingEntry ::=
        SEQUENCE {
		voipPotsRingConfId  			INTEGER,
		voipPotsRingConfNameDefval		INTEGER,
		voipPotsRingConfName  			DisplayString,
		voipPotsRingConfPatternDefval	INTEGER,  
		voipPotsRingConfPatternOn1		INTEGER,
		voipPotsRingConfPatternOff1		INTEGER,
		voipPotsRingConfPatternOn2		INTEGER,
		voipPotsRingConfPatternOff2		INTEGER,
		voipPotsRingConfPatternOn3		INTEGER,
		voipPotsRingConfPatternOff3		INTEGER
	}

	voipPotsRingConfId OBJECT-TYPE
        SYNTAX INTEGER
        MAX-ACCESS read-only
        STATUS current
        DESCRIPTION
		"index"
        ::= { voipPotsRingEntry 1 } 
    
    voipPotsRingConfNameDefval OBJECT-TYPE
        SYNTAX INTEGER {
        		enable(1),
        		disable(2)
        	}
        MAX-ACCESS read-write
        STATUS current
        DESCRIPTION
		"Configure pots ring name to use default value.
		1 : enable 
		2 : disable"
        ::= { voipPotsRingEntry 2 }
        
     voipPotsRingConfName OBJECT-TYPE
        SYNTAX DisplayString
        MAX-ACCESS read-write
        STATUS current
        DESCRIPTION
		"name"
        ::= { voipPotsRingEntry 3 } 
        
     voipPotsRingConfPatternDefval OBJECT-TYPE
        SYNTAX INTEGER {
        		enable(1),
        		disable(2)
        	}
        MAX-ACCESS read-write
        STATUS current
        DESCRIPTION
		"Configure pots ring pattern to use default value.
		1 : enable 
		2 : disable"
        ::= { voipPotsRingEntry 4 }    
        
     voipPotsRingConfPatternOn1 OBJECT-TYPE
        SYNTAX INTEGER
        MAX-ACCESS read-write
        STATUS current
        DESCRIPTION
		"first on time"
        ::= { voipPotsRingEntry 5 }    
     
     voipPotsRingConfPatternOff1 OBJECT-TYPE
        SYNTAX INTEGER
        MAX-ACCESS read-write
        STATUS current
        DESCRIPTION
		"first off time"
        ::= { voipPotsRingEntry 6 }  
        
     voipPotsRingConfPatternOn2 OBJECT-TYPE
        SYNTAX INTEGER
        MAX-ACCESS read-write
        STATUS current
        DESCRIPTION
		"second on time"
        ::= { voipPotsRingEntry 7 }  
        
     voipPotsRingConfPatternOff2 OBJECT-TYPE
        SYNTAX INTEGER
        MAX-ACCESS read-write
        STATUS current
        DESCRIPTION
		"second off time"
        ::= { voipPotsRingEntry 8 } 
     
     voipPotsRingConfPatternOn3 OBJECT-TYPE
        SYNTAX INTEGER
        MAX-ACCESS read-write
        STATUS current
        DESCRIPTION
		"third on time"
        ::= { voipPotsRingEntry 9 }  
        
     voipPotsRingConfPatternOff3 OBJECT-TYPE
        SYNTAX INTEGER
        MAX-ACCESS read-write
        STATUS current
        DESCRIPTION
		"third off time"
        ::= { voipPotsRingEntry 10 }  
        
-- voipPotsFlash
    voipPotsFlashDefval OBJECT-TYPE
        SYNTAX INTEGER {
        		enable(1),
        		disable(2)
        	}
        MAX-ACCESS read-write
        STATUS current
        DESCRIPTION
		"Configure pots flash to use default setting.
		1 : enable 
		2 : disable"
        ::= { voipPotsFlash 1 }
    
    voipPotsFlashMinTime OBJECT-TYPE
        SYNTAX INTEGER
        MAX-ACCESS read-write
        STATUS current
        DESCRIPTION
		"Minimum time of hook-flash detection period."
        ::= { voipPotsFlash 2 }
        
    voipPotsFlashMaxTime OBJECT-TYPE
        SYNTAX INTEGER
        MAX-ACCESS read-write
        STATUS current
        DESCRIPTION
		"Maximum time of hook-flash detection period."
        ::= { voipPotsFlash 3 }  
        
 -- voipPotsRingVoltage       
    voipPotsRingVoltage OBJECT-TYPE
        SYNTAX INTEGER(25..90)
        MAX-ACCESS read-write
        STATUS current
        DESCRIPTION
		"The ring output voltage of pots
		25~90, in unit of Vrms.
		0 means set to default value."
        ::= { voipPots 3 }
        
 -- VoIP Map

	voipIfindexMap		OBJECT IDENTIFIER ::= { voip 13 }

 -- VoIP Map voipIfindex 2 ifindex
 	
	voipInterfaceMapTable  OBJECT-TYPE
        SYNTAX SEQUENCE OF VoipInterfaceMapEntry
        MAX-ACCESS not-accessible
        STATUS current
        DESCRIPTION
		"A list of interface entries map voip interface indexes to interface indexes."
        ::= { voipIfindexMap 1 }
        
	voipInterfaceMapEntry OBJECT-TYPE
        SYNTAX VoipInterfaceMapEntry
        MAX-ACCESS not-accessible
        STATUS current
        DESCRIPTION
        	"An entry in voipInterfaceMapTable. "
        INDEX { voipIfIndex }
        ::= { voipInterfaceMapTable 1 }
        
	VoipInterfaceMapEntry ::=
	    SEQUENCE {
			voipIfIndex  			InterfaceIndex,
			ifIndexValue			InterfaceIndex
	}
	
	voipIfIndex OBJECT-TYPE
        SYNTAX InterfaceIndex
        MAX-ACCESS not-accessible
        STATUS current
        DESCRIPTION
		"voip index interface"
        ::= { voipInterfaceMapEntry 1 }
        
    ifIndexValue OBJECT-TYPE
        SYNTAX InterfaceIndex
        MAX-ACCESS read-only
        STATUS current
        DESCRIPTION
		"Mapped interface index value for a voip interface index."
        ::= { voipInterfaceMapEntry 2 }
  
 -- VoIP Map ifindex 2 voipIfindex
 
	voipIfTable  OBJECT-TYPE
        SYNTAX SEQUENCE OF VoipIfEntry
        MAX-ACCESS not-accessible
        STATUS current
        DESCRIPTION
		"A list of interface entries map interface indexes to voip interface indexes."
        ::= { voipIfindexMap 2 }
        
	voipIfEntry  OBJECT-TYPE
        SYNTAX VoipIfEntry
        MAX-ACCESS not-accessible
        STATUS current
        DESCRIPTION
        	"An entry in voipData2PotsIndexMapEntry. "
        INDEX { ifIndex }
        ::= { voipIfTable 1 }
        
    VoipIfEntry ::=
	    SEQUENCE {
			voipIfIndexValue  			InterfaceIndex
	}
	
	voipIfIndexValue OBJECT-TYPE
        SYNTAX InterfaceIndex
        MAX-ACCESS read-only
        STATUS current
        DESCRIPTION
		"Mapped voip interface index value for a interface index."
        ::= { voipIfEntry 1 }


    voipSingleIp	OBJECT IDENTIFIER ::= { voip 14 }

    voipExtH248					OBJECT IDENTIFIER ::= { voipSingleIp 1 }
    voipExtStats				OBJECT IDENTIFIER ::= { voipSingleIp 2 }
    voipExtSipProfile			OBJECT IDENTIFIER ::= { voipSingleIp 3 }
	--voipExtMaxNumOfVoipDialPlan	OBJECT IDENTIFIER ::= { voipSingleIp 4 }
	--voipExtDialPlanTable		OBJECT IDENTIFIER ::= { voipSingleIp 5 }
    voipExtSip					OBJECT IDENTIFIER ::= { voipSingleIp 6 }
    --voipExtSipLineConfTable		OBJECT IDENTIFIER ::= { voipSingleIp 7 }
    --voipExtSipLineStatTable		OBJECT IDENTIFIER ::= { voipSingleIp 8 }

-- voipExtH248InterfaceConf
    voipExtH248InterfaceConf OBJECT IDENTIFIER ::= { voipExtH248 1 }
        
      voipExtH248InterfaceConfMgName OBJECT-TYPE
        SYNTAX DisplayString (SIZE(1..31))
        MAX-ACCESS read-write
        STATUS current
        DESCRIPTION
					"MG name."
        ::= { voipExtH248InterfaceConf 1 }
        
	  voipExtH248InterfaceConfMgEnable OBJECT-TYPE
        SYNTAX INTEGER {
        		enable(1),
        		disable(2)
        	}
        MAX-ACCESS read-write
        STATUS current
        DESCRIPTION
		     "Enable/disable MG."
        ::= { voipExtH248InterfaceConf 2 }
        
      voipExtH248InterfaceConfH248Profile OBJECT-TYPE
        SYNTAX DisplayString (SIZE(1..31))
        MAX-ACCESS read-write
        STATUS current
        DESCRIPTION
		     "H.248 profile name."
        ::= { voipExtH248InterfaceConf 3 }
        
      voipExtH248InterfaceConfPort OBJECT-TYPE
        SYNTAX INTEGER (1025..65535)
        MAX-ACCESS read-write
        STATUS current
        DESCRIPTION
					"MG port number."
        ::= { voipExtH248InterfaceConf 4 }
      
      voipExtH248InterfaceConfSignalIp OBJECT-TYPE
        SYNTAX IpAddress
        MAX-ACCESS read-write
        STATUS current
        DESCRIPTION
					"Signaling Ip"
        ::= { voipExtH248InterfaceConf 5 }
          
			voipExtH248InterfaceConfSignalMasklen   OBJECT-TYPE
        SYNTAX INTEGER
        MAX-ACCESS read-write
        STATUS current
        DESCRIPTION
					"Signaling network mask, 0~32"
        ::= { voipExtH248InterfaceConf 6 }		
        
      voipExtH248InterfaceConfSignalVid     OBJECT-TYPE
        SYNTAX VlanIndex
        MAX-ACCESS read-write
        STATUS current
        DESCRIPTION
     			"1~4094"
        ::= { voipExtH248InterfaceConf 7 }
                
      voipExtH248InterfaceConfMediaIp OBJECT-TYPE
        SYNTAX IpAddress
        MAX-ACCESS read-write
        STATUS current
        DESCRIPTION
					"Media Ip"
        ::= { voipExtH248InterfaceConf 8 }
          
			voipExtH248InterfaceConfMediaMasklen   OBJECT-TYPE
        SYNTAX INTEGER
        MAX-ACCESS read-write
        STATUS current
        DESCRIPTION
					"Media network mask, 0~32"
        ::= { voipExtH248InterfaceConf 9 }		
        
      voipExtH248InterfaceConfMediaVid     OBJECT-TYPE
        SYNTAX VlanIndex
        MAX-ACCESS read-write
        STATUS current
        DESCRIPTION
     			"1~4094"
        ::= { voipExtH248InterfaceConf 10 }

      voipExtH248InterfaceConfDnsIp OBJECT-TYPE
        SYNTAX IpAddress
        MAX-ACCESS read-write
        STATUS current
        DESCRIPTION
					"DNS Ip"
        ::= { voipExtH248InterfaceConf 11 }
        
      voipExtH248InterfaceConfRegisterRetry OBJECT-TYPE
        SYNTAX INTEGER (1..1440)
        MAX-ACCESS read-write
        STATUS current
        DESCRIPTION
					"Register retry time interval, in unit of minute. range is 1 to 1440."
        ::= { voipExtH248InterfaceConf 12 }


	  voipExtH248InterfaceMaxNumOfVoipRoute OBJECT-TYPE
        SYNTAX INTEGER
        MAX-ACCESS read-only
        STATUS current
        DESCRIPTION
        	""
        ::= { voipExtH248 2 }

-- voipExtH248InterfaceRouteTable

     voipExtH248InterfaceRouteTable OBJECT-TYPE
        SYNTAX SEQUENCE OF VoipExtH248InterfaceRouteEntry
        MAX-ACCESS not-accessible
        STATUS current
        DESCRIPTION
        	""
        ::= { voipExtH248 3 }
	
     voipExtH248InterfaceRouteEntry OBJECT-TYPE
        SYNTAX VoipExtH248InterfaceRouteEntry
        MAX-ACCESS not-accessible
        STATUS current
        DESCRIPTION
        	"An entry of voipExtH248InterfaceRouteTable."
        INDEX { voipExtH248InterfaceRouteIp, voipExtH248InterfaceRouteGateway, voipExtH248InterfaceRouteMask }
        ::= { voipExtH248InterfaceRouteTable 1 }

     VoipExtH248InterfaceRouteEntry ::=
        	SEQUENCE {
        		voipExtH248InterfaceRouteIp					IpAddress,
        		voipExtH248InterfaceRouteGateway		IpAddress,
        		voipExtH248InterfaceRouteMask				INTEGER,
        		voipExtH248InterfaceRouteMetric			INTEGER,
        		voipExtH248InterfaceRouteRowStatus	RowStatus
          }

      voipExtH248InterfaceRouteIp OBJECT-TYPE
        SYNTAX IpAddress
        MAX-ACCESS read-only
        STATUS current
        DESCRIPTION
        	"IP address."
        ::= { voipExtH248InterfaceRouteEntry 1 }
        
      voipExtH248InterfaceRouteGateway OBJECT-TYPE
        SYNTAX IpAddress
        MAX-ACCESS read-only
        STATUS current
        DESCRIPTION
        	"Gateway IP."
        ::= { voipExtH248InterfaceRouteEntry 2 }
        
      voipExtH248InterfaceRouteMask OBJECT-TYPE
        SYNTAX INTEGER (0..32)
        MAX-ACCESS read-only
        STATUS current
        DESCRIPTION
        	"Network mask."
        ::= { voipExtH248InterfaceRouteEntry 3 }
        
      voipExtH248InterfaceRouteMetric OBJECT-TYPE
        SYNTAX INTEGER (1..15)
        MAX-ACCESS read-create
        STATUS current
        DESCRIPTION
        	"Metric number of the route."
        ::= { voipExtH248InterfaceRouteEntry 4 }
        
      voipExtH248InterfaceRouteRowStatus OBJECT-TYPE
        SYNTAX RowStatus
        MAX-ACCESS read-create
        STATUS current
        DESCRIPTION
        	"This object is used to create a new entry or delete an existing entry in this table."
        ::= { voipExtH248InterfaceRouteEntry 5 }

-- voipExtH248InterfaceStat

      voipExtH248InterfaceStat OBJECT IDENTIFIER ::={ voipExtStats 1 }

        voipExtH248InterfaceStatMgState OBJECT-TYPE
			SYNTAX INTEGER {
					disable(1),
					registering(2),
					registered(3),     
					unregistering(4),
					unregistered(5),
					inactivity-timeout(6),
					activity-back(7),
					disconnected(8), 
					disabled-by-MGC(9)
			}
			MAX-ACCESS read-only
			STATUS current
			DESCRIPTION
				"Mg State"
			::= { voipExtH248InterfaceStat 1 }
						   	    
        voipExtH248InterfaceStatPrimaryProtectionState  OBJECT-TYPE
			SYNTAX INTEGER {
					invalid(1),
					active(2),
					standby(3)
			}
			MAX-ACCESS read-only
			STATUS current
			DESCRIPTION
				"Primary Protection State"
			::= { voipExtH248InterfaceStat 2 }
			
        voipExtH248InterfaceStatSecondaryProtectionState  OBJECT-TYPE
			SYNTAX INTEGER {
					invalid(1),
					active(2),
					standby(3)
			}
			MAX-ACCESS read-only
			STATUS current
			DESCRIPTION
				"Secondary Protection State"
			::= { voipExtH248InterfaceStat 3 }
		
        voipExtH248InterfaceStatRedundantState   OBJECT-TYPE
			SYNTAX INTEGER {
					out-of-sync(1),
					authorization(2),
					synchronizing(3),
					in-service(4)
			}
			MAX-ACCESS read-only
			STATUS current
			DESCRIPTION
				"Redundant State"
			::= { voipExtH248InterfaceStat 4 }

      	voipExtH248InterfaceStatMgcIp OBJECT-TYPE
        	SYNTAX IpAddress
        	MAX-ACCESS read-only
        	STATUS current
        	DESCRIPTION
        		"MGC IP address."
        	::= { voipExtH248InterfaceStat 5 }
        	
       	voipExtH248InterfaceStatMgH248Mac OBJECT-TYPE
		    SYNTAX DisplayString
        	MAX-ACCESS read-only
        	STATUS current
        	DESCRIPTION
        		"The MAC used by megaco packets."
        	::= { voipExtH248InterfaceStat 6 }

        voipExtH248InterfaceStatLocalcallStat OBJECT-TYPE
		    SYNTAX INTEGER {
					inactive(1),
					active(2)
			}
        	MAX-ACCESS read-only
        	STATUS current
        	DESCRIPTION
        		"Local call state."
        	::= { voipExtH248InterfaceStat 7 }

-- voipExtH248MediaStatTable  

        voipExtH248MediaStatTable OBJECT-TYPE
        SYNTAX SEQUENCE OF VoipExtH248MediaStatEntry
        MAX-ACCESS not-accessible
        STATUS current
        DESCRIPTION
        	""
        ::= { voipExtStats 2 }

        voipExtH248MediaStatEntry OBJECT-TYPE
        SYNTAX VoipExtH248MediaStatEntry
        MAX-ACCESS not-accessible
        STATUS current
        DESCRIPTION
        	"An entry of voipExtH248MediaStatTable."
        INDEX { voipExtH248MediaStatSlotId }
        ::= { voipExtH248MediaStatTable 1 }

        VoipExtH248MediaStatEntry ::=
        	SEQUENCE {
                	voipExtH248MediaStatSlotId  	INTEGER,
               		voipExtH248MediaStatPortCount    	INTEGER,
               		voipExtH248MediaStatState   	INTEGER
              	}
              	
		voipExtH248MediaStatSlotId  OBJECT-TYPE
			SYNTAX INTEGER
			MAX-ACCESS read-only
			STATUS current
			DESCRIPTION
				"Slot ID"
			::= { voipExtH248MediaStatEntry 1 }
			   	    
 		voipExtH248MediaStatPortCount    OBJECT-TYPE
			SYNTAX INTEGER
			MAX-ACCESS read-only
			STATUS current
			DESCRIPTION
				"port count"
			::= { voipExtH248MediaStatEntry 2 }   
			

		voipExtH248MediaStatState     OBJECT-TYPE
			SYNTAX INTEGER
			{
				unregistered(1),
				registered(2),
				invalid(3),
				unknown(4)
			}
			MAX-ACCESS read-only
			STATUS current
			DESCRIPTION
				"state"
			::= { voipExtH248MediaStatEntry 3 }   

-- voipExtH248TerminationStatTable  
        
voipExtH248TerminationStatTable OBJECT-TYPE
        SYNTAX SEQUENCE OF VoipExtH248TerminationStatEntry
        MAX-ACCESS not-accessible
        STATUS current
        DESCRIPTION
        	""
        ::= { voipExtStats 3 }
        
        voipExtH248TerminationStatEntry OBJECT-TYPE
        SYNTAX VoipExtH248TerminationStatEntry  
        MAX-ACCESS not-accessible
        STATUS current
        DESCRIPTION
        	"An entry of voipExtH248TerminationStatStateTable."
        INDEX { voipExtH248TerminationStatStateSlotId,voipExtH248TerminationStatStatePortNumber }
        ::= { voipExtH248TerminationStatTable 1 }

        VoipExtH248TerminationStatEntry ::=
        SEQUENCE {
          voipExtH248TerminationStatStateSlotId      INTEGER,
          voipExtH248TerminationStatStatePortNumber   INTEGER, 
          voipExtH248TerminationStatName 			DisplayString,
          voipExtH248TerminationStatPhoneState   		INTEGER,
        	voipExtH248TerminationStatCallServiceState    	INTEGER
        }

	voipExtH248TerminationStatStateSlotId OBJECT-TYPE
	SYNTAX INTEGER
	MAX-ACCESS read-only
	STATUS current
	DESCRIPTION
	    "Media Card Id of the termination."
	::= { voipExtH248TerminationStatEntry 1 }
	
	voipExtH248TerminationStatStatePortNumber OBJECT-TYPE
	SYNTAX INTEGER
	MAX-ACCESS read-only
	STATUS current
	DESCRIPTION
	    "Port number the termination."
	::= { voipExtH248TerminationStatEntry 2 }

              	
	voipExtH248TerminationStatName  OBJECT-TYPE
	SYNTAX DisplayString
	MAX-ACCESS read-only
	STATUS current
	DESCRIPTION
		"Termination Name."
	::= { voipExtH248TerminationStatEntry 3 }
						
	voipExtH248TerminationStatPhoneState  OBJECT-TYPE
	SYNTAX INTEGER{
			disabled(1),
			on-hook(2),
			off-hook(3),						
			ringing(4),					
			testing(5),
			power-cut-down(6),
			fault(7),						
			bad(8),					
			uninitialized(9),						
			unknown(10)
	}
	MAX-ACCESS read-only
	STATUS current
	DESCRIPTION
		"Phone State"
	::= { voipExtH248TerminationStatEntry 4 }
			   	                                 
	voipExtH248TerminationStatCallServiceState   OBJECT-TYPE
	SYNTAX INTEGER{
			disabled(1),
			out-of-service(2),
			idle(3),
			waiting-for-dialing(4),
			dialing-out(5),
			ringing(6),
			conversation-caller(7),
			conversation-callee(8),
			fax-modem-caller(9),
			fax-modem-callee(10),
			waiting-for-on-hook(13),
			dialing-timeout(14),
			alerting-off-hook(15),
			power-cut-down(16),
			unknown(17)
	}
	MAX-ACCESS read-only
	STATUS current
	DESCRIPTION
		"Call Service State"
	::= { voipExtH248TerminationStatEntry 5 }

-- voipExtH248TerminationStatQuery		
	voipExtH248TerminationStatQuery	OBJECT IDENTIFIER ::= { voipExtStats 4 }
			
        voipExtH248TerminationStatQueryTerminationName OBJECT-TYPE
        SYNTAX DisplayString (SIZE(1..31))
        MAX-ACCESS read-write
        STATUS current
        DESCRIPTION
				"Termination Name"
        ::= { voipExtH248TerminationStatQuery 1 }
        	
	     voipExtH248TerminationStatQuerySlotId OBJECT-TYPE
        SYNTAX INTEGER
        MAX-ACCESS read-only
        STATUS current
        DESCRIPTION
        "Slot Id"
        ::= { voipExtH248TerminationStatQuery 2 }
                        
      voipExtH248TerminationStatQueryPortNumber OBJECT-TYPE
        SYNTAX INTEGER
        MAX-ACCESS read-only
        STATUS current
        DESCRIPTION
        "Port Number"
        ::= { voipExtH248TerminationStatQuery 3 }
        
      voipExtH248TerminationStatQueryPhoneState OBJECT-TYPE
       	SYNTAX INTEGER{
					disabled(1),
					on-hook(2),
					off-hook(3),						
					ringing(4),					
					testing(5),
					power-cut-down(6),
					fault(7),						
					bad(8),					
					uninitialized(9),						
					unknown(10)
			  }
        MAX-ACCESS read-only
        STATUS current
        DESCRIPTION
        "Phone State"
        ::= { voipExtH248TerminationStatQuery 4 }
        
      voipExtH248TerminationStatQueryCallServiceState OBJECT-TYPE
        SYNTAX INTEGER{
					disabled(1),
					out-of-service(2),
					idle(3),						
					waiting-for-dialing(4),					
					ringing(5),
					conversation-caller(6),
					conversation-callee(7),						
					fax-modem-caller(8),
					fax-modem-callee(9),
					waiting-for-on-hook(12),
					dialing-timeout(13),					
					alerting-off-hook(14),
					power-cut-down(15)
			  }
		    MAX-ACCESS read-only
        STATUS current
        DESCRIPTION
        "CallService State"
        ::= { voipExtH248TerminationStatQuery 5 }
	
-- voipExtSipProfile      
  
        voipExtMaxNumOfSipProfiles OBJECT-TYPE
        SYNTAX INTEGER
        MAX-ACCESS read-only
        STATUS current
        DESCRIPTION
        	"The maximum number of SIP profiles supported by the system."
        ::= { voipExtSipProfile 1 }
        
        voipExtSipProfileTable OBJECT-TYPE
        SYNTAX SEQUENCE OF VoipExtSipProfileEntry
        MAX-ACCESS not-accessible
        STATUS current
        DESCRIPTION
                "This table includes SIP protocol related configuration.
                This table is supported by R4.01 and later versions."
        ::= { voipExtSipProfile 2 }

		voipExtSipProfileEntry OBJECT-TYPE
        SYNTAX VoipExtSipProfileEntry
        MAX-ACCESS not-accessible
        STATUS current
        DESCRIPTION
		"An entry in voipExtSipProfileTable."
        INDEX { IMPLIED voipExtSipProfileName }
        ::= { voipExtSipProfileTable 1 }

        VoipExtSipProfileEntry ::=
        	SEQUENCE {
				voipExtSipProfileName			DisplayString,
				voipExtSipProfileSipSvr			DisplayString,
				voipExtSipProfileRegSvr			DisplayString,
				voipExtSipProfileProxySvr		DisplayString,
				voipExtSipProfileSipPort		INTEGER,
				voipExtSipProfileRegSvrPort		INTEGER,
				voipExtSipProfileProxySvrPort	INTEGER,	
				voipExtSipProfilePbit			INTEGER,
				voipExtSipProfileDscp			INTEGER,
				voipExtSipProfileKeepAlive		INTEGER, 
				voipExtSipProfilePrack			INTEGER,
				voipExtSipProfileSe				INTEGER,
				voipExtSipProfileSwitchType		INTEGER,		
				voipExtSipProfileRtpStartPort	INTEGER,
				voipExtSipProfileRtpEndPort		INTEGER,
				voipExtSipProfileRegistrationExpire		INTEGER,
				voipExtSipProfileRegistrationExpireTime	INTEGER,
				voipExtSipProfileRegistrationRetryTime	INTEGER,
				voipExtSipProfileRowStatus		RowStatus,
				voipExtSipProfilePrefixAddDigits		DisplayString
           	}

        voipExtSipProfileName OBJECT-TYPE
        SYNTAX DisplayString (SIZE (1..31))
        MAX-ACCESS read-only
        STATUS current
        DESCRIPTION
                "This object is used by the SIP profile table in order to identify a row of this table."
        ::= { voipExtSipProfileEntry 1 }

        voipExtSipProfileSipSvr OBJECT-TYPE
        SYNTAX DisplayString
        MAX-ACCESS read-create
        STATUS current
        DESCRIPTION
                "IP used for SIP registration or SIP domain name."
        ::= { voipExtSipProfileEntry 2 }

		voipExtSipProfileRegSvr OBJECT-TYPE
        SYNTAX DisplayString
        MAX-ACCESS read-create
        STATUS current
        DESCRIPTION
                "Registration server IP or registration server domain name."
        ::= { voipExtSipProfileEntry 3 }
        
        voipExtSipProfileProxySvr OBJECT-TYPE
        SYNTAX DisplayString
        MAX-ACCESS read-create
        STATUS current
        DESCRIPTION
                "Proxy server IP or proxy server doamin name."
        ::= { voipExtSipProfileEntry 4 }
        
        voipExtSipProfileSipPort OBJECT-TYPE
        SYNTAX INTEGER (1025..65535)
        MAX-ACCESS read-create
        STATUS current
        DESCRIPTION
                "SIP UA port number."
        ::= { voipExtSipProfileEntry 5 }
        
        voipExtSipProfileRegSvrPort OBJECT-TYPE
        SYNTAX INTEGER (1025..65535)
        MAX-ACCESS read-create
        STATUS current
        DESCRIPTION
                "Registration server port number."
        ::= { voipExtSipProfileEntry 6 }
        
        voipExtSipProfileProxySvrPort OBJECT-TYPE
        SYNTAX INTEGER (1025..65535)
        MAX-ACCESS read-create
        STATUS current
        DESCRIPTION
                "Proxy server port number."
        ::= { voipExtSipProfileEntry 7 }
        
        voipExtSipProfilePbit OBJECT-TYPE
        SYNTAX INTEGER (0..7)
        MAX-ACCESS read-create
        STATUS current
        DESCRIPTION
                "802.1p bit for SIP and RTP packet."
        ::= { voipExtSipProfileEntry 8 }
        
        voipExtSipProfileDscp OBJECT-TYPE
        SYNTAX INTEGER (0..63)
        MAX-ACCESS read-create
        STATUS current
        DESCRIPTION
                "DSCP for SIP and RTP packet."
        ::= { voipExtSipProfileEntry 9 }
        
        voipExtSipProfileKeepAlive OBJECT-TYPE
        SYNTAX INTEGER {
        		on(1),
        		off(2)
        	}
        MAX-ACCESS read-create
        STATUS current
        DESCRIPTION
                ""
        ::= { voipExtSipProfileEntry 10 }
        
        voipExtSipProfilePrack OBJECT-TYPE
        SYNTAX INTEGER {
        		on(1),
        		off(2)
        	}
        MAX-ACCESS read-create
        STATUS current
        DESCRIPTION
                ""
        ::= { voipExtSipProfileEntry 11 }

        
        voipExtSipProfileSe OBJECT-TYPE
        SYNTAX INTEGER (90..65535)
        UNITS "second"
        MAX-ACCESS read-create
        STATUS current
        DESCRIPTION
                "Session expiration time in seconds."
        ::= { voipExtSipProfileEntry 12 }    
        
        voipExtSipProfileSwitchType OBJECT-TYPE
        SYNTAX INTEGER {
        	default(0),
        	nsn(1),
        	alu(2)
        }
        MAX-ACCESS read-create
        STATUS current
        DESCRIPTION
                "Switch type"
        ::= { voipExtSipProfileEntry 13 }
        
        voipExtSipProfileRtpStartPort OBJECT-TYPE
        SYNTAX INTEGER
        MAX-ACCESS read-create
        STATUS current
        DESCRIPTION
                "start of RTP port number. This MIB object is supported by R5.05 and later versions."
        ::= { voipExtSipProfileEntry 14 }   
        
        voipExtSipProfileRtpEndPort OBJECT-TYPE
        SYNTAX INTEGER
        MAX-ACCESS read-create
        STATUS current
        DESCRIPTION
                "end of RTP port number. This MIB object is supported by R5.05 and later versions."
        ::= { voipExtSipProfileEntry 15 }
        
		voipExtSipProfileRegistrationExpire OBJECT-TYPE
        SYNTAX INTEGER {
        		on(1),
        		off(2)
        	}
        MAX-ACCESS read-create
        STATUS current
        DESCRIPTION
                ""
        ::= { voipExtSipProfileEntry 16 }
		
		voipExtSipProfileRegistrationExpireTime OBJECT-TYPE
        SYNTAX INTEGER
        MAX-ACCESS read-create
        STATUS current
        DESCRIPTION
                "registration expiration time under registered state, 120~65535 seconds"
        ::= { voipExtSipProfileEntry 17 }
		
		voipExtSipProfileRegistrationRetryTime OBJECT-TYPE
        SYNTAX INTEGER
        MAX-ACCESS read-create
        STATUS current
        DESCRIPTION
                "registration retry time under un-registered state, 120~900 seconds"
        ::= { voipExtSipProfileEntry 18 }
		
        voipExtSipProfileRowStatus OBJECT-TYPE
        SYNTAX RowStatus
        MAX-ACCESS read-create
        STATUS current
        DESCRIPTION
                "This object is used to create a new row or delete an existing row in the table."
        ::= { voipExtSipProfileEntry 19 }

        voipExtSipProfilePrefixAddDigits OBJECT-TYPE
        SYNTAX DisplayString (SIZE (1..31))
        MAX-ACCESS read-only
        STATUS current
        DESCRIPTION
                "The prefix digits add before tel number"
        ::= { voipExtSipProfileEntry 20 }
-- sip call service profile

	voipExtMaxNumOfSipCallSvcProfiles OBJECT-TYPE
        SYNTAX INTEGER
        MAX-ACCESS read-only
        STATUS current
        DESCRIPTION
        	"The maximum number of SIP call service profiles supported by the system."
        ::= { voipExtSipProfile 3 }
        
	voipExtSipCallSvcProfileTable OBJECT-TYPE
        SYNTAX SEQUENCE OF VoipExtSipCallSvcProfileEntry
        MAX-ACCESS not-accessible
        STATUS current
        DESCRIPTION
                "This table includes SIP call service related configuration.
                This table is supported by R4.01 and later versions."
        ::= { voipExtSipProfile 4 }

	voipExtSipCallSvcProfileEntry OBJECT-TYPE
        SYNTAX VoipExtSipCallSvcProfileEntry
        MAX-ACCESS not-accessible
        STATUS current
        DESCRIPTION
		"An entry in sipCallSvcProfileTable."
        INDEX { IMPLIED voipExtSipCallSvcProfileName }
        ::= { voipExtSipCallSvcProfileTable 1 }

        VoipExtSipCallSvcProfileEntry ::=
        	SEQUENCE {
        	voipExtSipCallSvcProfileName				DisplayString,
        	voipExtSipCallSvcProfileKeypattern			DisplayString,  
        	voipExtSipCallSvcProfileDialPlanOn			INTEGER,
			voipExtSipCallSvcProfileDialPlanCc			DisplayString,
			voipExtSipCallSvcProfileDialPlanNdc			DisplayString,
			voipExtSipCallSvcProfileDialPlanTable		DisplayString,
			voipExtSipCallSvcProfileDndOn				INTEGER, 
			voipExtSipCallSvcProfileDtmf				INTEGER, 
			voipExtSipCallSvcProfileDtmfRfc2833Payload	INTEGER,
			--voipExtSipCallSvcProfileCallHoldOn			INTEGER, 
			voipExtSipCallSvcProfileCallWaitOn			INTEGER, 
			voipExtSipCallSvcProfileClipOn				INTEGER, 
			voipExtSipCallSvcProfileClirOn				INTEGER,
			voipExtSipCallSvcProfileCallTransferOn		INTEGER,
			voipExtSipCallSvcProfileCallConferenceOn	INTEGER,			
			voipExtSipCallSvcProfileFax					INTEGER,
			voipExtSipCallSvcProfileFirstDigit			INTEGER,
			voipExtSipCallSvcProfileInterdigit			INTEGER,  
			voipExtSipCallSvcProfileMatchdigit			INTEGER,
			voipExtSipCallSvcProfileFlash				INTEGER,
			voipExtSipCallSvcProfileFlashPattern		DisplayString,
			voipExtSipCallSvcProfileLocalCallOn			INTEGER,
			voipExtSipCallSvcProfileMWIOn				INTEGER,
			voipExtSipCallSvcProfileCentrexOn			INTEGER,
			voipExtSipCallSvcProfileRowStatus			RowStatus			
        	}

        voipExtSipCallSvcProfileName OBJECT-TYPE
        SYNTAX DisplayString (SIZE (1..31))
        MAX-ACCESS read-only
        STATUS current
        DESCRIPTION
                "This object is used by the SIP call service profile table in order to identify a row of this table."
        ::= { voipExtSipCallSvcProfileEntry 1 }

		voipExtSipCallSvcProfileKeypattern OBJECT-TYPE
        SYNTAX DisplayString (SIZE(1..31))
        MAX-ACCESS read-create
        STATUS current
        DESCRIPTION
                "Key pattern table name. This object is supported by R5.01 and later versions."
        ::= { voipExtSipCallSvcProfileEntry 2 }
		        		
        voipExtSipCallSvcProfileDialPlanOn OBJECT-TYPE
        SYNTAX INTEGER {
        		on(1),
        		off(2)
        	}
        MAX-ACCESS read-create
        STATUS current
        DESCRIPTION
                "Please set CC, NDC, and dialplan table first."
        ::= { voipExtSipCallSvcProfileEntry 3 }
        
        voipExtSipCallSvcProfileDialPlanCc OBJECT-TYPE
        SYNTAX DisplayString (SIZE(1..7))
        MAX-ACCESS read-create
        STATUS current
        DESCRIPTION
                "Country code, only digit 0..9 are allowed."
        ::= { voipExtSipCallSvcProfileEntry 4 }
        
        voipExtSipCallSvcProfileDialPlanNdc OBJECT-TYPE
        SYNTAX DisplayString (SIZE(1..7))
        MAX-ACCESS read-create
        STATUS current
        DESCRIPTION
                "National destination code, only digit 0..9 are allowed."
        ::= { voipExtSipCallSvcProfileEntry 5 }
        
        voipExtSipCallSvcProfileDialPlanTable OBJECT-TYPE
        SYNTAX DisplayString (SIZE(1..31))
        MAX-ACCESS read-create
        STATUS current
        DESCRIPTION
                "Numbering plan table name."
        ::= { voipExtSipCallSvcProfileEntry 6 }
        
        voipExtSipCallSvcProfileDndOn OBJECT-TYPE
        SYNTAX INTEGER {
        		on(1),
        		off(2)
        	}
        MAX-ACCESS read-create
        STATUS current
        DESCRIPTION
                "Do not Distrurb."
        ::= { voipExtSipCallSvcProfileEntry 7 }
        
        voipExtSipCallSvcProfileDtmf OBJECT-TYPE
        SYNTAX INTEGER {
        		bypass(1),
        		rfc2833(2),
        		rfc2833like(3),
        		sipinfo(4),
        		plaintext(5)
        	}
        MAX-ACCESS read-create
        STATUS current
        DESCRIPTION
                "dtmf bypass : bypass DTMF tone
		 dtmf rfc2833 : DTMF tone relay according to RFC2833
		 dtmf rfc2833like : DTMF tone relay by SIP INFO message, but RFC2833 payload
		 dtmf sipinfo : DTMF tone relay by SIP INFO signal message
		 dtmf plaintext : DTMF tone relay by SIP INFO plain text message"
        ::= { voipExtSipCallSvcProfileEntry 8 }
		
		voipExtSipCallSvcProfileDtmfRfc2833Payload OBJECT-TYPE
        SYNTAX INTEGER
        MAX-ACCESS read-create
        STATUS current
        DESCRIPTION
        "dtmf rfc2833 payload type, 96~100"
        ::= { voipExtSipCallSvcProfileEntry 9 }
		
		--voipExtSipCallSvcProfileCallHoldOn OBJECT-TYPE
        --SYNTAX INTEGER {
        --		on(1),
        --		off(2)
        --	}
        --MAX-ACCESS read-create
        --STATUS current
        --DESCRIPTION
        --        ""
        --::= { voipExtSipCallSvcProfileEntry 10 }
		
		voipExtSipCallSvcProfileCallWaitOn OBJECT-TYPE
        SYNTAX INTEGER {
        		on(1),
        		off(2)
        	}
        MAX-ACCESS read-create
        STATUS current
        DESCRIPTION
                ""
        ::= { voipExtSipCallSvcProfileEntry 11 }
		
		voipExtSipCallSvcProfileClipOn OBJECT-TYPE
        SYNTAX INTEGER {
        		on(1),
        		off(2)
        	}
        MAX-ACCESS read-create
        STATUS current
        DESCRIPTION
                ""
        ::= { voipExtSipCallSvcProfileEntry 12 }
		
		voipExtSipCallSvcProfileClirOn OBJECT-TYPE
        SYNTAX INTEGER {
        		on(1),
        		off(2)
        	}
        MAX-ACCESS read-create
        STATUS current
        DESCRIPTION
                ""
        ::= { voipExtSipCallSvcProfileEntry 13 }
		
		voipExtSipCallSvcProfileCallTransferOn OBJECT-TYPE
        SYNTAX INTEGER {
        		on(1),
        		off(2)
        	}
        MAX-ACCESS read-create
        STATUS current
        DESCRIPTION
                ""
        ::= { voipExtSipCallSvcProfileEntry 14 }
        
		voipExtSipCallSvcProfileCallConferenceOn OBJECT-TYPE
        SYNTAX INTEGER {
        		on(1),
        		off(2)
        	}
        MAX-ACCESS read-create
        STATUS current
        DESCRIPTION
                ""
        ::= { voipExtSipCallSvcProfileEntry 15 }
        
        voipExtSipCallSvcProfileFax OBJECT-TYPE
        SYNTAX INTEGER {
        		g711(1),
        		t38(2)
        	}
        MAX-ACCESS read-create
        STATUS current
        DESCRIPTION
                "fax g711 : FAX service pass through by ITU-T G.711
		 fax t38 : FAX service by ITU-T T.38 UDP"
        ::= { voipExtSipCallSvcProfileEntry 16 }
        
		voipExtSipCallSvcProfileFirstDigit OBJECT-TYPE
        SYNTAX INTEGER
        MAX-ACCESS read-create
        STATUS current
        DESCRIPTION
                "first digit timeout. This MIB object is supported by R5.05 and later versions."
        ::= { voipExtSipCallSvcProfileEntry 17 }
        
        voipExtSipCallSvcProfileInterdigit OBJECT-TYPE
        SYNTAX INTEGER
        MAX-ACCESS read-create
        STATUS current
        DESCRIPTION
                "inter digit timeout. This MIB object is supported by R5.05 and later versions."
        ::= { voipExtSipCallSvcProfileEntry 18 }
        
        voipExtSipCallSvcProfileMatchdigit OBJECT-TYPE
        SYNTAX INTEGER
        MAX-ACCESS read-create
        STATUS current
        DESCRIPTION
                "match digit timeout. This MIB object is supported by R5.05 and later versions."
        ::= { voipExtSipCallSvcProfileEntry 19 }

		
		voipExtSipCallSvcProfileFlash OBJECT-TYPE
        SYNTAX INTEGER {
        		invite(1),
        		rfc2833(2),
        		rfc2833like(3),
        		sipinfo1(4),
        		sipinfo2(5),
        		sipinfo3(6),
        		sipinfo4(7),
        		sipinfo5(8),
        		sipinfo6(9),
				skip(10)
        	}
        MAX-ACCESS read-create
        STATUS current
        DESCRIPTION
                "flash invite : send SIP INVITE message
		 flash rfc2833 : flash relay according to RFC2833
		 flash rfc2833like : flash relay by SIP INFO message, but RFC2833 payload
		 flash sipinfo1 : flash relay by SIP INFO signal=16 message
		 flash sipinfo2 : flash relay by SIP INFO signal=hf message
		 flash sipinfo3 : flash relay by SIP INFO signal=hook-flash message
		 flash sipinfo4 : flash relay by SIP INFO plain text message
		 flash sipinfo5 : flash relay by multiple SIP INFO signal messages and
		                   signal content come from specified pattern string
		 flash sipinfo6 : flash relay by SIP INFO specified information message
		 skip : no flash event, only onhook and offhook"
        ::= { voipExtSipCallSvcProfileEntry 20 }
		
		voipExtSipCallSvcProfileFlashPattern OBJECT-TYPE
        SYNTAX DisplayString
        MAX-ACCESS read-create
        STATUS current
        DESCRIPTION
                ""
        ::= { voipExtSipCallSvcProfileEntry 21 }
		
		voipExtSipCallSvcProfileLocalCallOn OBJECT-TYPE
        SYNTAX INTEGER {
        		on(1),
        		off(2)
        	}
        MAX-ACCESS read-create
        STATUS current
        DESCRIPTION
                ""
        ::= { voipExtSipCallSvcProfileEntry 22 }
		
		voipExtSipCallSvcProfileMWIOn OBJECT-TYPE
        SYNTAX INTEGER {
        		on(1),
        		off(2)
        	}
        MAX-ACCESS read-create
        STATUS current
        DESCRIPTION
                ""
        ::= { voipExtSipCallSvcProfileEntry 23 }
		
		voipExtSipCallSvcProfileCentrexOn OBJECT-TYPE
        SYNTAX INTEGER {
        		on(1),
        		off(2)
        	}
        MAX-ACCESS read-create
        STATUS current
        DESCRIPTION
                ""
        ::= { voipExtSipCallSvcProfileEntry 24 }
		
        voipExtSipCallSvcProfileRowStatus OBJECT-TYPE
        SYNTAX RowStatus
        MAX-ACCESS read-create
        STATUS current
        DESCRIPTION
                "This object is used to create a new row or delete an existing row in the table."
        ::= { voipExtSipCallSvcProfileEntry 25 } 
        
-- sip call service profile local help table   

		voipExtSipCallSvcProfileLocalHelpTable OBJECT-TYPE
        SYNTAX SEQUENCE OF VoipExtSipCallSvcProfileLocalHelpEntry
        MAX-ACCESS not-accessible
        STATUS current
        DESCRIPTION
                "This table is supported by R5.01 and later versions."
        ::= { voipExtSipProfile 5 }

		voipExtSipCallSvcProfileLocalHelpEntry OBJECT-TYPE
        SYNTAX VoipExtSipCallSvcProfileLocalHelpEntry
        MAX-ACCESS not-accessible
        STATUS current
        DESCRIPTION
		"An entry in sipCallSvcProfileLocalHelpTable."
        INDEX { voipExtSipCallSvcProfileName, voipExtSipCallSvcProfileLocalHelpIndex  }
        ::= { voipExtSipCallSvcProfileLocalHelpTable 1 }

        VoipExtSipCallSvcProfileLocalHelpEntry ::=
        	SEQUENCE {
			voipExtSipCallSvcProfileLocalHelpIndex  	INTEGER,
			voipExtSipCallSvcProfileLocalHelpTableName	DisplayString,
			voipExtSipCallSvcProfileLocalHelpTableTel	DisplayString
           	}

        voipExtSipCallSvcProfileLocalHelpIndex OBJECT-TYPE
        SYNTAX INTEGER (1..8)
        MAX-ACCESS read-only
        STATUS current
        DESCRIPTION
                "Index number."
        ::= { voipExtSipCallSvcProfileLocalHelpEntry 1 }
        
        voipExtSipCallSvcProfileLocalHelpTableName OBJECT-TYPE
        SYNTAX DisplayString (SIZE(1..31))
        MAX-ACCESS read-write
        STATUS current
        DESCRIPTION
                "Local help table name."
        ::= { voipExtSipCallSvcProfileLocalHelpEntry 2 }
        
        voipExtSipCallSvcProfileLocalHelpTableTel OBJECT-TYPE
        SYNTAX DisplayString (SIZE(1..15))
        MAX-ACCESS read-write
        STATUS current
        DESCRIPTION
                "Local help telephone number. Only digit characters are allowed.
                Note that sipCallSvcProfileLocalHelpTableName and sipCallSvcProfileLocalHelpTableTel
                must be set sequentially."
        ::= { voipExtSipCallSvcProfileLocalHelpEntry 3 }

-- voipExtSipDialPlanTable

		voipExtMaxNumOfVoipDialPlan OBJECT-TYPE
        SYNTAX INTEGER
        MAX-ACCESS read-only
        STATUS current
        DESCRIPTION
        	"The maximum number of VoIP dial plan supported by the system."
        ::= { voipSingleIp 4 }
        
        voipExtDialPlanTable OBJECT-TYPE
        SYNTAX SEQUENCE OF VoipExtDialPlanEntry
        MAX-ACCESS not-accessible
        STATUS current
        DESCRIPTION
        	"Configure dialing plan entry of specified index in specified payphone charging table."
        ::= { voipSingleIp 5 }
	
        voipExtDialPlanEntry OBJECT-TYPE
        SYNTAX VoipExtDialPlanEntry
        MAX-ACCESS not-accessible
        STATUS current
        DESCRIPTION
        	"An entry of voipExtDialPlanTable."
        INDEX { voipExtDialPlanName, voipExtDialPlanIndex }
        ::= { voipExtDialPlanTable 1 }

        VoipExtDialPlanEntry ::=
        	SEQUENCE {
        		voipExtDialPlanName			DisplayString,
        		voipExtDialPlanIndex		INTEGER,
        		voipExtDialPlanPattern		DisplayString,
        		voipExtDialPlanRule			DisplayString,
        		voipExtDialPlanRowStatus	RowStatus
              	}

		voipExtDialPlanName OBJECT-TYPE
        SYNTAX DisplayString (SIZE (1..31))
        MAX-ACCESS read-only
        STATUS current
        DESCRIPTION
        	"Dialing plan table name."
        ::= { voipExtDialPlanEntry 1 }
        
        voipExtDialPlanIndex OBJECT-TYPE
        SYNTAX INTEGER (1..16)
        MAX-ACCESS read-only
        STATUS current
        DESCRIPTION
        	""
        ::= { voipExtDialPlanEntry 2 }
        
        voipExtDialPlanPattern OBJECT-TYPE
        SYNTAX DisplayString (SIZE(1..47))
        MAX-ACCESS read-create
        STATUS current
        DESCRIPTION
       	    "up to 47 characters, allow digit, '*', and '#' characters and 
        	meaning characters that include 'x', '.', '|' and range format 
        	characters that include '~', ',' and parenthesis '(', ')' 
        	and brackets '[', ']' and at most one parenthesis pair,
        	examples: '002(x.)', '0(x.)', and '(x.)'" 

        ::= { voipExtDialPlanEntry 3 }
        
        voipExtDialPlanRule OBJECT-TYPE
        SYNTAX DisplayString (SIZE(1..15))
        MAX-ACCESS read-create
        STATUS current
        DESCRIPTION
        	"Allowed characters are 0~9, and '\c' stand for country code, 
        	'\d' stand for national destination code, 
        	'\1' stand for matched string enclosed by the parenthesis pair,
        	and 'deny' stand for the pattern specified is not allowed.
        	Examples: '\1', '\c\1', and '\c\d\1'."
        ::= { voipExtDialPlanEntry 4 }
        
        voipExtDialPlanRowStatus OBJECT-TYPE
        SYNTAX RowStatus
        MAX-ACCESS read-create
        STATUS current
        DESCRIPTION
        	"This object is used to create a new entry or delete an existing entry in this table."
        ::= { voipExtDialPlanEntry 5 }	

-- voipExtSipIp

    voipExtSipIp OBJECT IDENTIFIER ::= { voipExtSip 1 }
      
		voipExtSipSignalIp OBJECT-TYPE
        SYNTAX IpAddress
        MAX-ACCESS read-write
        STATUS current
        DESCRIPTION
					"Signaling Ip"
        ::= { voipExtSipIp 1 }
          
		voipExtSipSignalMask OBJECT-TYPE
        SYNTAX INTEGER
        MAX-ACCESS read-write
        STATUS current
        DESCRIPTION
					"Signaling network mask, 0~32"
        ::= { voipExtSipIp 2 }		
        
        voipExtSipSignalVid OBJECT-TYPE
        SYNTAX VlanIndex
        MAX-ACCESS read-write
        STATUS current
        DESCRIPTION
     			"1~4094"
        ::= { voipExtSipIp 3 }
                
        voipExtSipMediaIp OBJECT-TYPE
        SYNTAX IpAddress
        MAX-ACCESS read-write
        STATUS current
        DESCRIPTION
					"RTP IP"
        ::= { voipExtSipIp 4 }
          
		voipExtSipMediaMask OBJECT-TYPE
        SYNTAX INTEGER
        MAX-ACCESS read-write
        STATUS current
        DESCRIPTION
					"RTP network mask, 0~32"
        ::= { voipExtSipIp 5 }		
        
		voipExtSipMediaVid OBJECT-TYPE
        SYNTAX VlanIndex
        MAX-ACCESS read-write
        STATUS current
        DESCRIPTION
     			"1~4094"
        ::= { voipExtSipIp 6 }

		voipExtSipDnsIp OBJECT-TYPE
        SYNTAX IpAddress
        MAX-ACCESS read-write
        STATUS current
        DESCRIPTION
					"Primary DNS IP. Set to '0.0.0.0' will clear both voipExtSipDnsIp and voipExtSipDnsIp2"
        ::= { voipExtSipIp 7 }
		
		voipExtSipDnsIp2 OBJECT-TYPE
        SYNTAX IpAddress
        MAX-ACCESS read-write
        STATUS current
        DESCRIPTION
					"Secondary DNS IP. could not be set when voipExtSipDnsIp is '0.0.0.0',
					set voipExtSipDnsIp or voipExtSipDnsIp2 with '0.0.0.0' to clear."
        ::= { voipExtSipIp 8 }

		voipExtSipMaxNumOfVoipRoute OBJECT-TYPE
        SYNTAX INTEGER
        MAX-ACCESS read-only
        STATUS current
        DESCRIPTION
        	""
        ::= { voipExtSip 2 }

-- voipExtSipRouteTable

		voipExtSipRouteTable OBJECT-TYPE
        SYNTAX SEQUENCE OF VoipExtSipRouteEntry
        MAX-ACCESS not-accessible
        STATUS current
        DESCRIPTION
        	""
        ::= { voipExtSip 3 }
	
		voipExtSipRouteEntry OBJECT-TYPE
        SYNTAX VoipExtSipRouteEntry
        MAX-ACCESS not-accessible
        STATUS current
        DESCRIPTION
        	"An entry of voipExtSipRouteTable."
        INDEX { voipExtSipRouteIp, voipExtSipRouteGateway, voipExtSipRouteMask }
        ::= { voipExtSipRouteTable 1 }

		VoipExtSipRouteEntry ::=
        	SEQUENCE {
        		voipExtSipRouteIp			IpAddress,
        		voipExtSipRouteGateway		IpAddress,
        		voipExtSipRouteMask			INTEGER,
        		voipExtSipRouteMetric		INTEGER,
        		voipExtSipRouteRowStatus	RowStatus
          }

		voipExtSipRouteIp OBJECT-TYPE
        SYNTAX IpAddress
        MAX-ACCESS read-only
        STATUS current
        DESCRIPTION
        	"IP address."
        ::= { voipExtSipRouteEntry 1 }
        
		voipExtSipRouteGateway OBJECT-TYPE
        SYNTAX IpAddress
        MAX-ACCESS read-only
        STATUS current
        DESCRIPTION
        	"Gateway IP."
        ::= { voipExtSipRouteEntry 2 }
        
		voipExtSipRouteMask OBJECT-TYPE
        SYNTAX INTEGER (0..32)
        MAX-ACCESS read-only
        STATUS current
        DESCRIPTION
        	"Network mask."
        ::= { voipExtSipRouteEntry 3 }
        
		voipExtSipRouteMetric OBJECT-TYPE
        SYNTAX INTEGER (1..15)
        MAX-ACCESS read-create
        STATUS current
        DESCRIPTION
        	"Metric number of the route."
        ::= { voipExtSipRouteEntry 4 }
        
		voipExtSipRouteRowStatus OBJECT-TYPE
        SYNTAX RowStatus
        MAX-ACCESS read-create
        STATUS current
        DESCRIPTION
        	"This object is used to create a new entry or delete an existing entry in this table."
        ::= { voipExtSipRouteEntry 5 }
                     		
		voipExtSipRegcount OBJECT-TYPE
		SYNTAX INTEGER (0..255)
        MAX-ACCESS read-write
        STATUS current
        DESCRIPTION
        	"register times per second, 1~255. 0 means off."
        ::= { voipExtSip 4 }
		
		voipExtSipCptReorder OBJECT-TYPE
		SYNTAX INTEGER (5..300)
        MAX-ACCESS read-write
        STATUS current
        DESCRIPTION
        	"Timeout of re-order tone, 5~300"
        ::= { voipExtSip 5 }
		
		voipExtSipCptHowler OBJECT-TYPE
		SYNTAX INTEGER (5..300)
        MAX-ACCESS read-write
        STATUS current
        DESCRIPTION
        	"Timeout of re-order tone, 5~300"
        ::= { voipExtSip 6 }
		
		voipExtSipCptAlerting OBJECT-TYPE
		SYNTAX INTEGER (60..1200)
        MAX-ACCESS read-write
        STATUS current
        DESCRIPTION
        	"Timeout of re-order tone, 60~1200"
        ::= { voipExtSip 7 } 
        
		voipExtSipPktLog OBJECT-TYPE
		SYNTAX INTEGER {
        		on(1),
        		off(2)
          	}
        MAX-ACCESS read-write
        STATUS current
        DESCRIPTION
        	"SIP packet log on/off"
        ::= { voipExtSip 8 }
        
		voipExtSipPktLogClear OBJECT-TYPE
		SYNTAX INTEGER 
		MAX-ACCESS read-write
        STATUS current
        DESCRIPTION
        	"Set 1 to clear SIP packet log"
        ::= { voipExtSip 9 }

        
--	voipExtSipLineConfTable   

        voipExtSipLineConfTable OBJECT-TYPE
        SYNTAX SEQUENCE OF VoipExtSipLineConfEntry
        MAX-ACCESS not-accessible
        STATUS current
        DESCRIPTION
		"This table includes common attributes describing the VoIP line."
        ::= { voipSingleIp 7 }

		voipExtSipLineConfEntry OBJECT-TYPE
        SYNTAX VoipExtSipLineConfEntry
        MAX-ACCESS not-accessible
        STATUS current
        DESCRIPTION
        	"An entry in voipExtSipLineConfTable."
        INDEX { voipIfIndex }
        ::= { voipExtSipLineConfTable 1 }

        VoipExtSipLineConfEntry ::=
           SEQUENCE {
				voipExtSipLineConfHotlineOn				INTEGER,
				voipExtSipLineConfHotlineNo				DisplayString,
				voipExtSipLineConfHotlineTimeout		INTEGER,
				voipExtSipLineConfTax					INTEGER
			}

        voipExtSipLineConfHotlineOn OBJECT-TYPE
        SYNTAX INTEGER {
        		on(1),
        		off(2)
        	}
        MAX-ACCESS read-write
        STATUS current
        DESCRIPTION
		""
        ::= { voipExtSipLineConfEntry 1 }
        
        voipExtSipLineConfHotlineNo OBJECT-TYPE
        SYNTAX DisplayString (SIZE(1..31))
        MAX-ACCESS read-write
        STATUS current
        DESCRIPTION
		"only alphanumeric characters and '+' are allowed,
         or use two quotation marks () to clear the field.
         Note: '+' only is allowed at the first character"
        ::= { voipExtSipLineConfEntry 2 }
        
        voipExtSipLineConfHotlineTimeout OBJECT-TYPE
        SYNTAX INTEGER
        MAX-ACCESS read-write
        STATUS current
        DESCRIPTION
		"0~255 seconds, 0 means dialling immediately."
        ::= { voipExtSipLineConfEntry 3 }

		voipExtSipLineConfTax OBJECT-TYPE
        SYNTAX INTEGER{
					mode-disable(0),
					mode-12K(1),
					mode-16K(2),
					mode-reversal-12K(3),
					mode-reversal-16K(4),
					mode-reversal-steady(5),
					mode-reversal-pulse(6)
		}
        MAX-ACCESS read-write
        STATUS current
        DESCRIPTION
		"metering mode"
        ::= { voipExtSipLineConfEntry 4 }
		
-- voipExtSipLineStatTable

		voipExtSipLineStatusTable OBJECT-TYPE
        SYNTAX SEQUENCE OF VoipExtSipLineStatusEntry
        MAX-ACCESS not-accessible
        STATUS current
        DESCRIPTION
		"The table displays VoIP line status. This table is supported by R4.01 and later versions."
		::= { voipSingleIp 8 }
                                                                           
		voipExtSipLineStatusEntry OBJECT-TYPE
        SYNTAX VoipExtSipLineStatusEntry
        MAX-ACCESS not-accessible
        STATUS current
        DESCRIPTION
        	"An entry of voipExtSipLineStatTable."
        INDEX { voipIfIndex }
        ::= { voipExtSipLineStatusTable 1 }

        VoipExtSipLineStatusEntry ::=
           SEQUENCE {
				voipExtSipLineStatusFxsStatus			INTEGER,
				voipExtSipLineStatusServiceStatus		INTEGER,
				voipExtSipLineStatusLocalcallStatus		INTEGER
			}
              	              	
	voipExtSipLineStatusFxsStatus OBJECT-TYPE
	SYNTAX INTEGER {
			disabled(1),
			on-hook(2),
			off-hook(3),
			ringing(4),
			power-cut-down(5),
			testing(6),
			fault(7),
			bad(8),
			uninitialized(9)
		}
	MAX-ACCESS read-only
	STATUS current
	DESCRIPTION
		"FXS status of the line."
	::= { voipExtSipLineStatusEntry 1 }
	 
	voipExtSipLineStatusServiceStatus OBJECT-TYPE
	SYNTAX INTEGER {
			disabled(1),
			out-of-service(2),
			idle(3),
			waiting-for-dialing(4),
			dialing-out(5),
			ringing(6),
			conversation-caller(7),
			conversation-callee(8),
			fax-modem-caller(9),
			fax-modem-callee(10),
			fax-modem-caller(11),
			fax-modem-callee(12),
			waiting-for-on-hook(13),
			dialing-timeout(14),
			alerting-off-hook(15),
			power-cut-down(16)
		}
	MAX-ACCESS read-only
	STATUS current
	DESCRIPTION
		"Service status of the line."
	::= { voipExtSipLineStatusEntry 2 }
	
	voipExtSipLineStatusLocalcallStatus OBJECT-TYPE
	SYNTAX INTEGER {
			on(1),
			off(2)
		}
	MAX-ACCESS read-only
	STATUS current
	DESCRIPTION
		"Localcall status of the line."
	::= { voipExtSipLineStatusEntry 3 }

               
----------------------------------------
-- ima
----------------------------------------
  
--  	imaGroupTable				OBJECT IDENTIFIER ::= { ima 1 }
	imaGroupChan				OBJECT IDENTIFIER ::= { ima 2 } 
	
-- imaGroupTable
    imaGroupTable OBJECT-TYPE
        SYNTAX SEQUENCE OF ImaGroupEntry
        MAX-ACCESS not-accessible
        STATUS current
        DESCRIPTION
        	"This table is supported by R5.03 and later versions."
        ::= { ima 1 }    
        
    imaGroupEntry OBJECT-TYPE
        SYNTAX ImaGroupEntry
        MAX-ACCESS not-accessible
        STATUS current
        DESCRIPTION
		"An entry of imaGroupTable."
        INDEX { imaGroupIndex }
        ::= { imaGroupTable 1 }

        ImaGroupEntry ::=
        	SEQUENCE {
			imaGroupIndex		INTEGER,
			imaGroupClkMode		INTEGER,
			imaGroupVersion		INTEGER
           	}
         
    imaGroupIndex OBJECT-TYPE
        SYNTAX INTEGER
        MAX-ACCESS read-only
        STATUS current
        DESCRIPTION
                ""
         ::= { imaGroupEntry 1 } 
         
    imaGroupClkMode OBJECT-TYPE
        SYNTAX INTEGER {
        		ctc-loop(1),
        		ctc-local(2),
        		itc(3)
        	}
        MAX-ACCESS read-create
        STATUS current
        DESCRIPTION
                ""
         ::= { imaGroupEntry 2 }  
         
    imaGroupVersion OBJECT-TYPE
        SYNTAX INTEGER {
        		version-1-0(1),
        		version-1-1(2)
        	}
        MAX-ACCESS read-create
        STATUS current
        DESCRIPTION
                ""
         ::= { imaGroupEntry 3 } 

-- ImaGroupChan     
	-- ImaGroupChanNumTable
	imaGroupChanNumTable OBJECT-TYPE
        SYNTAX SEQUENCE OF ImaGroupChanNumEntry
        MAX-ACCESS not-accessible
        STATUS current
        DESCRIPTION
        	"This table is supported by R5.03 and later versions."
        ::= { imaGroupChan 1 }    
        
    imaGroupChanNumEntry OBJECT-TYPE
        SYNTAX ImaGroupChanNumEntry
        MAX-ACCESS not-accessible
        STATUS current
        DESCRIPTION
		"An entry of ImaGroupChanNumTable."
        INDEX { imaGroupChanNumSlot }
        ::= { imaGroupChanNumTable 1 }

        ImaGroupChanNumEntry ::=
        	SEQUENCE {
			imaGroupChanNumSlot			INTEGER,
			imaGroupChanNumMaximum		INTEGER, 
			imaGroupChanNumCurrentTotal			INTEGER,
			imaGroupChanNumCurrentPvc			INTEGER,
			imaGroupChanNumCurrentDtpvc			INTEGER
           	}

        imaGroupChanNumSlot OBJECT-TYPE
        SYNTAX INTEGER
        MAX-ACCESS read-only
        STATUS current
        DESCRIPTION
                ""
         ::= { imaGroupChanNumEntry 1 }
         
        imaGroupChanNumMaximum OBJECT-TYPE
        SYNTAX INTEGER
        MAX-ACCESS read-only
        STATUS current
        DESCRIPTION
                ""
         ::= { imaGroupChanNumEntry 2 }

        imaGroupChanNumCurrentTotal OBJECT-TYPE
        SYNTAX INTEGER
        MAX-ACCESS read-only
        STATUS current
        DESCRIPTION
                ""
         ::= { imaGroupChanNumEntry 3 }

        imaGroupChanNumCurrentPvc OBJECT-TYPE
        SYNTAX INTEGER
        MAX-ACCESS read-only
        STATUS current
        DESCRIPTION
                ""
         ::= { imaGroupChanNumEntry 4 }

        imaGroupChanNumCurrentDtpvc OBJECT-TYPE
        SYNTAX INTEGER
        MAX-ACCESS read-only
        STATUS current
        DESCRIPTION
                ""
         ::= { imaGroupChanNumEntry 5 }	
	-- imaGroupPvcTable

    imaGroupPvcTable OBJECT-TYPE
        SYNTAX SEQUENCE OF ImaGroupPvcEntry
        MAX-ACCESS not-accessible
        STATUS current
        DESCRIPTION
        	"This table includes IMA Group PVC configuration.
        	This table is supported by R5.03 and later versions."
        ::= { imaGroupChan 2 }

	imaGroupPvcEntry OBJECT-TYPE
        SYNTAX ImaGroupPvcEntry
        MAX-ACCESS not-accessible
        STATUS current
        DESCRIPTION
		"An entry of imaGroupPvcTable."
        INDEX { imaGroupPvcGroupIndex, imaGroupPvcVpi, imaGroupPvcVci, imaGroupPvcPvid }
        ::= { imaGroupPvcTable 1 }

        ImaGroupPvcEntry ::=
        	SEQUENCE {
			imaGroupPvcGroupIndex	INTEGER, 
			imaGroupPvcVpi			INTEGER,
			imaGroupPvcVci			INTEGER,
			imaGroupPvcPvid			VlanIndex,
			imaGroupPvcEncap		INTEGER,
			imaGroupPvcPriority		INTEGER,
			imaGruopPvcProfile		DisplayString,
			imaGroupPvcRowStatus	RowStatus,
			imaGroupPvcEgressTag	INTEGER
           	}
         
        imaGroupPvcGroupIndex OBJECT-TYPE
        SYNTAX INTEGER
        MAX-ACCESS read-only
        STATUS current
        DESCRIPTION
                ""
         ::= { imaGroupPvcEntry 1 }

        imaGroupPvcVpi OBJECT-TYPE
        SYNTAX INTEGER (0..255)
        MAX-ACCESS read-only
        STATUS current
        DESCRIPTION
                "VPI of the pvc."
         ::= { imaGroupPvcEntry 2 }

        imaGroupPvcVci OBJECT-TYPE
        SYNTAX INTEGER (1..65535)
        MAX-ACCESS read-only
       	STATUS current
        DESCRIPTION
                "VCI of the pvc."
         ::= { imaGroupPvcEntry 3 }

        imaGroupPvcPvid OBJECT-TYPE
        SYNTAX VlanIndex
        MAX-ACCESS read-only
        STATUS current
        DESCRIPTION
                "PVID of the pvc."
         ::= { imaGroupPvcEntry 4 }

        imaGroupPvcEncap OBJECT-TYPE
        SYNTAX INTEGER {
        		llc(1),
        		vc(2)
        	}
        MAX-ACCESS read-create
        STATUS current
        DESCRIPTION
                "Encapsulation of the pvc."
         ::= { imaGroupPvcEntry 5 }

        imaGroupPvcPriority OBJECT-TYPE
        SYNTAX INTEGER (0..7)
        MAX-ACCESS read-create
        STATUS current
        DESCRIPTION
                "priority of the pvc."
         ::= { imaGroupPvcEntry 6 }

        imaGruopPvcProfile OBJECT-TYPE
        SYNTAX DisplayString (SIZE (1..31))
        MAX-ACCESS read-create
        STATUS current
        DESCRIPTION
                "The value of this object identifies the row in the atmProfileTable, which applies for this pvc."
         ::= { imaGroupPvcEntry 7 }

        imaGroupPvcRowStatus OBJECT-TYPE
        SYNTAX RowStatus
        MAX-ACCESS read-create
        STATUS current
        DESCRIPTION
                "This object is used to create a new row or delete an existing row in this table."
         ::= { imaGroupPvcEntry 8 }  
         
        imaGroupPvcEgressTag OBJECT-TYPE
        SYNTAX INTEGER {
        		tag(1),
        		untag(2)
        	}
        MAX-ACCESS read-create
        STATUS current
        DESCRIPTION
                "Encapsulation of the pvc."
         ::= { imaGroupPvcEntry 9 } 
         
-- imaGroupDtPvcTable

     imaGroupDtPvcTable OBJECT-TYPE
        SYNTAX SEQUENCE OF ImaGroupDtPvcEntry
        MAX-ACCESS not-accessible
        STATUS current
        DESCRIPTION
        	"This table includes IMA Group Double Tagging PVC configuration.
        	This table is supported by R5.03 and later versions."
        ::= { imaGroupChan 3 }

	imaGroupDtPvcEntry OBJECT-TYPE
        SYNTAX ImaGroupDtPvcEntry
        MAX-ACCESS not-accessible
        STATUS current
        DESCRIPTION
		"An entry of imaGroupDtPvcTable."
        INDEX { imaGroupDTPvcGroupIndex, imaGroupDtPvcVpi, imaGroupDtPvcVci, imaGroupDtPvcSvid, imaGroupDtPvcCvid }
        ::= { imaGroupDtPvcTable 1 }

        ImaGroupDtPvcEntry ::=
        	SEQUENCE {   
      		imaGroupDTPvcGroupIndex		INTEGER,  		
			imaGroupDtPvcVpi			INTEGER,
			imaGroupDtPvcVci			INTEGER,
			imaGroupDtPvcSvid			VlanIndex,
			imaGroupDtPvcCvid			VlanIndex,
			imaGroupDtPvcEncap			INTEGER,
			imaGroupDtPvcSPriority		INTEGER,
			imaGroupDtPvcCPriority		INTEGER,
			imaGroupDtPvcProfile		DisplayString,
			imaGroupDtPvcRowStatus		RowStatus
           	}
         
        imaGroupDTPvcGroupIndex OBJECT-TYPE
        SYNTAX INTEGER
        MAX-ACCESS read-only
        STATUS current
        DESCRIPTION
                ""
         ::= { imaGroupDtPvcEntry 1 }
         
        imaGroupDtPvcVpi OBJECT-TYPE
        SYNTAX INTEGER (0..255)
        MAX-ACCESS read-only
        STATUS current
        DESCRIPTION
                "VPI of the pvc."
         ::= { imaGroupDtPvcEntry 2 }

        imaGroupDtPvcVci OBJECT-TYPE
        SYNTAX INTEGER (1..65535)
        MAX-ACCESS read-only
       	STATUS current
        DESCRIPTION
                "VCI of the pvc."
         ::= { imaGroupDtPvcEntry 3 }

        imaGroupDtPvcSvid OBJECT-TYPE
        SYNTAX VlanIndex
        MAX-ACCESS read-only
        STATUS current
        DESCRIPTION
                "s-tag of the pvc."
         ::= { imaGroupDtPvcEntry 4 }

        imaGroupDtPvcCvid OBJECT-TYPE
        SYNTAX VlanIndex
        MAX-ACCESS read-only
        STATUS current
        DESCRIPTION
                "c-tag of the pvc."
         ::= { imaGroupDtPvcEntry 5 }

        imaGroupDtPvcEncap OBJECT-TYPE
        SYNTAX INTEGER {
        		llc(1),
        		vc(2)
        	}
        MAX-ACCESS read-create
        STATUS current
        DESCRIPTION
                "Encapsulation of the pvc."
         ::= { imaGroupDtPvcEntry 6 }

        imaGroupDtPvcSPriority OBJECT-TYPE
        SYNTAX INTEGER (0..7)
        MAX-ACCESS read-create
        STATUS current
        DESCRIPTION
                "s-priority of the pvc."
         ::= { imaGroupDtPvcEntry 7 }

        imaGroupDtPvcCPriority OBJECT-TYPE
        SYNTAX INTEGER (0..7)
        MAX-ACCESS read-create
        STATUS current
        DESCRIPTION
                "c-priority of the pvc."
         ::= { imaGroupDtPvcEntry 8 }

        imaGroupDtPvcProfile OBJECT-TYPE
        SYNTAX DisplayString (SIZE (1..31))
        MAX-ACCESS read-create
        STATUS current
        DESCRIPTION
                "The value of this object identifies the row in the atmProfileTable, which applies for this pvc."
         ::= { imaGroupDtPvcEntry 9 }

        imaGroupDtPvcRowStatus OBJECT-TYPE
        SYNTAX RowStatus
        MAX-ACCESS read-create
        STATUS current
        DESCRIPTION
                "This object is used to create a new row or delete an existing row in this table."
         ::= { imaGroupDtPvcEntry 10 }

-- imaMgmtPvcTable

    imaMgmtPvcTable OBJECT-TYPE
        SYNTAX SEQUENCE OF ImaMgmtPvcEntry
        MAX-ACCESS not-accessible
        STATUS current
        DESCRIPTION
        	"This table includes IMA Management PVC configuration.
        	This table is supported by R5.03 and later versions."
        ::= { ima 3 }

	imaMgmtPvcEntry OBJECT-TYPE
        SYNTAX ImaMgmtPvcEntry
        MAX-ACCESS not-accessible
        STATUS current
        DESCRIPTION
		"An entry of imaMgmtPvcTable."
        INDEX { imaMgmtPvcGroupIndex, imaMgmtPvcVpi, imaMgmtPvcVci, imaMgmtPvcPvid, imaMgmtPvcManagedIp, imaMgmtPvcGatewayIp }
        ::= { imaMgmtPvcTable 1 }

        ImaMgmtPvcEntry ::=
        	SEQUENCE {
			imaMgmtPvcGroupIndex			INTEGER, 
			imaMgmtPvcVpi			INTEGER,
			imaMgmtPvcVci			INTEGER,
			imaMgmtPvcPvid			VlanIndex,
			imaMgmtPvcEncap			INTEGER,
			imaMgmtPvcPriority		INTEGER,
			imaMgmtPvcProfile		DisplayString,
			imaMgmtPvcRowStatus		RowStatus, 
			imaMgmtPvcManagedIp		IpAddress,
			imaMgmtPvcGatewayIp		IpAddress
           	}
         
        imaMgmtPvcGroupIndex OBJECT-TYPE
        SYNTAX INTEGER
        MAX-ACCESS read-only
        STATUS current
        DESCRIPTION
                ""
         ::= { imaMgmtPvcEntry 1 }

        imaMgmtPvcVpi OBJECT-TYPE
        SYNTAX INTEGER (0..255)
        MAX-ACCESS read-only
        STATUS current
        DESCRIPTION
                "VPI of the pvc."
         ::= { imaMgmtPvcEntry 2 }

        imaMgmtPvcVci OBJECT-TYPE
        SYNTAX INTEGER (1..65535)
        MAX-ACCESS read-only
       	STATUS current
        DESCRIPTION
                "VCI of the pvc."
         ::= { imaMgmtPvcEntry 3 }

        imaMgmtPvcPvid OBJECT-TYPE
        SYNTAX VlanIndex
        MAX-ACCESS read-only
        STATUS current
        DESCRIPTION
                "PVID of the pvc."
         ::= { imaMgmtPvcEntry 4 }

        imaMgmtPvcEncap OBJECT-TYPE
        SYNTAX INTEGER {
        		llc(1),
        		vc(2)
        	}
        MAX-ACCESS read-write
        STATUS current
        DESCRIPTION
                "Encapsulation of the pvc."
         ::= { imaMgmtPvcEntry 5 }

        imaMgmtPvcPriority OBJECT-TYPE
        SYNTAX INTEGER (0..7)
        MAX-ACCESS read-write
        STATUS current
        DESCRIPTION
                "priority of the pvc."
         ::= { imaMgmtPvcEntry 6 }

        imaMgmtPvcProfile OBJECT-TYPE
        SYNTAX DisplayString (SIZE (1..31))
        MAX-ACCESS read-write
        STATUS current
        DESCRIPTION
                "The value of this object identifies the row in the atmProfileTable, which applies for this pvc."
         ::= { imaMgmtPvcEntry 7 }

        imaMgmtPvcRowStatus OBJECT-TYPE
        SYNTAX RowStatus
        MAX-ACCESS read-create
        STATUS current
        DESCRIPTION
                "This object is used to create a new row or delete an existing row in this table."
         ::= { imaMgmtPvcEntry 8 }
         
        imaMgmtPvcManagedIp OBJECT-TYPE
        SYNTAX IpAddress
        MAX-ACCESS read-only
        STATUS current
        DESCRIPTION
                ""
         ::= { imaMgmtPvcEntry 9 } 
         
       	imaMgmtPvcGatewayIp OBJECT-TYPE
        SYNTAX IpAddress
        MAX-ACCESS read-only
        STATUS current
        DESCRIPTION
                ""
         ::= { imaMgmtPvcEntry 10 }

                                                                                           	
----------------------------------------
-- trap
----------------------------------------

	object			OBJECT IDENTIFIER ::= { trap 1 }
	dsl			OBJECT IDENTIFIER ::= { trap 2 }
	equipment		OBJECT IDENTIFIER ::= { trap 3 }
	systrap			OBJECT IDENTIFIER ::= { trap 4 }
	enet			OBJECT IDENTIFIER ::= { trap 5 }
	interface		OBJECT IDENTIFIER ::= { trap 6 } 
	tdm				OBJECT IDENTIFIER ::= { trap 7 }   
	voiptrap			OBJECT IDENTIFIER ::= { trap 8 }
	
--------------------
-- object
--------------------

	eqpt48VPowerIndex OBJECT-TYPE
	SYNTAX INTEGER
	MAX-ACCESS read-only
	STATUS current
	DESCRIPTION
		"The index of DC 48V power supply."
	::= { object 1 }
	
	eqptAlarmInputIndex OBJECT-TYPE
	SYNTAX INTEGER
	MAX-ACCESS read-only
	STATUS current
	DESCRIPTION
		"The index of alarm input."
	::= { object 2 }

	eqptDslDeviceIndex OBJECT-TYPE
	SYNTAX INTEGER
	MAX-ACCESS read-only
	STATUS current
	DESCRIPTION
		"The index of DSL device."
	::= { object 3 }

	eqptShdslSubDeviceIndex	OBJECT-TYPE
	SYNTAX INTEGER
	MAX-ACCESS read-only
	STATUS current
	DESCRIPTION
		"The sub-device index of SHDSL device."
	::= { object 4 }

	sysUser OBJECT-TYPE
	SYNTAX DisplayString
	MAX-ACCESS read-only
	STATUS current
	DESCRIPTION
		"The user capable of administering this NE with different priority level."
	::= { object 5 }

	sysAccessPoint OBJECT-TYPE
	SYNTAX 	INTEGER {
			console(1),
			telnet(2),
			ftp(3),
			web(4),
			ssh(5)
		}
	MAX-ACCESS read-only
	STATUS current
	DESCRIPTION
		"The access point to this NE."
	::= { object 6 }

	sysAccessPointIndex OBJECT-TYPE
	SYNTAX INTEGER
	MAX-ACCESS read-only
	STATUS current
	DESCRIPTION
		"The access point index to this NE."
	::= { object 7 }
	
	sysUserLoginIp OBJECT-TYPE
	SYNTAX IpAddress
	MAX-ACCESS read-only
	STATUS current
	DESCRIPTION
		"The IP address from which the user login."
	::= { object 8 }			

	eqptLTResetSource OBJECT-TYPE
	SYNTAX 	INTEGER {
			user(1),
			nt(2)
		}
	MAX-ACCESS read-only
	STATUS current
	DESCRIPTION
		"The source that triggers LT reset."
	::= { object 9 }
	
	sysProfSyncIpAddress OBJECT-TYPE
	SYNTAX IpAddress
	MAX-ACCESS read-only
	STATUS current
	DESCRIPTION
		"The server IP address to be synchronized or the client IP address to synchronize."
	::= { object 10 } 	
	
	sysMacAntiSpoofOrig OBJECT-TYPE
	SYNTAX INTEGER
	MAX-ACCESS read-only
	STATUS current
	DESCRIPTION
		"The original port of Mac-AntiSpoofing."
	::= { object 11 }
	
	sysMacAntiSpoofNew OBJECT-TYPE
	SYNTAX INTEGER
	MAX-ACCESS read-only
	STATUS current
	DESCRIPTION
		"The new port of Mac-AntiSpoofing."
	::= { object 12 }
	
	sysMacAntiSpoofMac OBJECT-TYPE
	SYNTAX DisplayString
	MAX-ACCESS read-only
	STATUS current
	DESCRIPTION
		"The mac address of Mac-AntiSpoofing."
	::= { object 13 }
	
	intfCfmCcmErrorCause OBJECT-TYPE
	SYNTAX INTEGER {
			noDefect(1),
			rdiReceived(2),
			macDownReceivedFromDownMEP(3),
			lostConnectionToRemoteMEP(4),
			configurationError(5),
			maintenanceDomainCrossConnect(6)
		}
	MAX-ACCESS read-only
	STATUS current
	DESCRIPTION
		""
	::= { object 14 }

	e1AlarmStatus OBJECT-TYPE
	SYNTAX INTEGER {
			set(1),
			clear(2)
		}
	MAX-ACCESS read-only
	STATUS current
	DESCRIPTION
		""
	::= { object 15 }    
	
	e1AlarmCurrentValue OBJECT-TYPE
	SYNTAX INTEGER 
	MAX-ACCESS read-only
	STATUS current
	DESCRIPTION
		""
	::= { object 16 }  

	e1AlarmThreshold OBJECT-TYPE
	SYNTAX INTEGER 
	MAX-ACCESS read-only
	STATUS current
	DESCRIPTION
		""
	::= { object 17 }  
	
	dslMacAntiSpoofOrig OBJECT-TYPE
	SYNTAX INTEGER 
	MAX-ACCESS read-only
	STATUS current
	DESCRIPTION
		"The original port of xDSL Mac-AntiSpoofing."
	::= { object 18 }
	
	dslMacAntiSpoofMac OBJECT-TYPE
	SYNTAX DisplayString 
	MAX-ACCESS read-only
	STATUS current
	DESCRIPTION
		"The mac address of xDSL Mac-AntiSpoofing."
	::= { object 19 } 
	
	vopTermPhoneState OBJECT-TYPE
	SYNTAX INTEGER {
			disabled(0),
			on-hook(1),
			off-hook(2),
			ringing(3),
			testing(4),
			power-cut-down(5),
			fault(6),
			bad(7),
			uninitialized(8),
			unknown(9)
			
		}
	MAX-ACCESS read-only
	STATUS current
	DESCRIPTION
		"Phone Status"
	::= { object 20 }   
	
	vopRingTimerSegment OBJECT-TYPE
	SYNTAX INTEGER 
	MAX-ACCESS read-only
	STATUS current
	DESCRIPTION
		"Ring Timer Segment ID"
	::= { object 21 }  
	
	vopRingTimerId OBJECT-TYPE
	SYNTAX INTEGER 
	MAX-ACCESS read-only
	STATUS current
	DESCRIPTION
		"Ring Timer ID"
	::= { object 22 }

    vopDscCodecType OBJECT-TYPE
	SYNTAX INTEGER {
			g711a(0),
			g711mu(1),
			g723(2),
			g726-16(3),
			g726-24(4),
			g726-32(5),
			g726-40(6),
			g729ab(7),
			unused(255)			
		}
	MAX-ACCESS read-only
	STATUS current
	DESCRIPTION
		"Codec Type"
	::= { object 23 }
	
	vopMcMediaId OBJECT-TYPE
	SYNTAX INTEGER 
	MAX-ACCESS read-only
	STATUS current
	DESCRIPTION
		"Media Card ID"
	::= { object 24 }  
	
	vopMcPort OBJECT-TYPE
	SYNTAX INTEGER 
	MAX-ACCESS read-only
	STATUS current
	DESCRIPTION
		"port number"
	::= { object 25 } 
	
	vopDropCallType OBJECT-TYPE
	SYNTAX INTEGER {
			long-term(0),
			short-term(1)			
		}
	MAX-ACCESS read-only
	STATUS current
	DESCRIPTION
		""
	::= { object 26 }  
	
	sysUserLoginInetAddrType OBJECT-TYPE
	SYNTAX InetAddressType
	MAX-ACCESS read-only
	STATUS current
	DESCRIPTION
		""
	::= { object 27 } 
	
	sysUserLoginInetAddr OBJECT-TYPE
	SYNTAX InetAddress
	MAX-ACCESS read-only
	STATUS current
	DESCRIPTION
		""
	::= { object 28 }
	
	vopDeviceId OBJECT-TYPE
	SYNTAX INTEGER
	MAX-ACCESS read-only
	STATUS current
	DESCRIPTION
		""
	::= { object 29 }  
	
	vopBatteryNum OBJECT-TYPE
	SYNTAX INTEGER
	MAX-ACCESS read-only
	STATUS current
	DESCRIPTION
		""
	::= { object 30 }
	
	vopRingerShortCount OBJECT-TYPE
	SYNTAX INTEGER
	MAX-ACCESS read-only
	STATUS current
	DESCRIPTION
		""
	::= { object 31 } 
	
	vopMgcIP OBJECT-TYPE
	SYNTAX  IpAddress
	MAX-ACCESS read-only
	STATUS current
	DESCRIPTION
		"The IP address of Mgc."
	::= { object 32 }

    eqptSptMstiInstanceId OBJECT-TYPE
	SYNTAX 	INTEGER
	MAX-ACCESS read-only
	STATUS current
	DESCRIPTION
		"spanning tree msti instance number."
	::= { object 33 }
	
	eqptSptPortStateOrig OBJECT-TYPE
	SYNTAX 	INTEGER{
			discarding(0),
			learning(1),
			forwarding(2)			
		}
	MAX-ACCESS read-only
	STATUS current
	DESCRIPTION
		"The original port state of spanning tree ."
	::= { object 34 } 
	
	eqptSptPortStateNew OBJECT-TYPE
	SYNTAX 	INTEGER{
			discarding(0),
			learning(1),
			forwarding(2)			
		}
	MAX-ACCESS read-only
	STATUS current
	DESCRIPTION
		"The new port state of spanning tree."
	::= { object 35 }

	eqptSptPortRoleOrig OBJECT-TYPE
	SYNTAX 	INTEGER{
			disabled(0),
			alternated(1),
			backup(2),
			root(3),
			designated(4),
			master(5),
			nonStp(6)		
		}
	MAX-ACCESS read-only
	STATUS current
	DESCRIPTION
		"The original port role of spanning tree."
	::= { object 36 } 
	
	eqptSptPortRoleNew OBJECT-TYPE
	SYNTAX 	INTEGER{
			disabled(0),
			alternated(1),
			backup(2),
			root(3),
			designated(4),
			master(5),
			nonStp(6)		
		}
	MAX-ACCESS read-only
	STATUS current
	DESCRIPTION
		"The new port role of spanning tree."
	::= { object 37 }

		
--------------------
-- dsl
--------------------
	
	dslLineEnable NOTIFICATION-TYPE
	OBJECTS { ifIndex }
	STATUS current
	DESCRIPTION
		"The line is enabled by administrator."
	::= { dsl 1 }

	dslLineDisable NOTIFICATION-TYPE
	OBJECTS { ifIndex }
	STATUS current
	DESCRIPTION
		"The line is disabled by administrator."
	::= { dsl 2 }         	

	dslLineBelowPlannedRate NOTIFICATION-TYPE
	OBJECTS { ifIndex }
	STATUS current
	DESCRIPTION
		"The payload rate is below planned rate."
	::= { dsl 3 }

	dslLineLdmStart NOTIFICATION-TYPE
	OBJECTS { ifIndex }
	STATUS current
	DESCRIPTION
		"The line enters loop diagnosis mode."
	::= { dsl 4 }
	
	dslLineLdmDone NOTIFICATION-TYPE
	OBJECTS { ifIndex }
	STATUS current
	DESCRIPTION
		"The line exits loop diagnosis mode."
	::= { dsl 5 }
	
	dslLinePowerDownL2 NOTIFICATION-TYPE
	OBJECTS { ifIndex }
	STATUS current
	DESCRIPTION
		"The line enters power down L2 mode."
	::= { dsl 6 }
	
	dslLinePowerDownL0 NOTIFICATION-TYPE
	OBJECTS { ifIndex }
	STATUS current
	DESCRIPTION
		"The line enters power down L0 mode."
	::= { dsl 7 }
	
	dslLineFailure NOTIFICATION-TYPE
	OBJECTS { ifIndex }
	STATUS current
	DESCRIPTION
		"The line is failed."
	::= { dsl 8 }
	
	dslLineEnterTest NOTIFICATION-TYPE
	OBJECTS { ifIndex }
	STATUS current
	DESCRIPTION
		"The line enters testing mode."
	::= { dsl 9 }
	
	dslLineExitTest NOTIFICATION-TYPE
	OBJECTS { ifIndex }
	STATUS current
	DESCRIPTION
		"The line exits testing mode."
	::= { dsl 10 }
	
--	dslLineVdslPerfCodingViolationsThresh NOTIFICATION-TYPE
--	OBJECTS { vdsl2PMChCurr15MCodingViolations }
--	STATUS current
--	DESCRIPTION
--		"This notification indicates that the coding violations threshold has been reached/exceeded."
--	::= { dsl 11 }
	
	dslLineVdslRateChange NOTIFICATION-TYPE
	OBJECTS { vdslChanCurrTxRate }
	STATUS current
	DESCRIPTION
		"This notification indicates VDSL link rate change."
	::= { dsl 12 }

	dslLoopGuard NOTIFICATION-TYPE
	OBJECTS { ifIndex }
	STATUS current
	DESCRIPTION
		"Loop guard is traggered."
	::= { dsl 13 }  
	
	dslMacAntiSpoof NOTIFICATION-TYPE
	OBJECTS { dslMacAntiSpoofOrig, dslMacAntiSpoofMac, chassisId  }
	STATUS current
	DESCRIPTION
		"xDsl MAC spoofing is traggered."
	::= { dsl 14 }

	dslLineVturInfoReady NOTIFICATION-TYPE
	OBJECTS { ifIndex  }
	STATUS current
	DESCRIPTION
		"The vtur info is ready."
	::= { dsl 15 }

	dslLineVturLpr NOTIFICATION-TYPE
	OBJECTS { ifIndex  }
	STATUS current
	DESCRIPTION
		"CPE is down."
	::= { dsl 16 }
	
--------------------
-- equipment
--------------------

	eqpt48VPowerFailure NOTIFICATION-TYPE
	OBJECTS { 
			chassisId,
			eqpt48VPowerIndex
		}
	STATUS current
	DESCRIPTION
		"The power supply of DC 48V is failed."
	::= { equipment 1 }
	
	eqpt48VPowerNormal NOTIFICATION-TYPE
	OBJECTS {
			chassisId,
			eqpt48VPowerIndex
		}
	STATUS current
	DESCRIPTION
		"The power supply of DC 48V is normal."
	::= { equipment 2 }

	eqptVoltageError NOTIFICATION-TYPE
	OBJECTS {
			chassisId,
			slotId,
			voltageIndex,
			voltageCurValue,
			voltageLowThresh,
			voltageHighThresh
		}
	STATUS current
	DESCRIPTION
		"The voltage is abnormal."
	::= { equipment 3 }
	
	eqptVoltageNormal NOTIFICATION-TYPE
	OBJECTS {
			chassisId,
			slotId,
			voltageIndex
		}
	STATUS current
	DESCRIPTION
		"The voltage is normal."
	::= { equipment 4 }
	
	eqptTempError NOTIFICATION-TYPE
	OBJECTS {
			chassisId,
			slotId,
			temperatureIndex,
			temperatureCurValue,
			temperatureHighThresh,
			temperatureLowThresh
		}
	STATUS current
	DESCRIPTION
		"The temperature is abnormal."
	::= { equipment 5 }
	
	eqptTempNormal NOTIFICATION-TYPE
	OBJECTS {
			chassisId,
			slotId,
			temperatureIndex
		}
	STATUS current
	DESCRIPTION
		"The temperature is normal."
	::= { equipment 6 }
	
	eqptFanError NOTIFICATION-TYPE
	OBJECTS {
			chassisId,
			fanRpmIndex,
			fanRpmCurValue,
			fanRpmLowThresh,
			fanRpmHighThresh
		}
	STATUS current
	DESCRIPTION
		"The fan RPM is abnormal."
	::= { equipment 7 }
	
	eqptFanNormal NOTIFICATION-TYPE
	OBJECTS {
			chassisId,
			fanRpmIndex
		}
	STATUS current
	DESCRIPTION
		"The fan RPM is normal."
	::= { equipment 8 }
	
	eqptTempLowFanStop NOTIFICATION-TYPE
	OBJECTS {
			chassisId
		}
	STATUS current
	DESCRIPTION
		"The fan is stopped due to low temperature."
	::= { equipment 9 }
	
	eqptHWMonitorFailure NOTIFICATION-TYPE
	OBJECTS {
			chassisId,
			slotId
		}
	STATUS current
	DESCRIPTION
		"Hardware monitor diagnosis is failed."
	::= { equipment 10 }
	
	eqptExternalAlarmInput NOTIFICATION-TYPE
	OBJECTS {
			chassisId,
			eqptAlarmInputIndex,
			externalAlarmName
		}
	STATUS current
	DESCRIPTION
		"External alarm input."
	::= { equipment 11 }
			
	eqptTopologyChange NOTIFICATION-TYPE
	OBJECTS {
			chassisId
		}
	STATUS current
	DESCRIPTION
		"The change of spanning tree topology is detected."
	::= { equipment 12 }

	eqptFWUploadOK NOTIFICATION-TYPE
	OBJECTS {
			chassisId
		}
	STATUS current
	DESCRIPTION
		"Uploading firmware is completed."
	::= { equipment 13 }
	
	eqptFWUploadFailure NOTIFICATION-TYPE
	OBJECTS {
			chassisId
		}
	STATUS current
	DESCRIPTION
		"Uploading firmware is failed."
	::= { equipment 14 }

	eqptLTPlugIn NOTIFICATION-TYPE
	OBJECTS { 
			chassisId,
			slotId
		}
	STATUS current
	DESCRIPTION
		"LT is plugged in."
	::= { equipment 15 }

	eqptLTPullOut NOTIFICATION-TYPE
	OBJECTS {
			chassisId,
			slotId
		}
	STATUS current
	DESCRIPTION
		"LT is pulled out."
	::= { equipment 16 }

	eqptLTActive NOTIFICATION-TYPE
	OBJECTS { 
			chassisId,
			slotId
		}
	STATUS current
	DESCRIPTION
		"LT is active."
	::= { equipment 17 }

	eqptLTInactive NOTIFICATION-TYPE
	OBJECTS {
			chassisId,
			slotId
		}
	STATUS current
	DESCRIPTION
		"LT is inactive."
	::= { equipment 18 }

	eqptLTFWUploadOK NOTIFICATION-TYPE
	OBJECTS {
			chassisId,
			slotId
		}
	STATUS current
	DESCRIPTION
		"Uploading firmware to LT is completed."
	::= { equipment 19 }
	
	eqptLTFWUploadFailure NOTIFICATION-TYPE
	OBJECTS {
			chassisId,
			slotId
		}
	STATUS current
	DESCRIPTION
		"Uploading firmware to LT is failed."
	::= { equipment 20 }

	eqptLTDslDeviceFailure NOTIFICATION-TYPE
	OBJECTS {
			chassisId,
			slotId,
			eqptDslDeviceIndex
		}
	STATUS current
	DESCRIPTION
		"LT DSL device is failed."
	::= { equipment 21 }

	eqptLTDslDeviceRedownload NOTIFICATION-TYPE
	OBJECTS {
			chassisId,
			slotId,
			eqptDslDeviceIndex
		}
	STATUS current
	DESCRIPTION
		"The firmware of LT DSL device is re-downloaded."
	::= { equipment 22 }	

	eqptLTShdslDeviceRedownload NOTIFICATION-TYPE
	OBJECTS {
			chassisId,
			slotId,
			eqptDslDeviceIndex,
			eqptShdslSubDeviceIndex 
		}
	STATUS current
	DESCRIPTION
		"The firmware of LT DSL device is re-downloaded."
	::= { equipment 23 }

	eqptLTEnable NOTIFICATION-TYPE
	OBJECTS {
			chassisId,
			slotId
		}
	STATUS current
	DESCRIPTION
		"LT is enabled."
	::= { equipment 24 }

	eqptLTDisable NOTIFICATION-TYPE
	OBJECTS {
			chassisId,
			slotId
		}
	STATUS current
	DESCRIPTION
		"LT is disabled."
	::= { equipment 25 }

	eqptLTReset NOTIFICATION-TYPE
	OBJECTS {
			chassisId,
			slotId,
			eqptLTResetSource
		}
	STATUS current
	DESCRIPTION
		"LT is reset."
	::= { equipment 26 }

	eqptExternalAlarmInputRelease NOTIFICATION-TYPE
	OBJECTS {
			chassisId,
			eqptAlarmInputIndex,
			externalAlarmName
		}
	STATUS current
	DESCRIPTION
		"External alarm input is released."
	::= { equipment 27 }
	
	eqptNTSwitchOK NOTIFICATION-TYPE
	OBJECTS {
			chassisId,
			slotId
		}
	STATUS current
	DESCRIPTION
		"The trap signifies that MSC card is switched over successfully. The value of
      	     	slotId is the slot ID of the current working MSC."
	::= { equipment 28 }
	
	eqptCpuUtilizationHigh NOTIFICATION-TYPE
	OBJECTS {
			chassisId,
			slotId,
			cpuIndex,
			cpuCurValue,
			cpuHighThresh
		}
	STATUS current
	DESCRIPTION
		"The CPU utilization is over its high threshold."
	::= { equipment 29 }
	
	eqptCpuUtilizationNormal NOTIFICATION-TYPE
	OBJECTS {
			chassisId,
			slotId,
			cpuIndex
		}
	STATUS current
	DESCRIPTION
		"The CPU utilization is normal."
	::= { equipment 30 }
	
	eqptPacketBufferUsageHigh NOTIFICATION-TYPE
	OBJECTS {
			chassisId,
			slotId,
			packetBufferIndex,
			packetBufferCurValue,
			packetBufferHighThresh
		}
	STATUS current
	DESCRIPTION
		"The packet buffer usage is over its high threshold."
	::= { equipment 31 }
	
	eqptPacketBufferUsageNormal NOTIFICATION-TYPE
	OBJECTS {
			chassisId,
			slotId,
			packetBufferIndex
		}
	STATUS current
	DESCRIPTION
		"The packet buffer usage is normal."
	::= { equipment 32 }
	
	eqptMemoryUsageHigh NOTIFICATION-TYPE
	OBJECTS {
			chassisId,
			slotId,
			memoryIndex,
			memoryCurValue,
			memoryHighThresh
		}
	STATUS current
	DESCRIPTION
		"The memory usage is over its high threshold."
	::= { equipment 33 }
	
	eqptMemoryUsageNormal NOTIFICATION-TYPE
	OBJECTS {
			chassisId,
			slotId,
			memoryIndex
		}
	STATUS current
	DESCRIPTION
		"The memory usage is normal."
	::= { equipment 34 }  

	eqptDbInactive NOTIFICATION-TYPE
	OBJECTS {
			chassisId,
			slotId
		}
	STATUS current
	DESCRIPTION
		"The control card daughter board is inactive."
	::= { equipment 35 }
	
	eqptDbNormal NOTIFICATION-TYPE
	OBJECTS {
			chassisId,
			slotId
		}
	STATUS current
	DESCRIPTION
		"The control card daughter board is normal."
	::= { equipment 36 }

	eqptDbReset NOTIFICATION-TYPE
	OBJECTS {
			chassisId,
			slotId
		}
	STATUS current
	DESCRIPTION
		"The control card daughter board is reset."
	::= { equipment 37 }
	
	eqptSptPortStateChange NOTIFICATION-TYPE
	OBJECTS {
			eqptSptMstiInstanceId,
			ifIndex,
			eqptSptPortStateOrig,
			eqptSptPortStateNew
		}
	STATUS current
	DESCRIPTION
		"The spanning tree msti port state change."
	::= { equipment 38 }
	
	eqptSptPortRoleChange NOTIFICATION-TYPE
	OBJECTS {
			eqptSptMstiInstanceId,
			ifIndex,
			eqptSptPortRoleOrig,
			eqptSptPortRoleNew
		}
	STATUS current
	DESCRIPTION
		"The spanning tree msti port role change."
	::= { equipment 39 }

								
--------------------
-- systrap
--------------------

	sysReboot NOTIFICATION-TYPE
	OBJECTS {
			chassisId
		}
	STATUS current
	DESCRIPTION
		"System reboot."
	::= { systrap 1 }

	sysConfigChange NOTIFICATION-TYPE
	OBJECTS {
			chassisId
		}
	STATUS current
	DESCRIPTION
		"System configuration is changed."
	::= { systrap 2 }

	sysConfigUploadOK NOTIFICATION-TYPE
	OBJECTS {
			chassisId
		}
	STATUS current
	DESCRIPTION
		"Uploading system configuration is completed."
	::= { systrap 3 }

	sysConfigUploadFailure NOTIFICATION-TYPE
	OBJECTS {
			chassisId
		}
	STATUS current
	DESCRIPTION
		"Uploading system configuration is failed."
	::= { systrap 4 }

	sysTimeSyncFailure NOTIFICATION-TYPE
	OBJECTS {
			chassisId
		}
	STATUS current
	DESCRIPTION
		"Synchronizing time with the time server is failed."
	::= { systrap 5 }

	sysAlarmCutoffEnable NOTIFICATION-TYPE
	OBJECTS {
			chassisId
		}
	STATUS current
	DESCRIPTION
		"Alarm cutoff is activated."
	::= { systrap 6 }

	sysAlarmClearEnable NOTIFICATION-TYPE
	OBJECTS {
			chassisId
		}
	STATUS current
	DESCRIPTION
		"Alarm clear is activated."
	::= { systrap 7 }

	sysLoginFailure NOTIFICATION-TYPE
	OBJECTS {
			sysUser,
			sysAccessPoint,
			sysAccessPointIndex,
			sysUserLoginIp,
			chassisId
		}
	STATUS current
	DESCRIPTION
		"User login is failed."
	::= { systrap 8 }

	sysLogin NOTIFICATION-TYPE
	OBJECTS {
			sysUser,
			sysAccessPoint,
			sysAccessPointIndex,
			sysUserLoginIp,
			chassisId
		}
	STATUS current
	DESCRIPTION
		"User logins."
	::= { systrap 9 }
		
	sysUserAdded NOTIFICATION-TYPE
	OBJECTS {
			sysUser,
			chassisId
		}
	STATUS current
	DESCRIPTION
		"User added."
	::= { systrap 10 }

	sysUserDeleted NOTIFICATION-TYPE
	OBJECTS {
			sysUser,
			chassisId
		}
	STATUS current
	DESCRIPTION
		"User deleted."
	::= { systrap 11 }

	sysUserModified NOTIFICATION-TYPE
	OBJECTS {
			sysUser,
			chassisId
		}
	STATUS current
	DESCRIPTION
		"User modified."
	::= { systrap 12 }

	sysSvrSyncProfOK NOTIFICATION-TYPE
	OBJECTS {
			sysProfSyncIpAddress,
			chassisId
		}
	STATUS current
	DESCRIPTION
		"Server synchronize profiles successfully."
	::= { systrap 13 }
	
	sysSvrSyncProfFail NOTIFICATION-TYPE
	OBJECTS {
			sysProfSyncIpAddress,
			chassisId
		}
	STATUS current
	DESCRIPTION
		"Server failed to synchronize profiles to a client."
	::= { systrap 14 }
	
	sysCliSyncProfOK NOTIFICATION-TYPE
	OBJECTS {
			sysProfSyncIpAddress,
			chassisId
		}
	STATUS current
	DESCRIPTION
		"Client synchronize profiles from server successfully."
	::= { systrap 15 }
	
	sysCliSyncProfFail NOTIFICATION-TYPE
	OBJECTS {
			sysProfSyncIpAddress,
			chassisId
		}
	STATUS current
	DESCRIPTION
		"Client failed to synchronize profiles from server."
	::= { systrap 16 }
	
	sysMacAntiSpoofing NOTIFICATION-TYPE
	OBJECTS {
			sysMacAntiSpoofOrig,
			sysMacAntiSpoofNew,
			sysMacAntiSpoofMac,
			chassisId
		}
	STATUS current
	DESCRIPTION
		"MAC Anti-spoofing."
	::= { systrap 17 }
	
	sysClusterMemberAdd NOTIFICATION-TYPE
	OBJECTS {
			clusterMemberConfId
		}
	STATUS current
	DESCRIPTION
		"Cluster member is added."
	::= { systrap 18 }
	
	sysClusterMemberDelete NOTIFICATION-TYPE
	OBJECTS {
			clusterMemberConfId
		}
	STATUS current
	DESCRIPTION
		"Cluster member is deleted."
	::= { systrap 19 }
	
	sysClusterMemberActive NOTIFICATION-TYPE
	OBJECTS {
			clusterMemberConfId
		}
	STATUS current
	DESCRIPTION
		"Cluster member is active."
	::= { systrap 20 }
	
	sysClusterMemberInactive NOTIFICATION-TYPE
	OBJECTS {
			clusterMemberConfId
		}
	STATUS current
	DESCRIPTION
		"Cluster member is inactive."
	::= { systrap 21 } 

	sysLoginInet NOTIFICATION-TYPE
	OBJECTS {
			sysUser,
			sysAccessPoint,
			sysAccessPointIndex,
			sysUserLoginInetAddrType,
			sysUserLoginInetAddr,
			chassisId
		}
	STATUS current
	DESCRIPTION
		"User logins."
	::= { systrap 22 } 
	
	sysLoginFailureInet NOTIFICATION-TYPE
	OBJECTS {
			sysUser,
			sysAccessPoint,
			sysAccessPointIndex,
			sysUserLoginInetAddrType,
			sysUserLoginInetAddr,
			chassisId
		}
	STATUS current
	DESCRIPTION
		"User login is failed."
	::= { systrap 23 }

	
--------------------
-- enet
--------------------

	enetEnable NOTIFICATION-TYPE
	OBJECTS {
			ifIndex
		}
	STATUS current
	DESCRIPTION
		"Gigabit Ethernet interface is enabled."
	::= { enet 1 }

	enetDisable NOTIFICATION-TYPE
	OBJECTS {
			ifIndex
		}
	STATUS current
	DESCRIPTION
		"Gigabit Ethernet interface is disabled."
	::= { enet 2 }

	enetLoopGuard NOTIFICATION-TYPE
	OBJECTS {
			ifIndex
		}
	STATUS current
	DESCRIPTION
		"Loop guard is traggered."
	::= { enet 3 } 
	
	enetSfpError NOTIFICATION-TYPE
	OBJECTS {
			ifIndex
		}
	STATUS current
	DESCRIPTION
		"SFP DDMI parameters out of range."
	::= { enet 4 }
	
	enetSfpNormal NOTIFICATION-TYPE
	OBJECTS {
			ifIndex
		}
	STATUS current
	DESCRIPTION
		"SFP DDMI parameters back to range."
	::= { enet 5 }
	
	enetSfpTxEnable NOTIFICATION-TYPE
	OBJECTS {
			ifIndex
		}
	STATUS current
	DESCRIPTION
		"SFP TX power is enabled."
	::= { enet 6 }

    enetSfpTxDisable NOTIFICATION-TYPE
	OBJECTS {
			ifIndex
		}
	STATUS current
	DESCRIPTION
		"SFP TX power is disabled."
	::= { enet 7 }

--------------------
-- interface
--------------------

	cfmCcmError NOTIFICATION-TYPE
	OBJECTS {
			dot1agCfmMdMdLevel,
			dot1agCfmVlanPrimaryVid,
			dot1agCfmMepIdentifier,
			intfCfmCcmErrorCause
		}
	STATUS current
	DESCRIPTION
		""
	::= { interface 1 }

--------------------
-- tdm
--------------------

	e1AlarmLinkLOS NOTIFICATION-TYPE
	OBJECTS {
			ifIndex,
			e1AlarmStatus
		}
	STATUS current
	DESCRIPTION
		""
	::= { tdm 1 }
	
	e1AlarmPathLOF NOTIFICATION-TYPE
	OBJECTS {
			ifIndex,
			e1AlarmStatus
		}
	STATUS current
	DESCRIPTION
		""
	::= { tdm 2 }
	
	e1AlarmPathAIS NOTIFICATION-TYPE
	OBJECTS {
			ifIndex,
			e1AlarmStatus
		}
	STATUS current
	DESCRIPTION
		""
	::= { tdm 3 }
	
	e1AlarmPathRDI NOTIFICATION-TYPE
	OBJECTS {
			ifIndex,
			e1AlarmStatus
		}
	STATUS current
	DESCRIPTION
		""
	::= { tdm 4 }
	
	e1AlarmPathOCASMF NOTIFICATION-TYPE
	OBJECTS {
			ifIndex,
			e1AlarmStatus
		}
	STATUS current
	DESCRIPTION
		""
	::= { tdm 5 }
	
	e1AlarmPathOCRCMF NOTIFICATION-TYPE
	OBJECTS {
			ifIndex,
			e1AlarmStatus
		}
	STATUS current
	DESCRIPTION
		""
	::= { tdm 6 }

	e1AlarmLinkSF NOTIFICATION-TYPE
	OBJECTS {
			ifIndex,
			e1AlarmStatus
		}
	STATUS current
	DESCRIPTION
		""
	::= { tdm 7 }
	
	e1AlarmLinkSD NOTIFICATION-TYPE
	OBJECTS {
			ifIndex,
			e1AlarmStatus
		}
	STATUS current
	DESCRIPTION
		""
	::= { tdm 8 }

	e1AlarmTCAQuarterES NOTIFICATION-TYPE
	OBJECTS {
			ifIndex, 
			e1AlarmCurrentValue,
			e1AlarmThreshold
		}
	STATUS current
	DESCRIPTION
		""
	::= { tdm 9 }

	e1AlarmTCAQuarterSES NOTIFICATION-TYPE
	OBJECTS {
			ifIndex, 
			e1AlarmCurrentValue,
			e1AlarmThreshold
		}
	STATUS current
	DESCRIPTION
		""
	::= { tdm 10 }
	
	e1AlarmTCAQuarterUAS NOTIFICATION-TYPE
	OBJECTS {
			ifIndex, 
			e1AlarmCurrentValue,
			e1AlarmThreshold
		}
	STATUS current
	DESCRIPTION
		""
	::= { tdm 11 }
	
	e1AlarmTCADayES NOTIFICATION-TYPE
	OBJECTS {
			ifIndex, 
			e1AlarmCurrentValue,
			e1AlarmThreshold
		}
	STATUS current
	DESCRIPTION
		""
	::= { tdm 12 }
	
	e1AlarmTCADaySES NOTIFICATION-TYPE
	OBJECTS {
			ifIndex, 
			e1AlarmCurrentValue,
			e1AlarmThreshold
		}
	STATUS current
	DESCRIPTION
		""
	::= { tdm 13 }	

	e1AlarmTCADayUAS NOTIFICATION-TYPE
	OBJECTS {
			ifIndex, 
			e1AlarmCurrentValue,
			e1AlarmThreshold
		}
	STATUS current
	DESCRIPTION
		""
	::= { tdm 14 }

--------------------
-- voiptrap
--------------------

	vopTempError NOTIFICATION-TYPE
	OBJECTS {
			voipIfIndex,
			vopTermPhoneState
		}
	STATUS current
	DESCRIPTION
		"temperature out of low or high threshold"
	::= { voiptrap 1 }   
	
	vopTempNormal NOTIFICATION-TYPE
	OBJECTS {
			voipIfIndex,
			vopTermPhoneState
		}
	STATUS current
	DESCRIPTION
		"temperature normal"
	::= { voiptrap 2 }

    vopDCFail NOTIFICATION-TYPE
	OBJECTS {
			voipIfIndex,
			vopTermPhoneState
		}
	STATUS current
	DESCRIPTION
		"DC power feed got problem"
	::= { voiptrap 3 } 
	
	vopDCNormal NOTIFICATION-TYPE
	OBJECTS {
			voipIfIndex,
			vopTermPhoneState
		}
	STATUS current
	DESCRIPTION
		"DC power feed normal"
	::= { voiptrap 4 } 
	
	vopACFail NOTIFICATION-TYPE
	OBJECTS {
			voipIfIndex,
			vopTermPhoneState
		}
	STATUS current
	DESCRIPTION
		"AC power feed got problem"
	::= { voiptrap 5 }  
	
	vopACNormal NOTIFICATION-TYPE
	OBJECTS {
			voipIfIndex,
			vopTermPhoneState
		}
	STATUS current
	DESCRIPTION
		"AC power feed normal"
	::= { voiptrap 6 }   
	
	vopRingTimer NOTIFICATION-TYPE
	OBJECTS {
			 slotId,
			vopRingTimerSegment,
			vopRingTimerId
		}
	STATUS current
	DESCRIPTION
		"Ringer timer got problem"
	::= { voiptrap 7 } 
	
	vopRingResource NOTIFICATION-TYPE
	OBJECTS {
			voipIfIndex
		}
	STATUS current
	DESCRIPTION
		"Ringer electrical load exceed REN (Ring Equivalent number)"
	::= { voiptrap 8 }
	
	vopRingOverHead NOTIFICATION-TYPE
	OBJECTS {
			voipIfIndex
		}
	STATUS current
	DESCRIPTION
		"High load indication of RI (Ring Indicator, control signal from modem to computer, indicate phone line is ringing)"
	::= { voiptrap 9 } 
	
	vopNoFreeDSPChannel NOTIFICATION-TYPE
	OBJECTS {
			voipIfIndex,
			vopDscCodecType
		}
	STATUS current
	DESCRIPTION
		"DSP resource is not enough for voice processing"
	::= { voiptrap 10 } 
	
	vopMCMissing NOTIFICATION-TYPE
	OBJECTS {
			 slotId,
			vopMcMediaId
		}
	STATUS current
	DESCRIPTION
		"Signal Card detects Media Card missing"
	::= { voiptrap 11 }  
	
	vopSCMissing NOTIFICATION-TYPE
	OBJECTS {
			 slotId
		}
	STATUS current
	DESCRIPTION
		"Media Card detects Signaling Card missing"
	::= { voiptrap 12 }   
	
	vopTermNameDup NOTIFICATION-TYPE
	OBJECTS {
			 voipIfIndex

		}
	STATUS current
	DESCRIPTION
		"Duplicate termination name used"
	::= { voiptrap 13 }
	
	vopNoProtection NOTIFICATION-TYPE
	OBJECTS {
			  slotId
		}
	STATUS current
	DESCRIPTION
		"Can not find protection card on specified slot"
	::= { voiptrap 14 } 
	
	vopProtectionSwitch NOTIFICATION-TYPE
	OBJECTS {
			  slotId
		}
	STATUS current
	DESCRIPTION
		"Signal Card protection switch happened"
	::= { voiptrap 15 }      
	
	vopDropCall NOTIFICATION-TYPE
	OBJECTS {
			  slotId,
			  vopMcMediaId,
			  vopMcPort,
			  vopDropCallType
		}
	STATUS current
	DESCRIPTION
		"Phone call exceed short / long term limit"
	::= { voiptrap 16 } 
	
	vopBatteryFail NOTIFICATION-TYPE
	OBJECTS {
			  slotId,
			  vopBatteryNum 
		}
	STATUS current
	DESCRIPTION
		"CODEC/SLIC module report Battery power failed"
	::= { voiptrap 17 }
	
	vopBatteryNormal NOTIFICATION-TYPE
	OBJECTS {
			  slotId,
			  vopBatteryNum 
		}
	STATUS current
	DESCRIPTION
		"CODEC/SLIC module report Battery power normal"
	::= { voiptrap 18 } 
	
	vopClockFail NOTIFICATION-TYPE
	OBJECTS {
			  vopDeviceId 
		}
	STATUS current
	DESCRIPTION
		"VCP chip CLOCK failed or missing"
	::= { voiptrap 19 }
	
	vopClockNormal NOTIFICATION-TYPE
	OBJECTS {
			  vopDeviceId 
		}
	STATUS current
	DESCRIPTION
		"VCP chip CLOCK normal"
	::= { voiptrap 20 }

	vopRingerFail NOTIFICATION-TYPE
	OBJECTS {
			  slotId,
			  vopRingerShortCount  
		}
	STATUS current
	DESCRIPTION
		"CODEC/SLIC module external ringer does not work"
	::= { voiptrap 21 }
	
	vopRingerNormal NOTIFICATION-TYPE
	OBJECTS {
			  slotId,
			  vopRingerShortCount  
		}
	STATUS current
	DESCRIPTION
		"CODEC/SLIC module external ringer work normal"
	::= { voiptrap 22 }
	
	vopMgcMissing NOTIFICATION-TYPE
	OBJECTS {
			  slotId,
			  vopMgcIP  
		}
	STATUS current
	DESCRIPTION
		"Indicate the state of mgc. Missing trap will be issue when mg had registered to mgc, 
		and disconnected happened."
	::= { voiptrap 23 }
	
	vopMgcNormal NOTIFICATION-TYPE
	OBJECTS {
			  slotId,
			  vopMgcIP  
		}
	STATUS current
	DESCRIPTION
		"Indicate the state of mgc. Normal trap will be issue when missing trap is not clear 
		and mg registered to mgc again."
	::= { voiptrap 24 } 
	
	vopMgEnable NOTIFICATION-TYPE
	OBJECTS {
			  slotId  
		}
	STATUS current
	DESCRIPTION
		"Indicate the state of mg. Mg enable trap will be issued when user enable the mg in manual."
	::= { voiptrap 25 }
	
	vopMgDisable NOTIFICATION-TYPE
	OBJECTS {
			  slotId  
		}
	STATUS current
	DESCRIPTION
		"Indicate the state of mg. Mg disable trap will be issued when user disable the mg in manual."
	::= { voiptrap 26 }
		
	vopPortMissing NOTIFICATION-TYPE
	OBJECTS {
			  slotId,
			  vopMcMediaId,
			  vopMcPort
		}
	STATUS current
	DESCRIPTION
		"none."
	::= { voiptrap 27 } 
	
	vopPortNormal NOTIFICATION-TYPE
	OBJECTS {
			  slotId,
			  vopMcMediaId,
			  vopMcPort
		}
	STATUS current
	DESCRIPTION
		"none."
	::= { voiptrap 28 }

	vopMcNormal NOTIFICATION-TYPE
	OBJECTS {
			slotId,
			vopMcMediaId
		}
	STATUS current
	DESCRIPTION
		"MC is normal."
	::= { voiptrap 29 }

	vopScNormal NOTIFICATION-TYPE
	OBJECTS {
			slotId
		}
	STATUS current
	DESCRIPTION
		"SC is normal."
	::= { voiptrap 30 }

	vopScBulkSyncReady NOTIFICATION-TYPE
	OBJECTS {
			slotId
		}
	STATUS current
	DESCRIPTION
		"SC bulk sync completed."
	::= { voiptrap 31 }

	vopProtectionReady NOTIFICATION-TYPE
	OBJECTS {
			slotId
		}
	STATUS current
	DESCRIPTION
		"SC redundancy is ready."
	::= { voiptrap 32 }
		
END
