-- Copyright (C) 2008-2012 by Zhone Technologies.  All Rights Reserved.

-- ======================================================================
-- ==                                                                  ==
-- ==                    ZHNSYSTEM MIB                                 ==
-- ==                                                                  ==
-- ==  Copyright (C) 2008-2012 Zhone Technologies, Inc.                ==
-- ==  Confidential, Unpublished Property of Zhone Technologies.       ==
-- ==  Rights Reserved Under the Copyright Laws of the United States.  ==
-- ==                                                                  ==
-- ======================================================================

ZHNSYSTEM DEFINITIONS ::= BEGIN

IMPORTS
    MODULE-IDENTITY , OBJECT-TYPE , enterprises,
    Integer32, Unsigned32, IpAddress
        FROM SNMPv2-SMI
    MODULE-COMPLIANCE, OBJECT-GROUP
        FROM SNMPv2-CONF
    TEXTUAL-CONVENTION, DisplayString, MacAddress, RowStatus,
    TruthValue
        FROM SNMPv2-TC
    zhoneWtn
        FROM Zhone
    ZhoneRowStatus			
        FROM Zhone-TC;


zhnSystem  MODULE-IDENTITY
    LAST-UPDATED  "201207131200Z"  -- July 13, 2012
    ORGANIZATION "Zhone Technologies
                  MIB Working Group
                  Other information about group editing the MIB"
    CONTACT-INFO "Zhone Technologies, Inc.
                  Florida Design Center
                  8545 126th Avenue North
                  Largo, FL 33773
                  www.zhone.com

                  General Comments to: largo-mibwg-team@zhone.com"

    DESCRIPTION
        "This file defines the private Enterprise MIB extensions
         that define system related objects. 

         ==============================================================
         ==                                                          ==
         ==      Copyright (C) 2008-2012 Zhone Technologies, Inc.    ==
         ==                                                          ==
         =============================================================="

    REVISION "201207131200Z"  -- July 13, 2012
    DESCRIPTION "Added new zhnSystemTr69c objects."

    REVISION "201207061200Z"  -- July 6, 2012
    DESCRIPTION "Added new sysSnmpProvisioningLock and sysSnmpProvisioningChange
                 objects."

    REVISION "201205181200Z"  -- May 18, 2012
    DESCRIPTION "Added new zhnWanBackupTable, dnsProxyHostEntryTable,
                 and zhnDnsProxyHostMaxHostEntries objects."

    REVISION "201205161200Z"  -- May 16, 2012
	DESCRIPTION "Removed comma in the end of the last line of the enum definitions."

    REVISION "201204120000Z"  -- Apr 12, 2012
    DESCRIPTION "Added zhnSystemDNSClientObjects"

    REVISION "201202031200Z"  -- Feb 03, 2012
    DESCRIPTION "Added:
                   sysFirewallEnable
                   sysFirewallTcpSynCookies
    "
    REVISION "201201191420Z"  -- Jan 19, 2012
    DESCRIPTION "Added:
                   - Bootloader, FW, and alternate FW versions
                   - SNTP objects
                   - User Access Login objects
                   - Power-shedding objects
                   - Syslog objects
                   - coldStart, warmStart and enterprise trap filtering objects
    "
    REVISION "201109090100Z"  -- Sep 09, 2011
    DESCRIPTION "Changed the name of sysContact to zhnSysContact and
                 sysLocation to zhnSysLocation. And, added scalar
                 objects sysSystemClockSource, sysEthernetTransmitClockSource, 
                 and sysDs1ClockSourcePort."
    REVISION "201101050100Z"  -- Jan 05, 2011
    DESCRIPTION "Fixed typo in trapPort description."
    REVISION "200905200100Z"  -- May 20, 2009
    DESCRIPTION "General MIB file cleanup. Also added not-applicable values 
    to some of the textual convention objects."
    REVISION "200808250100Z"  -- Aug 25, 2008
    DESCRIPTION "Added Pseudo-Wire Emulation (PWE) System Timing objects."
    REVISION "200711260100Z"  -- Nov 26, 2007
    DESCRIPTION "Added Trap Manager Table, Community String Table, 
                 zhnSysLocation and zhnSysContact objects."
    REVISION "200703150100Z"  -- March 15, 2007
    DESCRIPTION "Added GPS location objects."
    REVISION "200610170100Z"
    DESCRIPTION "First Draft"

::= { zhoneWtn 2 }


zhnSystemObjects OBJECT IDENTIFIER ::= {zhnSystem 1}

zhnSystemGeneralObjects           OBJECT IDENTIFIER ::= { zhnSystemObjects 1 }
zhnSystemBoardObjects             OBJECT IDENTIFIER ::= { zhnSystemObjects 2 }
zhnSystemPldObjects               OBJECT IDENTIFIER ::= { zhnSystemObjects 3 }
zhnSystemRadioObjects             OBJECT IDENTIFIER ::= { zhnSystemObjects 4 }
zhnSystemEthernetLikeObjects      OBJECT IDENTIFIER ::= { zhnSystemObjects 5 }
zhnSystemTempSensorObjects        OBJECT IDENTIFIER ::= { zhnSystemObjects 6 }
zhnSystemSNMPObjects              OBJECT IDENTIFIER ::= { zhnSystemObjects 7 }
zhnSystemTrapObjects              OBJECT IDENTIFIER ::= { zhnSystemObjects 8 }
zhnSystemSyslogObjects            OBJECT IDENTIFIER ::= { zhnSystemObjects 9 }
zhnSystemSNTPObjects              OBJECT IDENTIFIER ::= { zhnSystemObjects 10 }
zhnSystemUserLoginObjects         OBJECT IDENTIFIER ::= { zhnSystemObjects 11 }
zhnSystemPowerSheddingObjects     OBJECT IDENTIFIER ::= { zhnSystemObjects 12 }
zhnSystemFirewallObjects          OBJECT IDENTIFIER ::= { zhnSystemObjects 13 }
zhnSystemDNSClientObjects         OBJECT IDENTIFIER ::= { zhnSystemObjects 14 }
zhnSystemDNSProxyObjects          OBJECT IDENTIFIER ::= { zhnSystemObjects 15 }
zhnSystemWanBackupObjects         OBJECT IDENTIFIER ::= { zhnSystemObjects 16 }
zhnSystemTr69cObjects             OBJECT IDENTIFIER ::= { zhnSystemObjects 17 }


-- ****************************************************************************
--
-- Textual Conventions
--

WFNT ::= TEXTUAL-CONVENTION
  STATUS        current
  DESCRIPTION   "The Wifi Network Type"
  SYNTAX        INTEGER {
                  notApplicable(0),   -- Not Applicable
                  baseStation(1),     -- BaseStation 
                  mesh(2)             -- Mesh unit 
                }

ELTYPE ::= TEXTUAL-CONVENTION
  STATUS        current
  DESCRIPTION   "Ethernet Like Interface Type"
  SYNTAX        INTEGER {
                  ethernet(1),     -- Real Ethernet interface
                  efm(2),          -- Ethernet First Mile
                  shdsl(3),        -- Ethernet Over Shdsl
                  docsis(4),       -- 
                  wimax(5)         -- 
                }

ELSUBTYPE ::= TEXTUAL-CONVENTION
  STATUS        current
  DESCRIPTION   "Ethernet Like Interface Sub-Type"
  SYNTAX        INTEGER {
                  none(0)     -- No Subtype defined for this Type
                }

LPT ::= TEXTUAL-CONVENTION
  STATUS        current
  DESCRIPTION   "Line Power Direction"
  SYNTAX        INTEGER {
                  none(0),   -- None
                  in(1),     -- Power coming into interface
                  out(2)     -- Power provided to interface
                }

UPT ::= TEXTUAL-CONVENTION
  STATUS        current
  DESCRIPTION   "Unit Power Supply Type"
  SYNTAX        INTEGER {
                  ac(1),     -- Alternating Current
                  dc(2)      -- Direct Current
                }

TCSI ::= TEXTUAL-CONVENTION
  STATUS        current
  DESCRIPTION   "Transmit Clock Source Items"
  SYNTAX        INTEGER {
                  notApplicable(0),   -- Not Applicable
                  loop(1),    -- Receive clock used a transmit clock
                  local(2),   -- Local clock source used a transmit clock
                  pwe(3)      -- Clock recovered from Data flow
                }

LTRI ::= TEXTUAL-CONVENTION
  STATUS        current
  DESCRIPTION   "Local Timing Reference Items"
  SYNTAX        INTEGER {
                  notApplicable(0), -- Not Applicable
                  ethernet(1),    -- Use SyncE 25MHz clock
                  internal(2),    -- Use internal oscillator
                  shdsl(3)        -- Use 8KHz SHDSL clock (CPE only)
                }

CSMI ::= TEXTUAL-CONVENTION
  STATUS        current
  DESCRIPTION   "Pseudo Wire Clock Synchronization Mode Items"
  SYNTAX        INTEGER {
                  notApplicable(0), -- Not Applicable
                  adaptive(1),      -- Adaptive Timing Mode
                  differential(2),  -- Differential Timing Mode
                  synchronous(3),   -- SHDSL Synch Timing Mode
                  dslAdaptive(4),   -- Adaptive DSL Timing Mode
                  loop(5)           -- Loop Timing Mode (Typically used for CO operations)
                }

SEI ::= TEXTUAL-CONVENTION
  STATUS        current
  DESCRIPTION   "Synchronous Ethernet Items"
  SYNTAX        INTEGER {
                  enable(1),      
                  disable(2)      
                }

CMI ::= TEXTUAL-CONVENTION
  STATUS        current
  DESCRIPTION   "Clock Mode Items"
  SYNTAX        INTEGER {
                  notApplicable(0), -- Not Applicable
                  normal(1),        -- Adaptive/Synch Timing Mode
                  differential(2)   -- Differential Timing Mode
                }

CDA ::= TEXTUAL-CONVENTION
  STATUS        current
  DESCRIPTION   "Configuration Database Action"
  SYNTAX        INTEGER {
                  noAction(0),        -- No Action
                  save(1),            -- Save current settings to database
                  resetToDefaults(2)  -- Reset database to factory defaults and reboot
                }

RBT ::= TEXTUAL-CONVENTION
  STATUS        current
  DESCRIPTION   "Software Reboot Action"
  SYNTAX        INTEGER {
                  noAction(0),        -- No Action
                  reboot(1)           -- Software reboot
                }

SCS ::= TEXTUAL-CONVENTION
  STATUS        current
  DESCRIPTION   "System Clock Source Items"
  SYNTAX        INTEGER {
                  notApplicable(0), -- Not Applicable
                  uplink(1),        -- System Clock recovered from the uplink
                  ds1(2),           -- System Clock recovered from a DS1 port
                  ieee1588(3)       -- System Clock recovered from ieee 1588 timing source
                }

ETCS ::= TEXTUAL-CONVENTION
  STATUS        current
  DESCRIPTION   "Ethernet Transmit Clock Source Items"
  SYNTAX        INTEGER {
                  notApplicable(0), -- Not Applicable
                  internal(1),      -- Clocking for ethernet ports derived from internal oscillator
                  systemClock(2)    -- Clocking for ethernet ports recovered from the System Clock Source
                }

SysFirmwareAction ::= TEXTUAL-CONVENTION
  STATUS        current
  DESCRIPTION   "Action to take on the current firmware version."
  SYNTAX        INTEGER {
                  noAction(0),           -- No action
                  restoreAltFirmware(1)  -- Restore alternate firmware version
                }

SysAdminStatus ::= TEXTUAL-CONVENTION
  STATUS        current
  DESCRIPTION   "Administrative status options for various system services,
                 like syslog and power-shedding."
  SYNTAX        INTEGER {
                  enable(1),      
                  disable(2)      
                }

SysLogLevel ::= TEXTUAL-CONVENTION
  STATUS        current
  DESCRIPTION   "SysLog logging level options, per RFC 3164."
  SYNTAX        INTEGER {
                  emergency(0),
                  alert(1),
                  critical(2),
                  error(3),
                  warning(4),
                  notice(5),
                  informational(6),
                  debug(7)
                }

SysLogMode ::= TEXTUAL-CONVENTION
  STATUS        current
  DESCRIPTION   "SysLog logging mode of operation."
  SYNTAX        INTEGER {
                  local(1),     -- Log messages only to the local, non-persistent log file
                  remote(2),    -- Log messages only to a remote syslog server
                  both(3)       -- Log messages to both a local log file and a remote syslog server
                }

SysSntpTimeZones ::= TEXTUAL-CONVENTION
  STATUS        current
  DESCRIPTION   "Simple Network Timing Protocol time zones."
  SYNTAX        INTEGER {
                  unknown(0),       -- Undefined time zone
                  abu(1),           -- GMT+04:00 Abu Dhabi, Muscat
                  adelaide(2),      -- GMT+09:30 Adelaide
                  alaska(3),        -- GMT-09:00 Alaska
                  almaty(4),        -- GMT+06:00 Almaty, Novosibirsk
                  amsterdam(5),     -- GMT+01:00 Amsterdam, Berlin, Bern, Rome, Stockholm, Vienna
                  arizona(6),       -- GMT-07:00 Arizona, Mazatlan
                  astana(7),        -- GMT+06:00 Astana, Dhaka
                  athens(8),        -- GMT+02:00 Athens, Istanbul, Minsk
                  atlantic(9),      -- GMT-04:00 Atlantic Time
                  auckland(10),     -- GMT+12:00 Auckland, Wellington
                  azores(11),       -- GMT-01:00 Azores
                  baghdad(12),      -- GMT+03:00 Baghdad
                  baku(13),         -- GMT+04:00 Baku, Tbilisi, Yerevan
                  bangkok(14),      -- GMT+07:00 Bangkok, Hanoi, Jakarta
                  beijing(15),      -- GMT+08:00 Beijing, Chongquing, Hong Kong, Urumqi
                  belgrade(16),     -- GMT+01:00 Belgrade, Bratislava, Budapest, Ljubljana, Prague
                  bogota(17),       -- GMT-05:00 Bogota, Lima, Quito
                  brasilia(18),     -- GMT-03:00 Brasilia
                  brisbane(19),     -- GMT+10:00 Brisbane
                  brussels(20),     -- GMT+01:00 Brussels, Copenhagen, Madrid, Paris
                  bucharest(21),    -- GMT+02:00 Bucharest
                  buenos(22),       -- GMT-03:00 Buenos Aires, Georgetown
                  cairo(23),        -- GMT+02:00 Cairo
                  canberra(24),     -- GMT+10:00 Canberra, Melbourne, Sydney
                  cape(25),         -- GMT-01:00 Cape Verde Is.
                  caracas(26),      -- GMT-04:00 Caracas, La Paz
                  casablanca(27),   -- GMT-00:00 Casablanca, Monrovia
                  central(28),      -- GMT-06:00 Central America
                  centraltime(29),  -- GMT-06:00 Central Time
                  chennai(30),      -- GMT+05:30 Chennai, Kolkata, Mumbai, New Delhi
                  chihuahua(31),    -- GMT-07:00 Chihuahua, La Paz
                  darwin(32),       -- GMT+09:30 Darwin
                  eastern(33),      -- GMT-05:00 Eastern Time
                  ekaterinburg(34), -- GMT+05:00 Ekaterinburg
                  fiji(35),         -- GMT+12:00 Fiji, Kamchatka, Marshall Is.
                  greenland(36),    -- GMT-03:00 Greenland
                  greenwich(37),    -- GMT-00:00 Greenwich Mean Time: Dublin, Edinburgh, Lisbon, London
                  guadalajara(38),  -- GMT-06:00 Guadalajara, Mexico City, Monterrey
                  guam(39),         -- GMT+10:00 Guam, Port Moresby
                  harare(40),       -- GMT+02:00 Harare, Pretoria
                  hawaii(41),       -- GMT-10:00 Hawaii
                  helsinki(42),     -- GMT+02:00 Helsinki, Kyiv, Riga, Sofia, Tallinn, Vilnius
                  hobart(43),       -- GMT+10:00 Hobart
                  indiana(44),      -- GMT-05:00 Indiana
                  international(45),-- GMT-12:00 International Date Line West
                  irkutsk(46),      -- GMT+08:00 Irkutsk, Ulaan Bataar
                  islamabad(47),    -- GMT+05:00 Islamabad, Karachi, Tashkent
                  jerusalem(48),    -- GMT+02:00 Jerusalem
                  kabul(49),        -- GMT+04:30 Kabul
                  kathmandu(50),    -- GMT+05:45 Kathmandu
                  krasnoyarsk(51),  -- GMT+07:00 Krasnoyarsk
                  kuala(52),        -- GMT+08:00 Kuala Lumpur, Singapore
                  kuwait(53),       -- GMT+03:00 Kuwait, Riyadh
                  magadan(54),      -- GMT+11:00 Magadan
                  midatlantic(55),  -- GMT-02:00 Mid-Atlantic
                  midway(56),       -- GMT-11:00 Midway Island, Samoa
                  moscow(57),       -- GMT+03:00 Moscow, St. Petersburg, Volgograd
                  mountain(58),     -- GMT-07:00 Mountain Time
                  nairobi(59),      -- GMT+03:00 Nairobi
                  newfoundland(60), -- GMT-03:30 Newfoundland
                  osaka(61),        -- GMT+09:00 Osaka, Sapporo, Tokyo
                  pacific(62),      -- GMT-08:00 Pacific Time, Tijuana
                  perth(63),        -- GMT+08:00 Perth
                  rangoon(64),      -- GMT+06:30 Rangoon
                  santiago(65),     -- GMT-04:00 Santiago
                  sarajevo(66),     -- GMT+01:00 Sarajevo, Skopje, Warsaw, Zagreb
                  saskatchewan(67), -- GMT-06:00 Saskatchewan
                  seoul(68),        -- GMT+09:00 Seoul
                  solomon(69),      -- GMT+11:00 Solomon Is., New Caledonia
                  sri(70),          -- GMT+06:00 Sri Jayawardenepura
                  taipei(71),       -- GMT+08:00 Taipei
                  tehran(72),       -- GMT+03:30 Tehran
                  vladivostok(73),  -- GMT+10:00 Vladivostok
                  west(74),         -- GMT+01:00 West Central Africa
                  yakutsk(75)       -- GMT+09:00 Yakutsk
                }

IPInterfaceAddressingTypeValues ::= TEXTUAL-CONVENTION
  STATUS        current
  DESCRIPTION   "The addressing method used to assign the LAN-side IP Address.
                 Enumeration of:
                     Unknown
                     Unconfigured
                     Default
                     DHCP
                     Static
                     PPPoE
                     OMCI
                "
  SYNTAX OCTET STRING (SIZE (0..32))

BasicAddressingTypeValues ::= TEXTUAL-CONVENTION
  STATUS        current
  DESCRIPTION   "Enumeration of:
                     DHCP - The DNS information is obtained via DHCP
                     Static - The DNS information is manually provisioned
		 "
  SYNTAX OCTET STRING (SIZE (0..16))



-- ****************************************************************************
--
-- System General Objects
--

-- read only system info

modelNumber OBJECT-TYPE
  SYNTAX        DisplayString
  MAX-ACCESS    read-only
  STATUS        current
  DESCRIPTION
         "model no. of the device"
  ::= { zhnSystemGeneralObjects 1}

macBaseAddress OBJECT-TYPE
  SYNTAX        MacAddress
  MAX-ACCESS    read-only
  STATUS        current
  DESCRIPTION
         "First MAC Address in series"
  ::= { zhnSystemGeneralObjects 2}

numberOfMacAddresses OBJECT-TYPE
  SYNTAX        Unsigned32(0..10)
  MAX-ACCESS    read-only
  STATUS        current
  DESCRIPTION
         "Number of MAC Address sequentially defined in the Unit starting
          at the MAC Base Address."
  ::= { zhnSystemGeneralObjects 3}


-- read-write system info

wifiNetworkType OBJECT-TYPE
  SYNTAX        WFNT
  MAX-ACCESS    read-write
  STATUS        current
  DESCRIPTION
    "Defines the Network Type or Mode of the Unit, i.e. Mesh or Base Station"
  ::= { zhnSystemGeneralObjects 4}

locationLatitude OBJECT-TYPE
  SYNTAX        DisplayString
  MAX-ACCESS    read-write
  STATUS        current
  DESCRIPTION
    "The latitude of the unit's location represented in degrees decimal.
     The format of the location's latitude is:

       [+ | -]ddd.dddddddd

     where + indicates north
           - indicates south
           d is a decimal digit (0 <= d <= 9)

     Valid range is -90 to +90 degrees."
  ::= { zhnSystemGeneralObjects 6 }

locationLongitude OBJECT-TYPE
  SYNTAX        DisplayString
  MAX-ACCESS    read-write
  STATUS        current
  DESCRIPTION
    "The longitude of the unit's location represented in degrees decimal.
     The format of the location's longitude is:

       [+ | -]ddd.dddddddd

     where + indicates east
           - indicates west
           d is a decimal digit (0 <= d <= 9)

     Valid range is -180 to +180 degrees."
  ::= { zhnSystemGeneralObjects 7 }


-- action parameter: needed for setting above scalars in dal_set requests

zhnSystemAction OBJECT-TYPE
  SYNTAX        RowStatus
  MAX-ACCESS    read-write
  STATUS        current
  DESCRIPTION 
     "Action parameter to handle the action on other scalars."
  ::= { zhnSystemGeneralObjects 8 }

zhnSysLocation OBJECT-TYPE
  SYNTAX        DisplayString
  MAX-ACCESS    read-write
  STATUS        current
  DESCRIPTION 
     "System location. This object is synonomous with the MIB II system
      sysLocation object."
  ::= { zhnSystemGeneralObjects 9 }

zhnSysContact OBJECT-TYPE
  SYNTAX        DisplayString
  MAX-ACCESS    read-write
  STATUS        current
  DESCRIPTION 
     "System contact. This object is synonomous with the MIB II system
      sysContact object."
  ::= { zhnSystemGeneralObjects 10 }

sysTransmitClockSource OBJECT-TYPE
  SYNTAX        TCSI
  MAX-ACCESS    read-write
  STATUS        current
  DESCRIPTION 
     "T1 Clock source for PWE device. Since both T1/E1 interfaces 
      will be required to have the same source, this object will 
      replace the dsx1TransmitClockSource object in the DS1-MIB.
      This object is not supported by ZNID devices."
  ::= { zhnSystemGeneralObjects 11 }

sysLocalTimingReference OBJECT-TYPE
  SYNTAX        LTRI
  MAX-ACCESS    read-write
  STATUS        current
  DESCRIPTION 
     "Source of the sysTransmitClockSource when set to Local.
      This object is not supported by ZNID devices."
  ::= { zhnSystemGeneralObjects 12 }

sysSynchronizationMode OBJECT-TYPE
  SYNTAX        CSMI
  MAX-ACCESS    read-write
  STATUS        current
  DESCRIPTION 
     "Determines the method of ensuring Service Clock synchronization
      between the Source and Remote PWE devices."
  ::= { zhnSystemGeneralObjects 13 }

sysSynchronousEthernet OBJECT-TYPE
  SYNTAX        SEI
  MAX-ACCESS    read-write
  STATUS        current
  DESCRIPTION 
     "Determines whether or not to use the 25MHz clock derived from the 
      Synchronous Ethernet Port. This object is not supported by ZNID
      devices."
  ::= { zhnSystemGeneralObjects 14 }

sysClockMode OBJECT-TYPE
  SYNTAX        CMI
  MAX-ACCESS    read-write
  STATUS        current
  DESCRIPTION 
     "Determines the mode for which the PWE chip will be initialized. "
  ::= { zhnSystemGeneralObjects 15 }

sysCfgDBAction OBJECT-TYPE
  SYNTAX        CDA
  MAX-ACCESS    read-write
  STATUS        current
  DESCRIPTION 
     "Perform an action on the configuration database."
  ::= { zhnSystemGeneralObjects 16 }

sysSoftwareReboot OBJECT-TYPE
  SYNTAX        RBT
  MAX-ACCESS    read-write
  STATUS        current
  DESCRIPTION 
     "Perform a software reboot."
  ::= { zhnSystemGeneralObjects 17 }

sysSystemClockSource OBJECT-TYPE
  SYNTAX        SCS
  MAX-ACCESS    read-write
  STATUS        current
  DESCRIPTION 
     "Determines the system-level clock mode for ZNID devices.

          uplink - the system will recover its clock from the configured
                   uplink (e.g. GPON, SPF1, SFP2, etc.). 
		   
          ds1 -  the system will recover its clock from the configured
                 sysDs1ClockSourcePort.
		 
          ieee1588 - the system will recover clock from the on-board 1588 
	         clock circuitry.
     "
  ::= { zhnSystemGeneralObjects 18 }
  
sysEthernetTransmitClockSource OBJECT-TYPE
  SYNTAX        ETCS
  MAX-ACCESS    read-write
  STATUS        current
  DESCRIPTION 
     "Determines the transmit clock source for all ethernet ports requiring
      a clock. 
      
          internal - all ethernet ports will recover clock from the local 
	             oscillator.
	  
          systemClock - all ethernet ports will recover clock from the 
                        sysSystemClockSource.
      "
  ::= { zhnSystemGeneralObjects 19 }

sysDs1ClockSourcePort OBJECT-TYPE
  SYNTAX        DisplayString
  MAX-ACCESS    read-write
  STATUS        current
  DESCRIPTION 
     "The interface name for the DS1 port providing transmit clock when the 
      sysSystemClockSource is set to ds1."
  ::= { zhnSystemGeneralObjects 20 }

sysBootloaderVersion OBJECT-TYPE
  SYNTAX        OCTET STRING (SIZE (1..64))
  MAX-ACCESS    read-only
  STATUS        current
  DESCRIPTION 
     "System bootloader (CFE) firmware version."
  ::= { zhnSystemGeneralObjects 21 }

sysFirmwareVersion OBJECT-TYPE
  SYNTAX        OCTET STRING (SIZE (1..64))
  MAX-ACCESS    read-only
  STATUS        current
  DESCRIPTION 
     "The version of firmware the system is currently running."
  ::= { zhnSystemGeneralObjects 22 }

sysAltFirmwareVersion OBJECT-TYPE
  SYNTAX        OCTET STRING (SIZE (1..64))
  MAX-ACCESS    read-only
  STATUS        current
  DESCRIPTION 
     "The alternate firmware version currently stored in system flash."
  ::= { zhnSystemGeneralObjects 23 }

sysRestoreAltFirmwareVersion OBJECT-TYPE
  SYNTAX        SysFirmwareAction
  MAX-ACCESS    read-write
  STATUS        current
  DESCRIPTION 
     "This object can be used to restore the version of firmware to 
      the alternate firmware version currently stored in flash."
  ::= { zhnSystemGeneralObjects 24 }

sysSnmpProvisioningLock OBJECT-TYPE
  SYNTAX        TruthValue
  MAX-ACCESS    read-write
  STATUS        current
  DESCRIPTION
     "This object can be set by an SNMP client to indicate that system
      configuration is in progress. All other SNMP clients will be locked
      out while this is set to true. This lock will timeout after 30
      seconds."
  ::= { zhnSystemGeneralObjects 25 }

sysSnmpProvisioningChange OBJECT-TYPE
  SYNTAX        Unsigned32
  MAX-ACCESS    read-write
  STATUS        current
  DESCRIPTION
     "This object can be incremented by SNMP clients to indicate a
      sysCfgDBAction save has taken place."
  ::= { zhnSystemGeneralObjects 26 }


-- ****************************************************************************
--
-- Board Descriptor Table
--
numberOfBoards OBJECT-TYPE
  SYNTAX        Unsigned32(0..4)
  MAX-ACCESS    read-only
  STATUS        current
  DESCRIPTION
    "Number of boards in the Unit with Name, Part Number, Serial Number
     and Revision Number values"
  ::= { zhnSystemBoardObjects 1}

boardDescriptorTable OBJECT-TYPE
  SYNTAX        SEQUENCE OF BoardDescriptorEntry
  MAX-ACCESS    not-accessible
  STATUS        current
  DESCRIPTION
    "Table of boards: Name, Part Number, Serial Number and Revision 
     Number values"
  ::= { zhnSystemBoardObjects 2}

boardDescriptorEntry OBJECT-TYPE
  SYNTAX        BoardDescriptorEntry
  MAX-ACCESS    not-accessible
  STATUS        current
  DESCRIPTION
    "Table of boards: Name, Part Number, Serial Number and Revision 
     Number values"
  INDEX        { boardIndex }
  ::= { boardDescriptorTable 1}

BoardDescriptorEntry ::=
  SEQUENCE {
      boardIndex         Unsigned32,
      boardName          DisplayString,
      boardPartNumber    DisplayString,
      boardSerialNumber  DisplayString,
      boardRevision      DisplayString
  }

boardIndex OBJECT-TYPE
  SYNTAX        Unsigned32(0..20)
  MAX-ACCESS    not-accessible
  STATUS        current
  DESCRIPTION
    "Board Index (Zero relative)"
  ::= { boardDescriptorEntry 1}

boardName OBJECT-TYPE
  SYNTAX        DisplayString
  MAX-ACCESS    read-only
  STATUS        current
  DESCRIPTION
    "Name of the Board as created by the system"
  ::= { boardDescriptorEntry 2}

boardPartNumber OBJECT-TYPE
  SYNTAX        DisplayString
  MAX-ACCESS    read-only
  STATUS        current
  DESCRIPTION
    "Part Number of the Board. Read from the board"
  ::= { boardDescriptorEntry 3}

boardSerialNumber OBJECT-TYPE
  SYNTAX        DisplayString
  MAX-ACCESS    read-only
  STATUS        current
  DESCRIPTION
    "Serial Number of the Board. Read from the board"
  ::= { boardDescriptorEntry 4}

boardRevision OBJECT-TYPE
  SYNTAX        DisplayString
  MAX-ACCESS    read-only
  STATUS        current
  DESCRIPTION
    "Revision Number of the Board. Read from the board"
  ::= { boardDescriptorEntry 5}


-- ****************************************************************************
--
-- PLD Descriptor Table
--
numberOfPlds OBJECT-TYPE
  SYNTAX        Unsigned32(0..20)
  MAX-ACCESS    read-only
  STATUS        current
  DESCRIPTION
    "Number of PLDs in the Unit with Name and Version Number values"
  ::= { zhnSystemPldObjects 1}

pldDescriptorTable OBJECT-TYPE
  SYNTAX        SEQUENCE OF PldDescriptorEntry
  MAX-ACCESS    not-accessible
  STATUS        current
  DESCRIPTION
    "Table of boards: Name, Part Number, Serial Number and Revision 
     Number values"
  ::= { zhnSystemPldObjects 2}

pldDescriptorEntry OBJECT-TYPE
  SYNTAX        PldDescriptorEntry
  MAX-ACCESS    not-accessible
  STATUS        current
  DESCRIPTION
    "Table of boards: Name, Part Number, Serial Number and Revision 
     Number values"
  INDEX        { pldIndex }
  ::= { pldDescriptorTable 1}

PldDescriptorEntry ::=
  SEQUENCE {
      pldIndex         Unsigned32,
      pldName          DisplayString,
      pldVersion       DisplayString
  }

pldIndex OBJECT-TYPE
  SYNTAX        Unsigned32(0..20)
  MAX-ACCESS    not-accessible
  STATUS        current
  DESCRIPTION
    "PLD Index (Zero relative)"
  ::= { pldDescriptorEntry 1}

pldName OBJECT-TYPE
  SYNTAX        DisplayString
  MAX-ACCESS    read-only
  STATUS        current
  DESCRIPTION
    "Name of the PLD as created by the system"
  ::= { pldDescriptorEntry 2}

pldVersion OBJECT-TYPE
  SYNTAX        DisplayString
  MAX-ACCESS    read-only
  STATUS        current
  DESCRIPTION
    "PLD Software Version. Read from the PLD"
  ::= { pldDescriptorEntry 3}


-- ****************************************************************************
--
-- System Radio Objects
--
numberOfRadios OBJECT-TYPE
  SYNTAX        Unsigned32(0..20)
  MAX-ACCESS    read-only
  STATUS        current
  DESCRIPTION
    "Number of Radios in the Unit"
  ::= { zhnSystemRadioObjects 1}


-- ****************************************************************************
--
-- Ethernet-like Interface Table
--
numberOfEthernetLikeInterfaces OBJECT-TYPE
  SYNTAX        Unsigned32(0..20)
  MAX-ACCESS    read-write
  STATUS        current
  DESCRIPTION
    "Number of Ethernet Like Interfaces with Name, Type and Subtype"
  ::= { zhnSystemEthernetLikeObjects 1}

ethernetlikeInterfaceTable OBJECT-TYPE
  SYNTAX        SEQUENCE OF EthernetlikeInterfaceEntry
  MAX-ACCESS    not-accessible
  STATUS        current
  DESCRIPTION
    "Table of ethernet-like Interfaces"
  ::= { zhnSystemEthernetLikeObjects 2}

ethernetlikeInterfaceEntry OBJECT-TYPE
  SYNTAX        EthernetlikeInterfaceEntry
  MAX-ACCESS    not-accessible
  STATUS        current
  DESCRIPTION
    "Table of ethernet-like interfaces having Name, type, subtype, number
     of ports, line power and number of pairs with power"
  INDEX        { etherIndex }
  ::= { ethernetlikeInterfaceTable 1}

EthernetlikeInterfaceEntry ::=
  SEQUENCE {
      etherIndex           Unsigned32,
      etherName            DisplayString,
      etherType            ELTYPE,
      etherSubtype         ELSUBTYPE,
      etherNumberOfPorts   Unsigned32,
      etherLinePower       LPT,
      etherPowerPairs      Integer32
  }

etherIndex OBJECT-TYPE
  SYNTAX        Unsigned32(0..20)
  MAX-ACCESS    not-accessible
  STATUS        current
  DESCRIPTION
    "Index of the Ethernet Like Interface (zero relative)"
  ::= { ethernetlikeInterfaceEntry 1}

etherName OBJECT-TYPE
  SYNTAX        DisplayString
  MAX-ACCESS    read-only
  STATUS        current
  DESCRIPTION
    "Name of the ethernet Like Interface as created by the system"
  ::= { ethernetlikeInterfaceEntry 2}

etherType OBJECT-TYPE
  SYNTAX        ELTYPE
  MAX-ACCESS    read-only
  STATUS        current
  DESCRIPTION
    "Type of Ethernet interface"
  ::= { ethernetlikeInterfaceEntry 3}

etherSubtype OBJECT-TYPE
  SYNTAX        ELSUBTYPE
  MAX-ACCESS    read-only
  STATUS        current
  DESCRIPTION
    "Subtype of Ethernet interface"
  ::= { ethernetlikeInterfaceEntry 4}


etherNumberOfPorts OBJECT-TYPE
  SYNTAX        Unsigned32(0..400)
  MAX-ACCESS    read-only
  STATUS        current
  DESCRIPTION
    "Number of Ports on the Ethernet interface"
  ::= { ethernetlikeInterfaceEntry 5}

etherLinePower OBJECT-TYPE
  SYNTAX        LPT
  MAX-ACCESS    read-only
  STATUS        current
  DESCRIPTION
    "Line Power Type on this Ethernet Interface"
  ::= { ethernetlikeInterfaceEntry 6}

etherPowerPairs OBJECT-TYPE
  SYNTAX        Integer32
  MAX-ACCESS    read-only
  STATUS        current
  DESCRIPTION
    "Number of line Pairs providing power on the Ethernet interface"
  ::= { ethernetlikeInterfaceEntry 7}


-- ****************************************************************************
--
-- Temperature Sensor Table
--
numberOfTemperatureSensors OBJECT-TYPE
  SYNTAX        Unsigned32(0..20)
  MAX-ACCESS    read-only
  STATUS        current
  DESCRIPTION
    "Number of Temperature Sensors in the Unit "
  ::= { zhnSystemTempSensorObjects 1}

temperatureSensorTable OBJECT-TYPE
  SYNTAX        SEQUENCE OF TemperatureSensorEntry
  MAX-ACCESS    not-accessible
  STATUS        current
  DESCRIPTION
    "Table of Temperature Sensors: Name, Maximum, and Minimum values"
  ::= { zhnSystemTempSensorObjects 2}

temperatureSensorEntry OBJECT-TYPE
  SYNTAX        TemperatureSensorEntry
  MAX-ACCESS    not-accessible
  STATUS        current
  DESCRIPTION
    "Table of Temperature Sensors: Name, Maximum, and Minimum values"
  INDEX        { temperatureSensorIndex  }
  ::= { temperatureSensorTable 1}

TemperatureSensorEntry ::=
  SEQUENCE {
      temperatureSensorIndex      Unsigned32,
      temperatureSensorName       DisplayString,
      temperatureSensorMaximum    DisplayString,
      temperatureSensorMinimum    DisplayString
  }

temperatureSensorIndex OBJECT-TYPE
  SYNTAX        Unsigned32(0..20)
  MAX-ACCESS    not-accessible
  STATUS        current
  DESCRIPTION
    "Temperature Sensor Index (Zero relative)"
  ::= { temperatureSensorEntry 1}

temperatureSensorName OBJECT-TYPE
  SYNTAX        DisplayString
  MAX-ACCESS    read-only
  STATUS        current
  DESCRIPTION
    "Name of the ethernet Like Interface as created by the system"
  ::= { temperatureSensorEntry 2}

temperatureSensorMaximum OBJECT-TYPE
  SYNTAX        DisplayString
  MAX-ACCESS    read-only
  STATUS        current
  DESCRIPTION
    "Maximum Temperature Recorded "
  ::= { temperatureSensorEntry 3}

temperatureSensorMinimum OBJECT-TYPE
  SYNTAX        DisplayString
  MAX-ACCESS    read-only
  STATUS        current
  DESCRIPTION
    "Minimum Temperature Recorded "
  ::= { temperatureSensorEntry 4}

powerSupplyType OBJECT-TYPE
  SYNTAX        UPT
  MAX-ACCESS    read-only
  STATUS        current
  DESCRIPTION
    "Type of Power Supply that the unit is using"
  ::= { zhnSystemGeneralObjects 5}


-- ****************************************************************************
--
-- SNMP Commmunity Table
--
numberOfCommunities OBJECT-TYPE
   SYNTAX        Unsigned32(0..9999)
   MAX-ACCESS    read-only
   STATUS        current
   DESCRIPTION   "Number of SNMP Communities configured in the Unit"
   ::= {zhnSystemSNMPObjects 1 }

zhnCommunityTable OBJECT-TYPE
   SYNTAX        SEQUENCE OF ZhnCommunityTableEntry
   MAX-ACCESS    not-accessible
   STATUS        current
   DESCRIPTION   "This table is used to set the various configuration
                  parameters for a particular community."
    ::= { zhnSystemSNMPObjects 2 }

zhnCommunityTableEntry OBJECT-TYPE
   SYNTAX        ZhnCommunityTableEntry
   MAX-ACCESS    not-accessible
   STATUS        current
   DESCRIPTION   "This object corresponds to an entry in the community table."
--  INDEX         { IMPLIED communityName }
   INDEX         { communityName }
   ::= { zhnCommunityTable 1 }

ZhnCommunityTableEntry ::=
   SEQUENCE {
     communityName      DisplayString,
     communityType      INTEGER,
     communityRowStatus RowStatus
 }
 
communityName OBJECT-TYPE
   SYNTAX        DisplayString
   MAX-ACCESS    not-accessible
   STATUS        current
   DESCRIPTION   "This object corresponds to the SNMP community string."
 ::= { zhnCommunityTableEntry 1 }

communityType OBJECT-TYPE
   SYNTAX INTEGER {
     readOnly (1),
     readWrite (2)
   }
   MAX-ACCESS read-write
   STATUS current
   DESCRIPTION
     "The access type of the community string.
      The default value of this object should be 
      read-only(1)."
 ::= { zhnCommunityTableEntry 2 }

communityRowStatus OBJECT-TYPE
   SYNTAX RowStatus 
   MAX-ACCESS read-create
   STATUS current
   DESCRIPTION   "When written, this object can be used to createAndGo(4) or 
                  destroy(6) a row from the table. A rowStatus value
                  of notInService(2) will also destroy a row. RowStatus
                  values of active(1), notReady(3), and createAndWait(5)
                  are ignored."
   ::= { zhnCommunityTableEntry 3 }


-- ****************************************************************************
--
-- SNMP Trap Manager Table
--
--  Default trap community string object goes here --

numberOfTrapManagers OBJECT-TYPE
   SYNTAX        Unsigned32(0..9999)
   MAX-ACCESS    read-only
   STATUS        current
   DESCRIPTION   "Number of Trap Managers configured in the Unit"
   ::= {zhnSystemTrapObjects 1 }

zhnDefaultTrapCommunity OBJECT-TYPE
   SYNTAX        DisplayString
   MAX-ACCESS    read-write
   STATUS        current
   DESCRIPTION   "This object corresponds to the default trap community string.
                  The default trap community string will be used when a
                  community name is not configured for a particular trap manager."
   ::= {zhnSystemTrapObjects 2 }

zhnTrapTypeLinkUpDown OBJECT-TYPE
   SYNTAX INTEGER {
                  enable(1),
                  disable(2)
   }
   MAX-ACCESS    read-write
   STATUS        current
   DESCRIPTION   "Enable or disable all link up/down traps."
   ::= {zhnSystemTrapObjects 3 }

zhnTrapTypeAuthFailure OBJECT-TYPE
   SYNTAX INTEGER {
                  enable(1),
                  disable(2)
   }
   MAX-ACCESS    read-write
   STATUS        current
   DESCRIPTION   "Enable or disable the generation of authorization failure traps."
   ::= {zhnSystemTrapObjects 4 }
 
zhnTrapTypeConfigChange OBJECT-TYPE
   SYNTAX INTEGER {
                  enable(1),
                  disable(2)
   }
   MAX-ACCESS    read-write
   STATUS        current
   DESCRIPTION   "Enable or disable the generation of configuration change traps.
                  This object is not supported by ZNID devices. Rather, the only
                  mechanism to disable the generation of configuration change 
                  traps in a ZNID device is to disable the generation of all
                  enterprise traps via the zhnTrapTypeEnterpise object."
   ::= {zhnSystemTrapObjects 5 }
 
zhnTrapManagerInfoTable OBJECT-TYPE
   SYNTAX        SEQUENCE OF ZhnTrapManagerInfoTableEntry
   MAX-ACCESS    not-accessible
   STATUS        current
   DESCRIPTION   "This table is used to set the trap destination address
                  for a particular community."
   ::= {zhnSystemTrapObjects 6 }
 
zhnTrapManagerInfoTableEntry OBJECT-TYPE
   SYNTAX        ZhnTrapManagerInfoTableEntry
   MAX-ACCESS    not-accessible
   STATUS        current
   DESCRIPTION   "This object corresponds to an entry in the community
                  trap address info table."
--   INDEX        { IMPLIED trapDestination }
   INDEX        { trapDestination }
   ::= { zhnTrapManagerInfoTable 1 }
 
ZhnTrapManagerInfoTableEntry ::=
   SEQUENCE {
     trapDestination   IpAddress,
     trapCommunityName DisplayString,
     trapVersion       INTEGER,
     trapPort          INTEGER,
     trapRowStatus     RowStatus
 }
 
trapDestination OBJECT-TYPE
   SYNTAX        IpAddress
   MAX-ACCESS    not-accessible
   STATUS        current
   DESCRIPTION   "The IP Address of the destination to which a trap
      		  must be sent."
   ::= { zhnTrapManagerInfoTableEntry 1 }
 
trapCommunityName OBJECT-TYPE
   SYNTAX        DisplayString
   MAX-ACCESS    read-write
   STATUS        current
   DESCRIPTION   "This object corresponds to the trap community string.
                  If not specified, the trapCommunityName will be set
                  to the zhnDefaultTrapCommunity object."
   ::= { zhnTrapManagerInfoTableEntry 2 }
    
trapVersion OBJECT-TYPE
   SYNTAX INTEGER {
                  v1(1),    -- SNMP V1 Traps
                  v2c(2)    -- SNMP V2 Traps and Notifications
   }
   MAX-ACCESS    read-write
   STATUS        current
   DESCRIPTION   "The trap types automatically supported by net-snmp
                  and enabled/disabled in snmpd.conf. If not specified, 
                  the trapVersion will be set the default value of v2c."
   ::= { zhnTrapManagerInfoTableEntry 3 }

trapPort OBJECT-TYPE
   SYNTAX        INTEGER (1..65536)
   MAX-ACCESS    read-write
   STATUS        current
   DESCRIPTION   "The udp/tcp port number to which a trap must be sent.
                  If not specified, the trapPort will be set
                  the default value of 162."
   ::= { zhnTrapManagerInfoTableEntry 4 }
 
trapRowStatus OBJECT-TYPE
   SYNTAX        RowStatus 
   MAX-ACCESS    read-create
   STATUS        current
   DESCRIPTION   "When written, this object can be used to createAndGo(4) or 
                  destroy(6) a row from the table. A rowStatus value
                  of notInService(2) will also destroy a row. RowStatus
                  values of active(1), notReady(3), and createAndWait(5)
                  are ignored."
   ::= { zhnTrapManagerInfoTableEntry 5 }

zhnTrapTypeColdStart OBJECT-TYPE
   SYNTAX INTEGER {
                  enable(1),
                  disable(2)
   }
   MAX-ACCESS    read-write
   STATUS        current
   DESCRIPTION   "Enable or disable the generation of coldstart traps.
                  A coldstart trap is generated each time the device
                  is restarted."
   ::= {zhnSystemTrapObjects 7 }
 
zhnTrapTypeWarmStart OBJECT-TYPE
   SYNTAX INTEGER {
                  enable(1),
                  disable(2)
   }
   MAX-ACCESS    read-write
   STATUS        current
   DESCRIPTION   "Enable or disable the generation of warmstart traps.
                  A warmstart trap is generated each time the device's
                  SNMP agent is restarted."
   ::= {zhnSystemTrapObjects 8 }
 
zhnTrapTypeEnterprise OBJECT-TYPE
   SYNTAX INTEGER {
                  enable(1),
                  disable(2)
   }
   MAX-ACCESS    read-write
   STATUS        current
   DESCRIPTION   "Enable or disable the generation of all enterprise traps."
   ::= {zhnSystemTrapObjects 9 }
 

-- ****************************************************************************
--
-- SNMP Fixed Commmunity Table
--
-- This table should be used for CPEs that support only two community
-- strings (i.e. a read-only and a read-write community).
--

zhnFixedCommunityTable OBJECT-TYPE
   SYNTAX        SEQUENCE OF ZhnFixedCommunityTableEntry
   MAX-ACCESS    not-accessible
   STATUS        current
   DESCRIPTION   "This table is used to configure a read-only and a
                  read-write community."
    ::= { zhnSystemSNMPObjects 3 }

zhnFixedCommunityTableEntry OBJECT-TYPE
   SYNTAX        ZhnFixedCommunityTableEntry
   MAX-ACCESS    not-accessible
   STATUS        current
   DESCRIPTION   "This object corresponds to an entry in the fixed community table."
--  INDEX         { IMPLIED communityType }
   INDEX         { communityType }
   ::= { zhnFixedCommunityTable 1 }

ZhnFixedCommunityTableEntry ::=
   SEQUENCE {
     fixedCommunityName      DisplayString,
     fixedCommunityType      INTEGER,
     fixedCommunityRowStatus RowStatus
 }
 
fixedCommunityName OBJECT-TYPE
   SYNTAX        DisplayString
   MAX-ACCESS    read-create
   STATUS        current
   DESCRIPTION   "This object corresponds to the SNMP community string."
 ::= { zhnFixedCommunityTableEntry 1 }

fixedCommunityType OBJECT-TYPE
   SYNTAX INTEGER {
     readOnly (1),
     readWrite (2)
   }
   MAX-ACCESS read-create 
   STATUS current
   DESCRIPTION
     "The access type of the community string.
      The default value of this object should be 
      read-only(1)."
 ::= { zhnFixedCommunityTableEntry 2 }

fixedCommunityRowStatus OBJECT-TYPE
   SYNTAX RowStatus 
   MAX-ACCESS read-create
   STATUS current
   DESCRIPTION   "When written, this object is ignored. When read, a
                  value of active(1) or notReady(3) will be returned."
   ::= { zhnFixedCommunityTableEntry 3 }


-- ****************************************************************************
--
-- System Log Scalar Objects
--
sysLogAdminStatus OBJECT-TYPE
  SYNTAX     SysAdminStatus
  MAX-ACCESS read-write
  STATUS     current
  DESCRIPTION
     "Enable or disable the Syslog service."
  ::= { zhnSystemSyslogObjects 1 }

sysLogLocalLogLevel OBJECT-TYPE
  SYNTAX     SysLogLevel
  MAX-ACCESS read-write
  STATUS     current
  DESCRIPTION   
     "SysLog local log level options, per RFC 3164. All
      logged events with a severity at or greater than this
      level will be logged to the local log file. Note, the
      local log file is not persistent across system reboots."
  ::= { zhnSystemSyslogObjects 2 }

sysLogRemoteLogLevel OBJECT-TYPE
  SYNTAX     SysLogLevel
  MAX-ACCESS read-write
  STATUS     current
  DESCRIPTION   
     "SysLog remote log level options, per RFC 3164. All
      logged events with a severity at or greater that this
      level will be sent to a remote Syslog server if the
      remote server address is configured and a route exists
      to the remote server."
  ::= { zhnSystemSyslogObjects 3 }

sysLogDisplayLogLevel OBJECT-TYPE
  SYNTAX     SysLogLevel
  MAX-ACCESS read-write
  STATUS     current
  DESCRIPTION   
     "SysLog log level options, per RFC 3164 for the display
      of log messages via a web browser. All logged events with 
      a severity level at or greater than this level will be 
      displayed."
  ::= { zhnSystemSyslogObjects 4 }

sysLogMode OBJECT-TYPE
  SYNTAX     SysLogMode
  MAX-ACCESS read-write
  STATUS     current
  DESCRIPTION   
     "SysLog logging mode of operation: 
         local(1),   -- Log messages only to the local, non-persistent log file
         remote(2),  -- Log messages only to a remote syslog server
         both(3),    -- Log messages to both a local log file and a remote syslog server
     "
  ::= { zhnSystemSyslogObjects 5 }

sysLogRemoteServerAddress OBJECT-TYPE
  SYNTAX     IpAddress
  MAX-ACCESS read-write
  STATUS     current
  DESCRIPTION   
     "The IP address of the remote syslog server."
  ::= { zhnSystemSyslogObjects 6 }

sysLogRemoteServerPort OBJECT-TYPE
  SYNTAX     Unsigned32 (1..65535)
  MAX-ACCESS read-write
  STATUS     current
  DESCRIPTION   
     "The UDP port to use to transfer syslog messages to the remote syslog server."
  ::= { zhnSystemSyslogObjects 7 }


-- ****************************************************************************
--
-- SNTP Server Scalar Objects
--
sntpAdminStatus OBJECT-TYPE
  SYNTAX     SysAdminStatus
  MAX-ACCESS read-write
  STATUS     current
  DESCRIPTION
     "Enable or disable the SNTP client."
  ::= { zhnSystemSNTPObjects 1 }

sntpOperStatus OBJECT-TYPE
  SYNTAX     SysAdminStatus
  MAX-ACCESS read-write
  STATUS     current
  DESCRIPTION
     "Current operational status of the SNTP client."
  ::= { zhnSystemSNTPObjects 2 }

sntpServer1 OBJECT-TYPE
  SYNTAX     OCTET STRING (SIZE (0..64))
  MAX-ACCESS read-write
  STATUS     current
  DESCRIPTION
     "The domain name or IP address of the first SNTP server with which to 
      synchronize the system time."
  ::= { zhnSystemSNTPObjects 3 }

sntpServer2 OBJECT-TYPE
  SYNTAX     OCTET STRING (SIZE (0..64))
  MAX-ACCESS read-write
  STATUS     current
  DESCRIPTION
     "The domain name or IP address of the second SNTP server with which to 
      synchronize the system time."
  ::= { zhnSystemSNTPObjects 4 }

sntpServer3 OBJECT-TYPE
  SYNTAX     OCTET STRING (SIZE (0..64))
  MAX-ACCESS read-write
  STATUS     current
  DESCRIPTION
     "The domain name or IP address of the third SNTP server with which to 
      synchronize the system time."
  ::= { zhnSystemSNTPObjects 5 }

sntpServer4 OBJECT-TYPE
  SYNTAX     OCTET STRING (SIZE (0..64))
  MAX-ACCESS read-write
  STATUS     current
  DESCRIPTION
     "The domain name or IP address of the fourth SNTP server with which to 
      synchronize the system time."
  ::= { zhnSystemSNTPObjects 6 }

sntpServer5 OBJECT-TYPE
  SYNTAX     OCTET STRING (SIZE (0..64))
  MAX-ACCESS read-write
  STATUS     current
  DESCRIPTION
     "The domain name or IP address of the fifth SNTP server with which to 
      synchronize the system time."
  ::= { zhnSystemSNTPObjects 7 }

sntpLocalTimeZone OBJECT-TYPE
  SYNTAX     SysSntpTimeZones
  MAX-ACCESS read-write
  STATUS     current
  DESCRIPTION
     "Indicates the local time zone."
  ::= { zhnSystemSNTPObjects 8 }

sntpCurrentDateAndTime OBJECT-TYPE
  SYNTAX     DisplayString
  MAX-ACCESS read-write
  STATUS     current
  DESCRIPTION
     "Indicates the current date and time."
  ::= { zhnSystemSNTPObjects 9 }


-- ****************************************************************************
--
-- System User Login Objects
--
adminUserName OBJECT-TYPE
  SYNTAX OCTET STRING (SIZE (0..16))
  MAX-ACCESS read-only 
  STATUS current
  DESCRIPTION       
     "The username required to login as the system administrator.
      This user has unrestricted access to change and view all 
      configuration, status and test parameters. "
  ::= { zhnSystemUserLoginObjects 1 }

adminPassword OBJECT-TYPE
  SYNTAX OCTET STRING (SIZE (0..16))
  MAX-ACCESS read-write 
  STATUS current
  DESCRIPTION       
     "The password required to login as the system administrator. This
      field cannot contain a SPACE and is returned as a string of asterisks."
  ::= { zhnSystemUserLoginObjects 2 }

supportUserName OBJECT-TYPE
  SYNTAX OCTET STRING (SIZE (0..16))
  MAX-ACCESS read-only 
  STATUS current
  DESCRIPTION       
     "The username required to login to support the system.
      This user has access to system parameters required to
      maintain the system and run diagnostic tests."
  ::= { zhnSystemUserLoginObjects 3 }

supportPassword OBJECT-TYPE
  SYNTAX OCTET STRING (SIZE (0..16))
  MAX-ACCESS read-write 
  STATUS current
  DESCRIPTION       
     "The password required to login to support the system. This
      field cannot contain a SPACE and is returned as a string of asterisks."
  ::= { zhnSystemUserLoginObjects 4 }

userUserName OBJECT-TYPE
  SYNTAX OCTET STRING (SIZE (0..16))
  MAX-ACCESS read-only 
  STATUS current
  DESCRIPTION       
     "The username required to login as a general user of the system.
      This user can view configuration settings and statistics, as 
      well as, update the system's software."
  ::= { zhnSystemUserLoginObjects 5 }

userPassword OBJECT-TYPE
  SYNTAX OCTET STRING (SIZE (0..16))
  MAX-ACCESS read-write 
  STATUS current
  DESCRIPTION       
     "The password required to login as a general user of the system.
      field cannot contain a SPACE and is returned as a string of asterisks."
  ::= { zhnSystemUserLoginObjects 6 }


-- ****************************************************************************
--
-- Power Shedding Feature Scalar Objects
--
powerSheddingAdminStatus OBJECT-TYPE
  SYNTAX        SysAdminStatus
  MAX-ACCESS    read-only
  STATUS        current
  DESCRIPTION
  "Configuration of parameters for the power-shedding feature.
   The power-shedding objects are only supported by systems that 
   include on-board power-management circuitry. When the system 
   detects that it is running on battery power, it has the option 
   to shut down all support (excluding the voice over IP telephone 
   service).The power-shedding administrative state will enable 
   or disable the power-shedding feature."
  ::= { zhnSystemPowerSheddingObjects 1 }

powerSheddingShutdownDelay OBJECT-TYPE
  SYNTAX        Unsigned32(1..60)
  MAX-ACCESS    read-only
  STATUS        current
  DESCRIPTION
  "The shutdown delay is the time delay, in minutes, after AC power is 
   lost, before shutting down non-voice services."
  ::= { zhnSystemPowerSheddingObjects 2}

powerSheddingRestoreDelay OBJECT-TYPE
  SYNTAX        Unsigned32(0..10)
  MAX-ACCESS    read-only
  STATUS        current
  DESCRIPTION
  "The restore delay is the time delay, in minutes, after AC power is 
   restored before switching on the services that were shut down due 
   to the power loss."
  ::= { zhnSystemPowerSheddingObjects 3}


-- ****************************************************************************
--
-- System Global Firewall Scalar Objects
--
sysFirewallEnable OBJECT-TYPE
  SYNTAX        TruthValue
  MAX-ACCESS    read-write
  STATUS        current
  DESCRIPTION
  "Enables or disables the firewall feature for the entire system."
  ::= { zhnSystemFirewallObjects 1 }

sysFirewallTcpSynCookies OBJECT-TYPE
  SYNTAX        TruthValue
  MAX-ACCESS    read-only
  STATUS        current
  DESCRIPTION
  "Enables or disables the TCP SYNCookie protection against SYN flooding
   denial-of-service attack." 
  ::= { zhnSystemFirewallObjects 2}

-- ****************************************************************************
--
-- System Global Domain Name Server (DNS) Client Scalar Objects
--
sysDNSAddressingType OBJECT-TYPE
  SYNTAX        IPInterfaceAddressingTypeValues
  MAX-ACCESS    read-write
  STATUS        current
  DESCRIPTION
  "Type of IP interface addressing method used to reach the DNS."
  ::= { zhnSystemDNSClientObjects 1 }

sysDNSDHCPSource OBJECT-TYPE
  SYNTAX        OCTET STRING (SIZE (0..16))
  MAX-ACCESS    read-write
  STATUS        current
  DESCRIPTION
  "Name of the interface used by the DHCP Client to obtain DNS information."
  ::= { zhnSystemDNSClientObjects 2 }

sysDNSPrimaryIPAddress OBJECT-TYPE
  SYNTAX        IpAddress
  MAX-ACCESS    read-write
  STATUS        current
  DESCRIPTION
  "Primary Address of DNS when the addressing type is set to Static."
  ::= { zhnSystemDNSClientObjects 3 }

sysDNSSecondaryIPAddress OBJECT-TYPE
  SYNTAX        IpAddress
  MAX-ACCESS    read-write
  STATUS        current
  DESCRIPTION
  "Secondary Address of DNS when the addressing type is set to Static."
  ::= { zhnSystemDNSClientObjects 4 }


-- ****************************************************************************
--
-- System Global Domain Name Server (DNS) Proxy Scalar and Tabular Objects
--
zhnDnsProxyHostMaxHostEntries OBJECT-TYPE
  SYNTAX        Unsigned32(0..24)
  MAX-ACCESS    read-write
  STATUS        current
  DESCRIPTION
     "The maximum number of host entries in the DnsProxyHostObjectTable."
  ::= { zhnSystemDNSProxyObjects 1 }

zhnDnsProxyHostTable OBJECT-TYPE
   SYNTAX        SEQUENCE OF ZhnDnsProxyHostEntry
   MAX-ACCESS    not-accessible
   STATUS        current
   DESCRIPTION   
      "This table is used to configure a DNS Proxy Host entry." 
    ::= { zhnSystemDNSProxyObjects 2 }

zhnDnsProxyHostEntry OBJECT-TYPE
   SYNTAX        ZhnDnsProxyHostEntry
   MAX-ACCESS    not-accessible
   STATUS        current
   DESCRIPTION   
      "This object corresponds to an entry in the DNS Proxy Host
       table."
   INDEX         { dnsProxyHostIndex }
   ::= { zhnDnsProxyHostTable 1 }

ZhnDnsProxyHostEntry ::=
   SEQUENCE {
     dnsProxyHostIndex          Unsigned32,
     dnsProxyHostIPAddress      IpAddress,
     dnsProxyHostName           OCTET STRING,
     dnsProxyRowStatus          ZhoneRowStatus
 }
 
dnsProxyHostIndex OBJECT-TYPE
  SYNTAX        Unsigned32(1..24)
  MAX-ACCESS    not-accessible
  STATUS        current
  DESCRIPTION   
     "Index into the DNS Proxy Host table"
  ::= { zhnDnsProxyHostEntry 1}

dnsProxyHostIPAddress OBJECT-TYPE
   SYNTAX        IpAddress
   MAX-ACCESS    read-write
   STATUS        current
   DESCRIPTION   
      "The local proxy host IP address."
   ::= { zhnDnsProxyHostEntry 2 }
 
dnsProxyHostName OBJECT-TYPE
   SYNTAX        OCTET STRING
   MAX-ACCESS    read-write
   STATUS        current
   DESCRIPTION   
      "The domain name assigned to the host IP address."
   ::= { zhnDnsProxyHostEntry 3 }

dnsProxyRowStatus OBJECT-TYPE
   SYNTAX        ZhoneRowStatus
   MAX-ACCESS    read-create
   STATUS        current
   DESCRIPTION   
      "Create or destroy a DNS Proxy Host. Upon creation,
       the dnsProxyHostIPAddress must be provided." 
   ::= { zhnDnsProxyHostEntry 4 }



-- ****************************************************************************
--
-- WAN Backup Scalar Objects
--
failoverTimer OBJECT-TYPE
  SYNTAX        Unsigned32
  MAX-ACCESS    read-write
  STATUS        current
  DESCRIPTION
     "The WAN Failover Timer is used to determine how long (in seconds)
      the Fiber uplink interface must be operationally DOWN before a
      USB Cellular WAN Backup connection will be initiated. The Default 
      value is 0 seconds, which DISABLES this feature. The recommended 
      value to enable this feature is 60 seconds."
  ::= { zhnSystemWanBackupObjects 1 }

restoralTimer OBJECT-TYPE
  SYNTAX        Unsigned32
  MAX-ACCESS    read-write
  STATUS        current
  DESCRIPTION
     "The WAN Restoral Timer is used to determine how long (in seconds)
      the Fiber uplink interface must remain in an operational UP condition
      before the Cellular Backup connection will be terminated and the 
      traffic that was being forwarded out the USB interface is forwarded 
      to the 5xx GEM instead.  The default value is 60 seconds."
  ::= { zhnSystemWanBackupObjects 2 }

backupDataVlan OBJECT-TYPE
  SYNTAX        Unsigned32(0..4096)
  MAX-ACCESS    read-write
  STATUS        current
  DESCRIPTION
  "This is the Internet Access VLAN (GEM 5xx), which is the only service
   that can be backed up using the USB Cellular modem."
  ::= { zhnSystemWanBackupObjects 3}

cellularPinNumber OBJECT-TYPE
  SYNTAX        OCTET STRING (SIZE (0..4))
  MAX-ACCESS    read-write
  STATUS        current
  DESCRIPTION
  "A 4 digit PIN code used to unlock the SIM card. For GPRS/UMTS networks,
   *99# is typically used.  For CDMA/EVDO networks, #777 is typically used."
  ::= { zhnSystemWanBackupObjects 4}

cellularDataNumber OBJECT-TYPE
  SYNTAX        OCTET STRING (SIZE (0..32))
  MAX-ACCESS    read-write
  STATUS        current
  DESCRIPTION
  "This is the number that the USB modem will dial to establish a cellular
   a cellular data connection. For GPRS/UMTS networks, *99# is typically used.
   For CDMA/EVDO networks, #777 is typically used."
  ::= { zhnSystemWanBackupObjects 5}

atInitCommands OBJECT-TYPE
  SYNTAX        OCTET STRING (SIZE (0..256))
  MAX-ACCESS    read-write
  STATUS        current
  DESCRIPTION
  "AT initialization command strings, if needed." 
  ::= { zhnSystemWanBackupObjects 6}

accessPointName OBJECT-TYPE
  SYNTAX        OCTET STRING (SIZE (0..32))
  MAX-ACCESS    read-write
  STATUS        current
  DESCRIPTION
  "The Access Point Name (APN) for connections to the GPRS/UMTS network.
   This should be provided by the ISP. In North America, 3G cellular carriers
   do not require an APN."
  ::= { zhnSystemWanBackupObjects 7}

chapPapUsername OBJECT-TYPE
  SYNTAX        OCTET STRING (SIZE (0..32))
  MAX-ACCESS    read-write
  STATUS        current
  DESCRIPTION
  "Required for CHAP or PAP authentication. This configuration item should
   be left blank if CHAP or PAP is not used."
  ::= { zhnSystemWanBackupObjects 8}

chapPapPassword OBJECT-TYPE
  SYNTAX        OCTET STRING (SIZE (0..32))
  MAX-ACCESS    read-write
  STATUS        current
  DESCRIPTION
  "Required for CHAP or PAP authentication. This configuration item should
   be left blank if CHAP or PAP is not used."
  ::= { zhnSystemWanBackupObjects 9}

connectionTimeout OBJECT-TYPE
  SYNTAX        Unsigned32
  MAX-ACCESS    read-write
  STATUS        current
  DESCRIPTION
  "Specifies the duration of inactivity in seconds before the cellular data 
   call will automatically terminate. A new call will be initiated automatically
   when a packet must be sent upstream on the designated VLAN if the WAN uplink
   is still Operationally Down. A value of 0 will DISABLE the Connection Timeout 
   feature."
  ::= { zhnSystemWanBackupObjects 10}

backupIpAddressMode OBJECT-TYPE
  SYNTAX        BasicAddressingTypeValues
  MAX-ACCESS    read-write
  STATUS        current
  DESCRIPTION
  "The WAN IP Address, Default Gateway IP Address, Subnet Mask and DNS Server 
   IP Address must all be defined for the USB Cellular Backup connection. When
   IP Address Mode is set to DHCP, a DHCP Request will be sent upstream after
   the Cellular Data Connection has been established to acquire this information
   dynamically. When the WAN Backup IP Addess Mode is set to Static, this 
   information ust be statically configured."
  ::= { zhnSystemWanBackupObjects 11}

backupIpAddress OBJECT-TYPE
  SYNTAX        IpAddress
  MAX-ACCESS    read-write
  STATUS        current
  DESCRIPTION
  "The IP Address to be used on the WAN uplink interface of a Cellular Backhaul
   connection.  This parameter is acquired dynamically in DHCP mode and only
   configurable if the BackupIpAddressMode is Static."
  ::= { zhnSystemWanBackupObjects 12}

backupDefaultGateway OBJECT-TYPE
  SYNTAX        IpAddress
  MAX-ACCESS    read-write
  STATUS        current
  DESCRIPTION
  "The IP Address of the Default Gateway to be used on the WAN uplink interface 
   of a Cellular Backhaul connection.  This parameter is acquired dynamically in 
   DHCP mode and only configurable if the BackupIpAddressMode is Static."
  ::= { zhnSystemWanBackupObjects 13}

backupSubnetMask OBJECT-TYPE
  SYNTAX        IpAddress
  MAX-ACCESS    read-write
  STATUS        current
  DESCRIPTION
  "The Subnet Mask to be used on the WAN uplink interface of a Cellular Backhaul
   connection.  This parameter is acquired dynamically in DHCP mode and only
   configurable if the BackupIpAddressMode is Static."
  ::= { zhnSystemWanBackupObjects 14}

backupPrimaryDns OBJECT-TYPE
  SYNTAX        IpAddress
  MAX-ACCESS    read-write
  STATUS        current
  DESCRIPTION
  "The IP Address of the Primary DNS Server to be used on the WAN uplink interface 
   of a Cellular Backhaul connection.  This parameter is acquired dynamically in 
   DHCP mode and only configurable if the BackupIpAddressMode is Static."
  ::= { zhnSystemWanBackupObjects 15}

backupSecondaryDns OBJECT-TYPE
  SYNTAX        IpAddress
  MAX-ACCESS    read-write
  STATUS        current
  DESCRIPTION
  "The IP Address of the Secondary DNS Server to be used on the WAN uplink interface 
   of a Cellular Backhaul connection.  This parameter is acquired dynamically in 
   DHCP mode and only configurable if the BackupIpAddressMode is Static."
  ::= { zhnSystemWanBackupObjects 16}


-- ****************************************************************************
--
-- TR69 Client Scalar Objects
--
sysTr69cConfigObjects OBJECT IDENTIFIER ::= { zhnSystemTr69cObjects 1 }
sysTr69cServerObjects OBJECT IDENTIFIER ::= { zhnSystemTr69cObjects 2 }


sysTr69cConfigLoggingSOAP OBJECT-TYPE
  SYNTAX        TruthValue
  MAX-ACCESS    read-write
  STATUS        current
  DESCRIPTION
      "Enable or disable showing SOAP messages on serial console and local 
       TR69 Client log file."
  ::= { sysTr69cConfigObjects 1 }

sysTr69cConfigConnectionRequestAuthentication OBJECT-TYPE
  SYNTAX        TruthValue
  MAX-ACCESS    read-write
  STATUS        current
  DESCRIPTION
      "Enable or disable connection request authentication."
  ::= { sysTr69cConfigObjects 2 }

sysTr69cServerURL OBJECT-TYPE
  SYNTAX        OCTET STRING (SIZE (0..256))
  MAX-ACCESS    read-write
  STATUS        current
  DESCRIPTION
      "URL for the CPE to connect to the ACS using the CPE WAN Management 
       Protocol. This parameter MUST be in the form of a valid HTTP or HTTPS 
       URL. The host portion of this URL is used by the CPE for server-side 
       certificate authentication when using SSL or TLS."
  ::= { sysTr69cServerObjects 1 }

sysTr69cServerLastConnectedURL OBJECT-TYPE
  SYNTAX        OCTET STRING (SIZE (0..256))
  MAX-ACCESS    read-only
  STATUS        current
  DESCRIPTION
     "This value records the last URL which connected successfully to 
      the TR69 client."
  ::= { sysTr69cServerObjects 2 }

sysTr69cServerUsername OBJECT-TYPE
  SYNTAX        OCTET STRING (SIZE (0..256))
  MAX-ACCESS    read-write
  STATUS        current
  DESCRIPTION
     "Username used to authenticate the CPE when making a connection to
      the ACS using the CPE WAN Management Protocol. This username is used
      only for HTTP-based authentication of the CPE."
  ::= { sysTr69cServerObjects 3 }

sysTr69cServerPassword OBJECT-TYPE
  SYNTAX        OCTET STRING (SIZE (0..256))
  MAX-ACCESS    read-write
  STATUS        current
  DESCRIPTION
     "Password used to authenticate the CPE when making a connection to
      the ACS using the CPE WAN Management Protocol. This username is used
      only for HTTP-based authentication of the CPE. When read by an ACS, 
      this parameter returns an empty string, regardless of the value."
  ::= { sysTr69cServerObjects 4 }

sysTr69cServerPeriodicInformEnable OBJECT-TYPE
  SYNTAX        TruthValue
  MAX-ACCESS    read-write
  STATUS        current
  DESCRIPTION
     "When set to TRUE, the CPE will periodically send CPE information to 
      the TR69 Server using the Inform method calls."
  ::= { sysTr69cServerObjects 5 }

sysTr69cServerPeriodicInformInterval OBJECT-TYPE
  SYNTAX        Unsigned32
  MAX-ACCESS    read-write
  STATUS        current
  DESCRIPTION
     "The duration in seconds of the interval for which the CPE MUST attempt to
      connect with the ACS and call the Inform method if PeriodicInform-Enable
      is true. "
  ::= { sysTr69cServerObjects 6 }

sysTr69cServerParameterKey OBJECT-TYPE
  SYNTAX        OCTET STRING (SIZE (0..32))
  MAX-ACCESS    read-only
  STATUS        current
  DESCRIPTION
     "ParameterKey provides the ACS a reliable and extensible means to track 
      changes made by the ACS. The value of ParameterKey MUST be equal to the
      value of the ParameterKey argument from  the most recent successful 
      SetParameterValues, AddObject, or DeleteObject method call from the ACS. 
      The CPE MUST set ParameterKey to the value specified in the corresponding 
      method arguments if and only if the method completes successfully and no 
      fault response is generated. If a method call does not complete successfully 
      implying that  the changes requested in the method did not take effect, 
      the value of ParameterKey MUST NOT be modified.  The CPE MUST only modify 
      the value of ParameterKey as a result of SetParameterValues, AddObject, 
      DeleteObject, or due to a factory reset. On factory reset, the value of 
      ParameterKey MUST be set to empty."
  ::= { sysTr69cServerObjects 7 }

sysTr69cServerBoundIfName OBJECT-TYPE
  SYNTAX        OCTET STRING (SIZE (0..32))
  MAX-ACCESS    read-write
  STATUS        current
  DESCRIPTION
     "Name of the WAN interface that the TR69 client should use when establishing
      communications with the ACS."
  ::= { sysTr69cServerObjects 8 }

sysTr69cServerConnectionRequestURL OBJECT-TYPE
  SYNTAX        OCTET STRING (SIZE (0..256))
  MAX-ACCESS    read-only
  STATUS        current
  DESCRIPTION
     "HTTP URL for an ACS to make a Connection Request notification to the CPE. 
      In the form: http://host:port/path. The host portion of the URL MAY be the
      IP address for the management interface of the CPE in lieu of a host
      name."
  ::= { sysTr69cServerObjects 9 }

sysTr69cServerConnectionRequestUsername OBJECT-TYPE
  SYNTAX        OCTET STRING (SIZE (0..256))
  MAX-ACCESS    read-write
  STATUS        current
  DESCRIPTION
     "Username used to authenticate an ACS making a Connection Request to the CPE."
  ::= { sysTr69cServerObjects 10 }

sysTr69cServerConnectionRequestPassword OBJECT-TYPE
  SYNTAX        OCTET STRING (SIZE (0..256))
  MAX-ACCESS    read-write
  STATUS        current
  DESCRIPTION
     "Password used to authenticate an ACS making a Connection Request to the CPE.
      When read by an ACS, this parameter returns an empty string, regardless of
      the actual value."
  ::= { sysTr69cServerObjects 11 }

sysTr69cServerUpgradesManaged OBJECT-TYPE
  SYNTAX        TruthValue
  MAX-ACCESS    read-write
  STATUS        current
  DESCRIPTION
     "Indicates whether or not the ACS will manage upgrades for the CPE. If
      true (1), the CPE SHOULD not use other means other than the ACS to seek 
      out available upgrades. If false (0), the CPE MAY use other means for 
      this purpose."
  ::= { sysTr69cServerObjects 12 }


-- ****************************************************************************
--
-- Conformance Information
--

zhnSystemConformance OBJECT IDENTIFIER ::= { zhnSystem 2 }

zhnSystemGroups OBJECT IDENTIFIER ::= { zhnSystemConformance 1}
zhnSystemCompliances OBJECT IDENTIFIER ::= { zhnSystemConformance 2}
 
--
-- Compliance Statements
--

zhnSystemCompliance  MODULE-COMPLIANCE
  STATUS        current
  DESCRIPTION
        "The Compliance statement for SNMP entities which
         manage the display of Zhone System Information"
  MODULE  -- this module
  MANDATORY-GROUPS {
         zhnSystemActiveGroup
  }
  GROUP    zhnSystemTablesItems
  DESCRIPTION " The table item should be filled in for any table
                with a value of 1 or more.  If the number of items
                for the table is zero, table will be skipped.
                However, when the number of item is one or more
                then all items in that table should be filled in
                that many times."

  GROUP    zhnSystemConfigItems
  DESCRIPTION "This group implements support for configurable system objects."

  OBJECT wifiNetworkType
  MIN-ACCESS read-only
  DESCRIPTION
        "Write access is not required"

  OBJECT numberOfEthernetLikeInterfaces
  MIN-ACCESS read-only
  DESCRIPTION
        "Write access is not required"

  GROUP    zhnSyslogConfigGroup
  DESCRIPTION "This group implements support for configurable system logging objects."

  GROUP    zhnSntpConfigGroup
  DESCRIPTION "This group implements support for configurable SNTP objects."

  GROUP    zhnUserLoginGroup
  DESCRIPTION "This group implements support for user access control objects."

  GROUP    zhnPowerSheddingGroup
  DESCRIPTION "This group implements support for configurable power-shedding objects."

  GROUP    zhnSystemFirewallGroup
  DESCRIPTION "This group implements support for configurable Firewall objects."

  GROUP    zhnSystemDNSClientGroup
  DESCRIPTION "This group implements support for configurable dns client objects."
 
  GROUP    zhnSystemDNSProxyHostGroup
  DESCRIPTION "This group implements support for configurable dns proxy objects."

  GROUP    zhnSystemWanBackupGroup
  DESCRIPTION "This group implements support for configurable WAN backup objects."
  ::= {zhnSystemCompliances 1}

--
-- Units of Conformance
--

zhnSystemActiveGroup OBJECT-GROUP
   OBJECTS {
       modelNumber,
       macBaseAddress,
       numberOfMacAddresses,
       numberOfBoards,
       numberOfPlds,
       numberOfRadios,
       wifiNetworkType,
       numberOfEthernetLikeInterfaces,
       numberOfTemperatureSensors,
       powerSupplyType,
       sysBootloaderVersion,
       sysFirmwareVersion,
       sysAltFirmwareVersion
   }
   STATUS current
   DESCRIPTION
      "A collection of System Information objects that are
       required for the device to be functional"
   ::= { zhnSystemGroups 1}

zhnSystemTablesItems OBJECT-GROUP
   OBJECTS {
       boardName,
       boardPartNumber,
       boardSerialNumber,
       boardRevision,
       pldName,
       pldVersion,
       etherName,    
       etherType,          
       etherSubtype,      
       etherNumberOfPorts,
       etherLinePower,   
       etherPowerPairs,      
       temperatureSensorName,
       temperatureSensorMaximum,
       temperatureSensorMinimum
   }
   STATUS current
   DESCRIPTION
      "The table items for the device that are filled in
       when the table is present"
   ::= { zhnSystemGroups 2}

zhnSystemConfigItems OBJECT-GROUP
   OBJECTS {
       locationLatitude,
       locationLongitude,
       zhnSystemAction,
       zhnSysLocation,
       zhnSysContact,
       sysTransmitClockSource,
       sysLocalTimingReference,
       sysSynchronizationMode,
       sysSynchronousEthernet,
       sysClockMode,
       sysCfgDBAction,
       sysSoftwareReboot,
       sysRestoreAltFirmwareVersion,
       sysSnmpProvisioningLock,
       sysSnmpProvisioningChange
   }
   STATUS current
   DESCRIPTION
      "The collection of configurable scalar system objects."
   ::= { zhnSystemGroups 3}

zhnSystemTrapItems OBJECT-GROUP
   OBJECTS {
     numberOfTrapManagers,
     zhnDefaultTrapCommunity,
     zhnTrapTypeLinkUpDown,
     zhnTrapTypeAuthFailure,
     zhnTrapTypeConfigChange,
     trapCommunityName,
     trapVersion,
     trapPort,
     trapRowStatus,
     zhnTrapTypeColdStart,
     zhnTrapTypeWarmStart,
     zhnTrapTypeEnterprise
   }
   STATUS current
   DESCRIPTION
      "The collection of SNMP trap objects."
   ::= { zhnSystemGroups 4}

zhnSystemCommunityItems OBJECT-GROUP
   OBJECTS {
     numberOfCommunities,
     communityType,
     communityRowStatus
   }
   STATUS current
   DESCRIPTION
      "The collection of SNMP community objects."
   ::= { zhnSystemGroups 5}

zhnSystemFixedCommunityItems OBJECT-GROUP
   OBJECTS {
     fixedCommunityName,
     fixedCommunityType,
     fixedCommunityRowStatus
   }
   STATUS current
   DESCRIPTION
      "The collection of pre-provisioned SNMP community objects."
   ::= { zhnSystemGroups 6}

zhnSystemClockingItems OBJECT-GROUP
   OBJECTS {
     sysSystemClockSource,
     sysEthernetTransmitClockSource,
     sysDs1ClockSourcePort
   }
   STATUS current
   DESCRIPTION
      "The collection of system-wide clocking parameters only 
       supported by ZNID devices."
   ::= { zhnSystemGroups 7}

zhnSyslogConfigGroup OBJECT-GROUP
   OBJECTS {
     sysLogAdminStatus,
     sysLogLocalLogLevel,
     sysLogRemoteLogLevel,
     sysLogDisplayLogLevel,
     sysLogMode,
     sysLogRemoteServerAddress,
     sysLogRemoteServerPort
   }
   STATUS current
   DESCRIPTION
      "The collection of system-wide logging parameters only 
       supported by ZNID devices."
   ::= { zhnSystemGroups 8}

zhnSntpConfigGroup OBJECT-GROUP
   OBJECTS {
     sntpAdminStatus,
     sntpOperStatus,
     sntpServer1,
     sntpServer2,
     sntpServer3,
     sntpServer4,
     sntpServer5,
     sntpLocalTimeZone,
     sntpCurrentDateAndTime
   }
   STATUS current
   DESCRIPTION
      "The collection of SNTP server parameters only 
       supported by ZNID devices."
   ::= { zhnSystemGroups 9}

zhnUserLoginGroup OBJECT-GROUP
   OBJECTS {
     adminUserName,
     adminPassword,
     supportUserName,
     supportPassword,
     userUserName,
     userPassword
   }
   STATUS current
   DESCRIPTION
      "The collection of User login parameters only 
       supported by ZNID devices."
   ::= { zhnSystemGroups 10}

zhnPowerSheddingGroup OBJECT-GROUP
   OBJECTS {
     powerSheddingAdminStatus,
     powerSheddingShutdownDelay,
     powerSheddingRestoreDelay
   }
   STATUS current
   DESCRIPTION
      "The collection of configurable power-shedding parameters only 
       supported by ZNID devices."
   ::= { zhnSystemGroups 11}

zhnSystemFirewallGroup OBJECT-GROUP
   OBJECTS {
     sysFirewallEnable,
     sysFirewallTcpSynCookies
   }
   STATUS current
   DESCRIPTION
      "The collection of system firewall parameters only supported by 
      ZNID devices."
   ::= { zhnSystemGroups 12}

zhnSystemDNSClientGroup OBJECT-GROUP
   OBJECTS {
     sysDNSAddressingType,
     sysDNSDHCPSource,
     sysDNSPrimaryIPAddress,
     sysDNSSecondaryIPAddress
   }
   STATUS current
   DESCRIPTION
      "The collection of system DNS Client parameters only supported by 
      ZNID devices."
   ::= { zhnSystemGroups 13}

zhnSystemDNSProxyHostGroup OBJECT-GROUP
   OBJECTS {
     zhnDnsProxyHostMaxHostEntries,
     dnsProxyHostIPAddress,
     dnsProxyHostName,
     dnsProxyRowStatus
   }
   STATUS current
   DESCRIPTION
      "The collection of system DNS Proxy Host parameters only supported by 
      ZNID devices."
   ::= { zhnSystemGroups 14}

zhnSystemWanBackupGroup OBJECT-GROUP
   OBJECTS {
     failoverTimer,
     restoralTimer,
     backupDataVlan,
     cellularPinNumber,
     cellularDataNumber,
     atInitCommands,
     accessPointName,
     chapPapUsername,
     chapPapPassword,
     connectionTimeout,
     backupIpAddressMode,
     backupIpAddress,
     backupDefaultGateway,
     backupSubnetMask,
     backupPrimaryDns,
     backupSecondaryDns
   }
   STATUS current
   DESCRIPTION
      "The collection of system WAN Backup parameters only supported by 
      ZNID devices."
   ::= { zhnSystemGroups 15}

zhnSystemTr69cGroup OBJECT-GROUP
   OBJECTS {
     sysTr69cConfigLoggingSOAP,
     sysTr69cConfigConnectionRequestAuthentication,
     sysTr69cServerURL,
     sysTr69cServerLastConnectedURL,
     sysTr69cServerUsername,
     sysTr69cServerPassword,
     sysTr69cServerPeriodicInformEnable,
     sysTr69cServerPeriodicInformInterval,
     sysTr69cServerParameterKey,
     sysTr69cServerBoundIfName,
     sysTr69cServerConnectionRequestURL,
     sysTr69cServerConnectionRequestUsername,
     sysTr69cServerConnectionRequestPassword,
     sysTr69cServerUpgradesManaged
   }
   STATUS current
   DESCRIPTION
      "The collection of system TR69 Client parameters only supported by 
      ZNID devices."
   ::= { zhnSystemGroups 16}

END
