--
-- comCes.mib
-- MIB generated by MG-SOFT Visual MIB Builder Version 3.0 Build 271
-- Wednesday, April 13, 2005 at 16:28:08
--

        ZHONE-COM-CES-MIB DEFINITIONS ::= BEGIN
 
                IMPORTS
                        atmfCESCbrIndex, atmfCESAtmIndex, atmfCESAtmVpi, atmfCESAtmVci, atmfCESCbrService, 
                        atmfCESCbrClockMode, atmfCESCas, atmfCESPartialFill, atmfCESBufMaxSize, atmfCESCdvRxT, 
                        atmfCESCellLossIntegrationPeriod, atmfCESConnType, atmfCESLocalAddr, atmfCESAdminStatus, atmfCESOperStatus, 
                        atmfCESConfRowStatus, atmfCESConfEntry 
                                FROM ATMF-CES                        
                        ifIndex                        
                                FROM IF-MIB                        
                        OBJECT-GROUP                        
                                FROM SNMPv2-CONF                        
                        IpAddress, Unsigned32, OBJECT-TYPE, MODULE-IDENTITY                        
                                FROM SNMPv2-SMI                        
                        zhoneCes, zhoneModules                        
                                FROM Zhone;
        
        
                comCesExtension MODULE-IDENTITY 
                        LAST-UPDATED "200508131230Z"		-- August 13, 2005 at 12:30 GMT
                        ORGANIZATION 
                                "Zhone Technologies, Inc."
                        CONTACT-INFO 
                                "  Postal: 
                                           Zhone Technologies, Inc.
                                           @ Zhone Way
                                           7001 Oakport Street
                                           Oakland, CA  94621
                                           USA
                                Toll-Free: +1 877-ZHONE20 (+1 877-946-6320)
                                      Tel: +1-510-777-7000
                                      Fax: +1-510-777-7001
                                   E-mail: support@zhone.com"
                        DESCRIPTION 
                                "This is the Zhone module identifier for the Zhone CES
                                MIB extension module."
                        REVISION "200504131204Z"		-- April 13, 2005 at 12:04 GMT
                        DESCRIPTION
                                "V01.00.01 - Add 4 new fields to
                                zhoneAtmfCesConfExt."
                        REVISION "200408161200Z"		-- August 16, 2004 at 12:00 GMT
                        DESCRIPTION
                                "V01.00.00 - Initial Release"
                        ::= { zhoneModules 108 }
-- To generate protection layer:
-- /vob/zhonetools/bin/pahrser.pl iftype.mib Zhone.mib Zhone-TC.mib
--    rfc2514.mib rfc2233.mib rfc2571.mib af-vtoa-0078_000.mib comCes.mib
-- 
-- To generate mib handlers:
-- /vob/EPILOGUE/binaries/emissary/solaris/mibcomp rfc2514.mib 
--    rfc1907.mib iftype.mib Zhone.mib Zhone-TC.mib rfc2233.mib
--    rfc2571.mib af-vtoa-0078_000.mib -stub -o comCesMibHdlr.c
--    comCes.mib
                
        
        
--
-- Node definitions
--
        
                -- 1.3.6.1.4.1.5504.4.10.1
                zhoneAtmfCESConfExtTable OBJECT-TYPE
                        SYNTAX SEQUENCE OF ZhoneAtmfCESConfExtEntry
                        MAX-ACCESS not-accessible
                        STATUS current
                        DESCRIPTION
                                "Zhone extension table for the atmfCesConfTable
                                defined in atmfCES."
                        ::= { zhoneCes 1 }
                
                -- 1.3.6.1.4.1.5504.4.10.1.1
                zhoneAtmfCESConfExtEntry OBJECT-TYPE
                        SYNTAX ZhoneAtmfCESConfExtEntry
                        MAX-ACCESS not-accessible
                        STATUS current
                        DESCRIPTION
                                "Zhone extension entry for the atmfCesConfEntry
                                defined in atmfCES."
                        AUGMENTS { atmfCESConfEntry }
                        ::= { zhoneAtmfCESConfExtTable 1 }
                
                ZhoneAtmfCESConfExtEntry ::=
                        SEQUENCE { 
                                zhoneAtmfCESDs0Bundle
                                        BITS,
                                zhoneAtmfCESConfExtAtmfCESSrcIpAddr
                                        IpAddress,
                                zhoneAtmfCESConfExtAtmfCESDstIpAddr
                                        IpAddress,
                                zhoneAtmfCESConfExtAtmfCESSrcPort
                                        Unsigned32,
                                zhoneAtmfCESConfExtAtmfCESDstPort
                                        Unsigned32
                         }

-- 
                -- 1.3.6.1.4.1.5504.4.10.1.1.1
                zhoneAtmfCESDs0Bundle OBJECT-TYPE
                        SYNTAX BITS
                                {
                                ts0(0),
                                ts1(1),
                                ts2(2),
                                ts3(3),
                                ts4(4),
                                ts5(5),
                                ts6(6),
                                ts7(7),
                                ts8(8),
                                ts9(9),
                                ts10(10),
                                ts11(11),
                                ts12(12),
                                ts13(13),
                                ts14(14),
                                ts15(15),
                                ts16(16),
                                ts17(17),
                                ts18(18),
                                ts19(19),
                                ts20(20),
                                ts21(21),
                                ts22(22),
                                ts23(23),
                                ts24(24),
                                ts25(25),
                                ts26(26),
                                ts27(27),
                                ts28(28),
                                ts29(29),
                                ts30(30),
                                ts31(31)
                                }
                        MAX-ACCESS read-create
                        STATUS current
                        DESCRIPTION
                                "This value is a bit field indicating the ds0's in the
                                ds0 bundles.
                                "
                        ::= { zhoneAtmfCESConfExtEntry 1 }
                
                -- 1.3.6.1.4.1.5504.4.10.1.1.2
                zhoneAtmfCESConfExtAtmfCESSrcIpAddr OBJECT-TYPE
                        SYNTAX IpAddress
                        MAX-ACCESS read-create
                        STATUS current
                        DESCRIPTION
                                "The local IP address associated with the ces DS0 bundle,
                                which must have an associated floating IP adress configured
                                on the UPLINK."
                        ::= { zhoneAtmfCESConfExtEntry 2 }
                
                -- 1.3.6.1.4.1.5504.4.10.1.1.3
                zhoneAtmfCESConfExtAtmfCESDstIpAddr OBJECT-TYPE
                        SYNTAX IpAddress
                        MAX-ACCESS read-create
                        STATUS current
                        DESCRIPTION
                                "The far end IP address destination for the ces DS0 Bundle
                                The local UPLINK must know how to route to the far end
                                IP address."
                        ::= { zhoneAtmfCESConfExtEntry 3 }
                
                -- 1.3.6.1.4.1.5504.4.10.1.1.4
                zhoneAtmfCESConfExtAtmfCESSrcPort OBJECT-TYPE
                        SYNTAX Unsigned32
                        MAX-ACCESS read-create
                        STATUS current
                        DESCRIPTION
                                "The local UDP port associated with the ces DS0 Bundle."
                        ::= { zhoneAtmfCESConfExtEntry 4 }
                
                -- 1.3.6.1.4.1.5504.4.10.1.1.5
                zhoneAtmfCESConfExtAtmfCESDstPort OBJECT-TYPE
                        SYNTAX Unsigned32
                        MAX-ACCESS read-create
                        STATUS current
                        DESCRIPTION
                                "The far end UDP port destination for the CES DS0 Bundle."
                        ::= { zhoneAtmfCESConfExtEntry 5 }
                
                -- 1.3.6.1.4.1.5504.4.10.2
                zhoneAtmfCESGroup OBJECT-GROUP
                        OBJECTS { zhoneAtmfCESDs0Bundle }
                        STATUS current
                        DESCRIPTION 
                                "A collection of object from zhoneAtmfCESConfExtTable"
                        ::= { zhoneCes 2 }
                
        
        END

--
-- comCes.mib
--
