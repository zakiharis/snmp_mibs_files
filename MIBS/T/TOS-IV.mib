-- **********************************************************************
-- TOS-IV.mib
--
-- Topsec Enterprise Specific MIB: Structure of Management Information
--
-- Copyright (c) 1998-2008, Beijing Topsec Network Security Technology Co.,Ltd. 
-- All Rights Reserved
--
-- The contents of this document are subject to change without notice.
-- **********************************************************************
--
--  Change History:
--
--	Mar 14,2008 - Edit by tos lk 
--
--  Mar 14,2008 - splited from old mib TOSVI-new.mib
--
-- **********************************************************************

TOS-IV DEFINITIONS ::= BEGIN

	IMPORTS
	    MODULE-IDENTITY,NOTIFICATION-TYPE,OBJECT-TYPE,                                       
	    Integer32, Counter32, Opaque,Gauge,IpAddress   
	    FROM SNMPv2-SMI
	    
	    TEXTUAL-CONVENTION,DisplayString,DateAndTime
			FROM SNMPv2-TC
			
			tosMib
			FROM TOS-SMI;
			
	--start list TOS IV table information
	tosIvTable  MODULE-IDENTITY
		  LAST-UPDATED "08-03-14" 
	    ORGANIZATION "TOPSEC"
	    CONTACT-INFO
	            " Topsec Beijing
	              China
	              E-mail: support@topsec.com.cn "
			DESCRIPTION
		        	"The (conceptual) table containing TOS IV information."
		        		        	    
	    REVISION     "07-05-14" 
	    DESCRIPTION
	            "Initial version."
	
		  REVISION     "07-12-7" 
	    DESCRIPTION
	            "split to 3 table"
	                        
	    REVISION    "20080314"
	    DESCRIPTION
	            "split the whole mib file into several part"

		::= { tosMib 12  }
		
		
		-- tos iv tunnel table
		
	tosIvTunTable OBJECT-TYPE
		SYNTAX		SEQUENCE OF TosIvTunEntry
		MAX-ACCESS	not-accessible
		STATUS			current
		DESCRIPTION
						"The (conceptiual) talbe containing TOS IV tunnel information."
		::= {	tosIvTable	1}

	tosIvTunEntry OBJECT-TYPE
		SYNTAX     TosIvTunEntry
		MAX-ACCESS not-accessible
		STATUS     current
		DESCRIPTION
		        "An entry (conceptual row) containing the information on IV."
		--INDEX      {  IVtunIndex }
		::= {  tosIvTunTable 1 }

	TosIvTunEntry ::= SEQUENCE {
		ivTunnelIndex       INTEGER,
		ivTunnelName				DisplayString,
		ivLocalInterface		DisplayString,		--? like eth0
		ivLocalProtectNet		IpAddress,
		ivLocalNetMask			IpAddress,
		ivRemoteDomainName	DisplayString,
		ivRemoteIpAddr			IpAddress,
		ivRemoteProtectNet	IpAddress,
		ivRemoteNetMask			IpAddress,
		ivTunnelStatus   		DisplayString
	     }

	ivTunnelIndex OBJECT-TYPE
		SYNTAX      INTEGER 
		MAX-ACCESS  read-only
		STATUS      current
		DESCRIPTION
		        "The Index of the IV table ."
		::= { tosIvTunEntry 1 }

	ivTunnelName  OBJECT-TYPE
		SYNTAX      DisplayString
		MAX-ACCESS  read-only
		STATUS      current
		DESCRIPTION
		        "The Name of the IV tunnel ."
		::= { tosIvTunEntry 2 }

	ivLcoalInterface OBJECT-TYPE
		SYNTAX      DisplayString   
		MAX-ACCESS  read-only
		STATUS      current
		DESCRIPTION
		        "The Local Interface name "
		::= { tosIvTunEntry 3 }

	ivLocalProtectNet  OBJECT-TYPE
		SYNTAX      IpAddress   
		MAX-ACCESS  read-only
		STATUS      current
		DESCRIPTION
		        "The Local protected Net IP address."
		::= { tosIvTunEntry 4 }
		
	ivLocalNetMask  OBJECT-TYPE
		SYNTAX      IpAddress   
		MAX-ACCESS  read-only
		STATUS      current
		DESCRIPTION
		        "The Local Netmask IP address."
		::= { tosIvTunEntry 5 }


	ivRemoteDomainName OBJECT-TYPE
		SYNTAX      DisplayString   
		MAX-ACCESS  read-only
		STATUS      current
		DESCRIPTION
		        "The Remote gateway name."
		::= { tosIvTunEntry 6 }
		
	ivRemoteIpAddr OBJECT-TYPE
		SYNTAX      DisplayString   
		MAX-ACCESS  read-only
		STATUS      current
		DESCRIPTION
		        "The Remote gateway ip address."
		::= { tosIvTunEntry 7 }

	ivRemoteProtectNet  OBJECT-TYPE
		SYNTAX      IpAddress   
		MAX-ACCESS  read-only
		STATUS      current
		DESCRIPTION
		        "The Remote Net IP address."
		::= { tosIvTunEntry 8 }
		
	ivRemoteNetMask  OBJECT-TYPE
		SYNTAX      IpAddress   
		MAX-ACCESS  read-only
		STATUS      current
		DESCRIPTION
		        "The Remote Net IP mask."
		::= { tosIvTunEntry 9 }
		
	ivTunnelStatus  OBJECT-TYPE
		SYNTAX      DisplayString
		MAX-ACCESS  read-only
		STATUS      current
		DESCRIPTION
		        "The IV tunnel  status."
		::= { tosIvTunEntry 10 }
		
		-- tos iv VRC user table
		
	tosIvVrcTable OBJECT-TYPE
		SYNTAX		SEQUENCE OF TosIvVrcEntry
		MAX-ACCESS	not-accessible
		STATUS			current
		DESCRIPTION
						"The (conceptiual) talbe containing TOS IV VRC user information."
		::= {	tosIvTable	2}

	tosIvVrcEntry OBJECT-TYPE
		SYNTAX     TosIvVrcEntry
		MAX-ACCESS not-accessible
		STATUS     current
		DESCRIPTION
		        "An entry (conceptual row) containing the information on tos IV VRC."
		--INDEX      {  IVVrcIndex }
		::= {  tosIvVrcTable 1 }	
		
		TosIvVrcEntry ::= SEQUENCE {
		ivVrcIndex       INTEGER,
		ivVrcUserName				DisplayString,
		ivVrcTunnelStatus		DisplayString,
		ivVrcVirtualIpAddr	IpAddress,
		ivVrcConnectIpAddr	IpAddress,
		ivVrcLogTime     		DateAndTime
	     }
	     
	ivVrcIndex OBJECT-TYPE
		SYNTAX      INTEGER 
		MAX-ACCESS  read-only
		STATUS      current
		DESCRIPTION
		        "The Index of the IV VRC table ."
		::= { tosIvVrcEntry 1 }

	ivVrcUserName OBJECT-TYPE
		SYNTAX      DisplayString 
		MAX-ACCESS  read-only
		STATUS      current
		DESCRIPTION
		        "The VRC user's name ."
		::= { tosIvVrcEntry 2 }

	ivVrcTunnelStatus OBJECT-TYPE
		SYNTAX      DisplayString 
		MAX-ACCESS  read-only
		STATUS      current
		DESCRIPTION
		        " the VRC tunnel statu ."
		::= { tosIvVrcEntry 3 }
		
	ivVrcVirtualIpAddr OBJECT-TYPE
		SYNTAX      IpAddress 
		MAX-ACCESS  read-only
		STATUS      current
		DESCRIPTION
		        " The VRC virtual IP address"
		::= { tosIvVrcEntry 4 }
		
	ivVrcConnectIpAddr OBJECT-TYPE
		SYNTAX      IpAddress 
		MAX-ACCESS  read-only
		STATUS      current
		DESCRIPTION
		        "The connect ip address"
		::= { tosIvVrcEntry 5 }
		
	ivVrcLogTime OBJECT-TYPE
		SYNTAX      DateAndTime 
		MAX-ACCESS  read-only
		STATUS      current
		DESCRIPTION
		        "The time since log in"
		::= { tosIvVrcEntry 6 }
		

		-- tos iv info table
		
	tosIvInfoTable OBJECT-TYPE
		SYNTAX		SEQUENCE OF TosIvInfoEntry
		MAX-ACCESS	not-accessible
		STATUS			current
		DESCRIPTION
						"The (conceptiual) talbe containing TOS IV information."
		::= {	tosIvTable	3}

	tosIvInfoEntry OBJECT-TYPE
		SYNTAX     TosIvInfoEntry
		MAX-ACCESS not-accessible
		STATUS     current
		DESCRIPTION
		        "An entry (conceptual row) containing the information on tos IV VRC."
		--INDEX      {  IVInfoTunNum }
		::= {  tosIvInfoTable 1 }	
		
		TosIvInfoEntry ::= SEQUENCE {
		ivInfoTunnelNumber 	INTEGER,
		ivInfoOutPkts				Counter32,
		ivInfoOuntDrops			Counter32,
		ivInfoOutErrors			Counter32,		
		ivInfoOutoctets			Counter32,
		ivInfoInPkts				Counter32,
		ivInfoInDrops				Counter32,
		ivInfoInErrors			Counter32,
		ivInfoInOctets   		Counter32
	     }

	ivInfoTunnelNumber OBJECT-TYPE
		SYNTAX      INTEGER 
		MAX-ACCESS  read-only
		STATUS      current
		DESCRIPTION
		        "The tunnel number of the iv  ."
		::= { tosIvInfoEntry 1 }
		
	ivInfoOutPkts OBJECT-TYPE
		SYNTAX      Counter32 
		MAX-ACCESS  read-only
		STATUS      current
		DESCRIPTION
		        "The total tx packet of the whole iv tunnels ."
		::= { tosIvInfoEntry 2 }
		
	ivInfoOutDrops OBJECT-TYPE
		SYNTAX      Counter32 
		MAX-ACCESS  read-only
		STATUS      current
		DESCRIPTION
		        "The total tx packets which are dropped of the whole iv tunnels"
		::= { tosIvInfoEntry 3 }
		
	ivInfoOutErrors OBJECT-TYPE
		SYNTAX      Counter32 
		MAX-ACCESS  read-only
		STATUS      current
		DESCRIPTION
		        "The total tx packets which have error of the iv tnuuels"
		::= { tosIvInfoEntry 4 }
		
	ivInfoOutOctets OBJECT-TYPE
		SYNTAX      Counter32 
		MAX-ACCESS  read-only
		STATUS      current
		DESCRIPTION
		        "The total tx octets of the whole iv tunnels"
		::= { tosIvInfoEntry 5 }
	
	ivInfoInPkts OBJECT-TYPE
		SYNTAX      Counter32 
		MAX-ACCESS  read-only
		STATUS      current
		DESCRIPTION
		        "The total rx packets of the whole iv tunnels"
		::= { tosIvInfoEntry 6 }
		
	ivInfoInDrops OBJECT-TYPE
		SYNTAX      Counter32 
		MAX-ACCESS  read-only
		STATUS      current
		DESCRIPTION
		        "The total rx octets which are dropped of the whole iv tunnels"
		::= { tosIvInfoEntry 7 }
		
	ivInfoInErrors OBJECT-TYPE
		SYNTAX      Counter32 
		MAX-ACCESS  read-only
		STATUS      current
		DESCRIPTION
		        "The total rx packets which have error of the iv tnuuels"
		::= { tosIvInfoEntry 8 }
		
	ivInfoInOctets OBJECT-TYPE
		SYNTAX      Counter32 
		MAX-ACCESS  read-only
		STATUS      current
		DESCRIPTION
		        "The total rx octets of the whole iv tunnels"
		::= { tosIvInfoEntry 9 }
		
	--end list TOS IV table information
	
END
