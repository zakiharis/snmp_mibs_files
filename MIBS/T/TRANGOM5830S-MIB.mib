-- Private MIB definition for Trango Systems
-- Access 58xx series wireless broadband Access Point M5830S-AP-60
-- Version: 1.1
-- Date: July 31, 2003
--
-- Copyright 2003: Trango Systems, Inc. All Rights Reserved.
-- Trango Systems, Inc. 15070 Avenue Of Science Suite 200 San Diego CA 92128 USA.
--
-- Reproduction of this document is authorized on condition that the
-- foregoing copyright notice is included.

TRANGOM5830S-MIB DEFINITIONS ::= BEGIN

-- MIB module for enterprise trango wireless broadband
-- of management of M5830S AP and SU units

	IMPORTS
        	enterprises, IpAddress, Counter
            		FROM RFC1155-SMI
        	TRAP-TYPE
            		FROM RFC-1215
	        OBJECT-TYPE
        		FROM RFC-1212;

	-- textual conventions

	DisplayString ::=
        OCTET STRING
            	-- This data type is used to model textual information taken
		-- from the NVT ASCII character set.  By convention, objects
            	-- with this syntax are declared as having
            	--
            	-- SIZE (0..255)


	-- trango wireless broadband MIB registration id assigned to 5454.
        -- customer needs to change this value based on their OEM value.
	trango		OBJECT IDENTIFIER ::= { enterprises 5454 }
	tbw	        OBJECT IDENTIFIER ::= { trango 1 }
	m5830sap	OBJECT IDENTIFIER ::= { tbw 20 }

	-- modules branched from m5830sap
	apsystem	OBJECT IDENTIFIER ::= { m5830sap 1 }
	aprf	    	OBJECT IDENTIFIER ::= { m5830sap 2 }
	su  	    	OBJECT IDENTIFIER ::= { m5830sap 3 }
	trapconfig  	OBJECT IDENTIFIER ::= { m5830sap 4 }
	mibinfo   	OBJECT IDENTIFIER ::= { m5830sap 5 }
    	m5830straps	OBJECT IDENTIFIER ::= { m5830sap 16}
    
	apversion	OBJECT IDENTIFIER ::= { apsystem 1 }
	apswitches	OBJECT IDENTIFIER ::= { apsystem 13}
	aptraffic	OBJECT IDENTIFIER ::= { apsystem 15}
	apipconfig	OBJECT IDENTIFIER ::= { apsystem 19}
	aprftable   	OBJECT IDENTIFIER ::= { aprf 3 }
	apism   	OBJECT IDENTIFIER ::= { aprf 4 }
	apunii  	OBJECT IDENTIFIER ::= { aprf 5 }
        sudb        	OBJECT IDENTIFIER ::= { su 5 }

	-- MIB objects defined below

	-- apsystem objects
	apversionHW	OBJECT-TYPE
		SYNTAX	OCTET STRING (SIZE(2))
            	ACCESS 	read-only
            	STATUS 	mandatory
	        DESCRIPTION
	    		"Hardware version."
            	::= { apversion 1 }

	apversionFW OBJECT-TYPE
            	SYNTAX	DisplayString (SIZE (0..80))
            	ACCESS 	read-only
            	STATUS 	mandatory
            	DESCRIPTION
	        	"Main firmware version.
                 	 Format: <code version>H<hardware version>D<date>."
            	::= { apversion 2 }

	apversionFPGA OBJECT-TYPE
    	    	SYNTAX	OCTET STRING (SIZE(4))
            	ACCESS 	read-only
            	STATUS 	mandatory
            	DESCRIPTION
	    		"FPGA firmware version."
            	::= { apversion 3 }

	apversionChecksum OBJECT-TYPE
    	    	SYNTAX 	OCTET STRING (SIZE(4))
            	ACCESS 	read-only
            	STATUS 	mandatory
            	DESCRIPTION
	    		"AP firmware checksum."
            	::= { apversion 4 }

	apsystemDeviceId OBJECT-TYPE
	    	SYNTAX 	OCTET STRING (SIZE(6))
	    	ACCESS 	read-only
	    	STATUS 	mandatory
	    	DESCRIPTION
			"MAC address."
	    	::= { apsystem 2 }

	apsystemBaseId OBJECT-TYPE
	    	SYNTAX 	INTEGER (0..127)
	    	ACCESS 	read-write
	    	STATUS 	mandatory
	    	DESCRIPTION
			"Cluster that the AP belongs to.
                 	 All APs and SUs in the same cluster shall have the same Base ID."
	    	::= { apsystem 3 }

	apsystemAPId OBJECT-TYPE
	    	SYNTAX	INTEGER (0..255)
	    	ACCESS 	read-write
	    	STATUS 	mandatory
	    	DESCRIPTION
			"AP ID. Each AP in a cluster shall have unique AP ID."
	    	::= { apsystem 4 }

	apsystemDefOpMode OBJECT-TYPE
	    	SYNTAX	INTEGER {
                	ap(1),
                       	off(0)
                  	}
	    	ACCESS 	read-write
	    	STATUS 	mandatory
	    	DESCRIPTION
			"The operation mode (ap or off) the radio is on after reboot/power cycle."
	    	::= { apsystem 5 }

	apsystemCurOpMode OBJECT-TYPE
	    	SYNTAX	INTEGER {
                       	ap(1),
                       	off(0)
                   	}
	    	ACCESS 	read-only
	    	STATUS 	mandatory
	    	DESCRIPTION
			"Radio's current operation mode."
	    	::= { apsystem 6 }
        
    	apsystemActivateOpmode OBJECT-TYPE
            	SYNTAX	INTEGER {
	        	deactivated(0),
                       	activateapmode(1)
                   	}
            	ACCESS 	read-write
            	STATUS  mandatory
            	DESCRIPTION
                	"Engage AP unit to ap operation mode."
            	DEFVAL	{ deactivated }
            	::= { apsystem 7 }

	apsystemIpAddr OBJECT-TYPE
		SYNTAX 	IpAddress
		ACCESS 	read-only
		STATUS 	mandatory
		DESCRIPTION
			"Current IP address."
		::= { apsystem 8 }

    	apsystemSubnet OBJECT-TYPE
		SYNTAX	IpAddress
		ACCESS	read-only
		STATUS	mandatory
		DESCRIPTION
			"Current Subnet mask."
		::= { apsystem 9 }

	apsystemDefaultGateway OBJECT-TYPE
		SYNTAX	IpAddress
		ACCESS	read-only
		STATUS	mandatory
		DESCRIPTION
			"Current Default gateway."
		::= { apsystem 10 }

	apsystemReadCommStr OBJECT-TYPE
        	SYNTAX  DisplayString (SIZE (0..32))
		ACCESS	read-write
		STATUS  mandatory
		DESCRIPTION
			"SNMP agent read community string. It is used for authentication purpose."
		::= { apsystem 11 }

	apsystemWriteCommStr OBJECT-TYPE
	        SYNTAX  DisplayString (SIZE (0..32))
		ACCESS	read-write
		STATUS  mandatory
		DESCRIPTION
			"SNMP agent write community string. It is used for authentication purpose."
		::= { apsystem 12 }

	apswitchesBlockBroadcastMulticast OBJECT-TYPE
		SYNTAX	INTEGER {
	        	passed(0),
        	        blocked(1)
                	}
		ACCESS 	read-write
		STATUS 	mandatory
		DESCRIPTION
			"This switch enables or disables the blocking of Ethernet
		         control packet except ICMP and ARP to reduce the amount
	                 of uneccessary overhead introduced to the wireless link."
		::= { apswitches 1 }

	apswitchesSUtoSU OBJECT-TYPE
 		SYNTAX	INTEGER {
                        disabled(0),
                        enabled(1)
                        }
		ACCESS 	read-write
		STATUS 	mandatory
		DESCRIPTION
			"This switch enables or disables the peer-to-peer
        	         feature among SUs through the AP. Before this switch
                         is turned on, all SUs that want to communicate with
                         each other have to be assigned to the same group."
		::= { apswitches 2 }

	apswitchesTFTPD OBJECT-TYPE
		SYNTAX	INTEGER {
	                disabled(0),
                        enabled(1)
                	}
		ACCESS 	read-write
		STATUS 	mandatory
		DESCRIPTION
			"This switch enables or disables the TFTP operation. When
	                 it is turned on, then the AP will be ready for code download."
		::= { apswitches 4 }

	apswitchesHTTPD OBJECT-TYPE
		SYNTAX	INTEGER {
                        disabled(0),
                        enabled(1)
                        }
		ACCESS 	read-write
		STATUS 	mandatory
		DESCRIPTION
			"When it is turned on, then the AP is accessible for
                         configuring via web browser (e.g. IE or Nescape)."
		::= { apswitches 5 }

	apsystemMIRThreshold OBJECT-TYPE
		SYNTAX	INTEGER {
                        disabled(0),
                        fourmbps(4),
                        fivembps(5),
                        sixmbps(6),
                        sevenmbps(7),
                        eightmbps(8)
                        }
		ACCESS	read-write
		STATUS  mandatory
		DESCRIPTION
			"Maximum Information Rate (in Kbps), the AP allows the
                         network to utilize before enforcing CIR on each subscriber."
		::= { apsystem 14 }

	aptrafficEthRxAvgThroughputLog OBJECT-TYPE
		SYNTAX 	INTEGER
		ACCESS	read-only	
		STATUS  mandatory
		DESCRIPTION
			"Average payload data throughput (in Kbits/sec)
                         received on Ethernet port over the last 60 seconds."
		::= { aptraffic 1 }

	aptrafficEthTxAvgThroughputLog OBJECT-TYPE
		SYNTAX 	INTEGER
		ACCESS	read-only
		STATUS	mandatory
		DESCRIPTION
			"Average payload data throughput (in Kbits/sec)
                         transmitted on Ethernet port over the last 60 seconds."
		::= { aptraffic 2 }

	aptrafficRfRxAvgThroughputLog OBJECT-TYPE
		SYNTAX 	INTEGER
		ACCESS	read-only
		STATUS	mandatory
		DESCRIPTION
			"Average payload data throughput (in Kbits/sec)
                         received on RF port over the last 60 seconds."
		::= { aptraffic 3 }

	aptrafficRfTxAvgThroughputLog OBJECT-TYPE
		SYNTAX 	INTEGER
		ACCESS	read-only
		STATUS	mandatory
		DESCRIPTION
			"Average payload data throughput (in Kbits/sec)
                         transmitted on RF port over the last 60 seconds."
		::= { aptraffic 4 }

	aptrafficEthInOctets OBJECT-TYPE
		SYNTAX 	Counter
		ACCESS	read-only
		STATUS	mandatory
		DESCRIPTION
			"Number of payload octets received on Ethernet port."
		::= { aptraffic 5 }

	aptrafficEthOutOctets OBJECT-TYPE
		SYNTAX 	Counter
		ACCESS	read-only
		STATUS	mandatory
		DESCRIPTION
			"Number of payload octets transmitted on Ethernet port."
		::= { aptraffic 6 }

	aptrafficRfInOctets OBJECT-TYPE
		SYNTAX 	Counter
		ACCESS	read-only
		STATUS	mandatory
		DESCRIPTION
			"Number of octets of SUs payload received from RF port."
		::= { aptraffic 7 }

	aptrafficRfOutOctets OBJECT-TYPE
		SYNTAX 	Counter
		ACCESS	read-only
		STATUS	mandatory
		DESCRIPTION
			"Number of octets of SUs payload transmitted to RF port."
		::= { aptraffic 8 }

    	apsystemTemperature OBJECT-TYPE
        	SYNTAX  INTEGER (-128..127)
        	ACCESS  read-only
        	STATUS  mandatory
        	DESCRIPTION
            		"Current AP temperature value (in Celsius)."
                ::= {apsystem 16 }

	apsystemUpdateFlashAndActivate OBJECT-TYPE
		SYNTAX	INTEGER {
                        no(0),
                        yes(1)
                        }
		ACCESS	read-write
		STATUS	mandatory
		DESCRIPTION
			"Save system setting values to Flash and activate the settings."
        	DEFVAL  {no}
		::= { apsystem 17 }

	apsystemReboot OBJECT-TYPE
		SYNTAX	INTEGER {
                        deactivated(0),
                        activated(1)
                        }
		ACCESS	read-write
		STATUS  mandatory
		DESCRIPTION
			"Reboot the radio."
        	DEFVAL { deactivated }
		::= { apsystem 18 }

	apipconfigIpAddress OBJECT-TYPE
		SYNTAX 	IpAddress
		ACCESS 	read-write
		STATUS 	mandatory
		DESCRIPTION
			"New IP address. It will be saved to
                         non-volatile memory and activated in 5 secs."
		::= { apipconfig 1 }

	apipconfigSubnet OBJECT-TYPE
		SYNTAX	IpAddress
		ACCESS	read-write
		STATUS	mandatory
		DESCRIPTION
			"New Subnet mask. It will be saved to
                         non-volatile memory and activated in 5 secs."
		::= { apipconfig 2 }

    	apipconfigDefaultGateway OBJECT-TYPE
		SYNTAX	IpAddress
		ACCESS	read-write
		STATUS	mandatory
		DESCRIPTION
			"New Default gateway. It will be saved to
                         non-volatile memory and activated in 5 secs."
		::= { apipconfig 3 }

	-- aprf objects
	aprfActiveChannel OBJECT-TYPE
		SYNTAX 	INTEGER (1..30)
		ACCESS	read-write
		STATUS	mandatory
		DESCRIPTION
			"It specifies the current channel number the radio operates on."
		::= { aprf 1 }

	aprfActivePolarization OBJECT-TYPE
                SYNTAX  DisplayString (SIZE (1))
		ACCESS	read-write
		STATUS	mandatory
		DESCRIPTION
			"It specifies the current polarization the radio operates on."
		::= { aprf 2 }

	aprftableChannel1 OBJECT-TYPE
		SYNTAX 	INTEGER (5260..5340 | 5736..5836)
		ACCESS	read-write
		STATUS	mandatory
		DESCRIPTION
			"RF channel 1 frequency (in MHz). It allows you to create your
	                 own channel instead of the manufacturing defaults in the AP.
                         Keep in mind that channel width is 20MHz, and the frequency
                         specified here is the center frequency.
                         Frequency (5260MHz - 5340MHz) is only applicable to M5830S radio."
		::= { aprftable 1 }

	aprftableChannel2 OBJECT-TYPE
		SYNTAX 	INTEGER (5260..5340 | 5736..5836)
		ACCESS	read-write
		STATUS	mandatory
		DESCRIPTION
			"RF channel 2 frequency (in MHz). It allows you to create your
	                 own channel instead of the manufacturing defaults in the AP.
        	         Keep in mind that channel width is 20MHz, and the frequency
	                 specified here is the center frequency.
        	         Frequency (5260MHz - 5340MHz) is only applicable to M5830S radio."
		::= { aprftable 2 }

	aprftableChannel3 OBJECT-TYPE
		SYNTAX 	INTEGER (5260..5340 | 5736..5836)
		ACCESS	read-write
		STATUS	mandatory
		DESCRIPTION
			"RF channel 3 frequency (in MHz). It allows you to create your
	                 own channel instead of the manufacturing defaults in the AP.
	                 Keep in mind that channel width is 20MHz, and the frequency
	                 specified here is the center frequency.
         	         Frequency (5260MHz - 5340MHz) is only applicable to M5830S radio."
		::= { aprftable 3 }

	aprftableChannel4 OBJECT-TYPE
		SYNTAX 	INTEGER (5260..5340 | 5736..5836)
		ACCESS	read-write
		STATUS	mandatory
		DESCRIPTION
			"RF channel 4 frequency (in MHz). It allows you to create your
	                 own channel instead of the manufacturing defaults in the AP.
        	         Keep in mind that channel width is 20MHz, and the frequency
	                 specified here is the center frequency.
        	         Frequency (5260MHz - 5340MHz) is only applicable to M5830S radio."
		::= { aprftable 4 }

	aprftableChannel5 OBJECT-TYPE
		SYNTAX 	INTEGER (5260..5340 | 5736..5836)
		ACCESS	read-write
		STATUS	mandatory
		DESCRIPTION
			"RF channel 5 frequency (in MHz). It allows you to create your
	                 own channel instead of the manufacturing defaults in the AP.
	                 Keep in mind that channel width is 20MHz, and the frequency
	                 specified here is the center frequency.
	                 Frequency (5260MHz - 5340MHz) is only applicable to M5830S radio."
		::= { aprftable 5 }

	aprftableChannel6 OBJECT-TYPE
		SYNTAX 	INTEGER (5260..5340 | 5736..5836)
		ACCESS	read-write
		STATUS	mandatory
		DESCRIPTION
			"RF channel 6 frequency (in MHz). It allows you to create your
   	                 own channel instead of the manufacturing defaults in the AP.
	                 Keep in mind that channel width is 20MHz, and the frequency
	                 specified here is the center frequency.
	                 Frequency (5260MHz - 5340MHz) is only applicable to M5830S radio."
		::= { aprftable 6 }

	aprftableChannel7 OBJECT-TYPE
		SYNTAX 	INTEGER (5260..5340 | 5736..5836)
		ACCESS	read-write
		STATUS	mandatory
		DESCRIPTION
			"RF channel 7 frequency (in MHz). It allows you to create your
	                 own channel instead of the manufacturing defaults in the AP.
	                 Keep in mind that channel width is 20MHz, and the frequency
        	         specified here is the center frequency.
	                 Frequency (5260MHz - 5340MHz) is only applicable to M5830S radio."
		::= { aprftable 7 }

	aprftableChannel8 OBJECT-TYPE
		SYNTAX 	INTEGER (5260..5340 | 5736..5836)
		ACCESS	read-write
		STATUS	mandatory
		DESCRIPTION
			"RF channel 8 frequency (in MHz). It allows you to create your
    	                 own channel instead of the manufacturing defaults in the AP.
        	         Keep in mind that channel width is 20MHz, and the frequency
	                 specified here is the center frequency.
        	         Frequency (5260MHz - 5340MHz) is only applicable to M5830S radio."
		::= { aprftable 8 }

	aprftableChannel9 OBJECT-TYPE
		SYNTAX 	INTEGER (5260..5340 | 5736..5836)
		ACCESS	read-write
		STATUS	mandatory
		DESCRIPTION
			"RF channel 9 frequency (in MHz). It allows you to create your
	                 own channel instead of the manufacturing defaults in the AP.
        	         Keep in mind that channel width is 20MHz, and the frequency
	                 specified here is the center frequency.
	                 Frequency (5260MHz - 5340MHz) is only applicable to M5830S radio."
		::= { aprftable 9 }

	aprftableChannel10 OBJECT-TYPE
		SYNTAX 	INTEGER (5260..5340 | 5736..5836)
		ACCESS	read-write
		STATUS	mandatory
		DESCRIPTION
			"RF channel 10 frequency (in MHz). It allows you to create your
	                 own channel instead of the manufacturing defaults in the AP.
        	         Keep in mind that channel width is 20MHz, and the frequency
	                 specified here is the center frequency.
        	         Frequency (5260MHz - 5340MHz) is only applicable to M5830S radio."
		::= { aprftable 10 }

	aprftableChannel11 OBJECT-TYPE
		SYNTAX 	INTEGER (5260..5340 | 5736..5836)
		ACCESS	read-write
		STATUS	mandatory
		DESCRIPTION
			"RF channel 11 frequency (in MHz). It allows you to create your
	                 own channel instead of the manufacturing defaults in the AP.
	                 Keep in mind that channel width is 20MHz, and the frequency
	                 specified here is the center frequency.
        	         Frequency (5260MHz - 5340MHz) is only applicable to M5830S radio."
		::= { aprftable 11 }

	aprftableChannel12 OBJECT-TYPE
		SYNTAX 	INTEGER (5260..5340 | 5736..5836)
		ACCESS	read-write
		STATUS	mandatory
		DESCRIPTION
			"RF channel 12 frequency (in MHz). It allows you to create your
	                 own channel instead of the manufacturing defaults in the AP.
	                 Keep in mind that channel width is 20MHz, and the frequency
	                 specified here is the center frequency.
	                 Frequency (5260MHz - 5340MHz) is only applicable to M5830S radio."
		::= { aprftable 12 }

	aprftableChannel13 OBJECT-TYPE
		SYNTAX 	INTEGER (5260..5340 | 5736..5836)
		ACCESS	read-write
		STATUS	mandatory
		DESCRIPTION
			"RF channel 13 frequency (in MHz). It allows you to create your
	                 own channel instead of the manufacturing defaults in the AP.
	                 Keep in mind that channel width is 20MHz, and the frequency
	                 specified here is the center frequency.
	                 Frequency (5260MHz - 5340MHz) is only applicable to M5830S radio."
		::= { aprftable 13 }

	aprftableChannel14 OBJECT-TYPE
		SYNTAX 	INTEGER (5260..5340 | 5736..5836)
		ACCESS	read-write
		STATUS	mandatory
		DESCRIPTION
			"RF channel 14 frequency (in MHz). It allows you to create your
	                 own channel instead of the manufacturing defaults in the AP.
	                 Keep in mind that channel width is 20MHz, and the frequency
	                 specified here is the center frequency.
	                 Frequency (5260MHz - 5340MHz) is only applicable to M5830S radio."
		::= { aprftable 14 }

	aprftableChannel15 OBJECT-TYPE
		SYNTAX 	INTEGER (5260..5340 | 5736..5836)
		ACCESS	read-write
		STATUS	mandatory
		DESCRIPTION
			"RF channel 15 frequency (in MHz). It allows you to create your
	                 own channel instead of the manufacturing defaults in the AP.
	                 Keep in mind that channel width is 20MHz, and the frequency
	                 specified here is the center frequency.
	                 Frequency (5260MHz - 5340MHz) is only applicable to M5830S radio."
		::= { aprftable 15 }

	aprftableChannel16 OBJECT-TYPE
		SYNTAX 	INTEGER (5260..5340 | 5736..5836)
		ACCESS	read-write
		STATUS	mandatory
		DESCRIPTION
			"RF channel 16 frequency (in MHz). It allows you to create your
        	         own channel instead of the manufacturing defaults in the AP.
	                 Keep in mind that channel width is 20MHz, and the frequency
	                 specified here is the center frequency.
	                 Frequency (5260MHz - 5340MHz) is only applicable to M5830S radio."
		::= { aprftable 16 }

	aprftableChannel17 OBJECT-TYPE
		SYNTAX 	INTEGER (5260..5340 | 5736..5836)
		ACCESS	read-write
		STATUS	mandatory
		DESCRIPTION
			"RF channel 17 frequency (in MHz). It allows you to create your
	                 own channel instead of the manufacturing defaults in the AP.
        	         Keep in mind that channel width is 20MHz, and the frequency
	                 specified here is the center frequency.
        	         Frequency (5260MHz - 5340MHz) is only applicable to M5830S radio."
		::= { aprftable 17 }

	aprftableChannel18 OBJECT-TYPE
		SYNTAX 	INTEGER (5260..5340 | 5736..5836)
		ACCESS	read-write
		STATUS	mandatory
		DESCRIPTION
			"RF channel 18 frequency (in MHz). It allows you to create your
	                 own channel instead of the manufacturing defaults in the AP.
        	         Keep in mind that channel width is 20MHz, and the frequency
	                 specified here is the center frequency.
	                 Frequency (5260MHz - 5340MHz) is only applicable to M5830S radio."
		::= { aprftable 18 }

	aprftableChannel19 OBJECT-TYPE
		SYNTAX 	INTEGER (5260..5340 | 5736..5836)
		ACCESS	read-write
		STATUS	mandatory
		DESCRIPTION
			"RF channel 19 frequency (in MHz). It allows you to create your
	                 own channel instead of the manufacturing defaults in the AP.
	                 Keep in mind that channel width is 20MHz, and the frequency
	                 specified here is the center frequency.
	                 Frequency (5260MHz - 5340MHz) is only applicable to M5830S radio."
		::= { aprftable 19 }

	aprftableChannel20 OBJECT-TYPE
		SYNTAX 	INTEGER (5260..5340 | 5736..5836)
		ACCESS	read-write
		STATUS	mandatory
		DESCRIPTION
			"RF channel 20 frequency (in MHz). It allows you to create your
	                 own channel instead of the manufacturing defaults in the AP.
	                 Keep in mind that channel width is 20MHz, and the frequency
	                 specified here is the center frequency.
	                 Frequency (5260MHz - 5340MHz) is only applicable to M5830S radio."
		::= { aprftable 20 }

	aprftableChannel21 OBJECT-TYPE
		SYNTAX 	INTEGER (5260..5340 | 5736..5836)
		ACCESS	read-write
		STATUS	mandatory
		DESCRIPTION
			"RF channel 21 frequency (in MHz). It allows you to create your
	                 own channel instead of the manufacturing defaults in the AP.
	                 Keep in mind that channel width is 20MHz, and the frequency
	                 specified here is the center frequency.
	                 Frequency (5260MHz - 5340MHz) is only applicable to M5830S radio."
		::= { aprftable 21 }

	aprftableChannel22 OBJECT-TYPE
		SYNTAX 	INTEGER (5260..5340 | 5736..5836)
		ACCESS	read-write
		STATUS	mandatory
		DESCRIPTION
			"RF channel 22 frequency (in MHz). It allows you to create your
	                 own channel instead of the manufacturing defaults in the AP.
        	         Keep in mind that channel width is 20MHz, and the frequency
	                 specified here is the center frequency.
	                 Frequency (5260MHz - 5340MHz) is only applicable to M5830S radio."
		::= { aprftable 22 }

	aprftableChannel23 OBJECT-TYPE
		SYNTAX 	INTEGER (5260..5340 | 5736..5836)
		ACCESS	read-write
		STATUS	mandatory
		DESCRIPTION
			"RF channel 23 frequency (in MHz). It allows you to create your
	                 own channel instead of the manufacturing defaults in the AP.
        	         Keep in mind that channel width is 20MHz, and the frequency
	                 specified here is the center frequency.
        	         Frequency (5260MHz - 5340MHz) is only applicable to M5830S radio."
		::= { aprftable 23 }

	aprftableChannel24 OBJECT-TYPE
		SYNTAX 	INTEGER (5260..5340 | 5736..5836)
		ACCESS	read-write
		STATUS	mandatory
		DESCRIPTION
			"RF channel 24 frequency (in MHz). It allows you to create your
	                 own channel instead of the manufacturing defaults in the AP.
        	         Keep in mind that channel width is 20MHz, and the frequency
	                 specified here is the center frequency.
	                 Frequency (5260MHz - 5340MHz) is only applicable to M5830S radio."
		::= { aprftable 24 }

	aprftableChannel25 OBJECT-TYPE
		SYNTAX 	INTEGER (5260..5340 | 5736..5836)
		ACCESS	read-write
		STATUS	mandatory
		DESCRIPTION
			"RF channel 25 frequency (in MHz). It allows you to create your
	                 own channel instead of the manufacturing defaults in the AP.
	                 Keep in mind that channel width is 20MHz, and the frequency
	                 specified here is the center frequency.
	                 Frequency (5260MHz - 5340MHz) is only applicable to M5830S radio."
		::= { aprftable 25 }

	aprftableChannel26 OBJECT-TYPE
		SYNTAX 	INTEGER (5260..5340 | 5736..5836)
		ACCESS	read-write
		STATUS	mandatory
		DESCRIPTION
			"RF channel 26 frequency (in MHz). It allows you to create your
	                 own channel instead of the manufacturing defaults in the AP.
	                 Keep in mind that channel width is 20MHz, and the frequency
	                 specified here is the center frequency.
	                 Frequency (5260MHz - 5340MHz) is only applicable to M5830S radio."
		::= { aprftable 26 }

	aprftableChannel27 OBJECT-TYPE
		SYNTAX 	INTEGER (5260..5340 | 5736..5836)
		ACCESS	read-write
		STATUS	mandatory
		DESCRIPTION
			"RF channel 27 frequency (in MHz). It allows you to create your
	                 own channel instead of the manufacturing defaults in the AP.
	                 Keep in mind that channel width is 20MHz, and the frequency
	                 specified here is the center frequency.
	                 Frequency (5260MHz - 5340MHz) is only applicable to M5830S radio."
		::= { aprftable 27 }

	aprftableChannel28 OBJECT-TYPE
		SYNTAX 	INTEGER (5260..5340 | 5736..5836)
		ACCESS	read-write
		STATUS	mandatory
		DESCRIPTION
			"RF channel 28 frequency (in MHz). It allows you to create your
	                 own channel instead of the manufacturing defaults in the AP.
	                 Keep in mind that channel width is 20MHz, and the frequency
	                 specified here is the center frequency.
	                 Frequency (5260MHz - 5340MHz) is only applicable to M5830S radio."
		::= { aprftable 28 }

	aprftableChannel29 OBJECT-TYPE
		SYNTAX 	INTEGER (5260..5340 | 5736..5836)
		ACCESS	read-write
		STATUS	mandatory
		DESCRIPTION
			"RF channel 29 frequency (in MHz). It allows you to create your
	                 own channel instead of the manufacturing defaults in the AP.
	                 Keep in mind that channel width is 20MHz, and the frequency
	                 specified here is the center frequency.
	                 Frequency (5260MHz - 5340MHz) is only applicable to M5830S radio."
		::= { aprftable 29 }

	aprftableChannel30 OBJECT-TYPE
		SYNTAX 	INTEGER (5260..5340 | 5736..5836)
		ACCESS	read-write
		STATUS	mandatory
		DESCRIPTION
			"RF channel 30 frequency (in MHz). It allows you to create your
	                 own channel instead of the manufacturing defaults in the AP.
	                 Keep in mind that channel width is 20MHz, and the frequency
	                 specified here is the center frequency.
	                 Frequency (5260MHz - 5340MHz) is only applicable to M5830S radio."
		::= { aprftable 30 }

	apismTxPowerMax OBJECT-TYPE
		SYNTAX 	INTEGER (-128..127)
		ACCESS	read-only
		STATUS	mandatory
		DESCRIPTION
	        	"The maximum ISM Tx power value can be set (in dBm)."
	        ::= { apism 1 }
    
	apismTxPowerMin OBJECT-TYPE
		SYNTAX 	INTEGER (-128..127)
		ACCESS	read-only
		STATUS	mandatory
		DESCRIPTION
        	    	"The minimum ISM Tx power value can be set (in dBm)."
	        ::= { apism 2 }
    
	apismTxPower OBJECT-TYPE
		SYNTAX 	INTEGER (-128..127)
		ACCESS	read-write
		STATUS	mandatory
		DESCRIPTION
			"ISM RF tx power (in dBm). It specifies the power output
	                 of the radio, excluding the antenna gain. Check parameters
        	         apismTxPowerMax and apismTxPowerMin for power setting range."
		::= { apism 3 }

	apismServiceRadius OBJECT-TYPE
		SYNTAX 	INTEGER {
                    	threemiles(3),
                    	tenmiles(10),
                    	twentymiles(20)
                	}
		ACCESS	read-write
		STATUS	mandatory
		DESCRIPTION
			"ISM RF service radius (in mile). It specifies the distance of
	                 the furthest SU the AP will serve. Based on this information,
        	         the AP will determine the maximum wait time for a SU to
	                 response to a poll before it starts to poll the next one."
		::= { apism 4 }

	apismRxThreshold OBJECT-TYPE
		SYNTAX 	INTEGER (-90 | -85 | -80 | -75 | -70 | -65)
		ACCESS	read-write
		STATUS	mandatory
		DESCRIPTION
			"ISM RF rx threshold (in dBm). It specifies the receiver sensitivity
	                 of the AP. By default, the radio's sensitivity is -82dBm.
        	         The higher the threshold is, the less sensitive the radio will be.
	                 In M5800S, the value -90 represents the rfrxthreshold is disabled."
		::= { apism 5 }

	apismTargetRSSI OBJECT-TYPE
		SYNTAX 	INTEGER (-85..-45)
		ACCESS	read-write
		STATUS	mandatory
		DESCRIPTION
			"ISM RF target RSSI (in dBm). It specifies the target RSSI from all SUs to
	                 the AP. Based on this parameter, the AP can power level each SU
        	         so that it receives same level of signal strength from all SUs,
	                 regardless far or near. Note that when you set the Target RSSI
	                 from SU, you need to consider AP's RF Rx Threshold value.
	                 The Target RSSI from SU must be 5dB higher than the RF Rx Threshold.
	                 When the RF Rx Threshold is disabled, the setting of the Target RSSI
	                 from SU shall be no less than -75dBm."
		::= { apism 6 }

	apuniiTxPowerMax OBJECT-TYPE
		SYNTAX 	INTEGER (-128..127)
		ACCESS	read-only
		STATUS	mandatory
		DESCRIPTION
            		"This object is only applicable to M5830S radio.
             		 The maximum UNII Tx power value can be set (in dBm)."
	        ::= { apunii 1 }
    
	apuniiTxPowerMin OBJECT-TYPE
		SYNTAX 	INTEGER (-128..127)
		ACCESS	read-only
		STATUS	mandatory
		DESCRIPTION
            		"This object is only applicable to M5830S radio.
             		 The minimum UNII Tx power value can be set (in dBm)."
	        ::= { apunii 2 }
        
 	apuniiTxPower OBJECT-TYPE
		SYNTAX 	INTEGER (-128..127)
		ACCESS	read-write
		STATUS	mandatory
		DESCRIPTION
            		"This object is only applicable to M5830S radio.
			 UNII RF tx power (in dBm). It specifies the power output
             		 of the radio, excluding the antenna gain. Check parameters
             		 apuniiTxPowerMax and apuniiTxPowerMin for power setting range."
		::= { apunii 3 }

	apuniiServiceRadius OBJECT-TYPE
		SYNTAX 	INTEGER {
                    	twomiles(2),
                    	threemiles(3),
                    	fourmiles(4)
                	}
		ACCESS	read-write
		STATUS	mandatory
		DESCRIPTION
            		"This object is only applicable to M5830S radio.
			 UNII RF service radius (in mile). It specifies the distance of
             		 the furthest SU the AP will serve. Based on this information,
             		 the AP will determine the maximum wait time for a SU to
             		 response to a poll before it starts to poll the next one."
		::= { apunii 4 }

	apuniiRxThreshold OBJECT-TYPE
		SYNTAX 	INTEGER (-90 | -85 | -80 | -75 | -70 | -65)
		ACCESS	read-write
		STATUS	mandatory
		DESCRIPTION
            		"This object is only applicable to M5830S radio.
             		 UNII RF rx threshold (in dBm). It specifies the receiver sensitivity of the AP."
		::= { apunii 5 }

	apuniiTargetRSSI OBJECT-TYPE
		SYNTAX 	INTEGER (-85..-45)
		ACCESS	read-write
		STATUS	mandatory
		DESCRIPTION
            		"This object is only applicable to M5830S radio.
			 UNII RF target RSSI (in dBm). It specifies the target RSSI from all SUs to
             	 	 the AP. Based on this parameter, the AP can power level each SU so that
             		 it receives same level of signal strength from all SUs, regardless far
             		 or near. Note that when you set the Target RSSI from SU, you need to
             		 consider AP's RF Rx Threshold value. The Target RSSI from SU must be 5dB
             		 higher than the RF Rx Threshold."
		::= { apunii 6 }

	-- SU objects
	suSUCount OBJECT-TYPE
 		SYNTAX	INTEGER (0..500)
		ACCESS	read-only
		STATUS	mandatory
		DESCRIPTION
			"Number of subscriber units in the subscriber database."
		::= { su 1 }

	suPowerLvlAll OBJECT-TYPE
		SYNTAX	INTEGER {
                    deactivated(0),
                    activated(1)
                }
		ACCESS	read-write
		STATUS	mandatory
		DESCRIPTION
			"It is a feature that is typically found in more
	             	 elaborate mobile systems such as cellular CDMA
        	     	 networks. Using this feature, all SUs have their
	             	 RF power output adjusted until the signal strength
        	     	 for each SU as received in the AP is roughly the same."
        	DEFVAL	{deactivated}
		::= { su 2 }

    	suStatisticsSamplePeriod OBJECT-TYPE
		SYNTAX	INTEGER (1..60)
	        ACCESS  read-write
        	STATUS  mandatory
	        DESCRIPTION
            		"A period (in minute) AP requests update on SU Info Table from all associated SUs."
        	::= { su 3 }

    	suRebootAll OBJECT-TYPE
        	SYNTAX  INTEGER {
                    	deactivated(0),
                    	activated(1)
                	}
        	ACCESS  read-write
	        STATUS  mandatory
        	DESCRIPTION
            		"AP broadcasts reboot command to all subscriber units."
	        DEFVAL { deactivated }
        	::= { su 4 }

    	sudbDeleteOrAddID OBJECT-TYPE
        	SYNTAX  INTEGER (1..8190)
		ACCESS	read-write
		STATUS	mandatory
		DESCRIPTION
			"Subscriber unit ID (1..8190). Each
             	 	 subscriber in a sector shall have a unique ID."
		::= { sudb 1 }

	sudbAddMAC OBJECT-TYPE
		SYNTAX	OCTET STRING (SIZE(6))
		ACCESS	read-write
		STATUS	mandatory
		DESCRIPTION
			"It is the MAC address of the subscriber unit,
		         which can be found on the back of the SU."
		::= { sudb 2 }

	sudbAddPolling OBJECT-TYPE
		SYNTAX	INTEGER {
	        	regular(1),
                    	priority(5)
                	}
		ACCESS	read-write
		STATUS	mandatory
		DESCRIPTION
			"It is service level value, regular or priority, of a SU.
	             	 The AP will poll priority user more often, thus better
	             	 network latency as the result. As the network latency
	             	 varies based on the number of subscriber units the AP
	             	 serves, priority user is guaranteed that the latency is
        	     	 NOT greater than 100ms regardless of the size of the network."
        	DEFVAL  {regular}
		::= { sudb 3 }

	sudbAddSUtoSU OBJECT-TYPE
		SYNTAX	INTEGER {
                    	nullgroup(0),
                    	group1(1),
                    	group2(2),
	              	group3(3),
        	        group4(4),
                	group5(5),
                    	group6(6),
                    	group7(7),
                    	group8(8),
                    	group9(9),
                    	groupA(10),
                    	groupB(11),
                    	groupC(12),
                    	groupD(13),
                    	groupE(14),
                    	groupF(15)
                	}
		ACCESS	read-write
		STATUS	mandatory
		DESCRIPTION
			"It is peer-to-peer group this SU belongs to.
	             	 With the SU to SU switch is turned on, SUs in
        	     	 the same peer-to-peer group can communicate to
             		 each other via the AP. There are totally 15 groups
             		 available. Note that the SU shall be set to priority
             		 user for this feature to improve latency."
        	DEFVAL  {nullgroup}
		::= { sudb 4 }

	sudbAddCIR OBJECT-TYPE
		SYNTAX	INTEGER (0..9999)
		ACCESS	read-write
		STATUS	mandatory
		DESCRIPTION
			"It is the Committed Information Rate (in Kbps) the AP allocates to SU."
        	DEFVAL { 128 }
		::= { sudb 5 }

	sudbAddMIR OBJECT-TYPE
		SYNTAX	INTEGER (0..9999)
		ACCESS	read-write
		STATUS	mandatory
		DESCRIPTION
			"It is the Maximum Information Rate (in Kbps) the AP allocates to SU."
        	DEFVAL { 9999 }
		::= { sudb 6 }

	sudbAdd OBJECT-TYPE
		SYNTAX	INTEGER {
                    	deactivated(0),
                    	add(1)
                	}
		ACCESS	read-write
		STATUS	mandatory
		DESCRIPTION
			"Add a subscriber (specified in object sudbDeleteOrAddID) to the subscriber database."
        	DEFVAL  {deactivated}
		::= { sudb 7 }

	sudbDelete OBJECT-TYPE
		SYNTAX	INTEGER {
                    	deactivated(0),
                    	delete(1)
                	}
		ACCESS	read-write
		STATUS	mandatory
		DESCRIPTION
			"Delete a subscriber (specified in object sudbDeleteOrAddID) from the subscriber database."
	        DEFVAL  {deactivated}
		::= { sudb 8 }

	suInfoTable OBJECT-TYPE
		SYNTAX	SEQUENCE OF SuInfoEntry
		ACCESS	not-accessible
		STATUS	mandatory
		DESCRIPTION
			"A table that contains subscriber unit entities."
		::= { su 6 }

	suInfoEntry OBJECT-TYPE
		SYNTAX	SuInfoEntry
		ACCESS	not-accessible
		STATUS	mandatory
		DESCRIPTION
			"Information about a specific subscriber unit retrieved by its ID number."
		INDEX	{ suID }
		::= { suInfoTable 1 }

	SuInfoEntry ::=
		SEQUENCE {
			suID			INTEGER,
			suMAC			OCTET STRING,
			suPolling		INTEGER,
			suSUtoSU 		INTEGER,
			suCIR 			INTEGER,
			suMIR			INTEGER,
			suIPAddr		IpAddress,
            		suRemarks               DisplayString,
			suHWVer			OCTET STRING,
			suFWVer			DisplayString,
			suFPGAVer		OCTET STRING,
			suChecksum		OCTET STRING,
			suAssociation	        INTEGER,
			suDIstance		INTEGER,
			suRSSIFromSU	        INTEGER,
			suRSSIFromAP	        INTEGER,
			suTxPower		INTEGER,
			suEthRxAvgThroughputLog	INTEGER,
			suEthTxAvgThroughputLog INTEGER,
			suRfRxAvgThroughputLog  INTEGER,
			suRfTxAvgThroughputLog  INTEGER,
            		suRfInOctets            Counter,
            		suRfOutOctets           Counter,
			suPowerLevel		INTEGER,
	            	suTemperature   	INTEGER,
            		suReboot        	INTEGER,
			suTCPIPForLocalEth	INTEGER
			}

	suID OBJECT-TYPE
		SYNTAX	INTEGER (1..8190)
		ACCESS	read-only
		STATUS	mandatory
		DESCRIPTION
			"Subscriber unit ID. Each subscriber in a sector shall have a unique ID."
		::= { suInfoEntry 1 }

	suMAC OBJECT-TYPE
		SYNTAX	OCTET STRING (SIZE(6))
		ACCESS	read-only
		STATUS	mandatory
		DESCRIPTION
			"Subscriber unit MAC Address. Format: 00 01 DE xx xx xx."
		::= { suInfoEntry 2 }

	suPolling OBJECT-TYPE
		SYNTAX	INTEGER {
                    regular(1),
                    priority(5)
                }
		ACCESS	read-only
		STATUS	mandatory
		DESCRIPTION
			"It is service level value, regular or priority, of a SU.
        	         The AP will poll priority user more often, thus better
	                 network latency as the result. As the network latency
	                 varies based on the number of subscriber units the AP
	                 serves, priority user is guaranteed that the latency is
	                 NOT greater than 100ms regardless of the size of the network."
        	DEFVAL  {regular}
		::= { suInfoEntry 3 }

	suSUtoSU OBJECT-TYPE
		SYNTAX	INTEGER {
                    	nullgroup(0),
                    	group1(1),
                    	group2(2),
                    	group3(3),
                    	group4(4),
                    	group5(5),
                    	group6(6),
                    	group7(7),
                    	group8(8),
                    	group9(9),
                    	groupA(10),
                    	groupB(11),
                    	groupC(12),
                    	groupD(13),
                    	groupE(14),
                    	groupF(15)
                	}
		ACCESS	read-only
		STATUS	mandatory
		DESCRIPTION
			"It is peer-to-peer group this SU belongs to.
	                 With the SU to SU switch is turned on, SUs in
        	         the same peer-to-peer group can communicate to
             		 each other via the AP. There are totally 15 groups
             		 available. Note that the SU shall be set to priority
             		 user for this feature to improve latency."
	        DEFVAL  {nullgroup}
		::= { suInfoEntry 4 }

	suCIR OBJECT-TYPE
		SYNTAX	INTEGER (0..9999)
		ACCESS	read-only
		STATUS	mandatory
		DESCRIPTION
			"It is the Committed Information Rate (in Kbps) the AP allocates to SU."
		::= { suInfoEntry 5 }

	suMIR OBJECT-TYPE
		SYNTAX	INTEGER (0..9999)
		ACCESS	read-only
		STATUS	mandatory
		DESCRIPTION
			"It is the Maximum Information Rate (in Kbps) the AP allocates to SU."
		::= { suInfoEntry 6 }

	suIPAddr OBJECT-TYPE
		SYNTAX	IpAddress
		ACCESS	read-only
		STATUS	mandatory
		DESCRIPTION
			"Subscriber unit IP Address."
		::= { suInfoEntry 7 }

	suRemarks OBJECT-TYPE
        	SYNTAX  DisplayString (SIZE (0..30))
        	ACCESS  read-only
        	STATUS  mandatory
        	DESCRIPTION
            		"Subscriber unit Remark."
	        ::= { suInfoEntry 8 }
    

	suHWVer OBJECT-TYPE
		SYNTAX	OCTET STRING (SIZE(2))
		ACCESS	read-only
		STATUS	mandatory
		DESCRIPTION
			"Subscriber unit Hardware Version."
		::= { suInfoEntry 9 }

	suFWVer OBJECT-TYPE
	        SYNTAX  DisplayString (SIZE (0..32))
		ACCESS	read-only
		STATUS	mandatory
		DESCRIPTION
			"Subscriber unit main firmware version."
		::= { suInfoEntry 10 }

	suFPGAVer OBJECT-TYPE
		SYNTAX	OCTET STRING (SIZE(4))
		ACCESS	read-only
		STATUS	mandatory
		DESCRIPTION
			"Subscriber unit FPGA firmware version."
		::= { suInfoEntry 11 }

	suChecksum OBJECT-TYPE
		SYNTAX	OCTET STRING (SIZE(4))
		ACCESS	read-only
		STATUS	mandatory
		DESCRIPTION
			"Subscriber unit firmware checksum."
		::= { suInfoEntry 12 }

	suAssociation OBJECT-TYPE
        SYNTAX  INTEGER {
                    associated(1),
                    notAssociated(0)
                }
		ACCESS	read-only
		STATUS	mandatory
		DESCRIPTION
			"Subscriber unit association status."
		::= { suInfoEntry 13 }

	suDIstance OBJECT-TYPE
		SYNTAX	INTEGER (0..40)
		ACCESS	read-only
		STATUS	mandatory
		DESCRIPTION
			"Distance of SU (in mile)."
		::= { suInfoEntry 14 }

	suRSSIFromSU OBJECT-TYPE
		SYNTAX	INTEGER (-128..127)
		ACCESS	read-only
		STATUS	mandatory
		DESCRIPTION
			"Subscriber unit RSSI from SU (in dBm)."
		::= { suInfoEntry 15 }

	suRSSIFromAP OBJECT-TYPE
		SYNTAX	INTEGER (-128..127)
		ACCESS	read-only
		STATUS	mandatory
		DESCRIPTION
			"Subscriber unit RSSI from AP (in dBm)."
		::= { suInfoEntry 16 }

	suTxPower OBJECT-TYPE
		SYNTAX	INTEGER (-128..127)
		ACCESS	read-only
		STATUS	mandatory
		DESCRIPTION
			"Subscriber unit Tx Power Level (in dBm)."
		::= { suInfoEntry 17 }

	suEthRxAvgThroughputLog OBJECT-TYPE
		SYNTAX	INTEGER
		ACCESS	read-only
		STATUS	mandatory
		DESCRIPTION
			"Average payload data throughput (in Kbits/sec) received on the
	                 Ethernet port over the period specified by suStatisticsSamplePeriod."
		::= { suInfoEntry 18 }

	suEthTxAvgThroughputLog OBJECT-TYPE
		SYNTAX	INTEGER
		ACCESS	read-only
		STATUS	mandatory
		DESCRIPTION
			"Average payload data throughput (in Kbits/sec) transmitted on the
	                 Ethernet port over the period specified by suStatisticsSamplePeriod."
		::= { suInfoEntry 19 }

	suRfRxAvgThroughputLog OBJECT-TYPE
		SYNTAX	INTEGER
		ACCESS	read-only
		STATUS	mandatory
		DESCRIPTION
			"Average payload data throughput (in Kbits/sec) received on the
	                 RF port over the period specified by suStatisticsSamplePeriod."
		::= { suInfoEntry 20 }

	suRfTxAvgThroughputLog OBJECT-TYPE
		SYNTAX	INTEGER
		ACCESS	read-only
		STATUS	mandatory
		DESCRIPTION
			"Average payload data throughput (in Kbits/sec) transmitted on the
	                 RF port over the period specified by suStatisticsSamplePeriod."
		::= { suInfoEntry 21 }

	suRfInOctets OBJECT-TYPE
		SYNTAX 	Counter
		ACCESS	read-only
		STATUS	mandatory
		DESCRIPTION
			"Number of payload octets received on the RF port."
		::= { suInfoEntry 22 }

	suRfOutOctets OBJECT-TYPE
		SYNTAX 	Counter
		ACCESS	read-only
		STATUS	mandatory
		DESCRIPTION
			"Number of payload octets transmitted on the RF port."
		::= { suInfoEntry 23 }

	suPowerLevel OBJECT-TYPE
		SYNTAX	INTEGER {
                    deactivated(0),
                    activated(1)
                }
		ACCESS	read-write
		STATUS	mandatory
		DESCRIPTION
			"It is a feature that is typically found in more
 	                 elaborate mobile systems such as cellular CDMA
	                 networks. Using this feature, the SU has its
	                 RF power output adjusted until its signal strength
	                 received in the AP is roughly the same."
		::= { suInfoEntry 24 }

	suTemperature OBJECT-TYPE
        	SYNTAX  INTEGER (-128..127)
        	ACCESS  read-only
	        STATUS  mandatory
        	DESCRIPTION
            		"Subscriber Unit temperature reading value (in Celsius)."
	        ::= { suInfoEntry 25 }

    	suReboot OBJECT-TYPE
        	SYNTAX  INTEGER {
                    	deactivated(0),
                    	activated(1)
                	}
	        ACCESS  read-write
        	STATUS  mandatory
	        DESCRIPTION
            		"AP issues reboot command to a specific subscriber unit."
	        DEFVAL { deactivated }
        	::= { suInfoEntry 26 }

	suTCPIPForLocalEth OBJECT-TYPE
		SYNTAX	INTEGER {
                    disabled(0),
                    enabled(1)
                }
		ACCESS 	read-write
		STATUS 	mandatory
		DESCRIPTION
			"When it is turned on, then the SU will process all the local TCP/IP service."
		::= { suInfoEntry 27 }

	-- trapconfig objects
	trapconfigTrapCount OBJECT-TYPE
		SYNTAX	INTEGER (0..255)
		ACCESS	read-only
		STATUS	mandatory
		DESCRIPTION
			"Types of trap."
		::= { trapconfig 1 }
        
    	trapconfigDest1IPAddress OBJECT-TYPE
		SYNTAX	IpAddress
		ACCESS	read-write
		STATUS	mandatory
		DESCRIPTION
			"Trap destination 1 IP address."
		::= { trapconfig 2 }
         
    	trapconfigDest2IPAddress OBJECT-TYPE
		SYNTAX	IpAddress
		ACCESS	read-write
		STATUS	mandatory
		DESCRIPTION
			"Trap destination 2 IP address."
		::= { trapconfig 3 }
 
	trapconfigTrapTable OBJECT-TYPE
		SYNTAX	SEQUENCE OF TrapconfigTrapEntry
		ACCESS	not-accessible
		STATUS	mandatory
		DESCRIPTION
			"A table that contains information of Trango trap events ."
		::= { trapconfig 4 }
	
	trapconfigTrapEntry OBJECT-TYPE
		SYNTAX	TrapconfigTrapEntry
		ACCESS	not-accessible
		STATUS	mandatory
		DESCRIPTION
			"Information about a specific Trango trap event."
		INDEX	{ aptrpIndex }
		::= { trapconfigTrapTable 1 }

	TrapconfigTrapEntry ::=
		SEQUENCE {
			aptrpIndex
				INTEGER,
			aptrpID
				INTEGER,
			aptrpCommStr
				DisplayString,
			aptrpEnable
				INTEGER
		}

	aptrpIndex	OBJECT-TYPE
		SYNTAX	INTEGER (1..5)
		ACCESS	read-only
		STATUS	mandatory
		DESCRIPTION
			"Trap index."
		::= { trapconfigTrapEntry 1 }
	
	aptrpID	OBJECT-TYPE
		SYNTAX	INTEGER (7..255)
		ACCESS	read-only
		STATUS	mandatory
		DESCRIPTION
			"Specific trap ID."
		::= { trapconfigTrapEntry 2 }
	
	aptrpCommStr OBJECT-TYPE
        SYNTAX  DisplayString (SIZE (0..32))
		ACCESS	read-write
		STATUS	mandatory
		DESCRIPTION
			"Specific trap community string."
		::= { trapconfigTrapEntry 3 }
	
	aptrpEnable OBJECT-TYPE
		SYNTAX	INTEGER {
                    disabled(0),
                    enabled(1)
                }
		ACCESS	read-write
		STATUS	mandatory
		DESCRIPTION
			"Enable a specific Trango trap event or not."
	        DEFVAL  {disabled}
		::= { trapconfigTrapEntry 4 }
	
	-- MIB version object
	mibinfoVersion OBJECT-TYPE
        SYNTAX  DisplayString (SIZE (0..32))
		ACCESS	read-only
		STATUS	mandatory
		DESCRIPTION
			"Trango MIB Version."
		::= { mibinfo 1 }

	-- Trap objects
	suLinkUp TRAP-TYPE
		ENTERPRISE m5830straps
		VARIABLES { suID }
		DESCRIPTION
		  	"The SNMP trap that is generated when a specific SU Associated."
		::= 7

	suLinkDown TRAP-TYPE
		ENTERPRISE m5830straps
		VARIABLES { suID }
		DESCRIPTION
		  	"The SNMP trap that is generated when a specific SU Powered Off."
		::= 8

	apOpModeFailure TRAP-TYPE
		ENTERPRISE m5830straps
		VARIABLES { apsystemBaseId }
		DESCRIPTION
		  	"The SNMP trap that is generated when a specific AP
           		 not being in ap mode during boot up sequence."
		::= 9

-- End of file <trango_M5830SAP_1p1.mib>
END
