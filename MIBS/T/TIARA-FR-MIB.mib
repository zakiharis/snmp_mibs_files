-- *****************************************************************
-- tiaranet-fr.mib:  Tiara Networks FR/MFR MIB
--
-- July,1st 1999, kumar
--
-- Copyright (c) 1999-2000 by Tiara Networks, Inc.
-- All rights reserved.
--
-- *****************************************************************

TIARA-FR-MIB DEFINITIONS ::= BEGIN

IMPORTS
    MODULE-IDENTITY, OBJECT-TYPE, 
    IpAddress, Integer32, Counter32    FROM SNMPv2-SMI
    TruthValue, RowStatus              FROM SNMPv2-TC
    DisplayString                      FROM RFC1213-MIB
    bundleId                           FROM TIARA-BUNDLE-MIB
    tiaraMgmt                          FROM TIARA-NETWORKS-SMI;


tiaraFrMib MODULE-IDENTITY
    LAST-UPDATED    "9907010000Z" 
    ORGANIZATION    "Tiara Networks Inc."
    CONTACT-INFO
                    "Tiara Networks
                     Customer Support
                     525 Race Street, Suite 100,
                     San Jose, CA 95126
                     USA

                     Tel: +1 408-216-4700
                     Fax: +1 408-216-4701

                     E-mail: support@tiaranetworks.com"

    DESCRIPTION
                    "This file contains Tiara Network Inc. specific MIB 
                     module for Frame Relay implementation."
                     
    REVISION        "9904230000Z"
    DESCRIPTION
                    "Initial version of this MIB module."
                      
                     ::= { tiaraMgmt 16 } 


-- frTable definition.
-- This table contains both the uni-link and multi-link frame-relay 
-- configuration parameters. Multilink frame-relay parameters can be
-- configured only after the bundle is configured with more than 1 t1
-- links.
-- A row in the table is implicitly created when a bundle is encapped 
-- with frame-relay. The bundle Id of the frame-relay encapped bundle 
-- is used to index into the frTable.

frTable         OBJECT-TYPE
    SYNTAX      SEQUENCE OF FrTableEntry
    MAX-ACCESS  not-accessible
    STATUS      current
    DESCRIPTION
                "A list of a Frame Relay interface configuration parameters.
                 The table contains parameters for both the uni and multi
                 link frame-relay interface."
    ::= {tiaraFrMib 1}


frTableEntry    OBJECT-TYPE
    SYNTAX      FrTableEntry
    MAX-ACCESS  not-accessible
    STATUS      current
    DESCRIPTION
                "An entry in the frTable.
                 The bundle Id forms the index into the table."
    INDEX       { bundleId }
    ::= {frTable 1}


FrTableEntry    ::=  SEQUENCE {
    frIfEnable         TruthValue,
    frEnablePvcAll     TruthValue,
    frFrameSize        Integer32 (56..4096),
    frIfType           INTEGER, 
    frLmiType          INTEGER,
    frLmiDceN392       Integer32 (1..10),
    frLmiDceN393       Integer32 (1..10),
    frLmiDteN392       Integer32 (1..10),
    frLmiDteN393       Integer32 (1..10),
    frLmiDteN391       Integer32 (1..255),
    frLmiKeepalive     Integer32 (5..255),
    mfrAckMsgTimer     Integer32 (1..10),
    mfrAckMsgMaxRetry  Integer32 (1..5),
    mfrClass           INTEGER,
    mfrClassThreshold  Integer32 (1..28),
    mfrFrameSize       Integer32 (56..4096),
    mfrHelloTimer      Integer32 (1..180),
    mfrSegThreshold    Integer32 (56..4096),
    mfrDiffDelay       Integer32 (10..128)
}


frIfEnable       OBJECT-TYPE
    SYNTAX       TruthValue
    MAX-ACCESS   read-write
    STATUS       current
    DESCRIPTION 
                 "Enables or disables the frame-relay interface. By 
                  default frame- relay interface is enabled. Writing 
                  zero (0) disables frame-relay interface."
    DEFVAL       { true }
    ::= { frTableEntry 1 }


frEnablePvcAll  OBJECT-TYPE
    SYNTAX      TruthValue
    MAX-ACCESS  read-write
    STATUS      current
    DESCRIPTION 
                "Enables all PVCs related to the interface. By default all 
                 PVCs related to an interface are disabled. Writing One (1) 
                 enables all PVCs at the same time for an interface indexed 
                 by bundleId."
    DEFVAL      { false }
    ::= { frTableEntry 2 }


frFrameSize     OBJECT-TYPE
    SYNTAX      Integer32(56..4096)
    UNITS       "bytes"
    MAX-ACCESS  read-write
    STATUS      current
    DESCRIPTION 
                "Maximum Size of the frame that will be configured for 
                 this Frame Relay interface. The value for frame size 
                 ranges from 56 to 4096 bytes, with a default value of
                 1600 bytes."
    DEFVAL { 1600 }
    ::= { frTableEntry 3 }


frIfType          OBJECT-TYPE
    SYNTAX        INTEGER {
                    dce(1),
                    dte(2),
                    nni(3)
                  }
    MAX-ACCESS    read-write
    STATUS        current
    DESCRIPTION 
                  "Indicates the interface type for the frame-relay 
                   interface."
    DEFVAL        { dte }
    ::= { frTableEntry 4 }


frLmiType        OBJECT-TYPE
    SYNTAX       INTEGER {
                   none(0),
                   cisco(2),
                   ansi(3),
                   q933a(4)
                 }
    MAX-ACCESS   read-write
    STATUS       current
    DESCRIPTION 
                 "Local management Interface type for the frame-relay
                  interface.
                  It can take any of the following three values: 
                  ansi  - ANSI T1.617 (Annex D), 
                  cisco - Cisco LMI,
                  q933a - ITU-T Q.933 (Annex A)
                  To disable lmi operation, set the value to none(0)."
    DEFVAL { ansi }
    ::= { frTableEntry 5 }


frLmiDceN392    OBJECT-TYPE
    SYNTAX      Integer32(1..10)
    MAX-ACCESS  read-write
    STATUS      current
    DESCRIPTION
                "DCE/UNI error threshold value. Ranges from 1 to 10,
                 with a default value of 9.  To configure the value
                 of this variable, LMI type should be configured."
    DEFVAL { 9 }
    ::= { frTableEntry 6 }


frLmiDceN393    OBJECT-TYPE
    SYNTAX      Integer32(1..10)
    MAX-ACCESS  read-write
    STATUS      current
    DESCRIPTION 
                "DCE/UNI monitored events count. Ranges from 1 to 10,
                 with a default value of 10.  To configure the value 
                 of this variable, LMI type should be configured."
    DEFVAL { 10 }
    ::= { frTableEntry 7 }


frLmiDteN392    OBJECT-TYPE
    SYNTAX      Integer32(1..10)
    MAX-ACCESS  read-write
    STATUS      current
    DESCRIPTION 
                "DTE/UNI error threshold. Ranges from 1 to 10, with a 
                 default value of 9.  To configure the value of this 
                 variable, LMI type should be configured."
    DEFVAL { 9 }
    ::= { frTableEntry 8}


frLmiDteN393    OBJECT-TYPE
    SYNTAX      Integer32(1..10)
    MAX-ACCESS  read-write
    STATUS      current
    DESCRIPTION 
                "DTE/UNI monitored events count. Ranges from 1 to 10,
                 with a default value of 10.  To configure the value
                 of this variable, LMI type should be configured."
    DEFVAL { 10 }
    ::= { frTableEntry 9 }


frLmiDteN391    OBJECT-TYPE
    SYNTAX      Integer32(1..255)
    MAX-ACCESS  read-write
    STATUS      current
    DESCRIPTION 
                "DTE/UNI full status polling interval. Ranges from 1 
                 to 255, with a default value of 6.  To configure the
                 value of this variable, LMI type should be configured."
    DEFVAL { 6 }
    ::= { frTableEntry 10 }


frLmiKeepalive    OBJECT-TYPE
    SYNTAX        Integer32(5..255)
    MAX-ACCESS    read-write
    STATUS        current
    DESCRIPTION 
                  "Local management interface keepalive polling interval
                   time in seconds. The value for this ranges from 5 
                   seconds to 255 seconds with a default value of 10 
                   seconds. To configure the value of this variable, 
                   LMI type should be configured."
    DEFVAL { 10 }
    ::= { frTableEntry 11}
    

mfrAckMsgTimer        OBJECT-TYPE
        SYNTAX        Integer32 (1..10)
        MAX-ACCESS    read-write
        STATUS        current
        DESCRIPTION
                      "The time to wait for an ADD_LINK_ACK message 
                       before timing out."
        DEFVAL {4}
        ::= { frTableEntry 12}


mfrAckMsgMaxRetry     OBJECT-TYPE
        SYNTAX        Integer32 (1..5)
        MAX-ACCESS    read-write
        STATUS        current
        DESCRIPTION 
                      "Maximum number of Retries for the Ack Msg. This 
                       variable can be set on a multilink bundle."
        DEFVAL  { 2 }
       ::= { frTableEntry 13 }


mfrClass         OBJECT-TYPE
    SYNTAX       INTEGER {
                   classA(1),
                   classB(2),
                   classC(3)
                 }
    MAX-ACCESS   read-write
    STATUS       current
    DESCRIPTION
                 "classA  -- bundle is UP when 1 link is UP
                  classB  -- bundle is UP when all links are UP
                  classC  -- bundle is UP when user-specific # of links 
                             are UP. 
                  In the case of classC, mfrClassThreshold should be 
                  configured with mfrClass in an atomic set operation.
                  This variable can be set on a multilink bundle but 
                  not on a uni link bundle."
    ::= { frTableEntry 14 }


mfrClassThreshold    OBJECT-TYPE
    SYNTAX           Integer32 (1..28)
    MAX-ACCESS       read-write
    STATUS           current
    DESCRIPTION
                     "Threshold - minimum number of links required to
                      activate bundle, for a mfrClass, classC. This 
                      variable can be set on a multilink bundle but not 
                      on a uni link bundle."
        ::= {frTableEntry 15 }


mfrFrameSize         OBJECT-TYPE
        SYNTAX       Integer32 (56..4096)
        MAX-ACCESS   read-write
        STATUS       current
        DESCRIPTION 
                     "The frame size for multi-link frame relay. This 
                      variable can be set on a multilink bundle but not
                      on a uni link bundle."
        ::= {frTableEntry 16 }


mfrHelloTimer        OBJECT-TYPE
        SYNTAX       Integer32 (1..180)
        MAX-ACCESS   read-write
        STATUS       current
        DESCRIPTION 
                     "Hello timer in seconds. This variable can be set
                      on a multilink bundle but not on a uni link bundle."
        ::= {frTableEntry 17 }


mfrSegThreshold      OBJECT-TYPE
        SYNTAX       Integer32 (56..4096)
        MAX-ACCESS   read-write
        STATUS       current
        DESCRIPTION 
                     "Segment threshold packet size in bytes. This variable
                      can be set on a multilink bundle but not on a uni link
                      bundle."
        ::= {frTableEntry 18 }


mfrDiffDelay         OBJECT-TYPE
        SYNTAX       Integer32 (10..128)
        MAX-ACCESS   read-write
        STATUS       current
        DESCRIPTION 
                     "Differential delay in milli seconds. This variable 
                      can be set on a multilink bundle but not on a uni 
                      link bundle."
        ::= { frTableEntry 19 }


-- frPvcTable definition
-- To configure a PVC on a frame-relay encapped bundle, set rowstatus
-- with a value CreateAndGo(4).
-- The index to the table is the bundle Id and the desired pvc number.


frPvcTable      OBJECT-TYPE
    SYNTAX      SEQUENCE OF FrPvcTableEntry
    MAX-ACCESS  not-accessible
    STATUS      current
    DESCRIPTION
                "A list of Frame Relay PVC parameters."
    ::= {tiaraFrMib 2}


frPvcTableEntry     OBJECT-TYPE
    SYNTAX          FrPvcTableEntry
    MAX-ACCESS      not-accessible
    STATUS          current
    DESCRIPTION
                    "An entry in the frPvcTable"
    INDEX           { bundleId, frPvcDlci }
    ::= { frPvcTable 1 }


FrPvcTableEntry  ::= SEQUENCE {
    frPvcDlci                      Integer32(16..991),
    frPvcEnable                    TruthValue, 
    frPvcDescr                     DisplayString,
    frPvcIpAddr                    IpAddress,
    frPvcIpSubnetMask              IpAddress,
    frPvcSrcForwardingPrimary      IpAddress,
    frPvcSrcForwardingSecondary    IpAddress,
    frPvcRemoteIpAddr              IpAddress,
    frPvcPolicingEnable            INTEGER,
    frPvcPolicingDe                TruthValue, 
    frPvcPolicingCir               Integer32,
    frPvcPolicingBc                Integer32,
    frPvcPolicingBe                Integer32,
    frPvcShapingCir                Integer32,
    frPvcShapingBcMax              Integer32,
    frPvcShapingBcMin              Integer32,
    frPvcShapingBe                 Integer32,
    frPvcDlciForSwitching          Integer32,
    frPvcBundleNameForSwitching    DisplayString,
    frPvcRowStatus                 RowStatus
  }


frPvcDlci           OBJECT-TYPE
    SYNTAX          Integer32(16..991)
    MAX-ACCESS      not-accessible
    STATUS          current
    DESCRIPTION
                    "Data Link Connection Identifier of the PVC. The value
                     ranges from 16 to 991. The Dlci is unique for a bundle
                     but Dlci numbers can be reused across bundles."
    ::= { frPvcTableEntry 1 }


frPvcEnable         OBJECT-TYPE
    SYNTAX          TruthValue 
    MAX-ACCESS      read-create
    STATUS          current
    DESCRIPTION
                    "Enables PVC for given interface name and DLCI number. By 
                     default PVC is disabled. Writing one(1) on this enables
                     PVC."
    DEFVAL          { false }
    ::= { frPvcTableEntry 2}


frPvcDescr       OBJECT-TYPE
    SYNTAX       DisplayString
    MAX-ACCESS   read-create
    STATUS       current
    DESCRIPTION
                 "Description for the configured PVC."
    DEFVAL      { "" }
    ::= { frPvcTableEntry 3 }


frPvcIpAddr       OBJECT-TYPE
    SYNTAX        IpAddress
    MAX-ACCESS    read-create
    STATUS        current
    DESCRIPTION
                  "IP address to be configured for the PVC. 
                   PVC IP subnet Mask variable should also be configured 
                   alongwith this variable. A set on this variable will be
                   successful only if the subnetmask is also set in the 
                   same request. To unconfigure the Ip address, a set is 
                   issued with the value of the ip address as 0.0.0.0"
    ::= { frPvcTableEntry 4 }
    

frPvcIpSubnetMask   OBJECT-TYPE
    SYNTAX          IpAddress
    MAX-ACCESS      read-create
    STATUS          current
    DESCRIPTION
                   "Subnet mask to be configured alongwith PVC IP address.
                    This variable should be configured alongwith PVC IP 
                    address."
    ::= { frPvcTableEntry 5 }


frPvcSrcForwardingPrimary   OBJECT-TYPE
    SYNTAX       IpAddress
    MAX-ACCESS   read-create
    STATUS       current
    DESCRIPTION
                 "Source forwarding IP address to be configured for PVC. To
                  unconfigure the source forwarding address, a set is issued
                  with the value of the address as 0.0.0.0. This is the
                  primary source forwarding address"
    ::= { frPvcTableEntry 6}
        
frPvcSrcForwardingSecondary OBJECT-TYPE
    SYNTAX       IpAddress
    MAX-ACCESS   read-create
    STATUS       current
    DESCRIPTION
                 "Optional secondary source forwarding address configured
                  for PVC, using alternate ethernet as backup. This 
                  variable should be configured along with the PVC primary
                  source forwarding address. To unconfigure the secondary 
                  forwarding address, a set is issued with the value of 
                  the primary source forwarding address as 0.0.0.0, or
                  a primary source forwarding address is set only, or both
                  primary and secondary are set to 0.0.0.0"
    ::= { frPvcTableEntry 7}

frPvcRemoteIpAddr    OBJECT-TYPE
    SYNTAX           IpAddress
    MAX-ACCESS       read-create
    STATUS           current
    DESCRIPTION
                     "Remote IP address to be mapped for PVC"
    ::= { frPvcTableEntry 8 }


frPvcPolicingEnable    OBJECT-TYPE
    SYNTAX             INTEGER {
                         none(0),
                         standard(2)
                       }
    MAX-ACCESS         read-create
    STATUS             current
    DESCRIPTION
                       "This variable is to disable/enable policing for PVC.
                        Writing zero (0) on this disables policing for the
                        PVC. By default policing is enabled."
    DEFVAL            { standard }
    ::= { frPvcTableEntry 9 }


frPvcPolicingDe     OBJECT-TYPE
    SYNTAX          TruthValue 
    MAX-ACCESS      read-create 
    STATUS          current
    DESCRIPTION
                    "If enabled, received frames that exceed policing 
                     threshold, will be tagged with DE bit. This variable
                     can be configured only if policing is enabled."
    DEFVAL { true }
    ::= { frPvcTableEntry 10 }


frPvcPolicingCir    OBJECT-TYPE
    SYNTAX          Integer32 
    UNITS           "bps"
    MAX-ACCESS      read-create
    STATUS          current
    DESCRIPTION
                    "Committed Information Rate( bits per second ) 
                     in receive direction for PVC. This variable can be
                     configured only if policing is enabled."
    ::= { frPvcTableEntry 11 }


frPvcPolicingBc     OBJECT-TYPE
    SYNTAX          Integer32 
    UNITS           "bps"
    MAX-ACCESS      read-create
    STATUS          current
    DESCRIPTION
                    "Committed Burst ( bits ) in receive direction for PVC.
                     This variable can be configured only if policing is 
                     enabled."
    ::= { frPvcTableEntry 12 }


frPvcPolicingBe     OBJECT-TYPE
    SYNTAX          Integer32
    MAX-ACCESS      read-create
    STATUS          current
    DESCRIPTION
                   "Excess burst ( bits ) in receive direction for PVC. This
                   variable can be configured only if policing enabled."
    DEFVAL         { 0 }
    ::= { frPvcTableEntry 13 }


frPvcShapingCir   OBJECT-TYPE
    SYNTAX        Integer32
    UNITS         "bps"
    MAX-ACCESS    read-create
    STATUS        current
    DESCRIPTION
                  "The committed information rate (in bits per second) to be 
                   configured for the PVC."
    ::= { frPvcTableEntry 14 }


frPvcShapingBcMax    OBJECT-TYPE
        SYNTAX       Integer32
        UNITS        "bps"
        MAX-ACCESS   read-create
        STATUS       current
        DESCRIPTION
                     "The maximum committed burst (bits) to be configured
                      for the PVC."
        ::= { frPvcTableEntry 15 }


frPvcShapingBcMin     OBJECT-TYPE
    SYNTAX            Integer32
    UNITS             "bps"
    MAX-ACCESS        read-create
    STATUS            current
    DESCRIPTION
                      "The minimum committed burst (bits) to be configured
                       for the PVC."
    ::= { frPvcTableEntry 16}


frPvcShapingBe       OBJECT-TYPE
    SYNTAX       Integer32
    MAX-ACCESS   read-create
    STATUS       current
    DESCRIPTION
                 "The excess burst (bits) to be configured for the PVC."
    DEFVAL       { 0 }
    ::= { frPvcTableEntry 17 }


frPvcDlciForSwitching     OBJECT-TYPE
    SYNTAX                Integer32
    MAX-ACCESS            read-create
    STATUS                current
    DESCRIPTION
                          "Data Link Connection Identifier of the PVC. The 
                           value for this variable ranges from 16 to 991.
                           frPvcBundleNameForSwitching should be set with 
                           frPvcDlciForSwitching as an atomic set."
    ::= { frPvcTableEntry 18 }


frPvcBundleNameForSwitching    OBJECT-TYPE
    SYNTAX                     DisplayString
    MAX-ACCESS                 read-create
    STATUS                     current
    DESCRIPTION
                               "The name of the bundle configured for Switching."
    ::= { frPvcTableEntry 19 }


frPvcRowStatus     OBJECT-TYPE
    SYNTAX         RowStatus
    MAX-ACCESS     read-create
    STATUS         current
    DESCRIPTION
                   "To create a row set row status to a value 
                    CreateAndGo(4), indexed by bundle Id and the 
                    desired dlci number."
    ::= { frPvcTableEntry 20 }


-- frStatsTable Definition
-- This table lists the statistics objects for a frame relay interface.
-- A row in the table is implicitly created when a bundle is encapped 
-- with frame-relay. The bundle Id of the frame-relay encapped bundle 
-- is used to index into the frTable

frStatsTable    OBJECT-TYPE
    SYNTAX      SEQUENCE OF FrStatsTableEntry
    MAX-ACCESS  not-accessible
    STATUS      current
    DESCRIPTION
                "The statistics objects for a frame-relay interface."
    ::= { tiaraFrMib 3 }


frStatsTableEntry   OBJECT-TYPE
    SYNTAX          FrStatsTableEntry
    MAX-ACCESS      not-accessible
    STATUS          current
    DESCRIPTION
                    "An entry in the frStatsTable."
    INDEX           { bundleId }
    ::= {frStatsTable 1 }


FrStatsTableEntry  ::= SEQUENCE {
    frStatsFramesRx        Counter32,
    frStatsInvFramesRx     Counter32,
    frStatsFECNsRx         Counter32,
    frStatsBECNsRx         Counter32,
    frStatsShortFramesRx   Counter32,
    frStatsLongFramesRx    Counter32,
    frStatsInvDLCIsRx      Counter32,
    frStatsUnknownDLCIsRx  Counter32,
    frStatsFramesTx        Counter32 
}


frStatsFramesRx    OBJECT-TYPE
    SYNTAX         Counter32
    MAX-ACCESS     read-only
    STATUS         current
    DESCRIPTION 
                   "Numbers of frames received."
    ::= { frStatsTableEntry 1 }


frStatsInvFramesRx   OBJECT-TYPE
    SYNTAX           Counter32
    MAX-ACCESS       read-only
    STATUS           current
    DESCRIPTION 
                     "Number of invalid frames received"
    ::= { frStatsTableEntry 2 }


frStatsFECNsRx    OBJECT-TYPE
    SYNTAX        Counter32
    MAX-ACCESS    read-only
    STATUS        current
    DESCRIPTION 
                  "Number of frames received with FECN bit on"
    ::= { frStatsTableEntry 3 }


frStatsBECNsRx  OBJECT-TYPE
    SYNTAX      Counter32
    MAX-ACCESS  read-only
    STATUS      current
    DESCRIPTION 
                "Number of frames received with BECN bit on."
    ::= { frStatsTableEntry 4 }


frStatsShortFramesRx    OBJECT-TYPE
    SYNTAX              Counter32
    MAX-ACCESS          read-only
    STATUS              current
    DESCRIPTION 
                        "Number of short frames received."
    ::= { frStatsTableEntry 5 }


frStatsLongFramesRx    OBJECT-TYPE
    SYNTAX             Counter32
    MAX-ACCESS         read-only
    STATUS             current
    DESCRIPTION 
                       "Number of long frames received."
    ::= { frStatsTableEntry 6 }


frStatsInvDLCIsRx    OBJECT-TYPE
    SYNTAX           Counter32
    MAX-ACCESS       read-only
    STATUS           current
    DESCRIPTION 
                     "Number of frames with invalid dlci received"
    ::= { frStatsTableEntry 7 }


frStatsUnknownDLCIsRx    OBJECT-TYPE
    SYNTAX               Counter32
    MAX-ACCESS           read-only
    STATUS               current
    DESCRIPTION 
                         "Number of frames with unknown dlci received"
    ::= { frStatsTableEntry 8 }


frStatsFramesTx     OBJECT-TYPE
    SYNTAX          Counter32
    MAX-ACCESS      read-only
    STATUS          current
    DESCRIPTION 
                    "Number of frames transmitted."
    ::= { frStatsTableEntry 9 }



-- FrPvcStats Table Definition
-- Statistics for a PVC
-- A row in the table is implicitly created when a pvc is configured 
-- on a bundle. The bundle Id and the dlci number are used as indices
-- to the table.


frPvcStatsTable   OBJECT-TYPE
    SYNTAX        SEQUENCE OF FrPvcStatsTableEntry
    MAX-ACCESS    not-accessible
    STATUS        current
    DESCRIPTION
                  "FR PVC Statistics Table"
    ::= {tiaraFrMib 4}


frPvcStatsTableEntry    OBJECT-TYPE
    SYNTAX              FrPvcStatsTableEntry
    MAX-ACCESS          not-accessible
    STATUS              current
    DESCRIPTION
                        "An entry in the FrPvcStats Table"
    INDEX               { bundleId, frPvcDlci }
    ::= {frPvcStatsTable 1 }


FrPvcStatsTableEntry ::= SEQUENCE {
    frPvcStatsBytesRxLastBootOrClear       Counter32,
    frPvcStatsBytesTxLastBootOrClear       Counter32,
    frPvcStatsPktsRxLastBootOrClear        Counter32,
    frPvcStatsPktsTxLastBootOrClear        Counter32,
    frPvcStatsErrPktsRxLastBootOrClear     Counter32,
    frPvcStatsUpDownStatesLastBootOrClear  Counter32,
    frPvcStatsBytesRxLastFiveMins          Counter32,
    frPvcStatsBytesTxLastFiveMins          Counter32,
    frPvcStatsPktsRxLastFiveMins           Counter32,
    frPvcStatsPktsTxLastFiveMins           Counter32,
    frPvcStatsErrPktsRxLastFiveMins        Counter32,
    frPvcStatsUpDownStatesLastFiveMins     Counter32
}


frPvcStatsBytesRxLastBootOrClear    OBJECT-TYPE
    SYNTAX                          Counter32
    MAX-ACCESS                      read-only
    STATUS                          current
    DESCRIPTION 
                                    "Number of bytes received on a pvc since
                                     boot or last statistics clear."
    ::= { frPvcStatsTableEntry 1 }


frPvcStatsBytesTxLastBootOrClear   OBJECT-TYPE
    SYNTAX                         Counter32
    MAX-ACCESS                     read-only
    STATUS                         current
    DESCRIPTION 
                                   "Number of bytes transmitted on a pvc since 
                                   boot or last statistics clear."
    ::= { frPvcStatsTableEntry 2 }


frPvcStatsPktsRxLastBootOrClear   OBJECT-TYPE
    SYNTAX                        Counter32
    MAX-ACCESS                    read-only
    STATUS                        current
    DESCRIPTION 
                                  "Number of packets received  since boot 
                                   or last statistics clear."
    ::= { frPvcStatsTableEntry 3 }


frPvcStatsPktsTxLastBootOrClear   OBJECT-TYPE
    SYNTAX                        Counter32
    MAX-ACCESS                    read-only
    STATUS                        current
    DESCRIPTION 
                                  "Number of packets transmitted since boot 
                                   or last statistics clear."
    ::= { frPvcStatsTableEntry 4 }


frPvcStatsErrPktsRxLastBootOrClear   OBJECT-TYPE
    SYNTAX                           Counter32
    MAX-ACCESS                       read-only
    STATUS                           current
    DESCRIPTION 
                                     "Number of errored packets received since
                                      boot or last statistics clear."
   ::= { frPvcStatsTableEntry 5 }


frPvcStatsUpDownStatesLastBootOrClear   OBJECT-TYPE
   SYNTAX                               Counter32
   MAX-ACCESS                           read-only
   STATUS                               current
   DESCRIPTION 
                                        "Number of times state(up or down) of
                                         the pvc changed in since boot or last
                                         statistics clear."
   ::= { frPvcStatsTableEntry 6 }


frPvcStatsBytesRxLastFiveMins          OBJECT-TYPE
    SYNTAX                             Counter32
    MAX-ACCESS                         read-only
    STATUS                             current
    DESCRIPTION 
                                       "Number of bytes received in the last 
                                        five minutes."
    ::= { frPvcStatsTableEntry 7 }


frPvcStatsBytesTxLastFiveMins          OBJECT-TYPE
    SYNTAX                             Counter32
    MAX-ACCESS                         read-only
    STATUS                             current
    DESCRIPTION 
                                       "Number of bytes transmitted in the last
                                        five minutes."
    ::= { frPvcStatsTableEntry 8 }


frPvcStatsPktsRxLastFiveMins           OBJECT-TYPE
    SYNTAX                             Counter32
    MAX-ACCESS                         read-only
    STATUS                             current
    DESCRIPTION 
                                       "Number of packets received in the last
                                        five minutes."
    ::= { frPvcStatsTableEntry 9 }


frPvcStatsPktsTxLastFiveMins          OBJECT-TYPE
    SYNTAX                            Counter32
    MAX-ACCESS                        read-only
    STATUS                            current
    DESCRIPTION 
                                      "Number of packets transmitted in the last
                                       five minutes."
    ::= { frPvcStatsTableEntry 10 }


frPvcStatsErrPktsRxLastFiveMins       OBJECT-TYPE
    SYNTAX                            Counter32
    MAX-ACCESS                        read-only
    STATUS                            current
    DESCRIPTION 
                                      "Number of errored packets received in the
                                       last five minutes." 
    ::= { frPvcStatsTableEntry 11 }

frPvcStatsUpDownStatesLastFiveMins    OBJECT-TYPE
    SYNTAX                            Counter32
    MAX-ACCESS                        read-only
    STATUS                            current
    DESCRIPTION 
                                      "Number of times state(up or down) of
                                       the pvc changed in the last five
                                       minutes."
    ::= { frPvcStatsTableEntry 12 }

-- frAvcTable definition
-- The following avc table lists all parameters associated with a 
-- avc.  Items such as encapsulation, IP address, and subnet mask
-- need to have proper values for the avc to function properly.
-- Default values may not work.

frAvcTable         OBJECT-TYPE
        SYNTAX          SEQUENCE OF FrAvcTableEntry
        MAX-ACCESS      not-accessible
        STATUS          current
        DESCRIPTION 
                        "End-to-End MFR avc parameters are defined
                        in this table."
        ::= {tiaraFrMib 5}

frAvcTableEntry    OBJECT-TYPE
        SYNTAX          FrAvcTableEntry
        MAX-ACCESS      not-accessible
        STATUS          current
        DESCRIPTION     "avc parameter entries are listed in this 
                        table."
        INDEX           { frAvcId }
        ::= {frAvcTable 1}

FrAvcTableEntry ::= SEQUENCE {
        frAvcId                         INTEGER,
        frAvcDlci                       Integer32(16..991),
        frAvcName                       DisplayString,
        frAvcDescr                      DisplayString,
        frAvcIpAddr                     IpAddress,
        frAvcIpSubnetMask               IpAddress,
        frAvcSrcForwardingPrimary       IpAddress,
        frAvcSrcForwardingSecondary     IpAddress,
        frAvcRemoteIpAddr               IpAddress,
        frAvcClass                      INTEGER,
        frAvcClassThreshold             Integer32,
        frAvcFragmentSize               Integer32,
        frAvcSegThreshold               Integer32,
        frAvcSequence                   INTEGER,
        frAvcNoOfCvcs                   Integer32,
        frAvcTotalBw                    Integer32,
        frAvcRowStatus                  RowStatus   
        }

frAvcId            OBJECT-TYPE
        SYNTAX          INTEGER 
        MAX-ACCESS      not-accessible  
        STATUS          current
        DESCRIPTION     "frAvcId is the identifier of an avc. To 
                        configure an avc, this parameter must be 
                        used as the index. This is assigned internally 
                        by the Tiara system. Whenever a row creation 
                        needs to occur in the avcTable, the 
                        frAvcId is entered as 65535."
        ::= { frAvcTableEntry 1}


frAvcDlci           OBJECT-TYPE
    SYNTAX          Integer32(16..991)
    MAX-ACCESS      read-create
    STATUS          current
    DESCRIPTION
                    "Data Link Connection Identifier of the avc. The value
                     ranges from 16 to 1022. This number is unique across
                     all the avcs created. Once set during creation,
                     it can't be changed."
        ::= { frAvcTableEntry 2}

frAvcName          OBJECT-TYPE
        SYNTAX          DisplayString (SIZE (1..8))
        MAX-ACCESS      read-create
        STATUS          current
        DESCRIPTION     "Name of the avc. To configure an avc, 
                        this parameter must be set. That is, a 
                        descriptive name should be given to an avc. 
                        The maximum length of an avc name is 8 
                        characters. This parameter is set once during 
                        the creation of an avc. an avc can not be 
                        renamed." 
        ::= { frAvcTableEntry 3}

frAvcDescr         OBJECT-TYPE
        SYNTAX          DisplayString (SIZE (1..25))
        MAX-ACCESS      read-create
        STATUS          current
        DESCRIPTION     "Brief description of the avc. The maximum 
                        length of this parameter is 25 characters."
        DEFVAL          { "" }
        ::= { frAvcTableEntry 4 }

frAvcIpAddr        OBJECT-TYPE
        SYNTAX          IpAddress
        MAX-ACCESS      read-create
        STATUS          current
        DESCRIPTION     "The avc's source IP address. This is one 
                        of the parameters required to set up IP 
                        multiplexing for an avc. Also the parameters
                        avcIpAddr and avcSubnetMask have to be set 
                        together during the same request. To unconfigure 
                        the IP address, a set operation is performed with 
                        the value 0.0.0.0" 
        DEFVAL          { 0 }  
        ::= { frAvcTableEntry 5}

frAvcIpSubnetMask    OBJECT-TYPE
        SYNTAX          IpAddress
        MAX-ACCESS      read-create
        STATUS          current
        DESCRIPTION     "This parameter represents the source subnet 
                        mask address. This is one of the parameters 
                        required to set up IP multiplexing for a 
                        avc. This parameter is set along with the 
                        avcIpAddr parameter during the same 
                        request." 
        DEFVAL          { 0 }  
        ::= { frAvcTableEntry 6}

frAvcSrcForwardingPrimary  OBJECT-TYPE
        SYNTAX          IpAddress
        MAX-ACCESS      read-create
        STATUS          current
        DESCRIPTION     "The avc's destination IP address. This is 
                        one of the parameters required to set up IP 
                        multiplexing for an avc. This parameter can 
                        be configured when the avc has been 
                        configured for IP multiplexing. To unconfigure 
                        the source forwarding address, a set operation 
                        is performed with the value 0.0.0.0. This is
                        the primary source forwarding address" 
        DEFVAL          { 0 }  
        ::= { frAvcTableEntry 7}

frAvcSrcForwardingSecondary OBJECT-TYPE
        SYNTAX          IpAddress
        MAX-ACCESS      read-create
        STATUS          current
        DESCRIPTION     "The avc's secondary or backup destination 
                        address. This address will be used only if  
                        the primary address uses an ethernet interface
                        and failover is enabled on that interface and
                        the interface goes down. The secondary source
                        forwarding address is an optional parameter, 
                        it should be a gateway on the alternate
                        ethernet This parameter is set along with the
                        primary source forwarding address parameter. 
                        To unconfigure this parameter a set operation 
                        is performed with the value 0.0.0.0 for the
                        primary address, or a primary address is set
                        with no secondary, or both primary and 
                        secondary are set to 0.0.0.0"
        DEFVAL          { 0 }  
        ::= { frAvcTableEntry 8}

frAvcRemoteIpAddr      OBJECT-TYPE
    SYNTAX           IpAddress
    MAX-ACCESS       read-create
    STATUS           current
    DESCRIPTION
                     "Remote IP address to be mapped for the avc. If configured,
                      the arp table is updated with this static entry and
                      inverse arp request packets are no longer sent for this
                      interface.To unconfigure this parameter, a set operation
                      is performed with the value 0.0.0.0 ."
        ::= { frAvcTableEntry 9}


frAvcClass           OBJECT-TYPE
    SYNTAX         INTEGER {
                   classA(1),
                   classB(2),
                   classC(3),
                   classD(4),
                   classE(5)
                 }
    MAX-ACCESS   read-write
    STATUS       current
    DESCRIPTION
                 "classA  -- avc is UP when at least 1 cvc is UP
                  classB  -- avc is UP when all cvcs are UP
                  classC  -- avc is UP when user-specified # of cvcs are UP
                  classD  -- avc is UP when user-specified min. CIR of each cvc is met
                  classE  -- avc is UP when user-specified min. CIR of the avc is met
                  In the case of classC/D/E, frAvcClassThreshold should be 
                  configured along with avcClass in an atomic set operation."
        ::= { frAvcTableEntry 10 }

frAvcClassThreshold    OBJECT-TYPE
    SYNTAX           Integer32
    MAX-ACCESS       read-write
    STATUS           current
    DESCRIPTION
                     "Threshold - minimum number of links required to
                      activate bundle, for the avcClass 'classC'. For
                      'classD' or 'classE', the value will be in bits per second.
                      For 'classA' and 'classB', this value will hold no
                      significance. "
        ::= { frAvcTableEntry 11}

frAvcFragmentSize      OBJECT-TYPE
        SYNTAX       Integer32 (56..4096)
        MAX-ACCESS   read-write
        STATUS       current
        DESCRIPTION 
                     "The frame size for multi-link frame relay End-to-End avc in 
                      bytes.  This value defines the maximum size of any fragment 
                      that can be transmitted on any cvc. Frames larger than this
                      size must be fragmented."
        ::= { frAvcTableEntry 12}

frAvcSegThreshold      OBJECT-TYPE
        SYNTAX       Integer32 (56..4096)
        MAX-ACCESS   read-write
        STATUS       current
        DESCRIPTION 
                     "Segment threshold packet size in bytes. This value defines
                      the minimum size of any fragment that can be transmitted on
                      any cvc. Frames smaller than this size must not be fragmented."
        ::= { frAvcTableEntry 13}

frAvcSequence          OBJECT-TYPE
	    SYNTAX       INTEGER {
		             short(1),
		             long(2)
		           }
    MAX-ACCESS   read-write
    STATUS       current
    DESCRIPTION
		"multilink frame relay sequence number length (short = 12 bits ; long = 
		24 bits.24 bit sequence space increases MFR header by 2 more bytes, but
        in those situations where the differential delay is high ( > 50 ms ),
        larger sequence numbers help reduce packet drops that can happen when
        short sequence numbers complete a cycle quickly."
	DEFVAL { long }
	::= { frAvcTableEntry 14}

frAvcNoOfCvcs      OBJECT-TYPE
        SYNTAX          Integer32
        MAX-ACCESS      read-only
        STATUS          current
        DESCRIPTION     "Indicates the number of links configured in 
                        the avc." 
        ::= { frAvcTableEntry 15}

frAvcTotalBw       OBJECT-TYPE
        SYNTAX          Integer32
        UNITS           "kbps"
        MAX-ACCESS      read-only
        STATUS          current
        DESCRIPTION     "Indicates the total bandwidth for this avc.
                        The avc bandwidth is the aggregated band-
                        widths of all the links assigned to a 
                        particular avc." 
        ::= { frAvcTableEntry 16}

frAvcRowStatus OBJECT-TYPE
        SYNTAX          RowStatus
        MAX-ACCESS      read-create
        STATUS          current
        DESCRIPTION     "frAvcRowStatus is used to add/delete a row 
                        in the table. Adding or deleting a row 
                        corresponds to creating an avc or deleting
                        an avc.  In order to add a row to the avc 
                        table, a set on this parameter should be done 
                        with the value 4 (createAndGo) and 
                        frAvcId parameter set with the value of 65535. 
                        A request to create a row can be 
                        completed successfully only if a set on the 
                        avcRowStatus and a set on the avcName 
                        come in the same request. To delete a row 
                        this parameter has to be set with the value 6
                        (destroy)." 
        ::= { frAvcTableEntry 17}

-- frCvcTable definition
-- The following avc table lists the two parameters associated with a 
-- cvc. The dlci and the bundle , the cvc belongs to.

frCvcTable         OBJECT-TYPE
        SYNTAX          SEQUENCE OF FrCvcTableEntry
        MAX-ACCESS      not-accessible
        STATUS          current
        DESCRIPTION 
                        "End-to-End MFR cvc parameters are defined
                        in this table."
        ::= {tiaraFrMib 6}

frCvcTableEntry    OBJECT-TYPE
        SYNTAX          FrCvcTableEntry
        MAX-ACCESS      not-accessible
        STATUS          current
        DESCRIPTION     "cvc parameter entries are listed in this 
                        table."
        INDEX           { frAvcId,bundleId,frCvcDlci }
        ::= {frCvcTable 1}

FrCvcTableEntry ::= SEQUENCE {
        frCvcDlci                       Integer32(16..991),
        frCvcBundleName                 DisplayString
        }

frCvcDlci           OBJECT-TYPE
    SYNTAX          Integer32(16..991)
    MAX-ACCESS      read-create
    STATUS          current
    DESCRIPTION
                    "Data Link Connection Identifier of the cvc. For End-to-End 
                     MFR avc, to assign a Constituent Virtual Circuit for 
                     aggregation, this CVC dlci is used in conjunction with
                     the cvcBundleName as an atomic set."
        ::= { frCvcTableEntry 1}


frCvcBundleName     OBJECT-TYPE
    SYNTAX          DisplayString
    MAX-ACCESS      read-create
    STATUS          current
    DESCRIPTION
                   "The name of the bundle of the CVC which needs to be added
                    to the avc. This parameter is used in confunction with the
                    frCvcDlci parameter as one atomic set operation."
        ::= { frCvcTableEntry 2}

-- avcStatsTable Definition
-- This table lists the statistics objects for a frame relay DTE-to-DTE
-- AVC interface.
-- A row in the table is implicitly created when an AVC is created. 
-- The frAvcId of the frame-relay AVC is used to index into the table. 

frAvcStatsTable    OBJECT-TYPE
    SYNTAX      SEQUENCE OF AvcStatsTableEntry
    MAX-ACCESS  not-accessible
    STATUS      current
    DESCRIPTION
                "The statistics objects for a frame-relay interface."
    ::= { tiaraFrMib 7 }


frAvcStatsTableEntry   OBJECT-TYPE
    SYNTAX          AvcStatsTableEntry
    MAX-ACCESS      not-accessible
    STATUS          current
    DESCRIPTION
                    "An entry in the frAvcStatsTable."
    INDEX           { frAvcId }
    ::= {frAvcStatsTable 1 }


AvcStatsTableEntry  ::= SEQUENCE {
    frAvcStatsBytesRxLastBootOrClear       Counter32,
    frAvcStatsBytesTxLastBootOrClear       Counter32,
    frAvcStatsPktsRxLastBootOrClear        Counter32,
    frAvcStatsPktsTxLastBootOrClear        Counter32,
    frAvcStatsErrPktsRxLastBootOrClear     Counter32,
    frAvcStatsUpDownStatesLastBootOrClear  Counter32,
    frAvcStatsBytesRxLastFiveMins          Counter32,
    frAvcStatsBytesTxLastFiveMins          Counter32,
    frAvcStatsPktsRxLastFiveMins           Counter32,
    frAvcStatsPktsTxLastFiveMins           Counter32,
    frAvcStatsErrPktsRxLastFiveMins        Counter32,
    frAvcStatsUpDownStatesLastFiveMins     Counter32
}

frAvcStatsBytesRxLastBootOrClear    OBJECT-TYPE
    SYNTAX                          Counter32
    MAX-ACCESS                      read-only
    STATUS                          current
    DESCRIPTION 
                                    "Number of bytes received on an avc since
                                     boot or last statistics clear."
    ::= { frAvcStatsTableEntry 1 }


frAvcStatsBytesTxLastBootOrClear   OBJECT-TYPE
    SYNTAX                         Counter32
    MAX-ACCESS                     read-only
    STATUS                         current
    DESCRIPTION 
                                   "Number of bytes transmitted on an avc  since 
                                   boot or last statistics clear."
    ::= { frAvcStatsTableEntry 2 }


frAvcStatsPktsRxLastBootOrClear   OBJECT-TYPE
    SYNTAX                        Counter32
    MAX-ACCESS                    read-only
    STATUS                        current
    DESCRIPTION 
                                  "Number of packets received  since boot 
                                   or last statistics clear."
    ::= { frAvcStatsTableEntry 3 }


frAvcStatsPktsTxLastBootOrClear   OBJECT-TYPE
    SYNTAX                        Counter32
    MAX-ACCESS                    read-only
    STATUS                        current
    DESCRIPTION 
                                  "Number of packets transmitted since boot 
                                   or last statistics clear."
    ::= { frAvcStatsTableEntry 4 }


frAvcStatsErrPktsRxLastBootOrClear   OBJECT-TYPE
    SYNTAX                           Counter32
    MAX-ACCESS                       read-only
    STATUS                           current
    DESCRIPTION 
                                     "Number of errored packets received since
                                      boot or last statistics clear."
   ::= { frAvcStatsTableEntry 5 }


frAvcStatsUpDownStatesLastBootOrClear   OBJECT-TYPE
   SYNTAX                               Counter32
   MAX-ACCESS                           read-only
   STATUS                               current
   DESCRIPTION 
                                        "Number of times state(up or down) of
                                         the avc changed in since boot or last
                                         statistics clear."
   ::= { frAvcStatsTableEntry 6 }


frAvcStatsBytesRxLastFiveMins          OBJECT-TYPE
    SYNTAX                             Counter32
    MAX-ACCESS                         read-only
    STATUS                             current
    DESCRIPTION 
                                       "Number of bytes received in the last 
                                        five minutes."
    ::= { frAvcStatsTableEntry 7 }


frAvcStatsBytesTxLastFiveMins          OBJECT-TYPE
    SYNTAX                             Counter32
    MAX-ACCESS                         read-only
    STATUS                             current
    DESCRIPTION 
                                       "Number of bytes transmitted in the last
                                        five minutes."
    ::= { frAvcStatsTableEntry 8 }


frAvcStatsPktsRxLastFiveMins           OBJECT-TYPE
    SYNTAX                             Counter32
    MAX-ACCESS                         read-only
    STATUS                             current
    DESCRIPTION 
                                       "Number of packets received in the last
                                        five minutes."
    ::= { frAvcStatsTableEntry 9 }


frAvcStatsPktsTxLastFiveMins          OBJECT-TYPE
    SYNTAX                            Counter32
    MAX-ACCESS                        read-only
    STATUS                            current
    DESCRIPTION 
                                      "Number of packets transmitted in the last
                                       five minutes."
    ::= { frAvcStatsTableEntry 10 }


frAvcStatsErrPktsRxLastFiveMins       OBJECT-TYPE
    SYNTAX                            Counter32
    MAX-ACCESS                        read-only
    STATUS                            current
    DESCRIPTION 
                                      "Number of errored packets received in the
                                       last five minutes." 
    ::= { frAvcStatsTableEntry 11 }

frAvcStatsUpDownStatesLastFiveMins    OBJECT-TYPE
    SYNTAX                            Counter32
    MAX-ACCESS                        read-only
    STATUS                            current
    DESCRIPTION 
                                      "Number of times state(up or down) of
                                       the avc changed in the last five
                                       minutes."
    ::= { frAvcStatsTableEntry 12 }

END
