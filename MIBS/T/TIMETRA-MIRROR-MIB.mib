TIMETRA-MIRROR-MIB DEFINITIONS ::= BEGIN

IMPORTS
    MODULE-IDENTITY, OBJECT-TYPE, NOTIFICATION-TYPE,
    Unsigned32, IpAddress, Integer32
        FROM SNMPv2-SMI

    MODULE-COMPLIANCE, OBJECT-GROUP, NOTIFICATION-GROUP
        FROM SNMPv2-CONF

    TEXTUAL-CONVENTION, RowStatus, TruthValue,
    MacAddress, TimeStamp, DisplayString
        FROM SNMPv2-TC

    timetraSRMIBModules, tmnxSRObjs, tmnxSRNotifyPrefix,
    tmnxSRConfs
        FROM TIMETRA-GLOBAL-MIB

    TItemDescription, TFCName, ServiceAdminStatus, ServiceOperStatus,
    TmnxPortID, TmnxEncapVal, TmnxServId, TNamedItem, TFCSet, TNamedItemOrEmpty,
    TPolicyID, SdpBindId, TSubHostId, TDirection, TmnxPppoeSessionId,
    TmnxVRtrID
        FROM TIMETRA-TC-MIB

    SdpId 
        FROM TIMETRA-SERV-MIB

    TIPFilterID, TMACFilterID, TEntryId, TFilterType, TFilterID, TEntryIdOrZero
        FROM TIMETRA-FILTER-MIB

    InetAddressType, InetAddress, InetAddressPrefixLength, InetPortNumber
        FROM INET-ADDRESS-MIB

    InterfaceIndexOrZero
        FROM IF-MIB
        
    vRtrID                                          
        FROM TIMETRA-VRTR-MIB
    ;

timetraMirrorMIBModule   MODULE-IDENTITY
        LAST-UPDATED "201102010000Z"
        ORGANIZATION "Alcatel-Lucent"
        CONTACT-INFO
            "Alcatel-Lucent SROS Support
             Web: http://support.alcatel-lucent.com"
        DESCRIPTION
        "This document is the SNMP MIB module to manage and provision 
         traffic mirroring on Alcatel-Lucent SROS systems.

         Copyright 2003-2011 Alcatel-Lucent. All rights reserved.
         Reproduction of this document is authorized on the condition that
         the foregoing copyright notice is included.

         This SNMP MIB module (Specification) embodies Alcatel-Lucent's
         proprietary intellectual property.  Alcatel-Lucent retains 
         all title and ownership in the Specification, including any 
         revisions.

         Alcatel-Lucent grants all interested parties a non-exclusive 
         license to use and distribute an unmodified copy of this 
         Specification in connection with management of Alcatel-Lucent
         products, and without fee, provided this copyright notice and 
         license appear on all copies.

         This Specification is supplied 'as is', and Alcatel-Lucent 
         makes no warranty, either express or implied, as to the use, 
         operation, condition, or performance of the Specification."

--
--  Revision History
--
        REVISION        "1102010000Z"
        DESCRIPTION     "Rev 9.0                1 Feb 2011 00:00
                         9.0 release of the TIMETRA-MIRROR-MIB."

        REVISION        "0801010000Z"
        DESCRIPTION     "Rev 6.0                01 Jan 2008 00:00
                         6.0 release of the TIMETRA-MIRROR-MIB."

        REVISION        "0701010000Z"
        DESCRIPTION     "Rev 5.0                01 Jan 2007 00:00
                         5.0 release of the TIMETRA-MIRROR-MIB."

        REVISION        "0501240000Z"   
        DESCRIPTION     "Rev 2.1                24 Jan 2005 00:00
                         2.1 release of the TIMETRA-MIRROR-MIB."

        REVISION        "0401150000Z"
        DESCRIPTION     "Rev 2.0                15 Jan 2004 00:00
                         2.0 release of the TIMETRA-MIRROR-MIB."

        REVISION        "0308150000Z"
        DESCRIPTION     "Rev 1.2                15 Aug 2003 00:00
                         1.2 release of the TIMETRA-MIRROR-MIB."

        REVISION        "200203140000Z"
        DESCRIPTION     "Rev 1.0                20 Jan 2003 00:00b
                         1.0 Release of the TIMETRA-MIRROR-MIB."

        REVISION        "200203140000Z"
        DESCRIPTION     "Rev 0.1                14 Mar 2002 00:00
                         Initial version of the TIMETRA-MIRROR-MIB."

        ::= { timetraSRMIBModules 18 }

tMirrorObjects              OBJECT IDENTIFIER ::= { tmnxSRObjs 18 }
tMirrorNotifyPrefix       OBJECT IDENTIFIER ::= { tmnxSRNotifyPrefix 18 }
    tMirrorNotifications      OBJECT IDENTIFIER ::= { tMirrorNotifyPrefix 0 }
tMirrorConformance          OBJECT IDENTIFIER ::= { tmnxSRConfs 18 }

tMirrorDestinationObjects   OBJECT IDENTIFIER ::= { tMirrorObjects 1 }
tMirrorSourceObjects        OBJECT IDENTIFIER ::= { tMirrorObjects 2 }
tMirrorSourceNotifyObjects  OBJECT IDENTIFIER ::= { tMirrorObjects 3 }
tMirrorRadiusLiObjects      OBJECT IDENTIFIER ::= { tMirrorObjects 4 }
tMirrorLiObjects            OBJECT IDENTIFIER ::= { tMirrorObjects 5 }
tMirrorLiNotifyObjects      OBJECT IDENTIFIER ::= { tMirrorObjects 6 }

--
-- textual conventions
--
TMplsLabel ::= TEXTUAL-CONVENTION
    STATUS       current
    DESCRIPTION 
        "An MPLS label; the 20-bit label value, excluding the TOS, S, 
         and x bits."
    REFERENCE
        ""
    SYNTAX Unsigned32 (0..1048575)

TEtherType ::= TEXTUAL-CONVENTION
    STATUS          current
    DESCRIPTION     "The TEtherType data type is a 16 bit value that represents 
                     the Ethertype of an Ethernet frame according to
                     IEEE 802.3x-1997.
        
                     In particular, it represents the stage 
                     of a PPPoE session. A value of 0x8863 specifies 
                     the discovery stage and a value of 0x8864 specifies 
                     the PPP session stage."
    SYNTAX          Unsigned32 (1536..65535) 
    
TSessionId ::= TEXTUAL-CONVENTION
    STATUS          current
    DESCRIPTION     "This is a 16 bit field which represents the Session 
                     Id. It is an unsigned value in network byte order. 
                     Its value varies depending on the session stage 
                     (discovery or PPP session). Before the access 
                     concentrator has assigned a session ID or if the 
                     session ID is unknown, the value is 0. For the PPP 
                     session stage, the value is fixed and defines a PPP
                     session and the Ethernet SOURCE_ADDR and 
                     DESTINATION_ADDR. The value 0xffff is reserved for 
                     future use and must not be used."
    SYNTAX          Unsigned32 (1..65535)       

TmnxMirrorEncapType ::= TEXTUAL-CONVENTION
    STATUS  current
    DESCRIPTION     "The TmnxMirrorEncapType data type is an enumerated 
                     integer that describes the port encapsulation supported
                     by a mirror service."
    SYNTAX  INTEGER {
                ether     (1),
                frameRelay(2),
                ppp       (3),
                atmSdu    (4),
                satopE1   (5),
                satopT1   (6),
                satopE3   (7),
                satopT3   (8),
                cesopsn   (9),
                cesopsnCas(10),
                ipOnly    (11)
            }

TmnxMirrorDestinationHeaderType ::= TEXTUAL-CONVENTION
    STATUS  current
    DESCRIPTION     "The TmnxMirrorDestinationHeaderType data type is
                     an enumerated integer that describes 
                     the header encapsulation supported by a mirror destination."
    SYNTAX  INTEGER {
                ipUdpShim              (1),
                ipGre                  (2)
            }

TmnxMirrorGatewayRole ::= TEXTUAL-CONVENTION
    STATUS  current
    DESCRIPTION     "The TmnxMirrorGatewayRole data type is
                     an enumerated integer that describes 
                     the role of a mirror gateway."
    SYNTAX  INTEGER {
                primary                (1),
                secondary              (2)
            }

TmnxInterceptionIdentifier ::= TEXTUAL-CONVENTION
    STATUS current
    DESCRIPTION 
        "TmnxInterceptionIdentifier is a 30-bits value that identifies
         a traffic flow being intercepted."
    SYNTAX Unsigned32 (0..1073741823)

--
-- mib objects
--

--
-- mirror destination table
--

tMirrorDestinationTable OBJECT-TYPE
    SYNTAX       SEQUENCE OF TMirrorDestinationEntry
    MAX-ACCESS   not-accessible
    STATUS       current
    DESCRIPTION  "The tMirrorDestinationTable has an entry for each 
                  mirror destination configured on the virtual router."
    ::= { tMirrorDestinationObjects 1 }

tMirrorDestinationEntry OBJECT-TYPE
    SYNTAX       TMirrorDestinationEntry
    MAX-ACCESS   not-accessible
    STATUS       current
    DESCRIPTION 
        "Each row represents information about a particular mirror destination.
         Entries are created by user.
         Entries are deleted by user.
        
         Entries in this table have an implied StorageType of 'nonVolatile'.
         That is, configured destination information is persistent
         across system restarts."
    INDEX { tMirrorDestinationIndex }
    ::= { tMirrorDestinationTable 1 }

TMirrorDestinationEntry ::= SEQUENCE
    {
        tMirrorDestinationIndex                TmnxServId,
        tMirrorDestinationRowStatus            RowStatus,
        tMirrorDestinationDescription          TItemDescription,
        tMirrorDestinationFC                   TFCName,
        tMirrorDestinationRemoteSource         TruthValue,
        tMirrorDestinationSapPortId            TmnxPortID,
        tMirrorDestinationSapEncapValue        TmnxEncapVal,
        tMirrorDestinationSdpNumber            SdpId,
        tMirrorDestinationSdpDestEncap         INTEGER,
        tMirrorDestinationAdminStatus          ServiceAdminStatus,
        tMirrorDestinationOperStatus           ServiceOperStatus,
        tMirrorDestinationTranslateDisable     TruthValue,
        tMirrorDestinationSliceSize            Unsigned32,
        tMirrorDestinationPppoeDestMacAddr     MacAddress,
        tMirrorDestinationPppoeSrcMacAddr      MacAddress,
        tMirrorDestinationPppoeEtype           TEtherType,
        tMirrorDestinationPppoeSessionId       TSessionId,    
        tMirrorDestinationSdpEgrSvcLabel       TMplsLabel,
        tMirrorDestinationSapEgressQosPolicyId TPolicyID,
        tMirrorDestinationEncapsulation        TmnxMirrorEncapType,   
        tMirrorDestinationSdpOperEgrSvcLabel   TMplsLabel,
        tMirrorDestinationEnablePortId         TruthValue,
        tMirrorDestSapEgrIpMirrorSA            MacAddress,
        tMirrorDestSapEgrIpMirrorDA            MacAddress,
        tMirrorDestLastChanged                 TimeStamp
    }

tMirrorDestinationIndex  OBJECT-TYPE
    SYNTAX       TmnxServId
    MAX-ACCESS   accessible-for-notify
    STATUS       current
    DESCRIPTION
        "Since packet mirroring is setup like a service, 
         tMirrorDestinationIndex represents the Service ID 
         associated with this mirror destination. It is 
         used as unique index in to this table. Only 255 
         mirror destination service IDs may be created per 
         system."
    ::= { tMirrorDestinationEntry 1 }

tMirrorDestinationRowStatus  OBJECT-TYPE
    SYNTAX       RowStatus
    MAX-ACCESS   read-create
    STATUS       current
    DESCRIPTION
        "The row status used for creation and deletion of entries in
         tMirrorDestinationTable.
         The only values supported during a set operation are createAndGo(4),  
         createAndWait(5) and destroy(6)."
    ::= { tMirrorDestinationEntry 2 }

tMirrorDestinationDescription  OBJECT-TYPE
    SYNTAX       TItemDescription
    MAX-ACCESS   read-create
    STATUS       current
    DESCRIPTION
        "Generic information about this mirror destination."
    DEFVAL { ''H }
    ::= { tMirrorDestinationEntry 3 }

tMirrorDestinationFC  OBJECT-TYPE
    SYNTAX       TFCName
    MAX-ACCESS   read-create
    STATUS       current
    DESCRIPTION
        "The forwarding class for all packets transmitted to 
         this mirror destination."
    DEFVAL { 'be'H }
   ::= { tMirrorDestinationEntry 4 }

tMirrorDestinationRemoteSource  OBJECT-TYPE
    SYNTAX       TruthValue
    MAX-ACCESS   read-create
    STATUS       current
    DESCRIPTION
        "When this value is 'true', the sources of the mirrored 
         packets can be on remote ESRs. If 'false', no remote ESR 
         access is allowed to the mirror destination."
    DEFVAL { false }
    ::= { tMirrorDestinationEntry 5 }

tMirrorDestinationSapPortId  OBJECT-TYPE
    SYNTAX       TmnxPortID
    MAX-ACCESS   read-create
    STATUS       current
    DESCRIPTION
        "The ID of the access port where the Service Access Point (SAP) 
         associated with this mirror destination service is defined.

         The default value for this object indicates invalid port-id."
    DEFVAL { '1E000000'H }
    ::= { tMirrorDestinationEntry 6 }

tMirrorDestinationSapEncapValue  OBJECT-TYPE
    SYNTAX       TmnxEncapVal
    MAX-ACCESS   read-create
    STATUS       current
    DESCRIPTION
        "The value of the label used to identify the SAP on the 
         access port specified by tMirrorDestinationSapPortId."
    DEFVAL { 0 }
    ::= { tMirrorDestinationEntry 7 }

tMirrorDestinationSdpNumber  OBJECT-TYPE
    SYNTAX       SdpId
    MAX-ACCESS   read-create
    STATUS       obsolete
    DESCRIPTION
        "The ID for the Service Destination Point (SDP) associated 
         with this mirror destination service. A value of 0 indicates 
         that no SDP is associated with the mirror service"
    DEFVAL { 0 }
    ::= { tMirrorDestinationEntry 8 }

tMirrorDestinationSdpDestEncap  OBJECT-TYPE
    SYNTAX       INTEGER { 
                     none(1), 
                     pos(2), 
                     ethernet(3) 
                 }
    MAX-ACCESS   read-create
    STATUS       obsolete
    DESCRIPTION
        "The frame type expected by the far end ESR at the other 
         end of the SDP identified by tMirrorDestinationSdpNumber."
    DEFVAL { none }
    ::= { tMirrorDestinationEntry 9 }

tMirrorDestinationAdminStatus  OBJECT-TYPE
    SYNTAX       ServiceAdminStatus
    MAX-ACCESS   read-create
    STATUS       current
    DESCRIPTION
        "The administrative status for this destination entry"
    DEFVAL { down }
    ::= { tMirrorDestinationEntry 10 }

tMirrorDestinationOperStatus  OBJECT-TYPE
    SYNTAX       ServiceOperStatus
    MAX-ACCESS   read-only
    STATUS       current
    DESCRIPTION
        "The operational status for this destination entry"
    ::= { tMirrorDestinationEntry 11 }

tMirrorDestinationTranslateDisable  OBJECT-TYPE
    SYNTAX       TruthValue
    MAX-ACCESS   read-create
    STATUS       obsolete
    DESCRIPTION
        "When this value is 'true', automatic translation of Ethernet 
         to PPP/BCP and PPP to PPPoE is disabled. When 'false' the 
         translation is enabled."
    DEFVAL { false }
    ::= { tMirrorDestinationEntry 12 }

tMirrorDestinationSliceSize  OBJECT-TYPE       
    SYNTAX       Unsigned32 (0|128..9216)
    MAX-ACCESS   read-create
    STATUS       current
    DESCRIPTION
        "The value of the slice-size i.e. maximum portion of the 
         mirrored frame that will be transmitted to the mirror 
         destination. Any frame larger than the slice-size will be 
         truncated to this value before transmission to the mirror 
         destination. A value of 0 indicates that mirrored packet 
         truncation based on slice size is disabled.

         When the miror destination is an ISA-AA Group, this must
         be set to a value of 0."
    DEFVAL { 0 }
    ::= { tMirrorDestinationEntry 13 }

tMirrorDestinationPppoeDestMacAddr  OBJECT-TYPE
    SYNTAX       MacAddress
    MAX-ACCESS   read-create
    STATUS       obsolete
    DESCRIPTION
        "This value specifies the MAC address to be used for 
         the Destination MAC Address field of the PPPoE Header 
         when using PPPoE encapsulation of PPP mirrored packets. 
         (The tMirrorDestinationTranslateDisable should be
         'false' to allow such encapsulation). This MAC address
         must not be a broadcast or multicast address."
    DEFVAL {'0003f8000000'H}
    ::= { tMirrorDestinationEntry 14 }
        
tMirrorDestinationPppoeSrcMacAddr  OBJECT-TYPE
    SYNTAX       MacAddress
    MAX-ACCESS   read-create
    STATUS       obsolete
    DESCRIPTION
        "This value specifies the MAC address to be used for 
         the Source MAC Address field of the PPPoE Header 
         when using PPPoE encapsulation of PPP mirrored packets. 
         This MAC address must not be a broadcast or multicast 
         address."
    DEFVAL {'0003f8000001'H} 
    ::= { tMirrorDestinationEntry 15 }

tMirrorDestinationPppoeEtype  OBJECT-TYPE
    SYNTAX       TEtherType
    MAX-ACCESS   read-create
    STATUS       obsolete
    DESCRIPTION
        "This value defines the PPPoE Ethertype that will be 
         included in the PPPoE header for PPPoE encapsulation of 
         PPP mirrored packets."
    DEFVAL { '8864'H }
    ::= { tMirrorDestinationEntry 16 }       

tMirrorDestinationPppoeSessionId  OBJECT-TYPE
    SYNTAX       TSessionId
    MAX-ACCESS   read-create
    STATUS       obsolete
    DESCRIPTION
        "This value defines the PPPoE session ID that will be 
         included in the PPPoE header for PPPoE encapsulation of 
         PPP mirrored packets."
    DEFVAL { 1 }
    ::= { tMirrorDestinationEntry 17 }     

tMirrorDestinationSdpEgrSvcLabel OBJECT-TYPE
    SYNTAX       TMplsLabel (0|16..1048575)
    MAX-ACCESS   read-create
    STATUS       obsolete
    DESCRIPTION
        "This value specifies the egress service label. It is used 
        by the SDP associated with this mirror destination entry
        to differentiate to the far-end each mirror destination 
        service bound to the SDP. This label is obtained manually 
        or through signalling with the far end."
    DEFVAL { 0 }
    ::= { tMirrorDestinationEntry 18 }

tMirrorDestinationSapEgressQosPolicyId OBJECT-TYPE
    SYNTAX       TPolicyID
    MAX-ACCESS   read-create
    STATUS       current
    DESCRIPTION  
        "This value indicates a row in the tSapEgressTable 
         corresponding to the egress QoS policy. A value of 0 
         indicates that no QoS policy is specified."
    DEFVAL { 1 }
    ::= { tMirrorDestinationEntry 19 }

tMirrorDestinationEncapsulation OBJECT-TYPE
    SYNTAX       TmnxMirrorEncapType
    MAX-ACCESS   read-create
    STATUS       current
    DESCRIPTION  
        "This value maintains the encapsulation supported by 
         this service.

         When the miror destination is an ISA-AA Group, this must
         be set to a value of 'ether'."
    DEFVAL { ether }
    ::= { tMirrorDestinationEntry 20 }

tMirrorDestinationSdpOperEgrSvcLabel OBJECT-TYPE
    SYNTAX       TMplsLabel
    MAX-ACCESS   read-only
    STATUS       obsolete
    DESCRIPTION  
        "If there is an active sdp being used by this service,
        tMirrorDestinationSdpOperEgrSvcLabel maintains the 
        operational label being used by the SDP. If the SDP 
        is being used, a value of '0' means the SDP transport
        is inactive."
    ::= { tMirrorDestinationEntry 21 }

tMirrorDestinationEnablePortId  OBJECT-TYPE
    SYNTAX       TruthValue
    MAX-ACCESS   read-create
    STATUS       current
    DESCRIPTION
        "The value of tMirrorDestinationEnablePortId indicates whether the
        port-id of the system is to be included in the mirrored packets. 

        The value of 'true' indicates that the port-id is to be included in the
        mirrored packets.

        An 'inconsistentValue' error is returned if an attempt is made to set
        the value of tMirrorDestinationEnablePortId to 'true' when
        tMirrorDestinationEncapsulation is not set to 'ppp (3)'."
    DEFVAL { false }
    ::= { tMirrorDestinationEntry 22 }

tMirrorDestSapEgrIpMirrorSA  OBJECT-TYPE
    SYNTAX       MacAddress
    MAX-ACCESS   read-create
    STATUS       current
    DESCRIPTION
        "This value of tMirrorDestSapEgrIpMirrorSA specifies the MAC address to
        be used for the Source MAC Address field in the mirrored packets when
        using IP mirror service.

        This MAC address must not be a broadcast or multicast address.

        An 'inconsistentValue' error is returned if an attempt is made to set
        the value of tMirrorDestSapEgrIpMirrorSA to other than default
        when tMirrorDestinationEncapsulation is not set to 'ipOnly (11)'."
    DEFVAL {'000000000000'H} 
    ::= { tMirrorDestinationEntry 23 }

tMirrorDestSapEgrIpMirrorDA  OBJECT-TYPE
    SYNTAX       MacAddress
    MAX-ACCESS   read-create
    STATUS       current
    DESCRIPTION
        "This value of tMirrorDestSapEgrIpMirrorDA specifies the MAC address to
        be used for the destination MAC Address field in the mirrored packets
        when using IP mirror service.

        An 'inconsistentValue' error is returned if an attempt is made to set
        the value of tMirrorDestSapEgrIpMirrorDA to other than default
        when tMirrorDestinationEncapsulation is not set to 'ipOnly (11)'."
    DEFVAL {'000000000000'H} 
    ::= { tMirrorDestinationEntry 24 }

tMirrorDestLastChanged  OBJECT-TYPE
    SYNTAX      TimeStamp
    MAX-ACCESS  read-only
    STATUS      current
    DESCRIPTION
         "The value of  tMirrorDestLastChanged  indicates the sysUpTime
          at the time of the last modification of this entry.

          If no changes were made to the entry since the last re-initialization
          of the local network management subsystem, then this object contains
          a zero value."
    ::= { tMirrorDestinationEntry 25 }

--
-- mirror destination remote source table
--

tMirrorDestinationRemoteSourceTable OBJECT-TYPE
    SYNTAX       SEQUENCE OF TMirrorDestinationRemoteSourceEntry
    MAX-ACCESS   not-accessible
    STATUS       current
    DESCRIPTION  
        "Each row in this table represents a remote source bound to a
         the mirror destination service."
    ::= { tMirrorDestinationObjects 2 }

tMirrorDestinationRemoteSourceEntry OBJECT-TYPE
    SYNTAX       TMirrorDestinationRemoteSourceEntry
    MAX-ACCESS   not-accessible
    STATUS       current
    DESCRIPTION 
        "Each row represents information about a remote source 
         associated with a mirror destination entry defined in 
         tMirrorDestinationTable. Each mirror destination may 
         be associated with 0 or more remote sources. 
         Entries are created by user.
         Entries are deleted by user, or by agent when the 
         tMirrorDestinationTable entry is destroyed.

         Entries in this table have an implied StorageType of 'nonVolatile'.
         That is, configured destination information is persistent
         across system restarts."
    INDEX { tMirrorDestinationIndex, 
            tMirrorDestinationRemoteSourceAddr } 
    ::= { tMirrorDestinationRemoteSourceTable 1 }

TMirrorDestinationRemoteSourceEntry ::= SEQUENCE
    {
        tMirrorDestinationRemoteSourceAddr              IpAddress,
        tMirrorDestinationRemoteSourceLabelSignaling    INTEGER,
        tMirrorDestinationRemoteSourceIngSvcLabel       TMplsLabel,
        tMirrorDestinationRemoteSourceRowStatus         RowStatus,
        tMirrorDestinationRemoteSourceOperIngSvcLabel   TMplsLabel,
        tMirrorDestRemoteSrcLastChgd                    TimeStamp,
        tMirrorDestRemoteSrcIsICB                       TruthValue,
        tMirrorDestRemoteSrcVcId                        Unsigned32
    }
    
tMirrorDestinationRemoteSourceAddr  OBJECT-TYPE
    SYNTAX       IpAddress
    MAX-ACCESS   read-only
    STATUS       current
    DESCRIPTION
        "The IP address of the remote source or the far-end ESR 
         which is allowed to be a source of packets for the mirror 
         destination service defined by tMirrorDestinationIndex."
    ::= { tMirrorDestinationRemoteSourceEntry 1 }

tMirrorDestinationRemoteSourceLabelSignaling  OBJECT-TYPE
    SYNTAX          INTEGER {
                        none(1),
                        tldp(2)
                    }
    MAX-ACCESS      read-create
    STATUS          current
    DESCRIPTION     
        "This object specifies the label signaling protocol used to obtain
        the ingress labels associated with the far-end ESR. When the 
        value of this object is none(1) then the labels are manually 
        assigned at the time the remote source is bound to the mirror
        destination service. When this value is tldp(2) the label is 
        obtained through signaling via the LDP.
        This value must be set for the row to become active(1)."
    ::= { tMirrorDestinationRemoteSourceEntry 2 }

tMirrorDestinationRemoteSourceIngSvcLabel OBJECT-TYPE
    SYNTAX       TMplsLabel (0|2048..18431)
    MAX-ACCESS   read-create
    STATUS       current
    DESCRIPTION
        "This value specifies the ingress service label. It is used 
        to identify a remote source bound to the mirror destination 
        service. This label is obtained manually or through signalling 
        with the far end.

        When tMirrorDestinationRemoteSourceLabelSignaling is set to 
        'none(1)', this object can take the values 2048..18431. When
        tMirrorDestinationRemoteSourceLabelSignaling is set to 'tldp(2)',
        this object will have a value of zero. Also, setting this object
        will reset signalling to 'none(1)'."
    DEFVAL { 0 }
    ::= { tMirrorDestinationRemoteSourceEntry 3 }

tMirrorDestinationRemoteSourceRowStatus OBJECT-TYPE
    SYNTAX       RowStatus
    MAX-ACCESS   read-create
    STATUS       current
    DESCRIPTION
        "The row status used for creation and deletion of entries in
         tMirrorDestinationRemoteSourceTable.
         The only values supported during a set operation are createAndGo(4),  
         createAndWait(5) and destroy(6)."
    ::= { tMirrorDestinationRemoteSourceEntry 4 }

tMirrorDestinationRemoteSourceOperIngSvcLabel OBJECT-TYPE
    SYNTAX       TMplsLabel
    MAX-ACCESS   read-only
    STATUS       current
    DESCRIPTION
        "This value specifies the ingress service label. It is used 
        by this identify a remote source bound to the mirror destination 
        service. This label is obtained manually or through signalling 
        with the far end. A value of '0' implies that the operational
        label is unresolved."
    ::= { tMirrorDestinationRemoteSourceEntry 5 }

tMirrorDestRemoteSrcLastChgd  OBJECT-TYPE
    SYNTAX      TimeStamp
    MAX-ACCESS  read-only
    STATUS      current
    DESCRIPTION
         "The value of tMirrorDestRemoteSrcLastChgd  indicates the sysUpTime
          at the time of the last modification of this entry.

          If no changes were made to the entry since the last re-initialization
          of the local network management subsystem, then this object contains
          a zero value."
    ::= { tMirrorDestinationRemoteSourceEntry 6 }

tMirrorDestRemoteSrcIsICB    OBJECT-TYPE
    SYNTAX      TruthValue
    MAX-ACCESS  read-create
    STATUS      current
    DESCRIPTION 
          "The value of tMirrorDestRemoteSrcIsICB specifies whether this
           is an inter-chassis backup remote-source."
    DEFVAL      { false }
    ::= { tMirrorDestinationRemoteSourceEntry 7 } 

tMirrorDestRemoteSrcVcId OBJECT-TYPE
    SYNTAX          Unsigned32
    MAX-ACCESS      read-create
    STATUS          current
    DESCRIPTION
          "The value of the object tMirrorDestRemoteSrcVcId specifies the 
           virtual-circuit associated with this remote-source.
           The default value of this object is equal to the service ID."
    ::= { tMirrorDestinationRemoteSourceEntry 8 } 

-- --------------------------------------
-- Destination Table Last Changed object
-- --------------------------------------
tMirrorDestTableLastChnged OBJECT-TYPE
    SYNTAX      TimeStamp
    MAX-ACCESS  read-only
    STATUS      current
    DESCRIPTION
         "The value of  tMirrorDestTableLastChnged indicates the sysUpTime
          at the time of the last modification of tMirrorDestinationTable.

          If no changes were made to the table since the last re-initialization
          of the local network management subsystem, then this object contains
          a zero value."
    ::= { tMirrorDestinationObjects 3 }

tMirrorDestRemSrcTblLastChgd OBJECT-TYPE
    SYNTAX      TimeStamp
    MAX-ACCESS  read-only
    STATUS      current
    DESCRIPTION
         "The value of tMirrorDestRemSrcTblLastChgd indicates the sysUpTime
          at the time of the last modification of
          tMirrorDestinationRemoteSourceTable.

          If no changes were made to the table since the last re-initialization
          of the local network management subsystem, then this object contains
          a zero value."
    ::= { tMirrorDestinationObjects 4 }

--
-- mirror source configuration objects
--
    
tMirrorSourceTable OBJECT-TYPE
    SYNTAX       SEQUENCE OF TMirrorSourceEntry
    MAX-ACCESS   not-accessible
    STATUS       current
    DESCRIPTION
        "The tMirrorSourceTable has information about each mirror source."
    ::= { tMirrorSourceObjects 1 }

tMirrorSourceEntry OBJECT-TYPE
    SYNTAX       TMirrorSourceEntry
    MAX-ACCESS   not-accessible
    STATUS       current
    DESCRIPTION 
        "Each row represents information about a particular mirror source.
         Entries are created and deleted when the mirror destination service
         associated with this mirror source is created or deleted 
         respectively.
         
         Entries in this table have an implied StorageType of 'nonVolatile'.
         That is, mirror source entry will be persistent across system 
         restarts. 
        "
    INDEX { tMirrorSourceIndex }
    ::= { tMirrorSourceTable 1 }

TMirrorSourceEntry ::= SEQUENCE
    {
        tMirrorSourceIndex        TmnxServId,
        tMirrorSourceAdminStatus  ServiceAdminStatus,       
        tMirrorSourceRowStatus    RowStatus,
        tMirrorSourceLastChgd  TimeStamp
    }

tMirrorSourceIndex  OBJECT-TYPE
    SYNTAX       TmnxServId
    MAX-ACCESS   accessible-for-notify
    STATUS       current
    DESCRIPTION
        "The mirror destination service ID that defines the context of 
         the mirror source. The mirror destination service represented 
         by this ID must exist as an entry within the tMirrorDestinationTable."
    ::= { tMirrorSourceEntry 1 }

tMirrorSourceAdminStatus  OBJECT-TYPE
    SYNTAX       ServiceAdminStatus
    MAX-ACCESS   read-create
    STATUS       current
    DESCRIPTION
        "The admininstrative status for this Mirror source entry."
    DEFVAL { up }
    ::= { tMirrorSourceEntry 2 }

tMirrorSourceRowStatus  OBJECT-TYPE
    SYNTAX       RowStatus
    MAX-ACCESS   read-create
    STATUS       current
    DESCRIPTION
        "The row status used for creation and deletion of entries in
         tMirrorSourceTable.  The mirror destination service
         represented by the tMirrorSourceIndex must exist as an entry
         within the tMirrorDestinationTable or row creation will fail
         with an inconsistentName error.  When the corresponding entry
         in the tMirrorDestinationTable is deleted this row entry will
         also be deleted."
    ::= { tMirrorSourceEntry 3 }

tMirrorSourceLastChgd  OBJECT-TYPE
    SYNTAX      TimeStamp
    MAX-ACCESS  read-only
    STATUS      current
    DESCRIPTION
         "The value of  tMirrorSourceLastChgd  indicates the sysUpTime
          at the time of the last modification of this entry.

          If no changes were made to the entry since the last re-initialization
          of the local network management subsystem, then this object contains
          a zero value."
    ::= { tMirrorSourceEntry 4 }


--
-- mirror source ip-filter table
--

tMirrorSourceIpFilterTable OBJECT-TYPE
    SYNTAX       SEQUENCE OF TMirrorSourceIpFilterEntry
    MAX-ACCESS   not-accessible
    STATUS       current
    DESCRIPTION  
        "Each row in this table represents an IP Filter Entry 
         associated with a mirror source."
    ::= { tMirrorSourceObjects 2 }

tMirrorSourceIpFilterEntry OBJECT-TYPE
    SYNTAX       TMirrorSourceIpFilterEntry
    MAX-ACCESS   not-accessible
    STATUS       current
    DESCRIPTION 
        "Each row represents information about a particular IP 
         Filter Entry associated with a mirror source defined in 
         the tMirrorSourceTable.
         Entries are created by user.
         Entries are deleted by user, or by agent when the tMirrorSourceTable 
         entry is destroyed.

         Entries in this table have an implied StorageType of 'volatile'.
         That is, configured mirror source information is not persistent
         across system restarts."
    INDEX { tMirrorSourceIndex, 
            tMirrorSourceIpFilter, 
            tMirrorSourceIpFilterParams }
    ::= { tMirrorSourceIpFilterTable 1 }

TMirrorSourceIpFilterEntry ::= SEQUENCE
    {
        tMirrorSourceIpFilter          TIPFilterID,
        tMirrorSourceIpFilterParams    TEntryId,
        tMirrorSourceIpFilterRowStatus RowStatus,
        tMirrorSourceIpFilterLastChgd  TimeStamp,
        tMirrorSourceIpFilterIntceptId TmnxInterceptionIdentifier,
        tMirrorSourceIpFilterSessionId Unsigned32
    }

tMirrorSourceIpFilter  OBJECT-TYPE
    SYNTAX       TIPFilterID (1..65535)
    MAX-ACCESS   not-accessible
    STATUS       current
    DESCRIPTION
        "This value specifies the IP Filter ID of the IP Filter Entry 
         associated with the mirror source defined by tMirrorSourceIndex."
    ::= { tMirrorSourceIpFilterEntry 1 }

tMirrorSourceIpFilterParams  OBJECT-TYPE
    SYNTAX       TEntryId
    MAX-ACCESS   not-accessible
    STATUS       current
    DESCRIPTION
        "This value corresponds to the Entry ID which identifies a specific 
         'Entry' within the IP Filter defined by tMirrorSourceIpFilter above. 
         
         Each IP Filter has a number of 'Entries' associated with it and each 
         Entry within the filter is identified by an Entry ID which is unique 
         within the filter."
    ::= { tMirrorSourceIpFilterEntry 2 }

tMirrorSourceIpFilterRowStatus  OBJECT-TYPE
    SYNTAX       RowStatus
    MAX-ACCESS   read-create
    STATUS       current
    DESCRIPTION
        "The row status used for creation and deletion of entries in
         tMirrorSourceIpFilterTable.
         The only values supported during a set operation are createAndGo(4),  
         createAndWait(5) and destroy(6)."
    ::= { tMirrorSourceIpFilterEntry 3 }

tMirrorSourceIpFilterLastChgd  OBJECT-TYPE
    SYNTAX      TimeStamp
    MAX-ACCESS  read-only
    STATUS      current
    DESCRIPTION
         "The value of tMirrorSourceIpFilterLastChgd  indicates the sysUpTime
          at the time of the last modification of this entry.

          If no changes were made to the entry since the last re-initialization
          of the local network management subsystem, then this object contains
          a zero value."
    ::= { tMirrorSourceIpFilterEntry 4 }

tMirrorSourceIpFilterIntceptId  OBJECT-TYPE
    SYNTAX       TmnxInterceptionIdentifier
    MAX-ACCESS   read-create
    STATUS       current
    DESCRIPTION
        "The value of tMirrorSourceIpFilterIntceptId specifies an 
         identification of the traffic flow corresponding to this conceptual
         row for the Lawful Intercept Gateway." 
     DEFVAL       { 0 }
    ::= { tMirrorSourceIpFilterEntry 5 }

tMirrorSourceIpFilterSessionId  OBJECT-TYPE
    SYNTAX       Unsigned32
    MAX-ACCESS   read-create
    STATUS       current
    DESCRIPTION
        "The value of tMirrorSourceIpFilterSessionId specifies an 
         identification of the traffic flow corresponding to this conceptual
         row for the Lawful Intercept Gateway." 
     DEFVAL       { 0 }
    ::= { tMirrorSourceIpFilterEntry 6 }

--
-- mirror source mac-filter table
--

tMirrorSourceMacFilterTable OBJECT-TYPE
    SYNTAX       SEQUENCE OF TMirrorSourceMacFilterEntry
    MAX-ACCESS   not-accessible
    STATUS       current
    DESCRIPTION  
        "The tMirrorSourceMacFilterTable contains information 
         about each MAC Filter Entry associated with a mirror 
         source."
    ::= { tMirrorSourceObjects 3 }

tMirrorSourceMacFilterEntry OBJECT-TYPE
    SYNTAX       TMirrorSourceMacFilterEntry
    MAX-ACCESS   not-accessible
    STATUS       current
    DESCRIPTION 
        "Each row represents information about a MAC Filter Entry 
         assocaited with a mirror source defined in the tMirrorSourceTable.
         Entries are created by user.    
         Entries are deleted by user, or by agent when the tMirrorSourceTable 
         entry is destroyed.

         Entries in this table have an implied StorageType of 'volatile'.
         That is, configured mirror source information is not persistent
         across system restarts."
    INDEX { tMirrorSourceIndex, 
            tMirrorSourceMacFilter, 
            tMirrorSourceMacFilterParams }
    ::= { tMirrorSourceMacFilterTable 1 }

TMirrorSourceMacFilterEntry ::= SEQUENCE
    {
        tMirrorSourceMacFilter          TMACFilterID,
        tMirrorSourceMacFilterParams    TEntryId,
        tMirrorSourceMacFilterRowStatus RowStatus,
        tMirrorSourceMacFilterLastChgd  TimeStamp,
        tMirrorSourceMacFilterIntceptId TmnxInterceptionIdentifier,
        tMirrorSourceMacFilterSessionId Unsigned32
    }

tMirrorSourceMacFilter  OBJECT-TYPE
    SYNTAX       TMACFilterID (1..65535)
    MAX-ACCESS   not-accessible
    STATUS       current
    DESCRIPTION
        "This value specifies the MAC Filter ID of the MAC Filter Entry 
         associated with the mirror source defined by tMirrorSourceIndex."
    ::= { tMirrorSourceMacFilterEntry 1 }

tMirrorSourceMacFilterParams  OBJECT-TYPE
    SYNTAX       TEntryId
    MAX-ACCESS   not-accessible
    STATUS       current
    DESCRIPTION
        "This value corresponds to the Entry ID which identifies a specific 
         'Entry' within the MAC Filter defined by tMirrorSourceMacFilter. 
         
         Each MAC Filter has a number of 'Entries' associated with it and each 
         Entry within the filter is identified by an Entry ID which is unique 
         within the filter."
    ::= { tMirrorSourceMacFilterEntry 2 }

tMirrorSourceMacFilterRowStatus  OBJECT-TYPE
    SYNTAX       RowStatus
    MAX-ACCESS   read-create
    STATUS       current
    DESCRIPTION
        "The row status used for creation and deletion of entries in
         tMirrorSourceMacFilterTable.
         The only values supported during a set operation are createAndGo(4),  
         createAndWait(5) and destroy(6)."
    ::= { tMirrorSourceMacFilterEntry 3 }

tMirrorSourceMacFilterLastChgd  OBJECT-TYPE
    SYNTAX      TimeStamp
    MAX-ACCESS  read-only
    STATUS      current
    DESCRIPTION
         "The value of tMirrorSourceMacFilterLastChgd  indicates the sysUpTime
          at the time of the last modification of this entry.

          If no changes were made to the entry since the last re-initialization
          of the local network management subsystem, then this object contains
          a zero value."
    ::= { tMirrorSourceMacFilterEntry 4 }

tMirrorSourceMacFilterIntceptId  OBJECT-TYPE
    SYNTAX       TmnxInterceptionIdentifier
    MAX-ACCESS   read-create
    STATUS       current
    DESCRIPTION
        "The value of tMirrorSourceMacFilterIntceptId specifies an 
         identification of the traffic flow corresponding to this conceptual
         row for the Lawful Intercept Gateway."
     DEFVAL       { 0 }
    ::= { tMirrorSourceMacFilterEntry 5 }

tMirrorSourceMacFilterSessionId  OBJECT-TYPE
    SYNTAX       Unsigned32
    MAX-ACCESS   read-create
    STATUS       current
    DESCRIPTION
        "The value of tMirrorSourceMacFilterSessionId specifies an 
         identification of the traffic flow corresponding to this conceptual
         row for the Lawful Intercept Gateway."
     DEFVAL       { 0 }
    ::= { tMirrorSourceMacFilterEntry 6 }

--
-- mirror source ingress-label table
--

tMirrorSourceIngressLabelTable OBJECT-TYPE
    SYNTAX       SEQUENCE OF TMirrorSourceIngressLabelEntry
    MAX-ACCESS   not-accessible
    STATUS       current
    DESCRIPTION  
        "Each row in this table represents an MPLS ingress label
         filter entry associated with a mirror source."
    ::= { tMirrorSourceObjects 4 }

tMirrorSourceIngressLabelEntry OBJECT-TYPE
    SYNTAX       TMirrorSourceIngressLabelEntry
    MAX-ACCESS   not-accessible
    STATUS       current
    DESCRIPTION 
        "Each row represents information about an MPLS ingress label
        filter entry associated with a mirror source.
        Entries are created by user.
        Entries are deleted by user, or by agent when the tMirrorSourceTable 
        entry is destroyed.

        Entries in this table have an implied StorageType of 'volatile'.
        That is, configured mirror source information is not persistent
        across system restarts.
        "
    INDEX { tMirrorSourceIndex, tMirrorSourceIngressLabelIndex }
    ::= { tMirrorSourceIngressLabelTable 1 }

TMirrorSourceIngressLabelEntry ::= SEQUENCE
    {
        tMirrorSourceIngressLabelIndex     TMplsLabel,
        tMirrorSourceIngressLabelRowStatus RowStatus,
        tMirrorSourceIngLabelLastChgd  TimeStamp
    }

tMirrorSourceIngressLabelIndex  OBJECT-TYPE
    SYNTAX       TMplsLabel
    MAX-ACCESS   not-accessible
    STATUS       current
    DESCRIPTION
        "This value specifies the MPLS label associated with this 
         MPLS ingress label filter entry. Ingress MPLS frames with 
         top-of-stack label matching to this value will be mirrored 
         to a given mirror destination."
    ::= { tMirrorSourceIngressLabelEntry 1 }

tMirrorSourceIngressLabelRowStatus  OBJECT-TYPE
    SYNTAX       RowStatus
    MAX-ACCESS   read-create
    STATUS       current
    DESCRIPTION
        "The row status used for creation and deletion of entries in
         tMirrorSourceIngressLabelTable.
         The only values supported during a set operation are createAndGo(4),  
         createAndWait(5) and destroy(6)."
    ::= { tMirrorSourceIngressLabelEntry 2 }

tMirrorSourceIngLabelLastChgd  OBJECT-TYPE
    SYNTAX      TimeStamp
    MAX-ACCESS  read-only
    STATUS      current
    DESCRIPTION
         "The value of tMirrorSourceIngLabelLastChgd  indicates the sysUpTime
          at the time of the last modification of this entry.

          If no changes were made to the entry since the last re-initialization
          of the local network management subsystem, then this object contains
          a zero value."
    ::= { tMirrorSourceIngressLabelEntry 3 }


--
-- mirror source port table
--

tMirrorSourcePortTable OBJECT-TYPE
    SYNTAX       SEQUENCE OF TMirrorSourcePortEntry
    MAX-ACCESS   not-accessible
    STATUS       current
    DESCRIPTION  
        "This table defines a list of (physical interface) ports for 
         each mirror source"
    ::= { tMirrorSourceObjects 5 }

tMirrorSourcePortEntry OBJECT-TYPE
    SYNTAX       TMirrorSourcePortEntry
    MAX-ACCESS   not-accessible
    STATUS       current
    DESCRIPTION 
        "Each row reprsents information about a port associated with 
         a Mirror source defined in tMirrorSourceTable.
         Entries are created by user.
         Entries are deleted by user, or by agent when the tMirrorSourceTable 
         entry is destroyed.

         Entries in this table have an implied StorageType of 'volatile'.
         That is, configured mirror source information is not persistent
         across system restarts."
    INDEX { tMirrorSourceIndex, tMirrorSourcePortIndex }
    ::= { tMirrorSourcePortTable 1 }

TMirrorSourcePortEntry ::= SEQUENCE
    {
        tMirrorSourcePortIndex           TmnxPortID,
        tMirrorSourcePortRowStatus       RowStatus,
        tMirrorSourcePortEgressEnabled   TruthValue,
        tMirrorSourcePortIngressEnabled  TruthValue,
        tMirrorSourcePortLastChgd        TimeStamp
    }

tMirrorSourcePortIndex  OBJECT-TYPE
    SYNTAX       TmnxPortID
    MAX-ACCESS   not-accessible
    STATUS       current
    DESCRIPTION
        "This value defines the Ethernet physical interface associated 
         with the mirror source defined by tMirrorSourceIndex."
    ::= { tMirrorSourcePortEntry 1 }

tMirrorSourcePortRowStatus  OBJECT-TYPE
    SYNTAX       RowStatus
    MAX-ACCESS   read-create
    STATUS       current
    DESCRIPTION
        "The row status used for creation and deletion of entries in
         tMirrorSourcePortTable.
         The only values supported during a set operation are createAndGo(4),  
         createAndWait(5) and destroy(6)."
    ::= { tMirrorSourcePortEntry 2 }

tMirrorSourcePortEgressEnabled  OBJECT-TYPE
    SYNTAX       TruthValue
    MAX-ACCESS   read-create
    STATUS       current
    DESCRIPTION
        "If this value is set to 'true', packets egressing the 
         port will be mirrored. If 'false', egress packets will 
         not be mirrored."
    DEFVAL { false }
    ::= { tMirrorSourcePortEntry 3 }

tMirrorSourcePortIngressEnabled  OBJECT-TYPE
    SYNTAX       TruthValue
    MAX-ACCESS   read-create
    STATUS       current
    DESCRIPTION
        "If this value is set to 'true', packets ingressing the 
         port will be mirrored. If 'false', ingress packets will 
         not be mirrored."
    DEFVAL { false }
    ::= { tMirrorSourcePortEntry 4 }

tMirrorSourcePortLastChgd  OBJECT-TYPE
    SYNTAX      TimeStamp
    MAX-ACCESS  read-only
    STATUS      current
    DESCRIPTION
         "The value of tMirrorSourcePortLastChgd  indicates the sysUpTime
          at the time of the last modification of this entry.

          If no changes were made to the entry since the last re-initialization
          of the local network management subsystem, then this object contains
          a zero value."
    ::= { tMirrorSourcePortEntry 5 }

--
-- mirror source sap table
--

tMirrorSourceSapTable OBJECT-TYPE
    SYNTAX       SEQUENCE OF TMirrorSourceSapEntry
    MAX-ACCESS   not-accessible
    STATUS       current
    DESCRIPTION  
        "Each row in this table represents a SAP (Service Access Point) 
         associated with a mirror source."
    ::= { tMirrorSourceObjects 6 }

tMirrorSourceSapEntry OBJECT-TYPE
    SYNTAX       TMirrorSourceSapEntry
    MAX-ACCESS   not-accessible
    STATUS       current
    DESCRIPTION 
        "Each row represents information about a SAP associated with a 
         mirror source defined in tMirrorSourceTable.
         Entries are created by user.
         Entries are deleted by user, or by agent when the tMirrorSourceTable 
         entry is destroyed.

         Entries in this table have an implied StorageType of 'volatile'.
         That is, configured mirror source information is not persistent
         across system restarts."
    INDEX { tMirrorSourceIndex, 
            tMirrorSourceSapPortId, 
            tMirrorSourceSapEncapValue }
    ::= { tMirrorSourceSapTable 1 }

TMirrorSourceSapEntry ::= SEQUENCE
    {
        tMirrorSourceSapPortId         TmnxPortID,
        tMirrorSourceSapEncapValue     TmnxEncapVal,
        tMirrorSourceSapRowStatus      RowStatus,
        tMirrorSourceSapEgressEnabled  TruthValue,
        tMirrorSourceSapIngressEnabled TruthValue,
        tMirrorSourceSapLastChgd       TimeStamp,
        tMirrorSourceSapIntceptId      TmnxInterceptionIdentifier,
        tMirrorSourceSapSessionId      Unsigned32
    }

tMirrorSourceSapPortId  OBJECT-TYPE
    SYNTAX       TmnxPortID
    MAX-ACCESS   accessible-for-notify
    STATUS       current
    DESCRIPTION
        "The ID of the access port for the Service Access Point (SAP) 
         associated with the mirror source defined by tMirrorSourceIndex."
    ::= { tMirrorSourceSapEntry 2 }

tMirrorSourceSapEncapValue  OBJECT-TYPE
    SYNTAX       TmnxEncapVal
    MAX-ACCESS   accessible-for-notify
    STATUS       current
    DESCRIPTION
        "The value of the label used to identify the SAP on the 
         access port specified by tMirrorSourceSapPortId."
    ::= { tMirrorSourceSapEntry 3 }

tMirrorSourceSapRowStatus  OBJECT-TYPE
    SYNTAX       RowStatus
    MAX-ACCESS   read-create
    STATUS       current
    DESCRIPTION
        "The row status used for creation and deletion of entries in
         tMirrorSourceSapTable.
         The only values supported during a set operation are createAndGo(4),  
         createAndWait(5) and destroy(6)."
    ::= { tMirrorSourceSapEntry 4 }

tMirrorSourceSapEgressEnabled  OBJECT-TYPE
    SYNTAX       TruthValue
    MAX-ACCESS   read-create
    STATUS       current
    DESCRIPTION
        "If this value is set to 'true', packets egressing the 
         SAP will be mirrored. If 'false', egress packets will 
         not be mirrored."
    DEFVAL { false }
    ::= { tMirrorSourceSapEntry 5 }

tMirrorSourceSapIngressEnabled  OBJECT-TYPE
    SYNTAX       TruthValue
    MAX-ACCESS   read-create
    STATUS       current
    DESCRIPTION
        "If this value is set to 'true', packets ingressing the 
         SAP will be mirrored. If 'false', ingress packets will 
         not be mirrored."
    DEFVAL { false }
    ::= { tMirrorSourceSapEntry 6 }

tMirrorSourceSapLastChgd  OBJECT-TYPE
    SYNTAX      TimeStamp
    MAX-ACCESS  read-only
    STATUS      current
    DESCRIPTION
         "The value of tMirrorSourceSapLastChgd  indicates the sysUpTime
          at the time of the last modification of this entry.

          If no changes were made to the entry since the last re-initialization
          of the local network management subsystem, then this object contains
          a zero value."
    ::= { tMirrorSourceSapEntry 7 }

tMirrorSourceSapIntceptId  OBJECT-TYPE
    SYNTAX       TmnxInterceptionIdentifier
    MAX-ACCESS   read-create
    STATUS       current
    DESCRIPTION
        "The value of tMirrorSourceMacFilterIntceptId specifies an 
         identification of the traffic flow corresponding to this conceptual
         row for the Lawful Intercept Gateway."
    DEFVAL       { 0 }
    ::= { tMirrorSourceSapEntry 8 }

tMirrorSourceSapSessionId  OBJECT-TYPE
    SYNTAX       Unsigned32
    MAX-ACCESS   read-create
    STATUS       current
    DESCRIPTION
        "The value of tMirrorSourceMacFilterSessionId specifies an 
         identification of the traffic flow corresponding to this conceptual
         row for the Lawful Intercept Gateway."
    DEFVAL       { 0 }
    ::= { tMirrorSourceSapEntry 9 }

--
--
-- mirror source subscriber table
--

tMirrorSourceSubTableLastChnged OBJECT-TYPE
    SYNTAX      TimeStamp
    MAX-ACCESS  read-only
    STATUS      current
    DESCRIPTION
        "The value of tMirrorSourceSubLastChanged is the timestamp of the 
         last change to this row in tMirrorSourceSubscriberTable."
    ::= { tMirrorSourceObjects 7 }

tMirrorSourceSubscriberTable OBJECT-TYPE
    SYNTAX       SEQUENCE OF TMirrorSourceSubscriberEntry
    MAX-ACCESS   not-accessible
    STATUS       current
    DESCRIPTION  
        "Each row in this table represents a subscriber associated with a
        mirror source."
    ::= { tMirrorSourceObjects 8 }

tMirrorSourceSubscriberEntry OBJECT-TYPE
    SYNTAX       TMirrorSourceSubscriberEntry
    MAX-ACCESS   not-accessible
    STATUS       current
    DESCRIPTION 
        "Each row represents information about a subscriber associated with a 
         mirror source defined in tMirrorSourceTable.

         Entries are created by user.

         Entries are deleted by user, or by agent when the tMirrorSourceTable 
         entry is destroyed.

         Entries in this table have an implied StorageType of 'volatile'.
         That is, configured mirror source information is not persistent
         across system restarts."
    INDEX { tMirrorSourceIndex, tMirrorSourceSubIdent }
    ::= { tMirrorSourceSubscriberTable 1 }

TMirrorSourceSubscriberEntry ::= SEQUENCE
    {
        tMirrorSourceSubIdent          TNamedItem,
        tMirrorSourceSubRowStatus      RowStatus,
        tMirrorSourceSubLastChanged    TimeStamp,
        tMirrorSourceSubPortId         TmnxPortID,
        tMirrorSourceSubEncapValue     TmnxEncapVal,
        tMirrorSourceSubIpAddrType     InetAddressType,
        tMirrorSourceSubIpAddr         InetAddress,
        tMirrorSourceSubMacAddr        MacAddress,
        tMirrorSourceSubSLAProfName    TNamedItemOrEmpty,
        tMirrorSourceSubFC             TFCSet,
        tMirrorSourceSubEgressEnabled  TruthValue,
        tMirrorSourceSubIngressEnabled TruthValue,
        tMirrorSourceSubIntceptId      TmnxInterceptionIdentifier,
        tMirrorSourceSubSessionId      Unsigned32
    }

tMirrorSourceSubIdent OBJECT-TYPE
    SYNTAX      TNamedItem
    MAX-ACCESS  accessible-for-notify
    STATUS      current
    DESCRIPTION
        "The value of tMirrorSourceSubIdent specifies the subscriber
         identification of this subscriber on this mirror source."
    ::= { tMirrorSourceSubscriberEntry 1 }

tMirrorSourceSubRowStatus  OBJECT-TYPE
    SYNTAX       RowStatus
    MAX-ACCESS   read-create
    STATUS       current
    DESCRIPTION
        "The row status used for creation and deletion of entries in
         the tMirrorSourceSubscriberTable."
    ::= { tMirrorSourceSubscriberEntry 2 }

tMirrorSourceSubLastChanged  OBJECT-TYPE
    SYNTAX      TimeStamp
    MAX-ACCESS  read-only
    STATUS      current
    DESCRIPTION
        "The value of tMirrorSourceSubLastChanged is the timestamp of the 
         last change to this row in the tMirrorSourceSubscriberTable."
    ::= { tMirrorSourceSubscriberEntry 3 }

tMirrorSourceSubPortId  OBJECT-TYPE
    SYNTAX       TmnxPortID
    MAX-ACCESS   read-create
    STATUS       current
    DESCRIPTION
        "The value of tMirrorSourceSubPortId specifies the ID of the access
        port for the Service Access Point (SAP) associated with the mirror
        source defined by tMirrorSourceIndex."
    DEFVAL { 0 }
    ::= { tMirrorSourceSubscriberEntry 4 }

tMirrorSourceSubEncapValue  OBJECT-TYPE
    SYNTAX       TmnxEncapVal
    MAX-ACCESS   read-create
    STATUS       current
    DESCRIPTION
        "The value of tMirrorSourceSubEncapValue specifies the label used to
        identify the SAP on the access port specified by 
        tMirrorSourceSubPortId."
    DEFVAL { 0 }
    ::= { tMirrorSourceSubscriberEntry 5 }

tMirrorSourceSubIpAddrType  OBJECT-TYPE
    SYNTAX       InetAddressType
    MAX-ACCESS   read-create
    STATUS       current
    DESCRIPTION
        "The value of tMirrorSourceSubIpAddrType indicates the address type of
        address in tMirrorSourceSubIpAddr." 
    DEFVAL { unknown }
    ::= { tMirrorSourceSubscriberEntry 6 }

tMirrorSourceSubIpAddr  OBJECT-TYPE
    SYNTAX       InetAddress (SIZE (0|4|16|20))
    MAX-ACCESS   read-create
    STATUS       current
    DESCRIPTION
        "The value of tMirrorSourceSubIpAddr specifies the IP address of the
        remote source or the far-end ESR which is allowed to be a source of
        packets for the mirror destination service defined by
        tMirrorDestinationIndex."
    DEFVAL { ''H }
    ::= { tMirrorSourceSubscriberEntry 7 }

tMirrorSourceSubMacAddr OBJECT-TYPE
    SYNTAX       MacAddress
    MAX-ACCESS   read-create
    STATUS       current
    DESCRIPTION
        "This value of tMirrorSourceSubMacAddr specifies the MAC address to be
        used to match the packets for tMirrorSourceSubIdent subscriber on
        tMirrorSourceIndex mirror source."
    DEFVAL {'000000000000'H}
    ::= { tMirrorSourceSubscriberEntry 8 }

tMirrorSourceSubSLAProfName OBJECT-TYPE
    SYNTAX      TNamedItemOrEmpty
    MAX-ACCESS  read-create
    STATUS      current
    DESCRIPTION
        "The value of tMirrorSourceSubSLAProfName specifies the SLA profile
        name which identifies the hosts as source for mirroring."
     DEFVAL { ''H }
    ::= { tMirrorSourceSubscriberEntry 9 }

tMirrorSourceSubFC  OBJECT-TYPE
    SYNTAX      TFCSet
    MAX-ACCESS   read-create
    STATUS       current
    DESCRIPTION
        "The value of tMirrorSourceSubFC specifies the forwarding classes
        traffic which should be mirrored. Setting multiple bits will mirror
        traffic from several forwarding classes."
    DEFVAL      { {} }
    ::= { tMirrorSourceSubscriberEntry 10 }

tMirrorSourceSubEgressEnabled  OBJECT-TYPE
    SYNTAX       TruthValue
    MAX-ACCESS   read-create
    STATUS       current
    DESCRIPTION
        "The value of tMirrorSourceSubEgressEnabled specifies whether packets
        egressing the SAPs will be mirrored.  If set to 'true', egress packets
        will be mirrored."
    DEFVAL { false }
    ::= { tMirrorSourceSubscriberEntry 11 }

tMirrorSourceSubIngressEnabled  OBJECT-TYPE
    SYNTAX       TruthValue
    MAX-ACCESS   read-create
    STATUS       current
    DESCRIPTION
        "The value of tMirrorSourceSubIngressEnabled specifies whether packets
        ingressing the SAPs will be mirrored. If set to 'true', ingress packets
        will be mirrored."
    DEFVAL { false }
    ::= { tMirrorSourceSubscriberEntry 12 }

tMirrorSourceSubIntceptId  OBJECT-TYPE
    SYNTAX       TmnxInterceptionIdentifier
    MAX-ACCESS   read-create
    STATUS       current
    DESCRIPTION
        "The value of tMirrorSourceSubIntceptId specifies an 
         identification of the traffic flow corresponding to this conceptual
         row for the Lawful Intercept Gateway." 
    DEFVAL { 0 }
    ::= { tMirrorSourceSubscriberEntry 13 }

tMirrorSourceSubSessionId  OBJECT-TYPE
    SYNTAX       Unsigned32
    MAX-ACCESS   read-create
    STATUS       current
    DESCRIPTION
        "The value of tMirrorSourceSubSessionId specifies an 
         identification of the traffic flow corresponding to this conceptual
         row for the Lawful Intercept Gateway." 
    DEFVAL { 0 }
    ::= { tMirrorSourceSubscriberEntry 14 }

--
-- mirror source isa application-assurance-group table
--

tMirrorSourceIsaAaGrpTable OBJECT-TYPE
    SYNTAX       SEQUENCE OF TMirrorSourceIsaAaGrpEntry
    MAX-ACCESS   not-accessible
    STATUS       current
    DESCRIPTION  
        "This table defines a list of (physical interface) tmnxBsxIsaAaGrpEntry
         rows for each mirror source"
    ::= { tMirrorSourceObjects 9 }

tMirrorSourceIsaAaGrpEntry OBJECT-TYPE
    SYNTAX       TMirrorSourceIsaAaGrpEntry
    MAX-ACCESS   not-accessible
    STATUS       current
    DESCRIPTION 
        "Each row reprsents information about an tmnxBsxIsaAaGrpEntry associated
         with a Mirror source defined in tMirrorSourceTable.
         Entries are created by user.
         Entries are deleted by user, or by agent when the tMirrorSourceTable 
         entry is destroyed.

         Entries in this table have an implied StorageType of 'volatile'.
         That is, configured mirror source information is not persistent
         across system restarts."
    INDEX { tMirrorSourceIndex, tMirrorSourceIsaAaGrpIndex }
    ::= { tMirrorSourceIsaAaGrpTable 1 }

TMirrorSourceIsaAaGrpEntry ::= SEQUENCE
    {
        tMirrorSourceIsaAaGrpIndex           Integer32,
        tMirrorSourceIsaAaGrpRowStatus       RowStatus,
        tMirrorSourceIsaAaGrpUnknownOnly     TruthValue,
        tMirrorSourceIsaAaGrpLastChgd        TimeStamp
    }

tMirrorSourceIsaAaGrpIndex  OBJECT-TYPE
    SYNTAX       Integer32
    MAX-ACCESS   not-accessible
    STATUS       current
    DESCRIPTION
        "tMirrorSourceIsaAaGrpIndex specifies the ISA Application
         Assurance Group TIMETRA-BSX-NG-MIB::tmnxBsxIsaAaGroupIndex
         as the mirror source defined by tMirrorSourceIndex."
    ::= { tMirrorSourceIsaAaGrpEntry 1 }

tMirrorSourceIsaAaGrpRowStatus  OBJECT-TYPE
    SYNTAX       RowStatus
    MAX-ACCESS   read-create
    STATUS       current
    DESCRIPTION
        "tMirrorSourceIsaAaGrpRowStatus specifies the creation and
         deletion of entries in tMirrorSourceIsaAaGrpTable.
         The only values supported during a set operation are
         createAndGo(4), createAndWait(5) and destroy(6)."
    ::= { tMirrorSourceIsaAaGrpEntry 2 }

tMirrorSourceIsaAaGrpUnknownOnly  OBJECT-TYPE
    SYNTAX       TruthValue
    MAX-ACCESS   read-create
    STATUS       current
    DESCRIPTION
        "tMirrorSourceIsaAaGrpUnknownOnly specifies the
         type of traffic to be mirrored by the ISA-AA Group.

         If this value is set to 'true', packets traversing the 
         ISA-AA Group will be mirrored only if not identified as a
         particular protocol. If 'false', all packets will be
         mirrored."
    DEFVAL { true }
    ::= { tMirrorSourceIsaAaGrpEntry 3 }

tMirrorSourceIsaAaGrpLastChgd  OBJECT-TYPE
    SYNTAX      TimeStamp
    MAX-ACCESS  read-only
    STATUS      current
    DESCRIPTION
         "The value of tMirrorSourceIsaAaGrpLastChgd indicates the sysUpTime
          at the time of the last modification of this entry.

          If no changes were made to the entry since the last re-initialization
          of the local network management subsystem, then this object contains
          a zero value."
    ::= { tMirrorSourceIsaAaGrpEntry 4 }

------------------------------------
-- Mirror Source Last Changed Objects
------------------------------------
tMirrorSrcTblLastChgd OBJECT-TYPE
    SYNTAX      TimeStamp
    MAX-ACCESS  read-only
    STATUS      current
    DESCRIPTION
         "The value of  tMirrorSrcTblLastChgd indicates the sysUpTime
          at the time of the last modification of tMirrorSourceTable.

          If no changes were made to the table since the last re-initialization
          of the local network management subsystem, then this object contains
          a zero value."
    ::= { tMirrorSourceObjects 10 }

tMirrorSrcIpFltrTblLastChgd OBJECT-TYPE
    SYNTAX      TimeStamp
    MAX-ACCESS  read-only
    STATUS      current
    DESCRIPTION
         "The value of  tMirrorSrcIpFltrTblLastChgd indicates the sysUpTime
          at the time of the last modification of tMirrorSourceIpFilterTable.

          If no changes were made to the table since the last re-initialization
          of the local network management subsystem, then this object contains
          a zero value."
    ::= { tMirrorSourceObjects 11 }

tMirrorSrcMacFltrTblLastChgd OBJECT-TYPE
    SYNTAX      TimeStamp
    MAX-ACCESS  read-only
    STATUS      current
    DESCRIPTION
         "The value of tMirrorSrcMacFltrTblLastChgd indicates the sysUpTime
          at the time of the last modification of tMirrorSourceMacFilterTable.

          If no changes were made to the table since the last re-initialization
          of the local network management subsystem, then this object contains
          a zero value."
    ::= { tMirrorSourceObjects 12 }

tMirrorSrcIngLblTblLastChgd OBJECT-TYPE
    SYNTAX      TimeStamp
    MAX-ACCESS  read-only
    STATUS      current
    DESCRIPTION
         "The value of  tMirrorSrcIngLblTblLastChgd indicates the sysUpTime
          at the time of the last modification of tMirrorSourceIngressLabelTable.

          If no changes were made to the table since the last re-initialization
          of the local network management subsystem, then this object contains
          a zero value."
    ::= { tMirrorSourceObjects 13 }

tMirrorSrcPortTblLastChgd OBJECT-TYPE
    SYNTAX      TimeStamp
    MAX-ACCESS  read-only
    STATUS      current
    DESCRIPTION
         "The value of  tMirrorSrcPortTblLastChgd indicates the sysUpTime
          at the time of the last modification of tMirrorSourcePortTable.

          If no changes were made to the table since the last re-initialization
          of the local network management subsystem, then this object contains
          a zero value."
    ::= { tMirrorSourceObjects 14 }

tMirrorSrcSapTblLastChgd OBJECT-TYPE
    SYNTAX      TimeStamp
    MAX-ACCESS  read-only
    STATUS      current
    DESCRIPTION
         "The value of  tMirrorSrcSapTblLastChgd indicates the sysUpTime
          at the time of the last modification of tMirrorSourceSapTable.

          If no changes were made to the table since the last re-initialization
          of the local network management subsystem, then this object contains
          a zero value."
    ::= { tMirrorSourceObjects 15 }

tMirrorSrcIsaAaGrpTblLastChgd OBJECT-TYPE
    SYNTAX      TimeStamp
    MAX-ACCESS  read-only
    STATUS      current
    DESCRIPTION
         "The value of tMirrorSrcIsaAaGrpTblLastChgd indicates the sysUpTime
          at the time of the last modification of tMirrorSourceIsaAaGrpTable.

          If no changes were made to the table since the last re-initialization
          of the local network management subsystem, then this object contains
          a zero value."
    ::= { tMirrorSourceObjects 16 }

--
-- mirror source ipv6-filter table
--

tMirrorSourceIpv6FilterTable OBJECT-TYPE
    SYNTAX       SEQUENCE OF TMirrorSourceIpv6FilterEntry
    MAX-ACCESS   not-accessible
    STATUS       current
    DESCRIPTION  
        "Each row in this table represents an IPv6 Filter Entry 
         associated with a mirror source."
    ::= { tMirrorSourceObjects 17 }

tMirrorSourceIpv6FilterEntry OBJECT-TYPE
    SYNTAX       TMirrorSourceIpv6FilterEntry
    MAX-ACCESS   not-accessible
    STATUS       current
    DESCRIPTION 
        "Each row represents information about a particular IPv6 
         Filter Entry associated with a mirror source defined in 
         the tMirrorSourceTable.
         Entries are created by user.
         Entries are deleted by user, or by agent when the tMirrorSourceTable 
         entry is destroyed.

         Entries in this table have an implied StorageType of 'volatile'.
         That is, configured mirror source information is not persistent
         across system restarts."
    INDEX { tMirrorSourceIndex, 
            tMirrorSourceIpv6Filter, 
            tMirrorSourceIpv6FilterParams }
    ::= { tMirrorSourceIpv6FilterTable 1 }

TMirrorSourceIpv6FilterEntry ::= SEQUENCE
    {
        tMirrorSourceIpv6Filter          TIPFilterID,
        tMirrorSourceIpv6FilterParams    TEntryId,
        tMirrorSourceIpv6FilterRowStatus RowStatus,
        tMirrorSourceIpv6FilterLastChgd  TimeStamp,
        tMirrorSourceIpv6FilterIntceptId TmnxInterceptionIdentifier,
        tMirrorSourceIpv6FilterSessionId Unsigned32
    }

tMirrorSourceIpv6Filter  OBJECT-TYPE
    SYNTAX       TIPFilterID (1..65535)
    MAX-ACCESS   not-accessible
    STATUS       current
    DESCRIPTION
        "This value specifies the IPv6 Filter ID of the IPv6 Filter Entry 
         associated with the mirror source defined by tMirrorSourceIndex."
    ::= { tMirrorSourceIpv6FilterEntry 1 }

tMirrorSourceIpv6FilterParams  OBJECT-TYPE
    SYNTAX       TEntryId
    MAX-ACCESS   not-accessible
    STATUS       current
    DESCRIPTION
        "This value corresponds to the Entry ID which identifies a specific 
         'Entry' within the IPv6 Filter defined by tMirrorSourceIpFilter above. 
         
         Each IPv6 Filter has a number of 'Entries' associated with it and each 
         Entry within the filter is identified by an Entry ID which is unique 
         within the filter."
    ::= { tMirrorSourceIpv6FilterEntry 2 }

tMirrorSourceIpv6FilterRowStatus  OBJECT-TYPE
    SYNTAX       RowStatus
    MAX-ACCESS   read-create
    STATUS       current
    DESCRIPTION
        "The row status used for creation and deletion of entries in
         tMirrorSourceIpFilterTable.
         The only values supported during a set operation are createAndGo(4),  
         createAndWait(5) and destroy(6)."
    ::= { tMirrorSourceIpv6FilterEntry 3 }

tMirrorSourceIpv6FilterLastChgd  OBJECT-TYPE
    SYNTAX      TimeStamp
    MAX-ACCESS  read-only
    STATUS      current
    DESCRIPTION
         "The value of tMirrorSourceIpv6FilterLastChgd  indicates the sysUpTime
          at the time of the last modification of this entry.

          If no changes were made to the entry since the last re-initialization
          of the local network management subsystem, then this object contains
          a zero value."
    ::= { tMirrorSourceIpv6FilterEntry 4 }

tMirrorSourceIpv6FilterIntceptId  OBJECT-TYPE
    SYNTAX       TmnxInterceptionIdentifier
    MAX-ACCESS   read-create
    STATUS       current
    DESCRIPTION
        "The value of tMirrorSourceIpv6FilterIntceptId specifies an 
         identification of the traffic flow corresponding to this conceptual
         row for the Lawful Intercept Gateway." 
     DEFVAL       { 0 }
    ::= { tMirrorSourceIpv6FilterEntry 5 }

tMirrorSourceIpv6FilterSessionId  OBJECT-TYPE
    SYNTAX       Unsigned32
    MAX-ACCESS   read-create
    STATUS       current
    DESCRIPTION
        "The value of tMirrorSourceIpv6FilterSessionId specifies an 
         identification of the traffic flow corresponding to this conceptual
         row for the Lawful Intercept Gateway." 
     DEFVAL       { 0 }
    ::= { tMirrorSourceIpv6FilterEntry 6 }


--
-- Objects for monitoring mirroring installed for LI (Lawfull Intercept)
-- on Radius request.
--
tMirrorRadiusLiTable OBJECT-TYPE
    SYNTAX       SEQUENCE OF TMirrorRadiusLiEntry
    MAX-ACCESS   not-accessible
    STATUS       current
    DESCRIPTION
        "The tMirrorRadiusLiTable contains information about each mirror source
         installed for LI (Lawfull Intercept) on request by Radius."
    ::= { tMirrorRadiusLiObjects 1 }

tMirrorRadiusLiEntry OBJECT-TYPE
    SYNTAX       TMirrorRadiusLiEntry
    MAX-ACCESS   not-accessible
    STATUS       current
    DESCRIPTION 
        "Each row represents information about a particular mirror source.
         Entries are created and deleted by the system while processing 
         LI mirror requests from Radius."
    INDEX {tRadiusLiMirrorDestinationIndex,
           tRadiusLiSrcHostServiceId,
           tRadiusLiSrcHostSapPortId,
           tRadiusLiSrcHostsapEncapValue,     
           tRadiusLiSrcHostIpAddrType,     
           tRadiusLiSrcHostIpAddr,        
           tRadiusLiSrcHostMacAddr,       
           tRadiusLiSrcHostPppoeSessionId}
    ::= { tMirrorRadiusLiTable 1 }

TMirrorRadiusLiEntry ::= SEQUENCE
    {
        tRadiusLiMirrorDestinationIndex  TmnxServId,
        tRadiusLiSrcHostServiceId        TmnxServId,
        tRadiusLiSrcHostSapPortId        TmnxPortID,
        tRadiusLiSrcHostsapEncapValue    TmnxEncapVal,     
        tRadiusLiSrcHostIpAddrType       InetAddressType,
        tRadiusLiSrcHostIpAddr           InetAddress,
        tRadiusLiSrcHostMacAddr          MacAddress,
        tRadiusLiSrcHostPppoeSessionId   TmnxPppoeSessionId,
        tRadiusLiSrcHostId               TSubHostId,   
        tRadiusLiMirrorDirection         TDirection,   
        tRadiusLiMirrorForwClassMap      TFCSet,
        tRadiusLiSrcIntceptId            TmnxInterceptionIdentifier,
        tRadiusLiSrcSessionId            Unsigned32
    }

tRadiusLiMirrorDestinationIndex  OBJECT-TYPE
    SYNTAX       TmnxServId
    MAX-ACCESS   not-accessible
    STATUS       current
    DESCRIPTION
        "Since packet mirroring is setup like a service, 
         tRadiusLiMirrorDestinationIndex represents the Service ID 
         associated with this mirror destination."
    ::= { tMirrorRadiusLiEntry 1 }

tRadiusLiSrcHostServiceId  OBJECT-TYPE
    SYNTAX       TmnxServId
    MAX-ACCESS   not-accessible
    STATUS       current
    DESCRIPTION
        "tRadiusLiSrcHostServiceId indicates the serviceId of the host being 
         mirrored for LI."
    ::= { tMirrorRadiusLiEntry 2 }

tRadiusLiSrcHostSapPortId  OBJECT-TYPE
    SYNTAX       TmnxPortID
    MAX-ACCESS   not-accessible
    STATUS       current
    DESCRIPTION
        "tRadiusLiSrcHostSapPortId indicates the SAP port ID of the host being 
         mirrored for LI."
    ::= { tMirrorRadiusLiEntry 3 }

tRadiusLiSrcHostsapEncapValue  OBJECT-TYPE
    SYNTAX       TmnxEncapVal
    MAX-ACCESS   not-accessible
    STATUS       current
    DESCRIPTION
        "tRadiusLiSrcHostSapPortId indicates the SAP Encap Value of the host
         being mirrored for LI."
    ::= { tMirrorRadiusLiEntry 4 }

tRadiusLiSrcHostIpAddrType  OBJECT-TYPE
    SYNTAX       InetAddressType (1..2)
    MAX-ACCESS   not-accessible
    STATUS       current
    DESCRIPTION
        "The value of tRadiusLiSrcHostIpAddrType indicates the address type of
         address in tRadiusLiSrcHostIpAddr."
    ::= { tMirrorRadiusLiEntry 5 }

tRadiusLiSrcHostIpAddr  OBJECT-TYPE
    SYNTAX       InetAddress (SIZE(0|4|16))
    MAX-ACCESS   not-accessible
    STATUS       current
    DESCRIPTION
        "The value of tRadiusLiSrcHostIpAddr indicates the IP address of the
         subscriber host being mirrored for LI."
    ::= { tMirrorRadiusLiEntry 6 }

tRadiusLiSrcHostMacAddr  OBJECT-TYPE
    SYNTAX       MacAddress
    MAX-ACCESS   not-accessible
    STATUS       current
    DESCRIPTION
        "The value of tRadiusLiSrcHostMacAddr indicates the MAC address of the
         subscriber host being mirrored for LI."
    ::= { tMirrorRadiusLiEntry 7 }

tRadiusLiSrcHostPppoeSessionId  OBJECT-TYPE
    SYNTAX       TmnxPppoeSessionId
    MAX-ACCESS   not-accessible
    STATUS       current
    DESCRIPTION
        "The value of tRadiusLiSrcHostMacAddr indicates the PPPoE Session Id
         of the subscriber host being mirrored for LI."
    ::= { tMirrorRadiusLiEntry 8 }

tRadiusLiSrcHostId  OBJECT-TYPE
    SYNTAX       TSubHostId
    MAX-ACCESS   read-only
    STATUS       current
    DESCRIPTION
        "The value of tRadiusLiSrcHostId indicates the host Id
         of the subscriber host being mirrored for LI."
    ::= { tMirrorRadiusLiEntry 9 }

tRadiusLiMirrorDirection  OBJECT-TYPE
    SYNTAX       TDirection
    MAX-ACCESS   read-only
    STATUS       current
    DESCRIPTION
        "The value of tRadiusLiMirrorDirection indicates the direction of the
         packets being mirrored for LI."
    ::= { tMirrorRadiusLiEntry  10 }

tRadiusLiMirrorForwClassMap  OBJECT-TYPE
    SYNTAX       TFCSet
    MAX-ACCESS   read-only
    STATUS       current
    DESCRIPTION
        "The value of tRadiusLiMirrorForwClassMap indicates the forwarding
         class(es) of the packets being mirrored for LI."
    ::= { tMirrorRadiusLiEntry 11 }

tRadiusLiSrcIntceptId  OBJECT-TYPE
    SYNTAX       TmnxInterceptionIdentifier
    MAX-ACCESS   read-only
    STATUS       current
    DESCRIPTION
        "The value of tMirrorSourceIpFilterIntceptId indicates an 
         identification of the traffic flow corresponding to this conceptual
         row for the Lawful Intercept Gateway." 
    ::= { tMirrorRadiusLiEntry 12 }

tRadiusLiSrcSessionId  OBJECT-TYPE
    SYNTAX       Unsigned32
    MAX-ACCESS   read-only
    STATUS       current
    DESCRIPTION
        "The value of tMirrorSourceIpFilterSessionId indicates an 
         identification of the traffic flow corresponding to this conceptual
         row for the Lawful Intercept Gateway." 
    ::= { tMirrorRadiusLiEntry 13 }

--------------------------------------------------------------------------------
-- Mirror Lawful Intercept Last Changed Objects
--------------------------------------------------------------------------------
tMirrorLiSourceNatTableLastCh OBJECT-TYPE
    SYNTAX      TimeStamp
    MAX-ACCESS  read-only
    STATUS      current
    DESCRIPTION
        "The value of the object tMirrorLiSourceNatTableLastCh indicates
         the value of sysUpTime at the time of the last modification of
         an entry in the tMirrorLiSourceNatTable."
    ::= { tMirrorLiObjects 1 }

tMirrorLiNatLsnSubTableLastCh OBJECT-TYPE
    SYNTAX      TimeStamp
    MAX-ACCESS  read-only
    STATUS      current
    DESCRIPTION
        "The value of the object tMirrorLiNatLsnSubTableLastCh indicates
         the value of sysUpTime at the time of the last modification of
         an entry in the tMirrorLiNatLsnSubTable."
    ::= { tMirrorLiObjects 2 }

tMirrorLiNatL2awSubTableLastCh OBJECT-TYPE
    SYNTAX      TimeStamp
    MAX-ACCESS  read-only
    STATUS      current
    DESCRIPTION
        "The value of the object tMirrorLiNatL2awSubTableLastCh indicates
         the value of sysUpTime at the time of the last modification of
         an entry in the tMirrorLiNatL2awSubTable."
    ::= { tMirrorLiObjects 3 }

tMirrorSourceLiMacFltrTableLstCh OBJECT-TYPE
SYNTAX      TimeStamp
MAX-ACCESS  read-only
STATUS      current
DESCRIPTION
    "The value of the object tMirrorSourceLiMacFltrTableLstCh indicates
     the value of sysUpTime at the time of the last modification of
     an entry in the tMirrorSourceLiMacFltrTable"
::= { tMirrorLiObjects 4 }

tMirrorLiNat64SubTableLastCh OBJECT-TYPE
    SYNTAX      TimeStamp
    MAX-ACCESS  read-only
    STATUS      current
    DESCRIPTION
        "The value of the object tMirrorLiNat64SubTableLastCh indicates
         the value of sysUpTime at the time of the last modification of
         an entry in the tMirrorLiNat64SubTable."
    ::= { tMirrorLiObjects 5 }

--------------------------------------------------------------------------------
-- mirror Lawful Intercept source NAT table
--------------------------------------------------------------------------------

tMirrorLiSourceNatTable OBJECT-TYPE
    SYNTAX       SEQUENCE OF TMirrorLiSourceNatEntry
    MAX-ACCESS   not-accessible
    STATUS       current
    DESCRIPTION  
        "The tMirrorLiSourceNatTable contains mirror source information for NAT.
         
         Conceptual rows in this table are created automatically by the system
         for each row in the tMirrorSourceTable where the value of 
         tMirrorSourceIndex refers to a row in the  tMirrorDestinationTable 
         where the value of tMirrorDestinationEncapsulation is equal to 'ether'."
        
    ::= { tMirrorLiObjects 100 }

tMirrorLiSourceNatEntry OBJECT-TYPE
    SYNTAX       TMirrorLiSourceNatEntry
    MAX-ACCESS   not-accessible
    STATUS       current
    DESCRIPTION 
        "Each row represents NAT information about for a mirror source defined
         in tMirrorSourceTable."
    INDEX { tMirrorSourceIndex }
    ::= { tMirrorLiSourceNatTable 1 }

TMirrorLiSourceNatEntry ::= SEQUENCE
    {
        tMirrorLiSourceNatLastChanged    TimeStamp,
        tMirrorLiSourceNatDestMacAddr    MacAddress,
        tMirrorLiSourceNatSrcMacAddr     MacAddress,
        tMirrorLiSourceNatEthertype      TEtherType
    }

tMirrorLiSourceNatLastChanged  OBJECT-TYPE
    SYNTAX      TimeStamp
    MAX-ACCESS  read-only
    STATUS      current
    DESCRIPTION
        "The value of tMirrorLiSourceNatLastChanged indicates the sysUpTime at
         the time of the most recent management-initiated change to this
         table row."
    ::= { tMirrorLiSourceNatEntry 2 }

tMirrorLiSourceNatDestMacAddr  OBJECT-TYPE
    SYNTAX       MacAddress
    MAX-ACCESS   read-create
    STATUS       current
    DESCRIPTION
        "The value of tMirrorLiSourceNatDestMacAddr specifies the Destination MAC
         Address field of the of the ethernet encapsulation used for the NAT
         subscribers associated with this mirror source.
         
         The value of tMirrorLiSourceNatDestMacAddr is only useful
         if the value of tMirrorDestinationEncapsulation of the corresponding
         mirror destination is equal to 'ether'.
         
         If no value for tMirrorLiSourceNatDestMacAddr is specified, the value
         of TIMETRA-CHASSIS-MIB::tmnxChassisBaseMacAddress is used."
    ::= { tMirrorLiSourceNatEntry 3 }
        
tMirrorLiSourceNatSrcMacAddr  OBJECT-TYPE
    SYNTAX       MacAddress
    MAX-ACCESS   read-create
    STATUS       current
    DESCRIPTION
        "The value of tMirrorLiSourceNatSrcMacAddr specifies the Source MAC
         Address field of the of the ethernet encapsulation used for the NAT
         subscribers associated with this mirror source.
         
         The value of tMirrorLiSourceNatSrcMacAddr is only useful
         if the value of tMirrorDestinationEncapsulation of the corresponding
         mirror destination is equal to 'ether'.
         
         If no value for tMirrorLiSourceNatSrcMacAddr is specified, the value
         of TIMETRA-CHASSIS-MIB::tmnxChassisBaseMacAddress is used."
    ::= { tMirrorLiSourceNatEntry 4 }

tMirrorLiSourceNatEthertype OBJECT-TYPE
    SYNTAX      TEtherType
    MAX-ACCESS  read-create
    STATUS      current
    DESCRIPTION
        "The value of tMirrorLiSourceNatEthertype specifies
         the ethertype of the ethernet encapsulation used for the NAT
         subscribers associated with this mirror source that have 
         an intercept identifier.
         
         If no intercept identifier is available for a NAT subscriber, 
         the value of tMirrorLiSourceNatEthertype is ignored.
         
         The value of tMirrorLiSourceNatEthertype is only useful
         if the value of tMirrorDestinationEncapsulation of the corresponding
         mirror destination is equal to 'ether'."
     DEFVAL { '700'H }
    ::= { tMirrorLiSourceNatEntry 5 }

--------------------------------------------------------------------------------
-- mirror Lawful Intercept source Large Scale NAT subscriber table
--------------------------------------------------------------------------------

tMirrorLiNatLsnSubTable OBJECT-TYPE
    SYNTAX       SEQUENCE OF TMirrorLiNatLsnSubEntry
    MAX-ACCESS   not-accessible
    STATUS       current
    DESCRIPTION  
        "The tMirrorLiNatLsnSubTable contains mirror source information
         installed for Large Scale NAT (LSN) subscribers, 
         including Dual Stack Lite subscribers."
    ::= { tMirrorLiObjects 101 }

tMirrorLiNatLsnSubEntry OBJECT-TYPE
    SYNTAX       TMirrorLiNatLsnSubEntry
    MAX-ACCESS   not-accessible
    STATUS       current
    DESCRIPTION 
        "Each row represents information about a NAT LSN subscriber
         associated with a mirror source defined in tMirrorSourceTable."
    INDEX { tMirrorSourceIndex, 
            vRtrID,
            tMirrorLiNatLsnSubAddrType,
            tMirrorLiNatLsnSubAddr,
            tMirrorLiNatLsnSubPrefixLength }
    ::= { tMirrorLiNatLsnSubTable 1 }

TMirrorLiNatLsnSubEntry ::= SEQUENCE
    {
        tMirrorLiNatLsnSubAddrType       InetAddressType,
        tMirrorLiNatLsnSubAddr           InetAddress,
        tMirrorLiNatLsnSubPrefixLength   InetAddressPrefixLength,
        tMirrorLiNatLsnSubRowStatus      RowStatus,
        tMirrorLiNatLsnSubLastChanged    TimeStamp,
        tMirrorLiNatLsnSubInterceptId    Unsigned32,
        tMirrorLiNatLsnSubSessionId         Unsigned32
    }

tMirrorLiNatLsnSubAddrType OBJECT-TYPE
    SYNTAX      InetAddressType
    MAX-ACCESS  not-accessible
    STATUS      current
    DESCRIPTION 
        "The value of tMirrorLiNatLsnSubAddrType indicates
         the address type of tMirrorLiNatLsnSubAddr."
    ::= { tMirrorLiNatLsnSubEntry 1 }

tMirrorLiNatLsnSubAddr OBJECT-TYPE
    SYNTAX      InetAddress (SIZE(4|16))
    MAX-ACCESS  not-accessible
    STATUS      current
    DESCRIPTION 
        "The value of tMirrorLiNatLsnSubAddr indicates
         the inside IP address of the subscriber."
    ::= { tMirrorLiNatLsnSubEntry 2 }

tMirrorLiNatLsnSubPrefixLength OBJECT-TYPE
    SYNTAX      InetAddressPrefixLength (1..128)
    MAX-ACCESS  not-accessible
    STATUS      current
    DESCRIPTION 
        "The value of tMirrorLiNatLsnSubPrefixLength indicates
         the prefix length of the subscriber.
         
         If the value of tMirrorLiNatLsnSubAddrType is equal to 'ipv4',
         the value of tMirrorLiNatLsnSubPrefixLength must be equal to 32."
    ::= { tMirrorLiNatLsnSubEntry 3 }

tMirrorLiNatLsnSubRowStatus  OBJECT-TYPE
    SYNTAX       RowStatus
    MAX-ACCESS   read-create
    STATUS       current
    DESCRIPTION
        "The row status used for creation and deletion of rows in
         the tMirrorLiNatLsnSubTable."
    ::= { tMirrorLiNatLsnSubEntry 4 }

tMirrorLiNatLsnSubLastChanged  OBJECT-TYPE
    SYNTAX      TimeStamp
    MAX-ACCESS  read-only
    STATUS      current
    DESCRIPTION
        "The value of tMirrorLiNatLsnSubLastChanged indicates the sysUpTime at
         the time of the most recent management-initiated change to this
         table row."
    ::= { tMirrorLiNatLsnSubEntry 5 }

tMirrorLiNatLsnSubInterceptId OBJECT-TYPE
    SYNTAX      Unsigned32
    MAX-ACCESS  read-create
    STATUS      current
    DESCRIPTION
        "The value of tMirrorLiNatLsnSubInterceptId specifies
         the intercept identifier."
     DEFVAL { 0 }
    ::= { tMirrorLiNatLsnSubEntry 6 }

tMirrorLiNatLsnSubSessionId OBJECT-TYPE
    SYNTAX      Unsigned32
    MAX-ACCESS  read-create
    STATUS      current
    DESCRIPTION
        "The value of tMirrorLiNatLsnSubSessionId specifies
         the session identifier."
     DEFVAL { 0 }
    ::= { tMirrorLiNatLsnSubEntry 7 }

--------------------------------------------------------------------------------
-- mirror Lawful Intercept source Layer-2-Aware NAT subscriber table
--------------------------------------------------------------------------------

tMirrorLiNatL2awSubTable OBJECT-TYPE
    SYNTAX       SEQUENCE OF TMirrorLiNatL2awSubEntry
    MAX-ACCESS   not-accessible
    STATUS       current
    DESCRIPTION  
        "The tMirrorLiNatL2awSubTable contains mirror source information
         installed for Layer-2-Aware subscribers."
    ::= { tMirrorLiObjects 102 }

tMirrorLiNatL2awSubEntry OBJECT-TYPE
    SYNTAX       TMirrorLiNatL2awSubEntry
    MAX-ACCESS   not-accessible
    STATUS       current
    DESCRIPTION 
        "Each row represents information about a Layer-2-Aware NAT subscriber
         associated with a mirror source defined in tMirrorSourceTable."
    INDEX { tMirrorSourceIndex, 
            tMirrorLiNatL2awSubIdent }
    ::= { tMirrorLiNatL2awSubTable 1 }

TMirrorLiNatL2awSubEntry ::= SEQUENCE
    {
        tMirrorLiNatL2awSubIdent         DisplayString,
        tMirrorLiNatL2awSubRowStatus     RowStatus,
        tMirrorLiNatL2awSubLastChanged   TimeStamp,
        tMirrorLiNatL2awSubInterceptId   Unsigned32,
        tMirrorLiNatL2awSubSessionId     Unsigned32
    }

tMirrorLiNatL2awSubIdent OBJECT-TYPE
    SYNTAX      DisplayString (SIZE (1..32))
    MAX-ACCESS  not-accessible
    STATUS      current
    DESCRIPTION
        "The value of tMirrorLiNatL2awSubIdent specifies the subscriber
         identification of this subscriber."
    ::= { tMirrorLiNatL2awSubEntry 1 }


tMirrorLiNatL2awSubRowStatus  OBJECT-TYPE
    SYNTAX       RowStatus
    MAX-ACCESS   read-create
    STATUS       current
    DESCRIPTION
        "The row status used for creation and deletion of rows in
         the tMirrorLiNatL2awSubTable."
    ::= { tMirrorLiNatL2awSubEntry 2 }

tMirrorLiNatL2awSubLastChanged  OBJECT-TYPE
    SYNTAX      TimeStamp
    MAX-ACCESS  read-only
    STATUS      current
    DESCRIPTION
        "The value of tMirrorLiNatL2awSubLastChanged indicates the sysUpTime at
         the time of the most recent management-initiated change to this
         table row."
    ::= { tMirrorLiNatL2awSubEntry 3 }

tMirrorLiNatL2awSubInterceptId OBJECT-TYPE
    SYNTAX      Unsigned32
    MAX-ACCESS  read-create
    STATUS      current
    DESCRIPTION
        "The value of tMirrorLiNatL2awSubInterceptId specifies
         the intercept identifier.
         
         The value zero specifies that there is no intercept identifier
         configured."
     DEFVAL { 0 }
    ::= { tMirrorLiNatL2awSubEntry 4 }

tMirrorLiNatL2awSubSessionId OBJECT-TYPE
    SYNTAX      Unsigned32
    MAX-ACCESS  read-create
    STATUS      current
    DESCRIPTION
        "The value of tMirrorLiNatL2awSubSessionId specifies
         the session identifier.
         
         The value zero specifies that there is no intercept identifier
         configured."
     DEFVAL { 0 }
    ::= { tMirrorLiNatL2awSubEntry 5 }

--------------------------------------------------------------------------------
-- mirror Lawful Intercept li-mac-filter source table
--------------------------------------------------------------------------------

tMirrorSourceLiMacFltrTable OBJECT-TYPE
    SYNTAX       SEQUENCE OF TMirrorSourceLiMacFltrEntry
    MAX-ACCESS   not-accessible
    STATUS       current
    DESCRIPTION  
        "The tMirrorSourceLiMacFltrTable contains information 
         about each Li-mac-filter Entry associated with a mirror 
         source."
    ::= { tMirrorLiObjects 103 }

tMirrorSourceLiMacFltrEntry OBJECT-TYPE
    SYNTAX       TMirrorSourceLiMacFltrEntry
    MAX-ACCESS   not-accessible
    STATUS       current
    DESCRIPTION 
        "Each row represents information about a li-mac-filter Entry 
         assocaited with a mirror source defined in the tMirrorSourceTable.
         Entries are created by user.    
         Entries are deleted by user, or by agent when the tMirrorSourceTable 
         entry is destroyed."
    INDEX { tMirrorSourceIndex, 
            tMirrorSourceLiMacFltr, 
            tMirrorSourceLiMacFltrParams }
    ::= { tMirrorSourceLiMacFltrTable 1 }

TMirrorSourceLiMacFltrEntry ::= SEQUENCE
    {
        tMirrorSourceLiMacFltr           TNamedItem,
        tMirrorSourceLiMacFltrParams     TEntryId,
        tMirrorSourceLiMacFltrRowStatus  RowStatus,
        tMirrorSourceLiMacFltrLastChgd   TimeStamp,
        tMirrorSourceLiMacFltrIntceptId  TmnxInterceptionIdentifier,
        tMirrorSourceLiMacFltrSessionId  Unsigned32
    }

tMirrorSourceLiMacFltr  OBJECT-TYPE
    SYNTAX      TNamedItem
    MAX-ACCESS   not-accessible
    STATUS       current
    DESCRIPTION
        "The value of the object tMirrorSourceLiMacFltr specifies the
         li-mac-filter name of the li-mac-filter entry 
         associated with the mirror source defined by tMirrorSourceIndex."
    ::= { tMirrorSourceLiMacFltrEntry 1 }

tMirrorSourceLiMacFltrParams  OBJECT-TYPE
    SYNTAX       TEntryId
    MAX-ACCESS   not-accessible
    STATUS       current
    DESCRIPTION
        "The value tMirrorSourceLiMacFltrParams specifies  the Entry ID
         which identifies a specific 
         'Entry' within the li-mac-filter defined by tMirrorSourceLiMacFltr. 
         
         Each li-mac-ilter has a number of 'Entries' associated with it and each 
         Entry within the filter is identified by an Entry ID which is unique 
         within the filter."
    ::= { tMirrorSourceLiMacFltrEntry 2 }

tMirrorSourceLiMacFltrRowStatus  OBJECT-TYPE
    SYNTAX       RowStatus
    MAX-ACCESS   read-create
    STATUS       current
    DESCRIPTION
        "The value of the object tMirrorSourceLiMacFltrRowStatus is used for 
         creation and deletion of entries in tMirrorSourceLiMacFltrTable."
    ::= { tMirrorSourceLiMacFltrEntry 3 }

tMirrorSourceLiMacFltrLastChgd  OBJECT-TYPE
    SYNTAX      TimeStamp
    MAX-ACCESS  read-only
    STATUS      current
    DESCRIPTION
         "The value of tMirrorSourceLiMacFltrLastChgd  indicates the sysUpTime
          at the time of the last modification of this entry.

          If no changes were made to the entry since the last re-initialization
          of the local network management subsystem, then this object contains
          a zero value."
    ::= { tMirrorSourceLiMacFltrEntry 4 }

tMirrorSourceLiMacFltrIntceptId  OBJECT-TYPE
    SYNTAX       TmnxInterceptionIdentifier
    MAX-ACCESS   read-create
    STATUS       current
    DESCRIPTION
        "The value of tMirrorSourceLiMacFltrIntceptId specifies an 
         identification of the traffic flow corresponding to this conceptual
         row for the Lawful Intercept Gateway."
     DEFVAL { 0 }
    ::= { tMirrorSourceLiMacFltrEntry 5 }

    tMirrorSourceLiMacFltrSessionId  OBJECT-TYPE
    SYNTAX       Unsigned32
    MAX-ACCESS   read-create
    STATUS       current
    DESCRIPTION
        "The value of tMirrorSourceLiMacFltrSessionId specifies an 
         identification of the traffic flow corresponding to this conceptual
         row for the Lawful Intercept Gateway."
     DEFVAL { 0 }
    ::= { tMirrorSourceLiMacFltrEntry 6 }
    
--------------------------------------------------------------------------------
-- mirror Lawful Intercept source NAT64 subscriber table
--------------------------------------------------------------------------------

tMirrorLiNat64SubTable OBJECT-TYPE
    SYNTAX       SEQUENCE OF TMirrorLiNat64SubEntry
    MAX-ACCESS   not-accessible
    STATUS       current
    DESCRIPTION  
        "The tMirrorLiNat64SubTable contains mirror source information
         installed for Large Scale NAT (LSN) subscribers, 
         including Dual Stack Lite subscribers."
    ::= { tMirrorLiObjects 104 }

tMirrorLiNat64SubEntry OBJECT-TYPE
    SYNTAX       TMirrorLiNat64SubEntry
    MAX-ACCESS   not-accessible
    STATUS       current
    DESCRIPTION 
        "Each row represents information about a NAT64 subscriber
         associated with a mirror source defined in tMirrorSourceTable."
    INDEX { tMirrorSourceIndex, 
            vRtrID,
            tMirrorLiNat64SubAddrType,
            tMirrorLiNat64SubAddr,
            tMirrorLiNat64SubPrefixLength }
    ::= { tMirrorLiNat64SubTable 1 }

TMirrorLiNat64SubEntry ::= SEQUENCE
    {
        tMirrorLiNat64SubAddrType        InetAddressType,
        tMirrorLiNat64SubAddr            InetAddress,
        tMirrorLiNat64SubPrefixLength    InetAddressPrefixLength,
        tMirrorLiNat64SubRowStatus       RowStatus,
        tMirrorLiNat64SubLastChanged     TimeStamp,
        tMirrorLiNat64SubInterceptId     Unsigned32,
        tMirrorLiNat64SubSessionId       Unsigned32
    }

tMirrorLiNat64SubAddrType OBJECT-TYPE
    SYNTAX      InetAddressType
    MAX-ACCESS  not-accessible
    STATUS      current
    DESCRIPTION 
        "The value of tMirrorLiNat64SubAddrType indicates
         the address type of tMirrorLiNat64SubAddr.
         
         The value of tMirrorLiNat64SubAddrType is always equal to 'ipv6'."
    ::= { tMirrorLiNat64SubEntry 1 }

tMirrorLiNat64SubAddr OBJECT-TYPE
    SYNTAX      InetAddress (SIZE(16))
    MAX-ACCESS  not-accessible
    STATUS      current
    DESCRIPTION 
        "The value of tMirrorLiNat64SubAddr indicates
         the inside IP address of the subscriber."
    ::= { tMirrorLiNat64SubEntry 2 }

tMirrorLiNat64SubPrefixLength OBJECT-TYPE
    SYNTAX      InetAddressPrefixLength (1..128)
    MAX-ACCESS  not-accessible
    STATUS      current
    DESCRIPTION 
        "The value of tMirrorLiNat64SubPrefixLength indicates
         the prefix length of the subscriber."
    ::= { tMirrorLiNat64SubEntry 3 }

tMirrorLiNat64SubRowStatus  OBJECT-TYPE
    SYNTAX       RowStatus
    MAX-ACCESS   read-create
    STATUS       current
    DESCRIPTION
        "The row status used for creation and deletion of rows in
         the tMirrorLiNat64SubTable."
    ::= { tMirrorLiNat64SubEntry 4 }

tMirrorLiNat64SubLastChanged  OBJECT-TYPE
    SYNTAX      TimeStamp
    MAX-ACCESS  read-only
    STATUS      current
    DESCRIPTION
        "The value of tMirrorLiNat64SubLastChanged indicates the sysUpTime at
         the time of the most recent management-initiated change to this
         table row."
    ::= { tMirrorLiNat64SubEntry 5 }

tMirrorLiNat64SubInterceptId OBJECT-TYPE
    SYNTAX      Unsigned32
    MAX-ACCESS  read-create
    STATUS      current
    DESCRIPTION
        "The value of tMirrorLiNat64SubInterceptId specifies
         the intercept identifier."
     DEFVAL { 0 }
    ::= { tMirrorLiNat64SubEntry 6 }

tMirrorLiNat64SubSessionId OBJECT-TYPE
    SYNTAX      Unsigned32
    MAX-ACCESS  read-create
    STATUS      current
    DESCRIPTION
        "The value of tMirrorLiNat64SubSessionId specifies
         the session identifier."
     DEFVAL { 0 }
    ::= { tMirrorLiNat64SubEntry 7 }

--
-- mirror destination Layer-3 encapsulation table
--

tMirrorDestL3EncTableLastCh OBJECT-TYPE
    SYNTAX      TimeStamp
    MAX-ACCESS  read-only
    STATUS      current
    DESCRIPTION
         "The value of  tMirrorDestL3EncTableLastCh indicates the sysUpTime
          at the time of the last modification of tMirrorDestL3EncTable.

          If no changes were made to the table since the last re-initialization
          of the local network management subsystem, then this object contains
          a zero value."
    ::= { tMirrorDestinationObjects 5 }

tMirrorDestL3EncTable OBJECT-TYPE
    SYNTAX       SEQUENCE OF TMirrorDestL3EncEntry
    MAX-ACCESS   not-accessible
    STATUS       current
    DESCRIPTION  "The tMirrorDestL3EncTable serves to configure
                  Layer-3 encapsulation information for the mirror destinations.
                   
                  The encapsulation referred to the encapsulation header added 
                  to identify a particular mirrored source flow."
    ::= { tMirrorDestinationObjects 6 }

tMirrorDestL3EncEntry OBJECT-TYPE
    SYNTAX       TMirrorDestL3EncEntry
    MAX-ACCESS   not-accessible
    STATUS       current
    DESCRIPTION 
        "Each row represents information about the Layer-3 encapsulation header
         of a particular mirror destination.
         
         Rows in this table can be created or deleted via SNMP operations.
        
         A row can only be created if the corresponding mirror destination
         supports Layer-3 encapsulation; in the corresponding row in the 
         tMirrorDestinationTable, the value of 
         the object tMirrorDestinationEncapsulation must be equal to
         'ether' or 'ipOnly'."
    INDEX { tMirrorDestinationIndex }
    ::= { tMirrorDestL3EncTable 1 }

TMirrorDestL3EncEntry ::= SEQUENCE
    {
        tMirrorDestL3EncRowStatus        RowStatus,
        tMirrorDestL3EncLastCh           TimeStamp,
        tMirrorDestL3EncHeaderType       TmnxMirrorDestinationHeaderType,
        tMirrorDestL3EncRouter           TmnxVRtrID,
        tMirrorDestL3EncUseDirectionBit  TruthValue
    }
    
tMirrorDestL3EncRowStatus OBJECT-TYPE
    SYNTAX      RowStatus
    MAX-ACCESS  read-create
    STATUS      current
    DESCRIPTION
       "The value of tMirrorDestL3EncRowStatus specifies
        the row status of this row."
::= { tMirrorDestL3EncEntry 1 }

tMirrorDestL3EncLastCh OBJECT-TYPE
    SYNTAX      TimeStamp
    MAX-ACCESS  read-only
    STATUS      current
    DESCRIPTION
        "The value of tMirrorDestL3EncLastCh indicates the sysUpTime at
         the time of the most recent management-initiated change to this
         table row."
::= { tMirrorDestL3EncEntry 2 }

tMirrorDestL3EncHeaderType OBJECT-TYPE
    SYNTAX      TmnxMirrorDestinationHeaderType
    MAX-ACCESS  read-create
    STATUS      current
    DESCRIPTION
       "The value of tMirrorDestL3EncHeaderType specifies the type of header
        encapsulation of this mirror destination.
        
        A value for this object must be provided when the row is created."
::= { tMirrorDestL3EncEntry 3 }
    
tMirrorDestL3EncRouter OBJECT-TYPE
    SYNTAX      TmnxVRtrID
    MAX-ACCESS  read-create
    STATUS      current
    DESCRIPTION
       "The value of tMirrorDestL3EncRouter specifies the identifier of the
        router instance to be used with routed encapsulation."
    DEFVAL { 1 }
::= { tMirrorDestL3EncEntry 4 }
    
tMirrorDestL3EncUseDirectionBit OBJECT-TYPE
    SYNTAX      TruthValue
    MAX-ACCESS  read-create
    STATUS      current
    DESCRIPTION
       "The value of tMirrorDestL3EncUseDirectionBit specifies if 
        the highest bit in the Interception ID field
        of the shim header is used to indicate the direction of the mirrored
        traffic flow.
        
        If the value of tMirrorDestL3EncUseDirectionBit is equal to 'true', this
        bit is not available to store a bit of the Interception ID."
    DEFVAL { false }
::= { tMirrorDestL3EncEntry 5 }
    
--
-- mirror Layer-3 gateway table
--

tMirrorDestL3GwTableLastCh OBJECT-TYPE
    SYNTAX      TimeStamp
    MAX-ACCESS  read-only
    STATUS      current
    DESCRIPTION
         "The value of  tMirrorDestL3GwTableLastCh indicates the sysUpTime
          at the time of the last modification of tMirrorDestL3GwTable.

          If no changes were made to the table since the last re-initialization
          of the local network management subsystem, then this object contains
          a zero value."
    ::= { tMirrorDestinationObjects 7 }

tMirrorDestL3GwTable OBJECT-TYPE
    SYNTAX       SEQUENCE OF TMirrorDestL3GwEntry
    MAX-ACCESS   not-accessible
    STATUS       current
    DESCRIPTION  "The tMirrorDestL3GwTable serves to configure Layer-3
                  encapsulation information for mirror destination gateways.
                   
                  The encapsulation referred to is the prepended encapsulation 
                  header added to identify a particular mirrored source flow."
    ::= { tMirrorDestinationObjects 8 }

tMirrorDestL3GwEntry OBJECT-TYPE
    SYNTAX       TMirrorDestL3GwEntry
    MAX-ACCESS   not-accessible
    STATUS       current
    DESCRIPTION 
        "Each row represents information about the Layer-3 encapsulation header
         of a particular mirror destination gateway.
         
         Rows in this table can be created or deleted via SNMP operations.
        
         A row can only be created if the corresponding mirror destination
         supports encapsulation."
    INDEX { tMirrorDestinationIndex,
            tMirrorDestL3GwRole }
    ::= { tMirrorDestL3GwTable 1 }

TMirrorDestL3GwEntry ::= SEQUENCE
    {
        tMirrorDestL3GwRole             TmnxMirrorGatewayRole,
        tMirrorDestL3GwRowStatus        RowStatus,
        tMirrorDestL3GwLastCh           TimeStamp,
        tMirrorDestL3GwSrcAddrType      InetAddressType,
        tMirrorDestL3GwSrcAddr          InetAddress,
        tMirrorDestL3GwDstAddrType      InetAddressType,
        tMirrorDestL3GwDstAddr          InetAddress,
        tMirrorDestL3GwUdpSrcPort       InetPortNumber,
        tMirrorDestL3GwUdpDstPort       InetPortNumber
    }
    
tMirrorDestL3GwRole OBJECT-TYPE
    SYNTAX      TmnxMirrorGatewayRole (1)
    MAX-ACCESS  not-accessible
    STATUS      current
    DESCRIPTION
       "The value of tMirrorDestL3GwRole specifies the role of this gateway.
        
        The only value supported is 'primary'."
::= { tMirrorDestL3GwEntry 1 }

tMirrorDestL3GwRowStatus OBJECT-TYPE
    SYNTAX      RowStatus
    MAX-ACCESS  read-create
    STATUS      current
    DESCRIPTION
       "The value of tMirrorDestL3GwRowStatus specifies
        the row status of this row."
    ::= { tMirrorDestL3GwEntry 2 }

tMirrorDestL3GwLastCh OBJECT-TYPE
    SYNTAX      TimeStamp
    MAX-ACCESS  read-only
    STATUS      current
    DESCRIPTION
        "The value of tMirrorDestL3GwLastCh indicates the sysUpTime at
         the time of the most recent management-initiated change to this
         table row."
    ::= { tMirrorDestL3GwEntry 3 }

tMirrorDestL3GwSrcAddrType OBJECT-TYPE
    SYNTAX      InetAddressType
    MAX-ACCESS  read-create
    STATUS      current
    DESCRIPTION 
        "The value of tMirrorDestL3GwSrcAddrType specifies
         the address type of tMirrorDestL3GwSrcAddr.
         
         The only values supported are 'unknown' and 'ipv4'."
    DEFVAL { unknown }
    ::= { tMirrorDestL3GwEntry 4 }

tMirrorDestL3GwSrcAddr OBJECT-TYPE
    SYNTAX      InetAddress (SIZE(0|4))
    MAX-ACCESS  read-create
    STATUS      current
    DESCRIPTION 
        "The value of tMirrorDestL3GwSrcAddrType specifies
         the source IP address to be used with this gateway.
         
         Only IPv4 addresses are supported."
     DEFVAL { ''H }  
    ::= { tMirrorDestL3GwEntry 5 }

tMirrorDestL3GwDstAddrType OBJECT-TYPE
    SYNTAX      InetAddressType
    MAX-ACCESS  read-create
    STATUS      current
    DESCRIPTION 
        "The value of tMirrorDestL3GwDstAddrType specifies
         the address type of tMirrorDestL3GwDstAddr.
         
         The only values supported are 'unknown' and 'ipv4'."
    DEFVAL { unknown }
    ::= { tMirrorDestL3GwEntry 6 }

tMirrorDestL3GwDstAddr OBJECT-TYPE
    SYNTAX      InetAddress (SIZE(0|4))
    MAX-ACCESS  read-create
    STATUS      current
    DESCRIPTION 
        "The value of tMirrorDestL3GwDstAddrType specifies
         the destination IP address of this gateway.
         
         Only IPv4 addresses are supported."
     DEFVAL { ''H }  
    ::= { tMirrorDestL3GwEntry 7 }

tMirrorDestL3GwUdpSrcPort OBJECT-TYPE
    SYNTAX      InetPortNumber
    MAX-ACCESS  read-create
    STATUS      current
    DESCRIPTION
       "The value of tMirrorDestL3GwUdpSrcPort specifies 
        the UDP source port to be used with this gateway if the value of
        the object tMirrorDestL3EncHeaderType in the corresponding row in the
        is equal to 'ipUdpShim'."
    DEFVAL { 0 }
::= { tMirrorDestL3GwEntry 8 }
    
tMirrorDestL3GwUdpDstPort OBJECT-TYPE
    SYNTAX      InetPortNumber
    MAX-ACCESS  read-create
    STATUS      current
    DESCRIPTION
       "The value of tMirrorDestL3GwUdpDstPort specifies 
        the UDP source port to be used with this gateway if the value of
        the object tMirrorDestL3EncHeaderType in the corresponding row in the
        is equal to 'ipUdpShim'."
    DEFVAL { 0 }
::= { tMirrorDestL3GwEntry 9 }
           
--
-- Notification Objects
--
tMirrorSourceChangeType  OBJECT-TYPE
    SYNTAX      INTEGER {
                    modified (1),
                    deleted  (2),
                    activated (3),
                    deactivated (4)
                }
    MAX-ACCESS  accessible-for-notify
    STATUS      current
    DESCRIPTION
        "The value of tMirrorSourceChangeType specifies the type of
         change made to a IP or MAC filter, IP or MAC filter entry, 
         sap, or subscriber associated with a configured mirror-source
         as indicated by the value of tMirrorSourceIndex.
         
         The values 'activated' and 'deactivated' apply only to
         subscriber IDs as indicated by the value of tMirrorSourceSubIdent."
    ::= { tMirrorSourceNotifyObjects 1 }

tMirrorSourceFilterId  OBJECT-TYPE
    SYNTAX      TFilterID    
    MAX-ACCESS  accessible-for-notify
    STATUS      current
    DESCRIPTION
        "The value of tMirrorSourceFilterId specifies the filter id
         for which this notification is being sent."
    ::= { tMirrorSourceNotifyObjects 3 }

tMirrorSourceFilterEntryId  OBJECT-TYPE
    SYNTAX      TEntryIdOrZero
    MAX-ACCESS  accessible-for-notify
    STATUS      current
    DESCRIPTION
        "The value of tMirrorSourceFilterEntryId specifies the entry
         in the filter for which this notification is being sent. 

         If set to 0, the attempted modification was to a global
         filter parameter."
    ::= { tMirrorSourceNotifyObjects 4 }

tMirrorSourceFilterObject  OBJECT-TYPE
    SYNTAX      OBJECT IDENTIFIER
    MAX-ACCESS  accessible-for-notify
    STATUS      current
    DESCRIPTION
        "The value of tMirrorSourceFilterObject specifies which
         object (containing a filter) the operator tried to change."
    ::= { tMirrorSourceNotifyObjects 7 }

tMirrorSourceFilterDescr  OBJECT-TYPE
    SYNTAX      DisplayString
    MAX-ACCESS  accessible-for-notify
    STATUS      current
    DESCRIPTION
        "The value of tMirrorSourceFilterDescr specifies additional
         information on the reason for sending the event."
    ::= { tMirrorSourceNotifyObjects 8 }

tMirrorFilterSvcId OBJECT-TYPE
    SYNTAX      TmnxServId
    MAX-ACCESS  accessible-for-notify
    STATUS      current
    DESCRIPTION
        "The value of tMirrorFilterSvcId specifies the service id
         to which this notification applies."
    ::= { tMirrorSourceNotifyObjects 9 }

tMirrorFilterPortId  OBJECT-TYPE
    SYNTAX      TmnxPortID
    MAX-ACCESS  accessible-for-notify
    STATUS      current
    DESCRIPTION
        "The value of tMirrorFilterPortId specifies together 
         with tMirrorFilterSapEncapValue the portId
         to which this notification applies."
    ::= { tMirrorSourceNotifyObjects 10 }

tMirrorFilterSapEncapValue  OBJECT-TYPE
    SYNTAX      TmnxEncapVal
    MAX-ACCESS  accessible-for-notify
    STATUS      current
    DESCRIPTION
        "The value of tMirrorFilterSapEncapValue specifies together 
         with tMirrorFilterPortId the portId
         to which this notification applies."
    ::= { tMirrorSourceNotifyObjects 11 }

tMirrorFilterSdpBindId  OBJECT-TYPE
    SYNTAX      SdpBindId
    MAX-ACCESS  accessible-for-notify
    STATUS      current
    DESCRIPTION
        "The value of tMirrorFilterSdpBindId specifies the
        sdp Bind Id to which this notification applies."
    ::= { tMirrorSourceNotifyObjects 12 }

tMirrorFilterType  OBJECT-TYPE
    SYNTAX      TFilterType
    MAX-ACCESS  accessible-for-notify
    STATUS      current
    DESCRIPTION
        "The value of tMirrorFilterType specifies the
          filter type this notification reports about."
    ::= { tMirrorSourceNotifyObjects 13 }

tMirrorFilterDirection  OBJECT-TYPE
    SYNTAX      INTEGER { ingress(1), egress(2) }
    MAX-ACCESS  accessible-for-notify
    STATUS      current
    DESCRIPTION
        "The value of tMirrorFilterDirection specifies the
         the direction (ingress/egress) the filter is applied
         about which this notification reports."
    ::= { tMirrorSourceNotifyObjects 14 }

tMirrorFilterId  OBJECT-TYPE
    SYNTAX      TFilterID
    MAX-ACCESS  accessible-for-notify
    STATUS      current
    DESCRIPTION
        "The value of tMirrorFilterId specifies the
         filter Id about which this notification reports."
    ::= { tMirrorSourceNotifyObjects 15 }

tMirrorFilterIfIndex  OBJECT-TYPE
    SYNTAX      InterfaceIndexOrZero
    MAX-ACCESS  accessible-for-notify
    STATUS      current
    DESCRIPTION
        "The value of tMirrorFilterIfIndex specifies the
         interface about which this notification reports."
    ::= { tMirrorSourceNotifyObjects 16 }

tMirrorFilterIfName  OBJECT-TYPE
    SYNTAX      TNamedItem
    MAX-ACCESS  accessible-for-notify
    STATUS      current
    DESCRIPTION
        "The value of tMirrorFilterIfName specifies the
         interface about which this notification reports."
    ::= { tMirrorSourceNotifyObjects 17 }

--
-- Notification Objects for Lawful Intercept only
--

tMirrorNotifyLiSvcId OBJECT-TYPE
    SYNTAX      TmnxServId
    MAX-ACCESS  accessible-for-notify
    STATUS      current
    DESCRIPTION
        "The value of tMirrorNotifyLiSvcId indicates a service ID."
    ::= { tMirrorLiNotifyObjects 1 }

tMirrorNotifyLiPortId  OBJECT-TYPE
    SYNTAX      TmnxPortID
    MAX-ACCESS  accessible-for-notify
    STATUS      current
    DESCRIPTION
        "The value of tMirrorNotifyLiPortId indicates a port ID."
    ::= { tMirrorLiNotifyObjects 2 }

tMirrorNotifyLiSapEncapValue  OBJECT-TYPE
    SYNTAX      TmnxEncapVal
    MAX-ACCESS  accessible-for-notify
    STATUS      current
    DESCRIPTION
        "The value of tMirrorNotifyLiSapEncapValue indicates
         an encapsulation value."
    ::= { tMirrorLiNotifyObjects 3 }

tMirrorNotifyLiDescription  OBJECT-TYPE
    SYNTAX      DisplayString  (SIZE(0..255))
    MAX-ACCESS  accessible-for-notify
    STATUS      current
    DESCRIPTION
        "The value of tMirrorNotifyLiDescription indicates additional
         information about a notification."
    ::= { tMirrorLiNotifyObjects 4 }

--
-- Notification Information
--

tMirrorSourceEnabled NOTIFICATION-TYPE
    OBJECTS { tMirrorSourceIndex
            }
    STATUS  current
    DESCRIPTION
        "The tMirrorSourceEnabled event is generated when the mirror 
         source is enabled."
    ::= { tMirrorNotifications 1 }

tMirrorSourceDisabled NOTIFICATION-TYPE
    OBJECTS { tMirrorSourceIndex
            }
    STATUS  current
    DESCRIPTION
        "The tMirrorSourceDisabled event is generated when the mirror 
         source is disabled."
    ::= { tMirrorNotifications 2 }

tMirrorDestinationEnabled NOTIFICATION-TYPE
    OBJECTS { tMirrorDestinationIndex
            }
    STATUS  current
    DESCRIPTION
        "The tMirrorDestinationEnabled event is generated when the mirror 
         destination is enabled."
    ::= { tMirrorNotifications 3 }

tMirrorDestinationDisabled NOTIFICATION-TYPE
    OBJECTS { tMirrorDestinationIndex
            }
    STATUS  current
    DESCRIPTION
        "The tMirrorDestinationDisabled event is generated when the mirror 
         destination is disabled."
    ::= { tMirrorNotifications 4 }

tMirrorSourceRemovedBySystem NOTIFICATION-TYPE
    OBJECTS { tMirrorSourceIndex
            }
    STATUS  current
    DESCRIPTION
        "The tMirrorSourceRemovedBySystem event is generated when the 
         mirror source is removed by the system."
    ::= { tMirrorNotifications 5 }

tMirrorSourceIpFilterChange       NOTIFICATION-TYPE
    OBJECTS { tMirrorSourceIndex,
              tMirrorSourceFilterId,
              tMirrorSourceFilterEntryId,
              tMirrorSourceChangeType
            }
    STATUS  current
    DESCRIPTION
        "The tMirrorSourceIpFilterChange event is generated when a IP filter or
         filter entry associated with the mirror-source indicated by
         tMirrorSourceIndex is 'modified' or 'deleted'.  If the only the base 
         filter is modified, tMirrorSourceFilterEntryId will have a value 
         of 0."
    ::= { tMirrorNotifications 6 }

tMirrorSourceMacFilterChange       NOTIFICATION-TYPE
    OBJECTS { tMirrorSourceIndex,
              tMirrorSourceFilterId,
              tMirrorSourceFilterEntryId,
              tMirrorSourceChangeType
            }
    STATUS  current
    DESCRIPTION
        "The tMirrorSourceMacFilterChange event is generated when a MAC 
         filter or filter entry associated with the mirror-source indicated by
         tMirrorSourceIndex is 'modified' or 'deleted'.  If the only the base 
         filter is modified, tMirrorSourceFilterEntryId will have a value 
         of 0."
    ::= { tMirrorNotifications 7 }

tMirrorSourceSapChange       NOTIFICATION-TYPE
    OBJECTS { tMirrorSourceIndex,
              tMirrorSourceSapPortId, 
              tMirrorSourceSapEncapValue,
              tMirrorSourceChangeType
            }
    STATUS  current
    DESCRIPTION
        "The tMirrorSourceSapChange event is generated when a SAP associated 
         with the mirror-source indicated by tMirrorSourceIndex is 'modified'
         or 'deleted'."
    ::=  { tMirrorNotifications 8 }

tMirrorSourceSubChange   NOTIFICATION-TYPE
    OBJECTS { tMirrorSourceIndex,
              tMirrorSourceSubIdent,
              tMirrorSourceChangeType
            }
    STATUS  current
    DESCRIPTION
        "The tMirrorSourceSubChange event is generated when a subscriber
         associated with the mirror-source indicated by tMirrorSourceIndex 
         is 'activated', 'deactivated', 'modified' or 'deleted'."
    ::=  { tMirrorNotifications 9 }

tMirrorSourceIPFltrChangeReject  NOTIFICATION-TYPE
    OBJECTS { tMirrorSourceIndex,
              tMirrorSourceFilterId,
              tMirrorSourceFilterEntryId
            }
    STATUS  current
    DESCRIPTION
        "The tMirrorSourceIPFltrChangeReject event is generated when 
         an operator is trying to modify a filter or a filter-entry
         of a filter that cannot currently be changed because the 
         filter is being used for mirrorring."
    ::=  { tMirrorNotifications 10 }

tMirrorSourceIP6FltrChangeReject  NOTIFICATION-TYPE
    OBJECTS { tMirrorSourceIndex,
              tMirrorSourceFilterId,
              tMirrorSourceFilterEntryId
            }
    STATUS  current
    DESCRIPTION
        "The tMirrorSourceIP6FltrChangeReject event is generated when 
         an operator is trying to modify a filter or a filter-entry
         of a filter that cannot currently be changed because the 
         filter is being used for mirrorring."
    ::=  { tMirrorNotifications 11 }

tMirrorSourceMacFltrChangeReject  NOTIFICATION-TYPE
    OBJECTS { tMirrorSourceIndex,
              tMirrorSourceFilterId,
              tMirrorSourceFilterEntryId
            }
    STATUS  current
    DESCRIPTION
        "The tMirrorSourceMacFltrChangeReject event is generated when 
         an operator is trying to modify a filter or a filter-entry
         of a filter that cannot currently be changed because the 
         filter is being used for mirrorring."
    ::=  { tMirrorNotifications 12 }

tMirrorSourceFilterAssignReject  NOTIFICATION-TYPE
    OBJECTS { tMirrorSourceFilterObject,
              tMirrorSourceFilterDescr
            }
    STATUS  current
    DESCRIPTION
        "The tMirrorSourceFilterAssignReject event is generated when 
         an operator is trying to modify a filter assignment
         of a filter that cannot currently be changed because the 
         filter is being used for mirrorring."
    ::=  { tMirrorNotifications 13 }

tMirrorDestinationChangeReject  NOTIFICATION-TYPE
    OBJECTS { tMirrorDestinationIndex 
            }
    STATUS  current
    DESCRIPTION
        "The tMirrorDestinationChangeReject event is generated when 
         an operator is trying to modify a mirror destination
         that cannot currently be changed because the destination 
         is being used for mirrorring."
    ::=  { tMirrorNotifications 14 }

tMirrorSourceFilterOverruled  NOTIFICATION-TYPE
    OBJECTS { tMirrorSourceFilterObject,
              tMirrorSourceFilterDescr
            }
    STATUS  current
    DESCRIPTION
        "The tMirrorSourceFilterOverruled event is generated when
         an assignment of a filter used for mirroring is overruled
         with another filter assignment.
         
         This situation may occur while using Time-Of-Day Suites."
    ::=  { tMirrorNotifications 15 }

tMirrorSourceFilterAssignWarn  NOTIFICATION-TYPE
    OBJECTS { tMirrorSourceFilterObject,
              tMirrorSourceFilterDescr
            }
    STATUS  current
    DESCRIPTION
        "The tMirrorSourceFilterAssignWarn event is generated when 
         an operator has made a filter assignment of a filter that is being  
         used for mirrorring, while that assignment may be overruled."
    ::=  { tMirrorNotifications 16 }

tMirrorFilterAssignToSapWarn  NOTIFICATION-TYPE
    OBJECTS { tMirrorFilterSvcId,
              tMirrorFilterPortId,
              tMirrorFilterSapEncapValue,
              tMirrorFilterType,
              tMirrorFilterDirection,
              tMirrorFilterId
            }
    STATUS  current
    DESCRIPTION
        "The tMirrorFilterAssignToSapWarn event is generated when 
         an operator assignes a filter to a SAP while this filter
         is being used by LI."
    ::=  { tMirrorNotifications 17 }

tMirrorFilterAssignToSdpWarn  NOTIFICATION-TYPE
    OBJECTS { tMirrorFilterSvcId,
              tMirrorFilterSdpBindId,
              tMirrorFilterType,
              tMirrorFilterDirection,
              tMirrorFilterId
            }
    STATUS  current
    DESCRIPTION
        "The tMirrorFilterAssignToSdpWarn event is generated when 
         an operator assignes a filter to a SDP while this filter
         is being used by LI."
    ::=  { tMirrorNotifications 18 }

tMirrorFilterAssignToItfWarn  NOTIFICATION-TYPE
    OBJECTS { tMirrorFilterIfIndex,
              tMirrorFilterIfName,
              tMirrorFilterType,
              tMirrorFilterDirection,
              tMirrorFilterId
            }
    STATUS  current
    DESCRIPTION
        "The tMirrorFilterAssignToItfWarn event is generated when 
         an operator assignes a filter to an interface while this filter
         is being used by LI."
    ::=  { tMirrorNotifications 19 }

tMirrorSourceLiFilterChanged  NOTIFICATION-TYPE
    OBJECTS { tMirrorSourceFilterObject,
              tMirrorSourceFilterDescr
            }
    STATUS  current
    DESCRIPTION
        "The tMirrorSourceLiFilterChanged event is generated when a parameter
         of a filter which is referenced by Lawful Intercept (LI),or a 
         parameter of one of its entry has been changed. 
         
         [CAUSE]
         This notification may be triggered only if LI filter lock has been 
         overruled, and one of the following actions has been done:
         
         1) a filter referenced by LI has been deleted.
         2) one of the parameters (default-action, scope) of a filter which
            is referenced by LI has been changed.
         3) a filter which is referenced by LI has been overwritten.
         4) new entry has been created for a filter which is referenced by LI.
         5) an entry of a filter which is referenced by LI has been activated.
         6) an entry has been removed from a filter which is referenced by LI.
         7) an entry of a filter which is referenced by LI has been 
            renumbered.
         8) one of the parameters of an entry in a filter which is referenced
            by LI has been changed.
         
         [EFFECT]
         Since a filter which is referenced by LI, or its parameter has been
         modified, the mirrored traffic may be changed."
    ::=  { tMirrorNotifications 20 }

tMirrorSourceLiSubProblem  NOTIFICATION-TYPE
     OBJECTS { tMirrorSourceSubIdent,
               tMirrorNotifyLiSvcId,
               tMirrorNotifyLiPortId,
               tMirrorNotifyLiSapEncapValue,
               tMirrorNotifyLiDescription
             }
     STATUS  current
     DESCRIPTION
         "The tMirrorSourceLiSubProblem event is generated when the system fails
          to intercept traffic for a subscriber.
          
          The SAP where the traffic comes into the system is indicated in the
          objects tMirrorNotifyLiSvcId, tMirrorNotifyLiPortId 
          and tMirrorNotifyLiSapEncapValue.
          
          [CAUSE]
          Detailed information about the exact cause of the notification 
          is available in the object tMirrorNotifyLiDescription.
          
          [EFFECT]
          Traffic of a subscriber subject to Lawful Intercept is not intercepted."
     ::=  { tMirrorNotifications 21 }

tMirrorSourceIpv6FilterChange       NOTIFICATION-TYPE
    OBJECTS { tMirrorSourceIndex,
              tMirrorSourceFilterId,
              tMirrorSourceFilterEntryId,
              tMirrorSourceChangeType
            }
    STATUS  current
    DESCRIPTION
        "The tMirrorSourceIpv6FilterChange event is generated when a IPv6 filter 
         or filter entry associated with the mirror-source indicated by
         tMirrorSourceIndex is 'modified' or 'deleted'.  If the only the base 
         filter is modified, tMirrorSourceFilterEntryId will have a value 
         of 0."
    ::= { tMirrorNotifications 22 }

tMirrorSourceIPv6FltrChangeRej  NOTIFICATION-TYPE
    OBJECTS { tMirrorSourceIndex,
              tMirrorSourceFilterId,
              tMirrorSourceFilterEntryId
            }
    STATUS  current
    DESCRIPTION
        "The tMirrorSourceIPv6FltrChangeRej event is generated when 
         an operator is trying to modify a filter or a filter-entry
         of a filter that cannot currently be changed because the 
         filter is being used for mirrorring."
    ::=  { tMirrorNotifications 23 }

--
-- Conformance Information
--

tMirrorCompliances  OBJECT IDENTIFIER ::= { tMirrorConformance 1 }
tMirrorGroups       OBJECT IDENTIFIER ::= { tMirrorConformance 2 }


-- compliance statements

-- tMirrorCompliance MODULE-COMPLIANCE
--    ::= { tMirrorCompliances 1 }

tMirrorR2r1Compliance MODULE-COMPLIANCE
    STATUS  obsolete
    DESCRIPTION
            "The compliance statement for revision 2.1 of 
             TIMETRA-MIRROR-MIB for management of extended Mirror
             features on Alcatel-Lucent SROS series systems."
    MODULE  -- this module
        MANDATORY-GROUPS { 
            tMirrorDestinationR2r1Group,
            tMirrorDestinationR2r1RemoteSourceGroup,
            tMirrorSourceGroup,
            tMirrorNotificationsGroup
        }
    ::= { tMirrorCompliances 2 }

tMirrorV6v0Compliance MODULE-COMPLIANCE
    STATUS  obsolete
    DESCRIPTION
            "The compliance statement for revision 2.1 of 
             TIMETRA-MIRROR-MIB for management of extended Mirror
             features on Alcatel-Lucent SROS series systems."
    MODULE  -- this module
        MANDATORY-GROUPS { 
            tMirrorDestinationV6v0Group,
            tMirrorDestinationR2r1RemoteSourceGroup,
            tMirrorSourceV6v0Group,
            tMirrorBsxV6v0Group,
            tMirrorNotificationsGroup,
            tMirrorSourceNotificationsV6v0Group
        }
    ::= { tMirrorCompliances 3 }

tMirrorV8v0Compliance MODULE-COMPLIANCE
    STATUS  obsolete
    DESCRIPTION
            "The compliance statement for revision 2.1 of 
             TIMETRA-MIRROR-MIB for management of extended Mirror
             features on Alcatel-Lucent SROS series systems."
    MODULE  -- this module
        MANDATORY-GROUPS { 
            tMirrorDestinationV8v0Group,
            tMirrorDestinationR2r1RemoteSourceGroup,
            tMirrorSourceV6v0Group,
            tMirrorBsxV6v0Group,
            tMirrorNotificationsGroup,
            tMirrorSourceNotificationsV6v0Group,
            tMirrorDestV8v0Group,
            tMirrorObsoletedV8v0Group,
            tMirrorRadiusLiV8v0Group
        }
    ::= { tMirrorCompliances 4 }

tMirrorV9v0Compliance MODULE-COMPLIANCE
    STATUS  obsolete
    DESCRIPTION
            "The compliance statement for revision 2.1 of 
             TIMETRA-MIRROR-MIB for management of extended Mirror
             features on Alcatel-Lucent SROS series systems."
    MODULE  -- this module
        MANDATORY-GROUPS { 
            tMirrorDestinationV8v0Group,
            tMirrorDestinationR2r1RemoteSourceGroup,
            tMirrorSourceV6v0Group,
            tMirrorBsxV6v0Group,
            tMirrorNotificationsGroup,
            tMirrorSourceNotificationsV6v0Group,
            tMirrorDestV8v0Group,
            tMirrorObsoletedV8v0Group,
            tMirrorRadiusLiV8v0Group,
            tMirrorSourceNotifGroup,
            tMirrorLiGroup
        }
    ::= { tMirrorCompliances 5 }

tMirrorV10v0Compliance MODULE-COMPLIANCE
    STATUS  current
    DESCRIPTION
            "The compliance statement for management of extended Mirror
             features on Alcatel-Lucent SROS series systems release 10.0."
    MODULE  -- this module
        MANDATORY-GROUPS { 
            tMirrorDestinationV8v0Group,
            tMirrorDestinationR2r1RemoteSourceGroup,
            tMirrorSourceV10v0Group,
            tMirrorBsxV6v0Group,
            tMirrorNotificationsGroup,
            tMirrorNotifV10v0Group,
            tMirrorSourceNotificationsV6v0Group,
            tMirrorDestV8v0Group,
            tMirrorObsoletedV8v0Group,
            tMirrorRadiusLiV8v0Group,
            tMirrorSourceNotifGroup,
            tMirrorLiGroup,
            tMirrorEncapV10v0Group,
            tMirrorLiSourceV10v0Group
        }
    ::= { tMirrorCompliances 6 }

-- units of conformance

-- tMirrorDestinationGroup OBJECT-GROUP
--    ::= { tMirrorGroups 1 }

-- tMirrorDestinationRemoteSourceGroup OBJECT-GROUP
--    ::= { tMirrorGroups 2 }

tMirrorSourceGroup OBJECT-GROUP
    OBJECTS {   tMirrorSourceAdminStatus,
                tMirrorSourceIpFilterRowStatus,
                tMirrorSourceMacFilterRowStatus,
                tMirrorSourceIngressLabelRowStatus,
                tMirrorSourcePortRowStatus,
                tMirrorSourcePortEgressEnabled,
                tMirrorSourcePortIngressEnabled,
                tMirrorSourceSapRowStatus,
                tMirrorSourceSapEgressEnabled,
                tMirrorSourceSapIngressEnabled
            }
    STATUS      obsolete
    DESCRIPTION
        "The group of objects supporting management of mirror sources
         on Alcatel-Lucent SROS series systems."
    ::= { tMirrorGroups 3 }

tMirrorNotificationsGroup NOTIFICATION-GROUP
    NOTIFICATIONS   {   tMirrorSourceEnabled,
                        tMirrorSourceDisabled,
                        tMirrorDestinationEnabled,
                        tMirrorDestinationDisabled,
                        tMirrorSourceRemovedBySystem
                    }
    STATUS      current
    DESCRIPTION
        "the group of notifications supporting management of mirror
        source and destination operational state changes on Alcatel-Lucent
        SROS series system.."
    ::= { tMirrorGroups 4 }

tMirrorDestinationR2r1Group OBJECT-GROUP
    OBJECTS {   tMirrorDestinationRowStatus,
                tMirrorDestinationDescription,
                tMirrorDestinationFC,
                tMirrorDestinationRemoteSource,
                tMirrorDestinationSapPortId,
                tMirrorDestinationSapEncapValue,
                tMirrorDestinationSdpNumber,
                tMirrorDestinationAdminStatus,
                tMirrorDestinationOperStatus,
                tMirrorDestinationSliceSize,
                tMirrorDestinationSdpEgrSvcLabel,
                tMirrorDestinationSapEgressQosPolicyId,
                tMirrorDestinationEncapsulation,   
                tMirrorDestinationSdpOperEgrSvcLabel
            }
    STATUS      obsolete
    DESCRIPTION
        "The group of objects supporting management of mirror destinations
         on Alcatel-Lucent SROS series systems."
    ::= { tMirrorGroups 5 }

tMirrorDestinationR2r1RemoteSourceGroup OBJECT-GROUP
    OBJECTS {   tMirrorDestinationRemoteSourceAddr,
                tMirrorDestinationRemoteSourceLabelSignaling,
                tMirrorDestinationRemoteSourceIngSvcLabel,
                tMirrorDestinationRemoteSourceRowStatus,
                tMirrorDestinationRemoteSourceOperIngSvcLabel
            }
    STATUS      current
    DESCRIPTION
        "The group of objects supporting management of remote sources 
         associated with mirror destinations on Alcatel-Lucent SROS series
         systems."
    ::= { tMirrorGroups 6 }

tMirrorR2r1ObsoleteGroup OBJECT-GROUP
    OBJECTS {   tMirrorDestinationSdpDestEncap,
                tMirrorDestinationTranslateDisable,
                tMirrorDestinationPppoeDestMacAddr,
                tMirrorDestinationPppoeSrcMacAddr,
                tMirrorDestinationPppoeEtype,
                tMirrorDestinationPppoeSessionId
            }
    STATUS      current
    DESCRIPTION
        "The group of objects which were obsoleted from 2.0 release
         on Alcatel-Lucent SROS series systems."
    ::= { tMirrorGroups 7 }

tMirrorNotifyObjsV5v0Group OBJECT-GROUP
    OBJECTS {   tMirrorDestinationIndex,
                tMirrorSourceIndex
            }
    STATUS      obsolete
    DESCRIPTION
        "The group of objects supporting management of notifications
         on Alcatel-Lucent SROS series systems."
    ::= { tMirrorGroups 8 }

tMirrorDestinationV6v0Group OBJECT-GROUP
    OBJECTS {   tMirrorDestinationRowStatus,
                tMirrorDestinationDescription,
                tMirrorDestinationFC,
                tMirrorDestinationRemoteSource,
                tMirrorDestinationSapPortId,
                tMirrorDestinationSapEncapValue,
                tMirrorDestinationAdminStatus,
                tMirrorDestinationOperStatus,
                tMirrorDestinationSliceSize,
                tMirrorDestinationSapEgressQosPolicyId,
                tMirrorDestinationEncapsulation,   
                tMirrorDestinationEnablePortId,
                tMirrorDestSapEgrIpMirrorSA,
                tMirrorDestSapEgrIpMirrorDA,
                tMirrorDestLastChanged,
                tMirrorDestTableLastChnged,
                tMirrorDestRemoteSrcLastChgd,
                tMirrorDestRemSrcTblLastChgd
            }
    STATUS      obsolete
    DESCRIPTION
        "The group of objects supporting management of mirror destinations
         on Alcatel-Lucent SROS series systems."
    ::= { tMirrorGroups 9 }

tMirrorSourceV6v0Group OBJECT-GROUP
    OBJECTS {   tMirrorSourceAdminStatus,
                tMirrorSourceRowStatus,
                tMirrorSourceIpFilterRowStatus,
                tMirrorSourceMacFilterRowStatus,
                tMirrorSourceIngressLabelRowStatus,
                tMirrorSourcePortRowStatus,
                tMirrorSourcePortEgressEnabled,
                tMirrorSourcePortIngressEnabled,
                tMirrorSourceSapRowStatus,
                tMirrorSourceSapEgressEnabled,
                tMirrorSourceSapIngressEnabled,
                tMirrorSourceSubTableLastChnged,
                tMirrorSourceSubRowStatus,
                tMirrorSourceSubLastChanged,
                tMirrorSourceSubPortId,
                tMirrorSourceSubEncapValue,
                tMirrorSourceSubIpAddrType,
                tMirrorSourceSubIpAddr,
                tMirrorSourceSubMacAddr,
                tMirrorSourceSubSLAProfName,
                tMirrorSourceSubFC,
                tMirrorSourceSubEgressEnabled,
                tMirrorSourceSubIngressEnabled,
                tMirrorSourceLastChgd,
                tMirrorSourceIpFilterLastChgd,
                tMirrorSourceMacFilterLastChgd,
                tMirrorSourceIngLabelLastChgd,
                tMirrorSourcePortLastChgd,
                tMirrorSourceSapLastChgd,
                tMirrorSrcTblLastChgd,
                tMirrorSrcIpFltrTblLastChgd,
                tMirrorSrcMacFltrTblLastChgd,
                tMirrorSrcIngLblTblLastChgd,
                tMirrorSrcPortTblLastChgd,
                tMirrorSrcSapTblLastChgd
              }
    STATUS      obsolete
    DESCRIPTION
        "The group of objects supporting management of mirror sources
         on Alcatel-Lucent SROS series systems."
    ::= { tMirrorGroups 10 }

tMirrorNotifyObjsV6v0Group OBJECT-GROUP
    OBJECTS {   tMirrorDestinationIndex,
                tMirrorSourceIndex,
                tMirrorSourceSapPortId,
                tMirrorSourceSapEncapValue,
                tMirrorSourceSubIdent,
                tMirrorSourceChangeType,
                tMirrorSourceFilterId,
                tMirrorSourceFilterEntryId,
                tMirrorSourceFilterObject,
                tMirrorSourceFilterDescr,
                tMirrorFilterSvcId,
                tMirrorFilterPortId,
                tMirrorFilterSapEncapValue,
                tMirrorFilterSdpBindId,
                tMirrorFilterType,
                tMirrorFilterDirection,
                tMirrorFilterId,
                tMirrorFilterIfIndex,
                tMirrorFilterIfName
            }                                      
    STATUS      current
    DESCRIPTION
        "The group of objects supporting management of notifications
         on Alcatel-Lucent SROS series systems."
    ::= { tMirrorGroups 11 }

tMirrorSourceNotificationsV6v0Group     NOTIFICATION-GROUP
    NOTIFICATIONS   {   tMirrorSourceIpFilterChange,
                        tMirrorSourceMacFilterChange,
                        tMirrorSourceSapChange,
                        tMirrorSourceSubChange,
                        tMirrorSourceIPFltrChangeReject,
                        tMirrorSourceIP6FltrChangeReject,
                        tMirrorSourceMacFltrChangeReject,
                        tMirrorSourceFilterAssignReject,
                        tMirrorDestinationChangeReject,
                        tMirrorSourceFilterOverruled,
                        tMirrorSourceFilterAssignWarn,
                        tMirrorFilterAssignToSapWarn,
                        tMirrorFilterAssignToSdpWarn,
                        tMirrorFilterAssignToItfWarn
                    }
    STATUS      current
    DESCRIPTION
        "The group of notifications supporting management of mirror
        source association changes added for the 6.0 release of 
        Alcatel-Lucent SROS series system."
    ::= { tMirrorGroups 12 }

tMirrorBsxV6v0Group OBJECT-GROUP
    OBJECTS {   tMirrorSourceIsaAaGrpRowStatus,
                tMirrorSourceIsaAaGrpUnknownOnly,
                tMirrorSourceIsaAaGrpLastChgd,
                tMirrorSrcIsaAaGrpTblLastChgd
            }
    STATUS      current
    DESCRIPTION
        "The group of objects supporting management of BSX
        (Application Assurance) mirror changes added for the
        6.0 release of Alcatel-Lucent SROS series system."
    ::= { tMirrorGroups 13 }
 
tMirrorDestV8v0Group OBJECT-GROUP
    OBJECTS {
                tMirrorDestRemoteSrcIsICB,
                tMirrorDestRemoteSrcVcId
            }
    STATUS      current
    DESCRIPTION
        "The group of objects supporting management of mirror changes added for
         the 8.0 release of Alcatel-Lucent SROS series system."
    ::= { tMirrorGroups 14 }

tMirrorObsoletedV8v0Group OBJECT-GROUP
    OBJECTS {
                tMirrorDestinationSdpNumber,
                tMirrorDestinationSdpEgrSvcLabel,
                tMirrorDestinationSdpOperEgrSvcLabel
            }
    STATUS      current
    DESCRIPTION
        "The group of mirror objects obsoleted in the 8.0 release of 
         Alcatel-Lucent SROS series system."
    ::= { tMirrorGroups 15 }

tMirrorDestinationV8v0Group OBJECT-GROUP
    OBJECTS {   tMirrorDestinationRowStatus,
                tMirrorDestinationDescription,
                tMirrorDestinationFC,
                tMirrorDestinationRemoteSource,
                tMirrorDestinationSapPortId,
                tMirrorDestinationSapEncapValue,
                tMirrorDestinationAdminStatus,
                tMirrorDestinationOperStatus,
                tMirrorDestinationSliceSize,
                tMirrorDestinationSapEgressQosPolicyId,
                tMirrorDestinationEncapsulation,   
                tMirrorDestinationEnablePortId,
                tMirrorDestSapEgrIpMirrorSA,
                tMirrorDestSapEgrIpMirrorDA,
                tMirrorDestLastChanged,
                tMirrorDestTableLastChnged,
                tMirrorDestRemoteSrcLastChgd,
                tMirrorDestRemSrcTblLastChgd
            }
    STATUS      current
    DESCRIPTION
        "The group of objects supporting management of mirror destinations
         on Alcatel-Lucent SROS series systems."
    ::= { tMirrorGroups 16 }

tMirrorRadiusLiV8v0Group OBJECT-GROUP
    OBJECTS {   
                tRadiusLiSrcHostId,             
                tRadiusLiMirrorDirection,       
                tRadiusLiMirrorForwClassMap    
            }
    STATUS      current
    DESCRIPTION
        "The group of objects supporting management of Radius LI mirror sources
         on Alcatel-Lucent SROS series systems."
    ::= { tMirrorGroups 17 }
    
tMirrorSourceNotifGroup NOTIFICATION-GROUP
    NOTIFICATIONS   {   
                        tMirrorSourceLiFilterChanged
                    }
    STATUS      current
    DESCRIPTION
        "The group of notifications supporting management of mirror
        source association of Alcatel-Lucent SROS series system."
    ::= { tMirrorGroups 18 }

tMirrorLiGroup OBJECT-GROUP
    OBJECTS {
                tMirrorLiSourceNatTableLastCh,
                tMirrorLiNatLsnSubTableLastCh,
                tMirrorLiSourceNatLastChanged,
                tMirrorLiSourceNatDestMacAddr,
                tMirrorLiSourceNatSrcMacAddr, 
                tMirrorLiSourceNatEthertype,  
                tMirrorLiNatLsnSubRowStatus,
                tMirrorLiNatLsnSubLastChanged,
                tMirrorLiNatLsnSubInterceptId,
                tMirrorLiNatL2awSubTableLastCh,
                tMirrorLiNatL2awSubRowStatus,
                tMirrorLiNatL2awSubLastChanged,
                tMirrorLiNatL2awSubInterceptId
            }
    STATUS      current
    DESCRIPTION
        "The group of objects supporting management of Lawful Intercept (LI)
         mirroring on Alcatel-Lucent SROS series systems."
    ::= { tMirrorGroups 20 }
        
tMirrorEncapGroup OBJECT-GROUP
    OBJECTS {
                tMirrorSourceIpFilterIntceptId,
                tMirrorSourceMacFilterIntceptId,
                tMirrorSourceSapIntceptId,
                tMirrorSourceSubIntceptId,
                tRadiusLiSrcIntceptId,
                tMirrorSourceIpFilterSessionId,
                tMirrorSourceMacFilterSessionId,
                tMirrorSourceSapSessionId,
                tMirrorSourceSubSessionId,
                tRadiusLiSrcSessionId,
                tMirrorLiNatLsnSubSessionId,
                tMirrorLiNatL2awSubSessionId,
                tMirrorDestL3EncTableLastCh,
                tMirrorDestL3EncRowStatus,
                tMirrorDestL3EncLastCh,
                tMirrorDestL3EncHeaderType,         
                tMirrorDestL3EncRouter,             
                tMirrorDestL3EncUseDirectionBit,
                tMirrorDestL3GwTableLastCh,
                tMirrorDestL3GwRowStatus,
                tMirrorDestL3GwLastCh,      
                tMirrorDestL3GwSrcAddrType, 
                tMirrorDestL3GwSrcAddr,     
                tMirrorDestL3GwDstAddrType, 
                tMirrorDestL3GwDstAddr,     
                tMirrorDestL3GwUdpSrcPort,  
                tMirrorDestL3GwUdpDstPort  
            }
    STATUS      obsolete
    DESCRIPTION
        "The group of objects supporting management of Lawful Intercept (LI)
         encapsulation on Alcatel-Lucent SROS series systems.
         
         This encapsulation refers to the encapsulation inserted to identify
         the intercept subject."
    ::= { tMirrorGroups 21 }
            
tMirrorNotifyObjsV10v0Group OBJECT-GROUP
    OBJECTS { 
                tMirrorNotifyLiDescription,
                tMirrorNotifyLiPortId,
                tMirrorNotifyLiSapEncapValue,
                tMirrorNotifyLiSvcId
            }                                      
    STATUS      current
    DESCRIPTION
        "The group of notification objects added in release 10.0
         of Alcatel-Lucent SROS series systems."
    ::= { tMirrorGroups 22 }

tMirrorNotifV10v0Group NOTIFICATION-GROUP
    NOTIFICATIONS   {   
                        tMirrorSourceLiSubProblem,
                        tMirrorSourceIpv6FilterChange,
                        tMirrorSourceIPv6FltrChangeRej
                    }
    STATUS      current
    DESCRIPTION
        "The group of mirror notifications added in release 10.0
         of Alcatel-Lucent SROS series systems."
    ::= { tMirrorGroups 23 }

tMirrorSourceV10v0Group OBJECT-GROUP
    OBJECTS {   tMirrorSourceAdminStatus,
                tMirrorSourceRowStatus,
                tMirrorSourceIpFilterRowStatus,
                tMirrorSourceMacFilterRowStatus,
                tMirrorSourceIngressLabelRowStatus,
                tMirrorSourcePortRowStatus,
                tMirrorSourcePortEgressEnabled,
                tMirrorSourcePortIngressEnabled,
                tMirrorSourceSapRowStatus,
                tMirrorSourceSapEgressEnabled,
                tMirrorSourceSapIngressEnabled,
                tMirrorSourceSubTableLastChnged,
                tMirrorSourceSubRowStatus,
                tMirrorSourceSubLastChanged,
                tMirrorSourceSubPortId,
                tMirrorSourceSubEncapValue,
                tMirrorSourceSubIpAddrType,
                tMirrorSourceSubIpAddr,
                tMirrorSourceSubMacAddr,
                tMirrorSourceSubSLAProfName,
                tMirrorSourceSubFC,
                tMirrorSourceSubEgressEnabled,
                tMirrorSourceSubIngressEnabled,
                tMirrorSourceLastChgd,
                tMirrorSourceIpFilterLastChgd,
                tMirrorSourceMacFilterLastChgd,
                tMirrorSourceIngLabelLastChgd,
                tMirrorSourcePortLastChgd,
                tMirrorSourceSapLastChgd,
                tMirrorSrcTblLastChgd,
                tMirrorSrcIpFltrTblLastChgd,
                tMirrorSrcMacFltrTblLastChgd,
                tMirrorSrcIngLblTblLastChgd,
                tMirrorSrcPortTblLastChgd,
                tMirrorSrcSapTblLastChgd,

                tMirrorSourceIpv6FilterRowStatus,
                tMirrorSourceIpv6FilterLastChgd
              }
    STATUS      current
    DESCRIPTION
        "The group of objects supporting management of mirror sources
         on Alcatel-Lucent SROS series R10.0 systems."
    ::= { tMirrorGroups 24 }

tMirrorEncapV10v0Group OBJECT-GROUP
    OBJECTS {
                tMirrorSourceIpFilterIntceptId,
                tMirrorSourceMacFilterIntceptId,
                tMirrorSourceSapIntceptId,
                tMirrorSourceSubIntceptId,
                tRadiusLiSrcIntceptId,
                tMirrorSourceIpFilterSessionId,
                tMirrorSourceMacFilterSessionId,
                tMirrorSourceSapSessionId,
                tMirrorSourceSubSessionId,
                tRadiusLiSrcSessionId,
                tMirrorLiNatLsnSubSessionId,
                tMirrorLiNatL2awSubSessionId,
                tMirrorDestL3EncTableLastCh,
                tMirrorDestL3EncRowStatus,
                tMirrorDestL3EncLastCh,
                tMirrorDestL3EncHeaderType,         
                tMirrorDestL3EncRouter,             
                tMirrorDestL3EncUseDirectionBit,
                tMirrorDestL3GwTableLastCh,
                tMirrorDestL3GwRowStatus,
                tMirrorDestL3GwLastCh,      
                tMirrorDestL3GwSrcAddrType, 
                tMirrorDestL3GwSrcAddr,     
                tMirrorDestL3GwDstAddrType, 
                tMirrorDestL3GwDstAddr,     
                tMirrorDestL3GwUdpSrcPort,  
                tMirrorDestL3GwUdpDstPort,

                tMirrorSourceIpv6FilterIntceptId,
                tMirrorSourceIpv6FilterSessionId
            }
    STATUS      current
    DESCRIPTION
        "The group of objects supporting management of Lawful Intercept (LI)
         encapsulation on Alcatel-Lucent SROS series R10.0 systems.
         
         This encapsulation refers to the encapsulation inserted to identify
         the intercept subject."
    ::= { tMirrorGroups 25 }

tMirrorLiSourceV10v0Group OBJECT-GROUP
    OBJECTS {
                tMirrorSourceLiMacFltrTableLstCh,
                tMirrorSourceLiMacFltrRowStatus,  
                tMirrorSourceLiMacFltrLastChgd,   
                tMirrorSourceLiMacFltrIntceptId,  
                tMirrorSourceLiMacFltrSessionId,
                tMirrorLiNat64SubTableLastCh,
                tMirrorLiNat64SubRowStatus,
                tMirrorLiNat64SubLastChanged,
                tMirrorLiNat64SubInterceptId,
                tMirrorLiNat64SubSessionId
            }
    STATUS      current
    DESCRIPTION
        "The group of objects supporting management of Lawful Intercept (LI)
         mirroring based on li-filters on Alcatel-Lucent SROS series systems."
    ::= { tMirrorGroups 26 }
            
END
