-- **********************************************************************
-- TOS-SMI.mib
--
-- Topsec Enterprise Specific MIB: Structure of Management Information
--
-- Copyright (c) 1998-2008, Beijing Topsec Network Security Technology Co.,Ltd. 
-- All Rights Reserved
--
-- The contents of this document are subject to change without notice.
-- **********************************************************************
--
--  Change History:
--
--	Mar 13,2008 - Edit by tos lk 
--
--  Mar 13,2008 - splited from old mib TOSVI-new.mib
--
-- **********************************************************************

TOS-SMI DEFINITIONS ::= BEGIN

IMPORTS
	    MODULE-IDENTITY, OBJECT-IDENTITY,enterprises 
	    FROM SNMPv2-SMI;

	topsec MODULE-IDENTITY
	    LAST-UPDATED "08-03-14" 
	    ORGANIZATION "TOPSEC"
	    CONTACT-INFO
	            " Topsec Beijing
	              China
	              E-mail: support@topsec.com.cn "
	    DESCRIPTION
	            "The MIB module for management of Topsec Operating System Security Product, independent of the specific encapsulation scheme in use."
	    
	    REVISION     "05-09-14" 
	    DESCRIPTION
	            "Initial version."
	    
	    REVISION    "20060809"
	    DESCRIPTION
	            "enterprises revised."
	    
	    REVISION    "20061020"
	    DESCRIPTION
	            "Mgmt revised."
	    
	    REVISION    "20070927"
	    DESCRIPTION
	            "ivtable;some other object changed ."

	    REVISION    "20080109"
	    DESCRIPTION
	            "system information"
	            
	    REVISION    "20080313"
	    DESCRIPTION
	            "split the whole mib file into several part"

	    REVISION    "20080313"
	    DESCRIPTION
	            "edit the file tos-smi.mib"
	            	            	            
	    ::= { enterprises 14331 }

	topsecMgmt	OBJECT IDENTIFIER ::= { topsec 5 }

	topsecExperiment	OBJECT IDENTIFIER ::= { topsecMgmt 4 }
	
	objects			OBJECT IDENTIFIER ::= { topsecMgmt 5 }
	
	tosMib	OBJECT IDENTIFIER ::= { objects 1 }

END
