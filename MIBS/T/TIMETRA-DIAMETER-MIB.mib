TIMETRA-DIAMETER-MIB DEFINITIONS ::= BEGIN

IMPORTS
    MODULE-IDENTITY, OBJECT-TYPE,
    NOTIFICATION-TYPE, Unsigned32,
    Counter32                                       FROM SNMPv2-SMI

    MODULE-COMPLIANCE, OBJECT-GROUP,
    NOTIFICATION-GROUP                              FROM SNMPv2-CONF

    RowStatus, TimeStamp, TruthValue,
    TEXTUAL-CONVENTION,
    DisplayString                                   FROM SNMPv2-TC

    timetraSRMIBModules, tmnxSRObjs,
    tmnxSRNotifyPrefix, tmnxSRConfs                 FROM TIMETRA-GLOBAL-MIB

    TNamedItem,
    TItemDescription,
    TmnxVRtrID,
    TmnxSubNasPortSuffixType,
    TmnxSubNasPortPrefixType
                                                    FROM TIMETRA-TC-MIB

    InetAddressType, InetAddress                    FROM INET-ADDRESS-MIB
    ;

timetraDiameterMIBModule MODULE-IDENTITY
        LAST-UPDATED "201202281200Z"
        ORGANIZATION "Alcatel-Lucent"
        CONTACT-INFO
            "Alcatel-Lucent SROS Support
             Web: http://support.alcatel-lucent.com"
    DESCRIPTION
        "This document is the SNMP MIB module to manage and provision
         DIAMETER on the Alcatel-Lucent SROS device.

         Copyright 2008-2012 Alcatel-Lucent. All rights reserved.
         Reproduction of this document is authorized on the condition that
         the foregoing copyright notice is included.

         This SNMP MIB module (Specification) embodies Alcatel-Lucent's
         proprietary intellectual property.  Alcatel-Lucent retains
         all title and ownership in the Specification, including any
         revisions.

         Alcatel-Lucent grants all interested parties a non-exclusive
         license to use and distribute an unmodified copy of this
         Specification in connection with management of Alcatel-Lucent
         products, and without fee, provided this copyright notice and
         license appear on all copies.

         This Specification is supplied 'as is', and Alcatel-Lucent
         makes no warranty, either express or implied, as to the use,
         operation, condition, or performance of the Specification."

    REVISION     "1202281200Z"
    DESCRIPTION  "Rev 10.0               28 Feb 2012 12:00
                  10.0 release of the TIMETRA-DIAMETER-MIB."

    REVISION     "1102010000Z"
    DESCRIPTION  "Rev 9.0                 1 Feb 2011 00:00
                  9.0 release of the TIMETRA-DIAMETER-MIB."

    REVISION     "0902280000Z"
    DESCRIPTION  "Rev 7.0                28 Feb 2009 00:00
                  7.0 release of the TIMETRA-DIAMETER-MIB."

    REVISION     "0807010000Z"
    DESCRIPTION  "Rev 0.1                01 July 2008 00:00
                  Initial version of the TIMETRA-DIAMETER-MIB."
        ::= { timetraSRMIBModules 58 }

-- ----------------------------------------------------------------------------
--  Alcatel-Lucent SROS series DIAMETER MIB structure
-- ----------------------------------------------------------------------------
tmnxDiameter                  OBJECT IDENTIFIER ::= { tmnxSRObjs 58 }
    tmnxDiameterBaseObjects       OBJECT IDENTIFIER ::= { tmnxDiameter 1   }
    tmnxDiameterDccaObjects       OBJECT IDENTIFIER ::= { tmnxDiameter 2   }
    tmnxDiameterNotificationObjs  OBJECT IDENTIFIER ::= { tmnxDiameter 100 }

tmnxDiameterConformance       OBJECT IDENTIFIER ::= { tmnxSRConfs 58 }
    tmnxDiameterCompliances       OBJECT IDENTIFIER ::= { tmnxDiameterConformance 1 }
    tmnxDiameterGroups            OBJECT IDENTIFIER ::= { tmnxDiameterConformance 2 }

tmnxDiameterNotifyPrefix      OBJECT IDENTIFIER ::= { tmnxSRNotifyPrefix 58 }
    tmnxDiameterNotifications     OBJECT IDENTIFIER ::= { tmnxDiameterNotifyPrefix 0 }

----------------------------------------------------------------------------
--  Textual Conventions
----------------------------------------------------------------------------
TmnxDiameterAdminStatus ::= TEXTUAL-CONVENTION
    STATUS      current
    DESCRIPTION
        "The TmnxDiameterAdminStatus data type is an enumerated integer that
         describes the values used to identify the administrative state."
    SYNTAX INTEGER {
        enabled  (1),
        disabled (2)
    }

TmnxDiamPeerTransportProt ::= TEXTUAL-CONVENTION
    STATUS      current
    DESCRIPTION
        "The TmnxDiamPeerTransportProt data type is an enumerated 
         integer that describes the different transport protocols that
         can be used to setup a DIAMETER connection."
    SYNTAX INTEGER {
        tcp  (1)
        -- stcp (2) 
    }

TmnxDiamCcFailureHndlng ::= TEXTUAL-CONVENTION
    STATUS      current
    DESCRIPTION
        "The TmnxDiamCcFailureHndlng data type is an enumerated 
         integer that describes the different actions that can be taken
         after a DCCA (Diameter Credit Control Application) session
         failure has occured."
    SYNTAX INTEGER {
        terminate         (1),
        continue          (2),
        retryAndTerminate (3) 
    }

TmnxDiamDccaApplicationType ::= TEXTUAL-CONVENTION
    STATUS      current
    DESCRIPTION
        "The TmnxDiamDccaApplicationType data type is an enumerated 
         integer that identifies the different DCCA (Diameter Credit Control 
         Application) application types.
         
         A particular value of TmnxDiamDccaApplicationType is associated with 
         a set of values for the Authentication-Application-Id AVP
         (Attribute Value Pair) in Diameter messages."
    SYNTAX INTEGER {
        vfDccaV2 (1),
        gx       (2) 
    }

TmnxDiamPlcyVendorSupportType ::= TEXTUAL-CONVENTION
    STATUS      current
    DESCRIPTION
        "The TmnxDiamPlcyVendorSupportType data type is an enumerated 
         integer that describes which vendor specific attributes
         are used in DCCA sessions."
    SYNTAX INTEGER {
        vodafone (1),
        threeGpp (2)
    }

TmnxDiamPlcyDccaAvpOriginType ::= TEXTUAL-CONVENTION
    STATUS      current
    DESCRIPTION
        "The TmnxDiamPlcyDccaAvpOriginType data type is an enumerated 
         integer that describes the origin of th information to send
         in the AVP."
    SYNTAX INTEGER {
        subscriberId (1),
        circuitId    (2),
        imsi         (3),
        msisdn       (4),
        imei         (5)
    }

----------------------------------------------------------------------------
--  tmnxDiameterBaseObjects Object definitions
----------------------------------------------------------------------------
-- --------------------------------------------------------
-- tmnxDiameterPlcyTable
-- --------------------------------------------------------
tmnxDiameterPlcyTableLastChngd OBJECT-TYPE
    SYNTAX      TimeStamp
    MAX-ACCESS  read-only
    STATUS      current
    DESCRIPTION
        "The value of tmnxDiameterPlcyTableLastChngd indicates the sysUpTime
         at the time of the most recent management-initiated change to the
         tmnxDiameterPlcyTable."
    ::= { tmnxDiameterBaseObjects 1 }

tmnxDiameterPlcyTable OBJECT-TYPE
    SYNTAX      SEQUENCE OF TmnxDiameterPlcyEntry
    MAX-ACCESS  not-accessible
    STATUS      current
    DESCRIPTION
        "The tmnxDiameterPlcyTable has an entry for each DIAMETER policy
         configured in the system."
    ::= { tmnxDiameterBaseObjects 2 }

tmnxDiameterPlcyEntry OBJECT-TYPE
    SYNTAX      TmnxDiameterPlcyEntry
    MAX-ACCESS  not-accessible
    STATUS      current
    DESCRIPTION
        "Each row entry represents a DIAMETER policy configured in the system.

         Entries can be created and deleted via SNMP SET operations on the
         object tmnxDiamPlcyRowStatus."
    INDEX { tmnxDiamPlcyName }
    ::= { tmnxDiameterPlcyTable 1 }

TmnxDiameterPlcyEntry ::=
    SEQUENCE {
        tmnxDiamPlcyName                TNamedItem,
        tmnxDiamPlcyRowStatus           RowStatus,
        tmnxDiamPlcyLastMgmtChange      TimeStamp,
        tmnxDiamPlcyDescription         TItemDescription,
        tmnxDiamPlcyOriginHost          DisplayString,
        tmnxDiamPlcyOriginRealm         DisplayString,
        tmnxDiamPlcyRouter              TmnxVRtrID,
        tmnxDiamPlcySourceAddrType      InetAddressType,
        tmnxDiamPlcySourceAddr          InetAddress,
        tmnxDiamPlcyWatchdogTimer       Unsigned32,
        tmnxDiamPlcyConnectionTimer     Unsigned32,
        tmnxDiamPlcyTransactionTimer    Unsigned32,
        tmnxDiamPlcyVendorSupport       TmnxDiamPlcyVendorSupportType
    }

tmnxDiamPlcyName OBJECT-TYPE
    SYNTAX      TNamedItem
    MAX-ACCESS  not-accessible
    STATUS      current
    DESCRIPTION
        "The value of tmnxDiamPlcyName specifies the name of the DIAMETER
         policy."
    ::= { tmnxDiameterPlcyEntry 1 }

tmnxDiamPlcyRowStatus OBJECT-TYPE
    SYNTAX      RowStatus
    MAX-ACCESS  read-create
    STATUS      current
    DESCRIPTION
        "The value of tmnxDiamPlcyRowStatus controls the creation and
         deletion of rows in this table."
    ::= { tmnxDiameterPlcyEntry 2 }

tmnxDiamPlcyLastMgmtChange OBJECT-TYPE
    SYNTAX      TimeStamp
    MAX-ACCESS  read-only
    STATUS      current
    DESCRIPTION
        "The value of tmnxDiamPlcyLastMgmtChange indicates the sysUpTime at
         the time of the most recent management-initiated change to this
         table row."
    ::= { tmnxDiameterPlcyEntry 3 }

tmnxDiamPlcyDescription OBJECT-TYPE
    SYNTAX      TItemDescription
    MAX-ACCESS  read-create
    STATUS      current
    DESCRIPTION
        "The value of tmnxDiamPlcyDescription specifies the user provided
         description of this DIAMETER policy."
    DEFVAL { "" }
    ::= { tmnxDiameterPlcyEntry 4 }

tmnxDiamPlcyOriginHost OBJECT-TYPE
    SYNTAX      DisplayString (SIZE(0..80))
    MAX-ACCESS  read-create
    STATUS      current
    DESCRIPTION
        "The value of tmnxDiamPlcyOriginHost specifies the
         Origin-Host AVP (Attribute Value Pair) used by this DIAMETER
         policy."
    DEFVAL { "" }
    ::= { tmnxDiameterPlcyEntry 5 }

tmnxDiamPlcyOriginRealm OBJECT-TYPE
    SYNTAX      DisplayString (SIZE(0..80))
    MAX-ACCESS  read-create
    STATUS      current
    DESCRIPTION
        "The value of tmnxDiamPlcyOriginRealm specifies the
         Origin-Realm AVP (Attribute Value Pair) used by this DIAMETER
         policy."
    DEFVAL { "" }
    ::= { tmnxDiameterPlcyEntry 6 }

tmnxDiamPlcyRouter OBJECT-TYPE
    SYNTAX      TmnxVRtrID
    MAX-ACCESS  read-create
    STATUS      current
    DESCRIPTION
        "The value of tmnxDiamPlcyRouter specifies the virtual router 
         in which the DIAMETER connection(s) will be established
         by this DIAMETER policy."
    DEFVAL { 1 } -- Base Router instance
    ::= { tmnxDiameterPlcyEntry 7 }

tmnxDiamPlcySourceAddrType OBJECT-TYPE
    SYNTAX      InetAddressType
    MAX-ACCESS  read-create
    STATUS      current
    DESCRIPTION
        "The value of tmnxDiamPlcySourceAddrType specifies the
         type of address contained in tmnxDiamPlcySourceAddr."
    DEFVAL { unknown }
    ::= { tmnxDiameterPlcyEntry 8 }

tmnxDiamPlcySourceAddr OBJECT-TYPE
    SYNTAX      InetAddress (SIZE(0|4))
    MAX-ACCESS  read-create
    STATUS      current
    DESCRIPTION
        "The value of tmnxDiamPlcySourceAddr specifies the
         source IP address used to setup DIAMETER connection in 
         this DIAMETER policy."
    DEFVAL { ''H }
    ::= { tmnxDiameterPlcyEntry 9 }

tmnxDiamPlcyWatchdogTimer OBJECT-TYPE
    SYNTAX      Unsigned32 (1..1000)
    UNITS       "seconds"
    MAX-ACCESS  read-create
    STATUS      current
    DESCRIPTION
        "The value of tmnxDiamPlcyWatchdogTimer specifies the
         device watchdog timer (TW) (in seconds) used on all connections
         by this DIAMETER policy."
    DEFVAL { 30 }
    ::= { tmnxDiameterPlcyEntry 10 }

tmnxDiamPlcyConnectionTimer OBJECT-TYPE
    SYNTAX      Unsigned32 (1..1000)
    UNITS       "seconds"
    MAX-ACCESS  read-create
    STATUS      current
    DESCRIPTION
        "The value of tmnxDiamPlcyConnectionTimer specifies the
         connection timer (TC) (in seconds) used by this DIAMETER policy.
         It defines the time the systems waits before attempting to 
         reconnect to a peer after the connection was lost."
    DEFVAL { 30 }
    ::= { tmnxDiameterPlcyEntry 11 }

tmnxDiamPlcyTransactionTimer OBJECT-TYPE
    SYNTAX      Unsigned32 (1..1000)
    UNITS       "seconds"
    MAX-ACCESS  read-create
    STATUS      current
    DESCRIPTION
        "The value of tmnxDiamPlcyTransactionTimer specifies the
         transaction timer (in seconds) used by this DIAMETER policy.
         This timer defines how long the system will wait for an answer
         from the peer after sending a request."
    DEFVAL { 30 }
    ::= { tmnxDiameterPlcyEntry 12 }

tmnxDiamPlcyVendorSupport OBJECT-TYPE
    SYNTAX      TmnxDiamPlcyVendorSupportType
    MAX-ACCESS  read-create
    STATUS      current
    DESCRIPTION
        "The value of tmnxDiamPlcyVendorSupport specifies
         which vendor specific attributes are used in DCCA sessions
         for this DIAMETER policy."
    DEFVAL { threeGpp }
    ::= { tmnxDiameterPlcyEntry 13 }

-- --------------------------------------------------------
-- tmnxDiameterPlcyPeerTable
-- --------------------------------------------------------
tmnxDiamPlcyPeerTableLastChngd OBJECT-TYPE
    SYNTAX      TimeStamp
    MAX-ACCESS  read-only
    STATUS      current
    DESCRIPTION
        "The value of tmnxDiamPlcyPeerTableLastChngd indicates the sysUpTime
         at the time of the most recent management-initiated change to the
         tmnxDiameterPlcyPeerTable."
    ::= { tmnxDiameterBaseObjects 3 }

tmnxDiameterPlcyPeerTable OBJECT-TYPE
    SYNTAX      SEQUENCE OF TmnxDiameterPlcyPeerEntry
    MAX-ACCESS  not-accessible
    STATUS      current
    DESCRIPTION
        "The tmnxDiameterPlcyPeerTable has an entry for each peer
         defined in a DIAMETER policy configured in the system."
    ::= { tmnxDiameterBaseObjects 4 }

tmnxDiameterPlcyPeerEntry OBJECT-TYPE
    SYNTAX      TmnxDiameterPlcyPeerEntry
    MAX-ACCESS  not-accessible
    STATUS      current
    DESCRIPTION
        "Each row entry represents a peer configured in a DIAMETER policy
         configured in the system.

         Entries can be created and deleted via SNMP SET operations on the
         object tmnxDiamPlcyPeerRowStatus."
    INDEX { tmnxDiamPlcyName,
            tmnxDiamPlcyPeerName }
    ::= { tmnxDiameterPlcyPeerTable 1 }

TmnxDiameterPlcyPeerEntry ::=
    SEQUENCE {
        tmnxDiamPlcyPeerName            TNamedItem,
        tmnxDiamPlcyPeerRowStatus       RowStatus,
        tmnxDiamPlcyPeerLastMgmtChange  TimeStamp,
        tmnxDiamPlcyPeerAdminState      TmnxDiameterAdminStatus,
        tmnxDiamPlcyPeerAddrType        InetAddressType,
        tmnxDiamPlcyPeerAddr            InetAddress,
        tmnxDiamPlcyPeerTransportProt   TmnxDiamPeerTransportProt,
        tmnxDiamPlcyPeerTransportPort   Unsigned32,
        tmnxDiamPlcyPeerDestHost        DisplayString,
        tmnxDiamPlcyPeerDestRealm       DisplayString,
        tmnxDiamPlcyPeerWatchdogTimer   Unsigned32,
        tmnxDiamPlcyPeerConnectionTimer Unsigned32,
        tmnxDiamPlcyPeerTransactTimer   Unsigned32,
        tmnxDiamPlcyPeerPreference      Unsigned32
    }

tmnxDiamPlcyPeerName OBJECT-TYPE
    SYNTAX      TNamedItem
    MAX-ACCESS  not-accessible
    STATUS      current
    DESCRIPTION
        "The value of tmnxDiamPlcyPeerName specifies the name of the 
         peer within a DIAMETER policy."
    ::= { tmnxDiameterPlcyPeerEntry 1 }

tmnxDiamPlcyPeerRowStatus OBJECT-TYPE
    SYNTAX      RowStatus
    MAX-ACCESS  read-create
    STATUS      current
    DESCRIPTION
        "The value of tmnxDiamPlcyPeerRowStatus controls the creation and
         deletion of rows in this table."
    ::= { tmnxDiameterPlcyPeerEntry 2 }

tmnxDiamPlcyPeerLastMgmtChange OBJECT-TYPE
    SYNTAX      TimeStamp
    MAX-ACCESS  read-only
    STATUS      current
    DESCRIPTION
        "The value of tmnxDiamPlcyPeerLastMgmtChange indicates the sysUpTime at
         the time of the most recent management-initiated change to this
         table row."
    ::= { tmnxDiameterPlcyPeerEntry 3 }

tmnxDiamPlcyPeerAdminState OBJECT-TYPE
    SYNTAX      TmnxDiameterAdminStatus
    MAX-ACCESS  read-create
    STATUS      current
    DESCRIPTION
        "The value of the object tmnxDiamPlcyPeerAdminState specifies the
         administrative state of the DIAMETER Policy peer."
    DEFVAL { disabled }
    ::= { tmnxDiameterPlcyPeerEntry 4 }

tmnxDiamPlcyPeerAddrType OBJECT-TYPE
    SYNTAX      InetAddressType
    MAX-ACCESS  read-create
    STATUS      current
    DESCRIPTION
        "The value of tmnxDiamPlcyPeerAddrType specifies the
         type of address contained in tmnxDiamPlcyPeerAddr."
    DEFVAL { unknown }
    ::= { tmnxDiameterPlcyPeerEntry 5 }

tmnxDiamPlcyPeerAddr OBJECT-TYPE
    SYNTAX      InetAddress (SIZE(0|4))
    MAX-ACCESS  read-create
    STATUS      current
    DESCRIPTION
        "The value of tmnxDiamPlcyPeerAddr specifies the IP
         address of this DIAMETER policy peer."
    DEFVAL { ''H }
    ::= { tmnxDiameterPlcyPeerEntry 6 }

tmnxDiamPlcyPeerTransportProt OBJECT-TYPE
    SYNTAX      TmnxDiamPeerTransportProt
    MAX-ACCESS  read-create
    STATUS      current
    DESCRIPTION
        "The value of tmnxDiamPlcyPeerTransportProt specifies the
         transport protocol used towards this DIAMETER policy peer."
    DEFVAL { tcp }
    ::= { tmnxDiameterPlcyPeerEntry 7 }

tmnxDiamPlcyPeerTransportPort OBJECT-TYPE
    SYNTAX      Unsigned32 (1..65535)
    MAX-ACCESS  read-create
    STATUS      current
    DESCRIPTION
        "The value of tmnxDiamPlcyPeerTransportPort specifies the
         transport protocol port number used towards this DIAMETER
         policy peer."
    DEFVAL { 3868 }
    ::= { tmnxDiameterPlcyPeerEntry 8 }

tmnxDiamPlcyPeerDestHost OBJECT-TYPE
    SYNTAX      DisplayString (SIZE(0..80))
    MAX-ACCESS  read-create
    STATUS      current
    DESCRIPTION
        "The value of tmnxDiamPlcyPeerDestHost specifies the
         Destination-Host AVP used by this DIAMETER
         policy peer."
    DEFVAL { "" }
    ::= { tmnxDiameterPlcyPeerEntry 9 }

tmnxDiamPlcyPeerDestRealm OBJECT-TYPE
    SYNTAX      DisplayString (SIZE(0..80))
    MAX-ACCESS  read-create
    STATUS      current
    DESCRIPTION
        "The value of tmnxDiamPlcyPeerDestRealm specifies the
         Destination-Realm AVP used by this DIAMETER
         policy peer."
    DEFVAL { "" }
    ::= { tmnxDiameterPlcyPeerEntry 10 }

tmnxDiamPlcyPeerWatchdogTimer OBJECT-TYPE
    SYNTAX      Unsigned32 (0|1..1000)
    UNITS       "seconds"
    MAX-ACCESS  read-create
    STATUS      current
    DESCRIPTION
        "The value of tmnxDiamPlcyPeerWatchdogTimer specifies the
         device watchdog timer (in seconds) used by this DIAMETER policy
         peer.
         
         A value '0' will cause the peer to use the watchdog timer
         defined at DIAMETER base level (tmnxDiamPlcyWatchdogTimer)."
    DEFVAL { 0 }
    ::= { tmnxDiameterPlcyPeerEntry 11 }

tmnxDiamPlcyPeerConnectionTimer OBJECT-TYPE
    SYNTAX      Unsigned32 (0|1..1000)
    UNITS       "seconds"
    MAX-ACCESS  read-create
    STATUS      current
    DESCRIPTION
        "The value of tmnxDiamPlcyPeerConnectionTimer specifies the
         device connection timer (in seconds) used by this DIAMETER policy
         peer.
         
         A value '0' will cause the peer to use the connection timer
         defined at DIAMETER base level (tmnxDiamPlcyConnectionTimer)."
    DEFVAL { 0 }
    ::= { tmnxDiameterPlcyPeerEntry 12 }

tmnxDiamPlcyPeerTransactTimer OBJECT-TYPE
    SYNTAX      Unsigned32 (0|1..1000)
    UNITS       "seconds"
    MAX-ACCESS  read-create
    STATUS      current
    DESCRIPTION
        "The value of tmnxDiamPlcyPeerTransactTimer specifies the device
         transaction timer (in seconds) used by this DIAMETER policy peer.
         
         A value '0' will cause the peer to use the transaction timer
         defined at DIAMETER base level (tmnxDiamPlcyTransactionTimer)."
    DEFVAL { 0 }
    ::= { tmnxDiameterPlcyPeerEntry 13 }

tmnxDiamPlcyPeerPreference OBJECT-TYPE
    SYNTAX      Unsigned32 (1..100)
    MAX-ACCESS  read-create
    STATUS      current
    DESCRIPTION
        "The value of tmnxDiamPlcyPeerPreference specifies the preference
         given to this DIAMETER policy peer with respect to the other peers
         associated with this DIAMETER policy.
         
         If multiple peers are available for this policy, only the available
         peer with the highest preference will be used.

         If multiple peers with the same preference are available, one of them
         will be used.
         
         The highest preference is specified by the value '1'."
    DEFVAL { 50 }
    ::= { tmnxDiameterPlcyPeerEntry 14 }

-- --------------------------------------------------------
-- tmnxDiamPlcyPeerInfoTable
--
--  Augmentation of the tmnxDiameterPlcyPeerTable
--  Use of AUGMENTS clause implies a one-to-one dependent relationship
--  between the base table, tmnxDiameterPlcyPeerTable, and the augmenting table,
--  tmnxDiamPlcyPeerInfoTable. This in effect extends the 
--  tmnxDiameterPlcyPeerTable with additional columns. Creation (or deletion) 
--  of a row in the tmnxDiameterPlcyPeerTable results in the same fate for the 
--  row in the tmnxDiamPlcyPeerInfoTable.
-- --------------------------------------------------------

tmnxDiamPlcyPeerInfoTable OBJECT-TYPE
    SYNTAX      SEQUENCE OF TmnxDiamPlcyPeerInfoEntry
    MAX-ACCESS  not-accessible
    STATUS      current
    DESCRIPTION
        "The tmnxDiamPlcyPeerInfoTable contains detailed runtime information 
        about the peers defined in a DIAMETER policy."
    ::= { tmnxDiameterBaseObjects 5 }

tmnxDiamPlcyPeerInfoEntry OBJECT-TYPE
    SYNTAX      TmnxDiamPlcyPeerInfoEntry
    MAX-ACCESS  not-accessible
    STATUS      current
    DESCRIPTION
        "Each conceptual row contains detailed runtime information
        about a peer defined in a DIAMETER policy.

        Entries in this table are created and removed automatically by the 
        system"
    AUGMENTS { tmnxDiameterPlcyPeerEntry }
    ::= { tmnxDiamPlcyPeerInfoTable 1 }

TmnxDiamPlcyPeerInfoEntry ::=
    SEQUENCE {
        tmnxDiamPeerPsmState                INTEGER,
        tmnxDiamPeerConnectionSuspended     TruthValue,
        tmnxDiamPeerCooldownSeqStage        INTEGER,
        tmnxDiamPeerOrder                   Unsigned32,
        tmnxDiamPeerPrimarySecondary        INTEGER,
        tmnxDiamPeerTcTimerTimeLeft         Unsigned32,
        tmnxDiamPeerTtTimerTimeLeft         Unsigned32,
        tmnxDiamPeerTwTimerTimeLeft         Unsigned32,
        tmnxDiamPeerWatchdogAlgActive       TruthValue,
        tmnxDiamPeerWatchdogAnswPending     TruthValue,
        tmnxDiamPeerCooldownSeqPending      TruthValue,
        tmnxDiamPeerCooldownSeqActive       TruthValue,
        tmnxDiamPeerPeerRemovalPending      TruthValue
    }

tmnxDiamPeerPsmState OBJECT-TYPE
    SYNTAX      INTEGER {
                    closed         (0),
                    wait-conn-ack  (1),
                    wait-i-cea     (2),
                    i-open         (3),
                    closing        (4)
                }
    MAX-ACCESS  read-only
    STATUS      current
    DESCRIPTION
        "The value of tmnxDiamPeerPsmState indicates the current state of the 
         DIAMETER peer's state machine."
    ::= { tmnxDiamPlcyPeerInfoEntry 1 }

tmnxDiamPeerConnectionSuspended OBJECT-TYPE
    SYNTAX      TruthValue
    MAX-ACCESS  read-only
    STATUS      current
    DESCRIPTION
        "The value of tmnxDiamPeerConnectionSuspended indicates whether the peer's
        DIAMETER connection that is in I-Open state has been temporarily put on 
        suspension."
    ::= { tmnxDiamPlcyPeerInfoEntry 2 }

tmnxDiamPeerCooldownSeqStage OBJECT-TYPE
    SYNTAX      INTEGER {
                    stage1  (0),
                    stage2  (1),
                    stage3  (2)
                }
    MAX-ACCESS  read-only
    STATUS      current
    DESCRIPTION
        "While the value of tmnxDiamPeerCooldownSeqActive is 'true',
         the value of tmnxDiamPeerCooldownSeqStage indicates the current
         stage of the cooling down sequence."
    ::= { tmnxDiamPlcyPeerInfoEntry 3 }

tmnxDiamPeerOrder OBJECT-TYPE
    SYNTAX      Unsigned32
    MAX-ACCESS  read-only
    STATUS      current
    DESCRIPTION
        "The value of tmnxDiamPeerOrder indicates the runtime order of the
         DIAMETER policy's peers. It is determined both by the configuration 
         level preference and other runtime conditions.
         
         A value of zero indicates this field is currently not applicable for 
         this peer."
    ::= { tmnxDiamPlcyPeerInfoEntry 4 }

tmnxDiamPeerPrimarySecondary OBJECT-TYPE
    SYNTAX      INTEGER {
                    none      (0),
                    primary   (1),
                    secondary (2)
                }
    MAX-ACCESS  read-only
    STATUS      current
    DESCRIPTION
        "The value of tmnxDiamPeerPrimarySecondary indicates whether the
         DIAMETER peer figures as primary or secondary peer in its policy."
    ::= { tmnxDiamPlcyPeerInfoEntry 5 }

tmnxDiamPeerTcTimerTimeLeft OBJECT-TYPE
    SYNTAX      Unsigned32
    MAX-ACCESS  read-only
    STATUS      current
    DESCRIPTION
        "The value of tmnxDiamPeerTcTimerTimeLeft indicates the current
         countdown progress of the DIAMETER peer's connection timer."
    ::= { tmnxDiamPlcyPeerInfoEntry 6 }

tmnxDiamPeerTtTimerTimeLeft OBJECT-TYPE
    SYNTAX      Unsigned32
    MAX-ACCESS  read-only
    STATUS      current
    DESCRIPTION
        "The value of tmnxDiamPeerTtTimerTimeLeft indicates the current
         countdown progress of the DIAMETER peer's transaction timer."
    ::= { tmnxDiamPlcyPeerInfoEntry 7 }

tmnxDiamPeerTwTimerTimeLeft OBJECT-TYPE
    SYNTAX      Unsigned32
    MAX-ACCESS  read-only
    STATUS      current
    DESCRIPTION
        "The value of tmnxDiamPeerTwTimerTimeLeft indicates the current
         countdown progress of the DIAMETER peer's watchdog timer."
    ::= { tmnxDiamPlcyPeerInfoEntry 8 }

tmnxDiamPeerWatchdogAlgActive OBJECT-TYPE
    SYNTAX      TruthValue
    MAX-ACCESS  read-only
    STATUS      current
    DESCRIPTION
        "The value of tmnxDiamPeerWatchdogAlgActive indicates whether the 
         DIAMETER application-layer watchdog algorithm is currently running."
    ::= { tmnxDiamPlcyPeerInfoEntry 9 }

tmnxDiamPeerWatchdogAnswPending OBJECT-TYPE
    SYNTAX      TruthValue
    MAX-ACCESS  read-only
    STATUS      current
    DESCRIPTION
        "The value of tmnxDiamPeerWatchdogAnswPending indicates whether 
         reception of a DIAMETER Device Watchdog Answer (DWA) is expected for a 
         corresponding Device Watchdog Request (DWR) waiting in the Pending 
         Message Queue (PMQ)."
    ::= { tmnxDiamPlcyPeerInfoEntry 10 }

tmnxDiamPeerCooldownSeqPending OBJECT-TYPE
    SYNTAX      TruthValue
    MAX-ACCESS  read-only
    STATUS      current
    DESCRIPTION
        "The value of tmnxDiamPeerCooldownSeqPending indicates whether the 
         DIAMETER peer's connection manages to get in a non-suspended I-Open 
         state."
    ::= { tmnxDiamPlcyPeerInfoEntry 11 }

tmnxDiamPeerCooldownSeqActive OBJECT-TYPE
    SYNTAX      TruthValue
    MAX-ACCESS  read-only
    STATUS      current
    DESCRIPTION
        "The value of tmnxDiamPeerCooldownSeqActive indicates whether the
         DIAMETER Cooldown Sequence is currently running."
    ::= { tmnxDiamPlcyPeerInfoEntry 12 }

tmnxDiamPeerPeerRemovalPending OBJECT-TYPE
    SYNTAX      TruthValue
    MAX-ACCESS  read-only
    STATUS      current
    DESCRIPTION
        "The value of tmnxDiamPeerPeerRemovalPending indicates whether the  
         execution of a DIAMETER peer's removal is still pending until the 
         disconnect-peer roundtrip has finished."
    ::= { tmnxDiamPlcyPeerInfoEntry 13 }

-- --------------------------------------------------------
-- tmnxDiamPlcyPeerStatsTable
--
--  Augmentation of the tmnxDiameterPlcyPeerTable
--  Use of AUGMENTS clause implies a one-to-one dependent relationship
--  between the base table, tmnxDiameterPlcyPeerTable, and the augmenting table,
--  tmnxDiamPlcyPeerStatsTable. This in effect extends the 
--  tmnxDiameterPlcyPeerTable with additional columns. Creation (or deletion) 
--  of a row in the tmnxDiameterPlcyPeerTable results in the same fate for the 
--  row in the tmnxDiamPlcyPeerStatsTable.
-- --------------------------------------------------------

tmnxDiamPlcyPeerStatsTable OBJECT-TYPE
    SYNTAX      SEQUENCE OF TmnxDiamPlcyPeerStatsEntry
    MAX-ACCESS  not-accessible
    STATUS      current
    DESCRIPTION
        "The tmnxDiamPlcyPeerStatsTable contains detailed statistics 
        about the peers defined in a DIAMETER policy."
    ::= { tmnxDiameterBaseObjects 6 }

tmnxDiamPlcyPeerStatsEntry OBJECT-TYPE
    SYNTAX      TmnxDiamPlcyPeerStatsEntry
    MAX-ACCESS  not-accessible
    STATUS      current
    DESCRIPTION
        "Each conceptual row contains detailed statistics
        about a peer defined in a DIAMETER policy.

        Entries in this table are created and removed automatically by the 
        system"
    AUGMENTS { tmnxDiameterPlcyPeerEntry }
    ::= { tmnxDiamPlcyPeerStatsTable 1 }

TmnxDiamPlcyPeerStatsEntry ::=
    SEQUENCE {
        tmnxDiamPeerStatsLastClearTime       TimeStamp,
        tmnxDiamPeerStCiTcpSendFailed        Counter32,
        tmnxDiamPeerStCiDiamRxDropCnt        Counter32,
        tmnxDiamPeerStCiDiamTxReqs           Counter32,
        tmnxDiamPeerStCiDiamRxResps          Counter32,
        tmnxDiamPeerStCiPendMsgsPMQ          Counter32,
        tmnxDiamPeerStCiReqTimeoutsPMQ       Counter32,
        tmnxDiamPeerStSiTcpSendFailed        Counter32,
        tmnxDiamPeerStSiDiamRxDropCnt        Counter32,
        tmnxDiamPeerStSiDiamRxReqs           Counter32,
        tmnxDiamPeerStSiDiamTxResps          Counter32,
        tmnxDiamPeerStErrHdlDiamTxErrCnt     Counter32,
        tmnxDiamPeerStErrHdlDiamRxErrCnt     Counter32,
        tmnxDiamPeerStCcrInitialTx           Counter32,
        tmnxDiamPeerStCcaInitialRx           Counter32,
        tmnxDiamPeerStCcrUpdateTx            Counter32,
        tmnxDiamPeerStCcaUpdateRx            Counter32,
        tmnxDiamPeerStCcrTerminateTx         Counter32,
        tmnxDiamPeerStCcaTerminateRx         Counter32,
        tmnxDiamPeerStCerTx                  Counter32,
        tmnxDiamPeerStCeaRx                  Counter32,
        tmnxDiamPeerStWdrTx                  Counter32,
        tmnxDiamPeerStWdaRx                  Counter32,
        tmnxDiamPeerStWdrRx                  Counter32,
        tmnxDiamPeerStWdaTx                  Counter32,
        tmnxDiamPeerStAsrRx                  Counter32,
        tmnxDiamPeerStAsaTx                  Counter32,
        tmnxDiamPeerStRarRx                  Counter32,
        tmnxDiamPeerStRaaTx                  Counter32,
        tmnxDiamPeerStDprTx                  Counter32,
        tmnxDiamPeerStDpaRx                  Counter32,
        tmnxDiamPeerStDprRx                  Counter32,
        tmnxDiamPeerStDpaTx                  Counter32
    }

tmnxDiamPeerStatsLastClearTime OBJECT-TYPE
    SYNTAX      TimeStamp
    MAX-ACCESS  read-only
    STATUS      current
    DESCRIPTION
        "The value of tmnxDiamPeerStatsLastClearTime indicates the sysUpTime
         when the counters of this row were last reset. A value of zero for
         this object indicates that the counters have not been reset since the
         system has last been initialized."
    ::= { tmnxDiamPlcyPeerStatsEntry 1 }

tmnxDiamPeerStCiTcpSendFailed OBJECT-TYPE
    SYNTAX      Counter32
    MAX-ACCESS  read-only
    STATUS      current
    DESCRIPTION
        "The value of tmnxDiamPeerStCiTcpSendFailed indicates client initiated
         roundtrip DIAMETER statistics regarding the number of TCP send 
         failures."
    ::= { tmnxDiamPlcyPeerStatsEntry 2 }

tmnxDiamPeerStCiDiamRxDropCnt OBJECT-TYPE
    SYNTAX      Counter32
    MAX-ACCESS  read-only
    STATUS      current
    DESCRIPTION
        "The value of tmnxDiamPeerStCiDiamRxDropCnt indicates client initiated
         roundtrip DIAMETER statistics regarding the number of dropped response 
         messages upon reception from server."
    ::= { tmnxDiamPlcyPeerStatsEntry 3 }

tmnxDiamPeerStCiDiamTxReqs OBJECT-TYPE
    SYNTAX      Counter32
    MAX-ACCESS  read-only
    STATUS      current
    DESCRIPTION
        "The value of tmnxDiamPeerStCiDiamTxReqs indicates client initiated
         roundtrip DIAMETER statistics regarding the number of request messages 
         sent to server."
    ::= { tmnxDiamPlcyPeerStatsEntry 4 }

tmnxDiamPeerStCiDiamRxResps OBJECT-TYPE
    SYNTAX      Counter32
    MAX-ACCESS  read-only
    STATUS      current
    DESCRIPTION
        "The value of tmnxDiamPeerStCiDiamRxResps indicates client initiated
         roundtrip DIAMETER statistics regarding the number of response 
         messages received from server."
    ::= { tmnxDiamPlcyPeerStatsEntry 5 }

tmnxDiamPeerStCiPendMsgsPMQ OBJECT-TYPE
    SYNTAX      Counter32
    MAX-ACCESS  read-only
    STATUS      current
    DESCRIPTION
        "The value of tmnxDiamPeerStCiPendMsgsPMQ indicates client initiated
         roundtrip DIAMETER statistics regarding the number of request messages 
         in the Pending Message Queue waiting to be matched with corresponding 
         response messages from the server."
    ::= { tmnxDiamPlcyPeerStatsEntry 6 }

tmnxDiamPeerStCiReqTimeoutsPMQ OBJECT-TYPE
    SYNTAX      Counter32
    MAX-ACCESS  read-only
    STATUS      current
    DESCRIPTION
        "The value of tmnxDiamPeerStCiReqTimeoutsPMQ indicates client initiated
         roundtrip DIAMETER statistics regarding the number of request messages 
         that were removed from the Pending Message Queue due to a match 
         timeout."
    ::= { tmnxDiamPlcyPeerStatsEntry 7 }

tmnxDiamPeerStSiTcpSendFailed OBJECT-TYPE
    SYNTAX      Counter32
    MAX-ACCESS  read-only
    STATUS      current
    DESCRIPTION
        "The value of tmnxDiamPeerStSiTcpSendFailed indicates client initiated
         roundtrip DIAMETER statistics regarding the number of TCP send 
         failures."
    ::= { tmnxDiamPlcyPeerStatsEntry 8 }

tmnxDiamPeerStSiDiamRxDropCnt OBJECT-TYPE
    SYNTAX      Counter32
    MAX-ACCESS  read-only
    STATUS      current
    DESCRIPTION
        "The value of tmnxDiamPeerStSiDiamRxDropCnt indicates client initiated
         roundtrip DIAMETER statistics regarding the number of dropped request 
         messages upon reception from server."
    ::= { tmnxDiamPlcyPeerStatsEntry 9 }

tmnxDiamPeerStSiDiamRxReqs OBJECT-TYPE
    SYNTAX      Counter32
    MAX-ACCESS  read-only
    STATUS      current
    DESCRIPTION
        "The value of tmnxDiamPeerStSiDiamRxReqs indicates client initiated
         roundtrip DIAMETER statistics regarding the number of request messages
         received from server."
    ::= { tmnxDiamPlcyPeerStatsEntry 10 }

tmnxDiamPeerStSiDiamTxResps OBJECT-TYPE
    SYNTAX      Counter32
    MAX-ACCESS  read-only
    STATUS      current
    DESCRIPTION
        "The value of tmnxDiamPeerStSiDiamTxResps indicates client initiated
         roundtrip DIAMETER statistics regarding the number of response messages
         sent to server."
    ::= { tmnxDiamPlcyPeerStatsEntry 11 }

tmnxDiamPeerStErrHdlDiamTxErrCnt OBJECT-TYPE
    SYNTAX      Counter32
    MAX-ACCESS  read-only
    STATUS      current
    DESCRIPTION
        "The value of this object is always equal to zero."
    ::= { tmnxDiamPlcyPeerStatsEntry 12 }

tmnxDiamPeerStErrHdlDiamRxErrCnt OBJECT-TYPE
    SYNTAX      Counter32
    MAX-ACCESS  read-only
    STATUS      current
    DESCRIPTION
        "The value of this object is always equal to zero."
    ::= { tmnxDiamPlcyPeerStatsEntry 13 }

tmnxDiamPeerStCcrInitialTx OBJECT-TYPE
    SYNTAX      Counter32
    MAX-ACCESS  read-only
    STATUS      current
    DESCRIPTION
        "The value of tmnxDiamPeerStCcrInitialTx indicates 
         the number of Credit Control Request messages with CC-Request-Type AVP
         equal to INITIAL_REQUEST
         that are transmitted to the server."
     REFERENCE
        "RFC 4006  Diameter Credit-Control Application,
         section 8.3 and Appendix A1."
    ::= { tmnxDiamPlcyPeerStatsEntry 14 }

tmnxDiamPeerStCcaInitialRx OBJECT-TYPE
    SYNTAX      Counter32
    MAX-ACCESS  read-only
    STATUS      current
    DESCRIPTION
        "The value of tmnxDiamPeerStCcaInitialRx indicates 
         the number of Credit Control Answer messages 
         in response to the CCR INITIAL_REQUEST
         that are received from the server."
     REFERENCE
        "RFC 4006  Diameter Credit-Control Application,
         section 8.3 and Appendix A1."
    ::= { tmnxDiamPlcyPeerStatsEntry 15 }

tmnxDiamPeerStCcrUpdateTx OBJECT-TYPE
    SYNTAX      Counter32
    MAX-ACCESS  read-only
    STATUS      current
    DESCRIPTION
        "The value of tmnxDiamPeerStCcrUpdateTx indicates 
         the number of Credit Control Request messages with CC-Request-Type AVP
         equal to UPDATE_REQUEST
         that are transmitted to the server."
     REFERENCE
        "RFC 4006  Diameter Credit-Control Application,
         section 8.3 and Appendix A1."
    ::= { tmnxDiamPlcyPeerStatsEntry 16 }

tmnxDiamPeerStCcaUpdateRx OBJECT-TYPE
    SYNTAX      Counter32
    MAX-ACCESS  read-only
    STATUS      current
    DESCRIPTION
        "The value of tmnxDiamPeerStCcaUpdateRx indicates 
         the number of Credit Control Answer messages 
         in response to the CCR UPDATE_REQUEST
         that are received from the server."
     REFERENCE
        "RFC 4006  Diameter Credit-Control Application,
         section 8.3 and Appendix A1."
    ::= { tmnxDiamPlcyPeerStatsEntry 17 }

tmnxDiamPeerStCcrTerminateTx OBJECT-TYPE
    SYNTAX      Counter32
    MAX-ACCESS  read-only
    STATUS      current
    DESCRIPTION
        "The value of tmnxDiamPeerStCcrTerminateTx indicates 
         the number of Credit Control Request messages with CC-Request-Type AVP
         equal to TERMINATION_REQUEST
         that are transmitted to the server."
     REFERENCE
        "RFC 4006  Diameter Credit-Control Application,
         section 8.3 and Appendix A1."
    ::= { tmnxDiamPlcyPeerStatsEntry 18 }

tmnxDiamPeerStCcaTerminateRx OBJECT-TYPE
    SYNTAX      Counter32
    MAX-ACCESS  read-only
    STATUS      current
    DESCRIPTION
        "The value of tmnxDiamPeerStCcaTerminateRx indicates 
         the number of Credit Control Answer messages 
         in response to the CCR TERMINATION_REQUEST
         that are received from the server."
     REFERENCE
        "RFC 4006  Diameter Credit-Control Application,
         section 8.3 and Appendix A1."
    ::= { tmnxDiamPlcyPeerStatsEntry 19 }

tmnxDiamPeerStCerTx OBJECT-TYPE
    SYNTAX      Counter32
    MAX-ACCESS  read-only
    STATUS      current
    DESCRIPTION
        "The value of tmnxDiamPeerStCerTx indicates 
         the number of Capabilities-Exchange-Request messages
         that are transmitted to the server."
     REFERENCE
        "RFC 3588 Diameter Based Protocol,
         section 5.3.1."
    ::= { tmnxDiamPlcyPeerStatsEntry 20 }

tmnxDiamPeerStCeaRx OBJECT-TYPE
    SYNTAX      Counter32
    MAX-ACCESS  read-only
    STATUS      current
    DESCRIPTION
        "The value of tmnxDiamPeerStCeaRx indicates 
         the number of Capabilities-Exchange-Answer messages 
         that are received from the server."
     REFERENCE
        "RFC 3588 Diameter Based Protocol,
         section 5.3.2."
    ::= { tmnxDiamPlcyPeerStatsEntry 21 }

tmnxDiamPeerStWdrTx OBJECT-TYPE
    SYNTAX      Counter32
    MAX-ACCESS  read-only
    STATUS      current
    DESCRIPTION
        "The value of tmnxDiamPeerStWdrTx indicates 
         the number of Device-Watchdog-Request messages
         that are transmitted to the server."
     REFERENCE
        "RFC 3588 Diameter Based Protocol,
         section 5.5.1."
    ::= { tmnxDiamPlcyPeerStatsEntry 24 }

tmnxDiamPeerStWdaRx OBJECT-TYPE
    SYNTAX      Counter32
    MAX-ACCESS  read-only
    STATUS      current
    DESCRIPTION
        "The value of tmnxDiamPeerStWdaRx indicates 
         the number of Device-Watchdog-Answer messages 
         that are received from the server."
     REFERENCE
        "RFC 3588 Diameter Based Protocol,
         section 5.5.2."
    ::= { tmnxDiamPlcyPeerStatsEntry 25 }

tmnxDiamPeerStWdrRx OBJECT-TYPE
    SYNTAX      Counter32
    MAX-ACCESS  read-only
    STATUS      current
    DESCRIPTION
        "The value of tmnxDiamPeerStWdrRx indicates 
         the number of Device-Watchdog-Request messages 
         that are received from the server."
     REFERENCE
        "RFC 3588 Diameter Based Protocol,
         section 5.5.1."
    ::= { tmnxDiamPlcyPeerStatsEntry 26 }

tmnxDiamPeerStWdaTx OBJECT-TYPE
    SYNTAX      Counter32
    MAX-ACCESS  read-only
    STATUS      current
    DESCRIPTION
        "The value of tmnxDiamPeerStWdaTx indicates 
         the number of Device-Watchdog-Answer messages
         that are transmitted to the server."
     REFERENCE
        "RFC 3588 Diameter Based Protocol,
         section 5.5.2."
    ::= { tmnxDiamPlcyPeerStatsEntry 27 }

tmnxDiamPeerStAsrRx OBJECT-TYPE
    SYNTAX      Counter32
    MAX-ACCESS  read-only
    STATUS      current
    DESCRIPTION
        "The value of tmnxDiamPeerStAsrRx indicates 
         the number of Abort-Session-Request messages 
         that are received from the server."
     REFERENCE
        "RFC 3588 Diameter Based Protocol,
         section 8.5.1."
    ::= { tmnxDiamPlcyPeerStatsEntry 30 }

tmnxDiamPeerStAsaTx OBJECT-TYPE
    SYNTAX      Counter32
    MAX-ACCESS  read-only
    STATUS      current
    DESCRIPTION
        "The value of tmnxDiamPeerStAsaTx indicates 
         the number of Abort-Session-Answer messages
         that are transmitted to the server."
     REFERENCE
        "RFC 3588 Diameter Based Protocol,
         section 8.5.2."
    ::= { tmnxDiamPlcyPeerStatsEntry 31 }

tmnxDiamPeerStRarRx OBJECT-TYPE
    SYNTAX      Counter32
    MAX-ACCESS  read-only
    STATUS      current
    DESCRIPTION
        "The value of tmnxDiamPeerStRarRx indicates 
         the number of Re-Auth-Request messages 
         that are received from the server."
     REFERENCE
        "RFC 3588 Diameter Based Protocol,
         section 8.3.1."
    ::= { tmnxDiamPlcyPeerStatsEntry 34 }

tmnxDiamPeerStRaaTx OBJECT-TYPE
    SYNTAX      Counter32
    MAX-ACCESS  read-only
    STATUS      current
    DESCRIPTION
        "The value of tmnxDiamPeerStRaaTx indicates 
         the number of Re-Auth-Answer messages
         that are transmitted to the server."
     REFERENCE
        "RFC 3588 Diameter Based Protocol,
         section 8.3.2."
    ::= { tmnxDiamPlcyPeerStatsEntry 35 }

tmnxDiamPeerStDprTx OBJECT-TYPE
    SYNTAX      Counter32
    MAX-ACCESS  read-only
    STATUS      current
    DESCRIPTION
        "The value of tmnxDiamPeerStDprTx indicates 
         the number of Disconnect-Peer-Request messages
         that are transmitted to the server."
     REFERENCE
        "RFC 3588 Diameter Based Protocol,
         section 5.4.1."
    ::= { tmnxDiamPlcyPeerStatsEntry 36 }

tmnxDiamPeerStDpaRx OBJECT-TYPE
    SYNTAX      Counter32
    MAX-ACCESS  read-only
    STATUS      current
    DESCRIPTION
        "The value of tmnxDiamPeerStDpaRx indicates 
         the number of Disconnect-Peer-Answer messages 
         that are received from the server."
     REFERENCE
        "RFC 3588 Diameter Based Protocol,
         section 5.4.2."
    ::= { tmnxDiamPlcyPeerStatsEntry 37 }

tmnxDiamPeerStDprRx OBJECT-TYPE
    SYNTAX      Counter32
    MAX-ACCESS  read-only
    STATUS      current
    DESCRIPTION
        "The value of tmnxDiamPeerStDprRx indicates 
         the number of Disconnect-Peer-Request messages 
         that are received from the server."
     REFERENCE
        "RFC 3588 Diameter Based Protocol,
         section 5.4.1."
    ::= { tmnxDiamPlcyPeerStatsEntry 38 }

tmnxDiamPeerStDpaTx OBJECT-TYPE
    SYNTAX      Counter32
    MAX-ACCESS  read-only
    STATUS      current
    DESCRIPTION
        "The value of tmnxDiamPeerStDpaTx indicates 
         the number of Disconnect-Peer-Answer messages
         that are transmitted to the server."
     REFERENCE
        "RFC 3588 Diameter Based Protocol,
         section 5.4.2."
    ::= { tmnxDiamPlcyPeerStatsEntry 39 }

----------------------------------------------------------------------------
--  tmnxDiameterDccaObjects Object definitions
----------------------------------------------------------------------------
-- --------------------------------------------------------
-- tmnxDiameterPlcyDccaTable
-- --------------------------------------------------------
tmnxDiamPlcyDccaTableLastChngd OBJECT-TYPE
    SYNTAX      TimeStamp
    MAX-ACCESS  read-only
    STATUS      current
    DESCRIPTION
        "The value of tmnxDiamPlcyDccaTableLastChngd indicates the sysUpTime
         at the time of the most recent management-initiated change to the
         tmnxDiameterPlcyDccaTable.
         DCCA = Diameter Credit Control Application."
    ::= { tmnxDiameterDccaObjects 1 }

tmnxDiameterPlcyDccaTable OBJECT-TYPE
    SYNTAX      SEQUENCE OF TmnxDiameterPlcyDccaEntry
    MAX-ACCESS  not-accessible
    STATUS      current
    DESCRIPTION
        "The tmnxDiameterPlcyDccaTable has an entry for each DIAMETER policy
         configured in the system."
    ::= { tmnxDiameterDccaObjects 2 }

tmnxDiameterPlcyDccaEntry OBJECT-TYPE
    SYNTAX      TmnxDiameterPlcyDccaEntry
    MAX-ACCESS  not-accessible
    STATUS      current
    DESCRIPTION
        "Each row entry represents DCCA parameters defined for this 
         DIAMETER policy.

         Entries are created and deleted by the system."
    AUGMENTS { tmnxDiameterPlcyEntry }
    ::= { tmnxDiameterPlcyDccaTable 1 }

TmnxDiameterPlcyDccaEntry ::=
    SEQUENCE {
        tmnxDiamPlcyDccaLastMgmtChange  TimeStamp,
        tmnxDiamPlcyDccaFailover        TruthValue,
        tmnxDiamPlcyDccaFailureHndlng   TmnxDiamCcFailureHndlng,
        tmnxDiamPlcyDccaTxTimer         Unsigned32,
        tmnxDiamPlcyDccaAvpServCntxtId  DisplayString,
        tmnxDiamPlcyDccaAvpCldStationId DisplayString,
        tmnxDiamPlcyDccaAvpRadiusUsrNme TruthValue,
        tmnxDiamPlcyDccaAvpSubIdOrg     TmnxDiamPlcyDccaAvpOriginType,
        tmnxDiamPlcyDccaAvpSubIdType    INTEGER,
        tmnxDiamPlcyDccaAvpNasP         TruthValue,
        tmnxDiamPlcyDccaAvpNasPPfixType TmnxSubNasPortPrefixType,
        tmnxDiamPlcyDccaAvpNasPPfixStr  DisplayString,
        tmnxDiamPlcyDccaAvpNasPSfixType TmnxSubNasPortSuffixType,
        tmnxDiamPlcyDccaAvpNasPType     TruthValue,
        tmnxDiamPlcyDccaAvpImsiOrg      TmnxDiamPlcyDccaAvpOriginType,
        tmnxDiamPlcyDccaApplicationType TmnxDiamDccaApplicationType,
        tmnxDiamPlcyDccaMaxPendingReq   Unsigned32,
        tmnxDiamPlcyDccaTxRetryLimit    Unsigned32,
        tmnxDiamPlcyDccaOutOfCreditRep  INTEGER
    }

tmnxDiamPlcyDccaLastMgmtChange OBJECT-TYPE
    SYNTAX      TimeStamp
    MAX-ACCESS  read-only
    STATUS      current
    DESCRIPTION
        "The value of tmnxDiamPlcyDccaLastMgmtChange indicates the sysUpTime at
         the time of the most recent management-initiated change to this
         table row."
    ::= { tmnxDiameterPlcyDccaEntry 1 }

tmnxDiamPlcyDccaFailover OBJECT-TYPE
    SYNTAX      TruthValue
    MAX-ACCESS  read-create
    STATUS      current
    DESCRIPTION
        "The value of tmnxDiamPlcyDccaFailover specifies whether or not
         moving the CC message stream to a backup server during an ongoing CC
         session is supported for this DIAMETER policy."
    DEFVAL { true }
    ::= { tmnxDiameterPlcyDccaEntry 2 }

tmnxDiamPlcyDccaFailureHndlng OBJECT-TYPE
    SYNTAX      TmnxDiamCcFailureHndlng
    MAX-ACCESS  read-create
    STATUS      current
    DESCRIPTION
        "The value of tmnxDiamPlcyDccaFailureHndlng specifies what action 
        to take in case of a DCCA session failure for this DIAMETER policy."
    DEFVAL { terminate }
    ::= { tmnxDiameterPlcyDccaEntry 3 }

tmnxDiamPlcyDccaTxTimer OBJECT-TYPE
    SYNTAX      Unsigned32(10..1000)
    UNITS       "seconds"
    MAX-ACCESS  read-create
    STATUS      current
    DESCRIPTION
        "The value of tmnxDiamPlcyDccaTxTimer specifies the DCCA Tx Timer 
         (in seconds) for this DIAMETER policy."
    DEFVAL { 10 }
    ::= { tmnxDiameterPlcyDccaEntry 4 }

tmnxDiamPlcyDccaAvpServCntxtId OBJECT-TYPE
    SYNTAX      DisplayString (SIZE(0..32))
    MAX-ACCESS  read-create
    STATUS      current
    DESCRIPTION
        "The value of tmnxDiamPlcyDccaAvpServCntxtId specifies the DCCA 
         Service-Context-Id AVP. If set the AVP will be included in CCR 
         (Credit Control Request) messages." 
    DEFVAL { "" }
    ::= { tmnxDiameterPlcyDccaEntry 5 }

tmnxDiamPlcyDccaAvpCldStationId OBJECT-TYPE
    SYNTAX      DisplayString (SIZE(0..64))
    MAX-ACCESS  read-create
    STATUS      current
    DESCRIPTION
        "The value of tmnxDiamPlcyDccaAvpCldStationId specifies the RADIUS
         Called-Station-Id AVP. If set, the AVP will be included in CCR
         (Credit Control Request) messages." 
    DEFVAL { "" }
    ::= { tmnxDiameterPlcyDccaEntry 6 }

tmnxDiamPlcyDccaAvpRadiusUsrNme OBJECT-TYPE
    SYNTAX      TruthValue
    MAX-ACCESS  read-create
    STATUS      current
    DESCRIPTION
        "The value of tmnxDiamPlcyDccaAvpRadiusUsrNme specifies  whether or
         not the DIAMETER User-Name AVP will be included in CCR(Credit Control
         Request) messages." 
    DEFVAL { false }
    ::= { tmnxDiameterPlcyDccaEntry 7 }

tmnxDiamPlcyDccaAvpSubIdOrg OBJECT-TYPE
    SYNTAX      TmnxDiamPlcyDccaAvpOriginType
    MAX-ACCESS  read-create
    STATUS      current
    DESCRIPTION
        "The value of tmnxDiamPlcyDccaAvpSubIdOrg specifies
         the origin of the information to send in the Subscription-Id-Data AVP."
    REFERENCE
       "RFC 4006 Diameter Credit-Control Application
        section 8.48. Subscription-Id-Data AVP."
    DEFVAL { subscriberId }
    ::= { tmnxDiameterPlcyDccaEntry 8 }

tmnxDiamPlcyDccaAvpSubIdType OBJECT-TYPE
    SYNTAX      INTEGER {
                    endUserE164                    (0),
                    endUserImsi                    (1),
                    endUserPrivate                 (4)
                }
    MAX-ACCESS  read-create
    STATUS      current
    DESCRIPTION
        "The value of tmnxDiamPlcyDccaAvpSubIdType specifies
         the type of the identifier stored in the Subscription-Id-Data AVP."
    REFERENCE
       "RFC 4006 Diameter Credit-Control Application
        section 8.47. Subscription-Id-Type AVP."
    DEFVAL { endUserPrivate }
    ::= { tmnxDiameterPlcyDccaEntry 9 }

tmnxDiamPlcyDccaAvpNasP OBJECT-TYPE
    SYNTAX      TruthValue
    MAX-ACCESS  read-create
    STATUS      current
    DESCRIPTION
        "The value of tmnxDiamPlcyDccaAvpNasP specifies
         if the NAS-Port-Id AVP will be included in applicable DIAMETER messages." 
    DEFVAL { false }
    ::= { tmnxDiameterPlcyDccaEntry 10 }

tmnxDiamPlcyDccaAvpNasPPfixType OBJECT-TYPE
    SYNTAX      TmnxSubNasPortPrefixType
    MAX-ACCESS  read-create
    STATUS      current
    DESCRIPTION
        "The value of tmnxDiamPlcyDccaAvpNasPPfixType specifies what type of
         prefix will be added to the NAS-Port AVP if included in DIAMETER
         messages."
    DEFVAL { none }
    ::= { tmnxDiameterPlcyDccaEntry 11 }

tmnxDiamPlcyDccaAvpNasPPfixStr OBJECT-TYPE
    SYNTAX      DisplayString (SIZE (0..8))
    MAX-ACCESS  read-create
    STATUS      current
    DESCRIPTION
        "The value of tmnxDiamPlcyDccaAvpNasPPfixStr specifies the user
         configurable string to be added as prefix to the NAS-Port AVP 
         if included in DIAMETER messages.
         
         This field is only applicable  if tmnxDiamPlcyDccaAvpNasPPfixType
         is set to 'userString'."
    DEFVAL { "" }
    ::= { tmnxDiameterPlcyDccaEntry 12 }

tmnxDiamPlcyDccaAvpNasPSfixType OBJECT-TYPE
    SYNTAX      TmnxSubNasPortSuffixType
    MAX-ACCESS  read-create
    STATUS      current
    DESCRIPTION
        "The value of tmnxDiamPlcyDccaAvpNasPSfixType specifies what type of
         suffix will be added to the NAS-Port attribute NAS-Port AVP 
         if included in DIAMETER messages."
    DEFVAL { none }
    ::= { tmnxDiameterPlcyDccaEntry 13 }

tmnxDiamPlcyDccaAvpNasPType OBJECT-TYPE
    SYNTAX      TruthValue
    MAX-ACCESS  read-create
    STATUS      current
    DESCRIPTION
        "The value of tmnxDiamPlcyDccaAvpNasP specifies
         if the NAS-Port-Type AVP will be included 
         in applicable DIAMETER messages." 
    DEFVAL { false }
    ::= { tmnxDiameterPlcyDccaEntry 14 }

tmnxDiamPlcyDccaAvpImsiOrg OBJECT-TYPE
    SYNTAX      TmnxDiamPlcyDccaAvpOriginType
    MAX-ACCESS  read-create
    STATUS      current
    DESCRIPTION
        "The value of tmnxDiamPlcyDccaAvpImsiOrg specifies
         the origin of the information to send in the International Mobile
         Subscriber Identity (IMSI) AVP."
    DEFVAL { subscriberId }
    ::= { tmnxDiameterPlcyDccaEntry 15 }

tmnxDiamPlcyDccaApplicationType OBJECT-TYPE
    SYNTAX      TmnxDiamDccaApplicationType
    MAX-ACCESS  read-create
    STATUS      current
    DESCRIPTION
        "The value of tmnxDiamPlcyDccaApplicationType specifies
         the application type associated with this policy.
         
         It defines the set of supported values for the Auth-Application-Id AVP.
         
         tmnxDiamPlcyDccaApplicationType | Auth-Application-Id
         --------------------------------|-------------------------------------
                                vfDccaV2 | 4        (standard)
                                      gx | 16777238 (vendor-specific 3GPP)
         "
    REFERENCE
       "RFC 3588 Diameter Based Protocol
        section 6.8. Auth-Application-Id AVP.
        
        IANA Authentication, Authorization, and Accounting (AAA) Parameters."
    DEFVAL { vfDccaV2 }
    ::= { tmnxDiameterPlcyDccaEntry 50 }

tmnxDiamPlcyDccaMaxPendingReq OBJECT-TYPE
    SYNTAX      Unsigned32(10..131072)
    MAX-ACCESS  read-create
    STATUS      current
    DESCRIPTION
        "The value of tmnxDiamPlcyDccaMaxPendingReq specifies 
         the maximum number of pending requests for this DIAMETER policy.
         
         If the maximum number of pending requests has been exceeded, further
         requests are buffered or dropped."
    DEFVAL { 10 }
    ::= { tmnxDiameterPlcyDccaEntry 51 }

tmnxDiamPlcyDccaTxRetryLimit OBJECT-TYPE
    SYNTAX      Unsigned32 (0..3)
    MAX-ACCESS  read-create
    STATUS      current
    DESCRIPTION
        "The value of tmnxDiamPlcyDccaTxRetryLimit specifies 
         the maximum number of retries for a CCR message
         associated with this DIAMETER policy."
    DEFVAL { 0 }
    ::= { tmnxDiameterPlcyDccaEntry 52 }

tmnxDiamPlcyDccaOutOfCreditRep OBJECT-TYPE
    SYNTAX      INTEGER {
                    final          (1),
                    quotaExhausted (2)
                }
    MAX-ACCESS  read-create
    STATUS      current
    DESCRIPTION
        "The value of tmnxDiamPlcyDccaOutOfCreditRep specifies 
         the reporting reason in an intermediate interrogation when the final
         granted units have been consumed and a corresponding
         out-of-credit-action different from 'disconnect-host' is started."
    DEFVAL { final }
    ::= { tmnxDiameterPlcyDccaEntry 53 }

----------------------------------------------------------------------------
--  Notifications
----------------------------------------------------------------------------

-- --------------------------------------------------------
-- Notification Objects
-- --------------------------------------------------------
tmnxDiamAppPlcyName OBJECT-TYPE
    SYNTAX      TNamedItem
    MAX-ACCESS  accessible-for-notify
    STATUS      current
    DESCRIPTION
        "The value of tmnxDiamAppPlcyName specifies the name of the DIAMETER
         policy."
    ::= { tmnxDiameterNotificationObjs 1 }

tmnxDiamAppPeerName OBJECT-TYPE
    SYNTAX      TNamedItem
    MAX-ACCESS  accessible-for-notify
    STATUS      current
    DESCRIPTION
        "The value of tmnxDiamAppPeerName specifies the name of the 
         peer within a DIAMETER policy."
    ::= { tmnxDiameterNotificationObjs 2 }

tmnxDiamAppTrapDescription OBJECT-TYPE
    SYNTAX      TItemDescription
    MAX-ACCESS  accessible-for-notify
    STATUS      current
    DESCRIPTION
        "The value of tmnxDiamAppTrapDescription specifies the diameter 
         application provided description of the failure for this trap."
    ::= { tmnxDiameterNotificationObjs 3 }

tmnxDiamAppSessionId OBJECT-TYPE
    SYNTAX      DisplayString (SIZE (1..102))
    MAX-ACCESS  accessible-for-notify
    STATUS      current
    DESCRIPTION     
        "The value of tmnxDiamAppSessionId specifies the diameter session id
         for this trap."
    ::= { tmnxDiameterNotificationObjs 4 }

tmnxDiamAppSubscrId OBJECT-TYPE
    SYNTAX      DisplayString (SIZE (1..32))
    MAX-ACCESS  accessible-for-notify
    STATUS      current
    DESCRIPTION
        "The value of tmnxDiamAppSubscrId specifies the subscriber
         identification for this trap."
    ::= { tmnxDiameterNotificationObjs 5 }

tmnxDiamAppSapId OBJECT-TYPE
    SYNTAX      DisplayString (SIZE (1..32))
    MAX-ACCESS  accessible-for-notify
    STATUS      current
    DESCRIPTION
        "The value of tmnxDiamAppSapId specifies the SAP
         identification for this trap."
    ::= { tmnxDiameterNotificationObjs 6 }

tmnxDiamAppSLAProfName OBJECT-TYPE
    SYNTAX      TNamedItem
    MAX-ACCESS  accessible-for-notify
    STATUS      current
    DESCRIPTION
        "The value of tmnxDiamAppSLAProfName specifies the SLA profile name
         for this trap."
    ::= { tmnxDiameterNotificationObjs 7 }

-- --------------------------------------------------------
-- Notifications
-- --------------------------------------------------------

tmnxDiamPolicyPeerStateChange NOTIFICATION-TYPE
    OBJECTS {
        tmnxDiamPeerPrimarySecondary,
        tmnxDiamPeerConnectionSuspended,
        tmnxDiamPeerCooldownSeqActive,
        tmnxDiamAppTrapDescription
    }
    STATUS  current
    DESCRIPTION
        "A tmnxDiamPolicyPeerStateChange notification is generated when the
         state of a DIAMETER policy peer changes."
    ::= { tmnxDiameterNotifications 1 }

tmnxDiamAppMessageDropped NOTIFICATION-TYPE
    OBJECTS {
        tmnxDiamAppPlcyName,
        tmnxDiamAppPeerName,
        tmnxDiamAppTrapDescription
    }
    STATUS current
    DESCRIPTION
        "The tmnxDiamAppMessageDropped notification indicates that
         the DIAMETER protocol has dropped a message due to some reason."
    ::= { tmnxDiameterNotifications 2}

tmnxDiamAppSessionFailure NOTIFICATION-TYPE
    OBJECTS {
        tmnxDiamAppSessionId,        
        tmnxDiamAppSubscrId,
        tmnxDiamAppSapId,
        tmnxDiamAppSLAProfName,
        tmnxDiamAppTrapDescription
    }
    STATUS current
    DESCRIPTION
        "The tmnxDiamAppSessionFailure notification indicates that
         the DIAMETER protocol has a session failure."
    ::= { tmnxDiameterNotifications 3}

----------------------------------------------------------------------------
--  Conformance Groups
----------------------------------------------------------------------------
tmnxDiameterBaseV7v0Group OBJECT-GROUP
    OBJECTS {
        tmnxDiameterPlcyTableLastChngd,
        tmnxDiamPlcyRowStatus,
        tmnxDiamPlcyLastMgmtChange,
        tmnxDiamPlcyDescription,
        tmnxDiamPlcyOriginHost,
        tmnxDiamPlcyOriginRealm,
        tmnxDiamPlcyRouter,
        tmnxDiamPlcySourceAddrType,
        tmnxDiamPlcySourceAddr,
        tmnxDiamPlcyWatchdogTimer,
        tmnxDiamPlcyConnectionTimer,
        tmnxDiamPlcyTransactionTimer,

        tmnxDiamPlcyPeerTableLastChngd,
        tmnxDiamPlcyPeerRowStatus,
        tmnxDiamPlcyPeerLastMgmtChange,
        tmnxDiamPlcyPeerAdminState,
        tmnxDiamPlcyPeerAddrType,
        tmnxDiamPlcyPeerAddr,
        tmnxDiamPlcyPeerTransportProt,
        tmnxDiamPlcyPeerTransportPort,
        tmnxDiamPlcyPeerDestHost,
        tmnxDiamPlcyPeerDestRealm,
        tmnxDiamPlcyPeerWatchdogTimer,
        tmnxDiamPlcyPeerConnectionTimer,
        tmnxDiamPlcyPeerTransactTimer,
        tmnxDiamPlcyPeerPreference
    }
    STATUS obsolete
    DESCRIPTION
        "The group of objects supporting DIAMETER on
         Alcatel-Lucent SROS series systems 7.0 release."
    ::= { tmnxDiameterGroups 1 }

tmnxDiameterDccaGroup OBJECT-GROUP
    OBJECTS {
        tmnxDiamPlcyDccaTableLastChngd,
        tmnxDiamPlcyDccaLastMgmtChange,
        tmnxDiamPlcyDccaFailover,
        tmnxDiamPlcyDccaFailureHndlng,
        tmnxDiamPlcyDccaTxTimer,
        tmnxDiamPlcyDccaAvpServCntxtId,
        tmnxDiamPlcyDccaAvpCldStationId,
        tmnxDiamPlcyDccaAvpRadiusUsrNme,
        tmnxDiamPlcyDccaAvpSubIdOrg,
        tmnxDiamPlcyDccaAvpSubIdType
     }
     STATUS current
     DESCRIPTION
         "The group of objects supporting DIAMETER DCCA on
          Alcatel-Lucent SROS series systems."
     ::= { tmnxDiameterGroups 2 }

tmnxDiameterBaseV8v0Group OBJECT-GROUP
    OBJECTS {
        tmnxDiameterPlcyTableLastChngd,
        tmnxDiamPlcyRowStatus,
        tmnxDiamPlcyLastMgmtChange,
        tmnxDiamPlcyDescription,
        tmnxDiamPlcyOriginHost,
        tmnxDiamPlcyOriginRealm,
        tmnxDiamPlcyRouter,
        tmnxDiamPlcySourceAddrType,
        tmnxDiamPlcySourceAddr,
        tmnxDiamPlcyWatchdogTimer,
        tmnxDiamPlcyConnectionTimer,
        tmnxDiamPlcyTransactionTimer,

        tmnxDiamPlcyPeerTableLastChngd,
        tmnxDiamPlcyPeerRowStatus,
        tmnxDiamPlcyPeerLastMgmtChange,
        tmnxDiamPlcyPeerAdminState,
        tmnxDiamPlcyPeerAddrType,
        tmnxDiamPlcyPeerAddr,
        tmnxDiamPlcyPeerTransportProt,
        tmnxDiamPlcyPeerTransportPort,
        tmnxDiamPlcyPeerDestHost,
        tmnxDiamPlcyPeerDestRealm,
        tmnxDiamPlcyPeerWatchdogTimer,
        tmnxDiamPlcyPeerConnectionTimer,
        tmnxDiamPlcyPeerTransactTimer,
        tmnxDiamPlcyPeerPreference,

        tmnxDiamPeerPsmState,
        tmnxDiamPeerConnectionSuspended,
        tmnxDiamPeerCooldownSeqStage,
        tmnxDiamPeerOrder,
        tmnxDiamPeerPrimarySecondary,
        tmnxDiamPeerTcTimerTimeLeft,
        tmnxDiamPeerTtTimerTimeLeft,
        tmnxDiamPeerTwTimerTimeLeft,
        tmnxDiamPeerWatchdogAlgActive,
        tmnxDiamPeerWatchdogAnswPending,
        tmnxDiamPeerCooldownSeqPending,
        tmnxDiamPeerCooldownSeqActive,
        tmnxDiamPeerPeerRemovalPending,

        tmnxDiamPeerStatsLastClearTime,
        tmnxDiamPeerStCiTcpSendFailed,
        tmnxDiamPeerStCiDiamRxDropCnt,
        tmnxDiamPeerStCiDiamTxReqs,
        tmnxDiamPeerStCiDiamRxResps,
        tmnxDiamPeerStCiPendMsgsPMQ,
        tmnxDiamPeerStCiReqTimeoutsPMQ,
        tmnxDiamPeerStSiTcpSendFailed,
        tmnxDiamPeerStSiDiamRxDropCnt,
        tmnxDiamPeerStSiDiamRxReqs,
        tmnxDiamPeerStSiDiamTxResps,
        tmnxDiamPeerStErrHdlDiamTxErrCnt,
        tmnxDiamPeerStErrHdlDiamRxErrCnt,
        tmnxDiamPeerStCcrInitialTx,
        tmnxDiamPeerStCcaInitialRx,  
        tmnxDiamPeerStCcrUpdateTx,   
        tmnxDiamPeerStCcaUpdateRx,
        tmnxDiamPeerStCcrTerminateTx,  
        tmnxDiamPeerStCcaTerminateRx,
        tmnxDiamPeerStCerTx,         
        tmnxDiamPeerStCeaRx,
        tmnxDiamPeerStWdrTx,
        tmnxDiamPeerStWdaRx,
        tmnxDiamPeerStWdrRx,
        tmnxDiamPeerStWdaTx,
        tmnxDiamPeerStAsrRx,
        tmnxDiamPeerStAsaTx,         
        tmnxDiamPeerStRarRx,
        tmnxDiamPeerStRaaTx,         
        tmnxDiamPeerStDprTx,
        tmnxDiamPeerStDpaRx,
        tmnxDiamPeerStDprRx,
        tmnxDiamPeerStDpaTx         
    }
    STATUS current
    DESCRIPTION
        "The group of objects supporting DIAMETER on
         Alcatel-Lucent SROS series systems 8.0 release."
    ::= { tmnxDiameterGroups 3 }

tmnxDiameterDccaGxGroup OBJECT-GROUP
    OBJECTS {
        tmnxDiamPlcyDccaAvpNasP,        
        tmnxDiamPlcyDccaAvpNasPPfixType,
        tmnxDiamPlcyDccaAvpNasPPfixStr, 
        tmnxDiamPlcyDccaAvpNasPSfixType,
        tmnxDiamPlcyDccaAvpNasPType,
        tmnxDiamPlcyDccaApplicationType,
        tmnxDiamPlcyDccaAvpImsiOrg,
        tmnxDiamPlcyDccaMaxPendingReq,
        tmnxDiamPlcyDccaTxRetryLimit
     }
     STATUS current
     DESCRIPTION
         "The group of objects supporting DIAMETER DCCA Gx Interface on
          Alcatel-Lucent SROS series systems."
     ::= { tmnxDiameterGroups 6 }

tmnxDiameterDccaV10v0Group OBJECT-GROUP
    OBJECTS {
        tmnxDiamPlcyVendorSupport,
        tmnxDiamPlcyDccaOutOfCreditRep
     }
     STATUS current
     DESCRIPTION
         "The group of objects supporting DIAMETER vendor type on
          Alcatel-Lucent SROS series systems."
     ::= { tmnxDiameterGroups 7 }

-- NOTIFICATION Group
tmnxDiameterNotifyV8v0Group NOTIFICATION-GROUP
    NOTIFICATIONS   {
        tmnxDiamPolicyPeerStateChange,
        tmnxDiamAppMessageDropped
    }
    STATUS obsolete
    DESCRIPTION
        "The group of notifications supporting DIAMETER on
         Alcatel-Lucent SROS series systems 8.0 release."
    ::= { tmnxDiameterGroups 4 }

tmnxDiameterV8v0NotifyObjsGroup OBJECT-GROUP
    OBJECTS   {
        tmnxDiamAppPlcyName,
        tmnxDiamAppPeerName,
        tmnxDiamAppTrapDescription
    }
    STATUS obsolete
    DESCRIPTION
        "The group of objects supporting management of DIAMETER
         notification objects on Alcatel-Lucent SROS series systems
         8.0 release."
    ::= { tmnxDiameterGroups 5 }

tmnxDiameterNotifyV10v0Group NOTIFICATION-GROUP
    NOTIFICATIONS   {
        tmnxDiamPolicyPeerStateChange,
        tmnxDiamAppMessageDropped,
        tmnxDiamAppSessionFailure
    }
    STATUS current
    DESCRIPTION
        "The group of notifications supporting DIAMETER on
         Alcatel-Lucent SROS series systems 10.0 release."
    ::= { tmnxDiameterGroups 8 }

tmnxDiameterV10v0NotifyObjsGroup OBJECT-GROUP
    OBJECTS   {
        tmnxDiamAppPlcyName,
        tmnxDiamAppPeerName,
        tmnxDiamAppTrapDescription,
        tmnxDiamAppSessionId,
        tmnxDiamAppSubscrId,
        tmnxDiamAppSapId,
        tmnxDiamAppSLAProfName
    }
    STATUS current
    DESCRIPTION
        "The group of objects supporting management of DIAMETER
         notification objects on Alcatel-Lucent SROS series systems
         10.0 release."
    ::= { tmnxDiameterGroups 9 }

----------------------------------------------------------------------------
--  Compliance Info
----------------------------------------------------------------------------
tmnxDiameterV8v0MIBCompliance MODULE-COMPLIANCE
    STATUS obsolete
    DESCRIPTION
        "The compliance statement for TIMETRA-DIAMETER-MIB
         on Alcatel-Lucent SROS and 7710 series systems release R8.0."
    MODULE  -- this module
        MANDATORY-GROUPS {
            tmnxDiameterBaseV8v0Group,
            tmnxDiameterDccaGroup,
            tmnxDiameterNotifyV8v0Group
        }
    ::= { tmnxDiameterCompliances 1 }

tmnxDiameterV10v0MIBCompliance MODULE-COMPLIANCE
    STATUS current
    DESCRIPTION
        "The compliance statement for TIMETRA-DIAMETER-MIB
         on Alcatel-Lucent SROS and 7710 series systems release R10.0."
    MODULE  -- this module
        MANDATORY-GROUPS {
            tmnxDiameterBaseV8v0Group,
            tmnxDiameterDccaGroup,
            tmnxDiameterNotifyV10v0Group,
            tmnxDiameterDccaGxGroup,
            tmnxDiameterDccaV10v0Group
        }
    ::= { tmnxDiameterCompliances 2 }

END
