TPLINK-SYSTOOL-MIB DEFINITIONS ::= BEGIN

IMPORTS
	OBJECT-TYPE
				FROM SNMPv2-SMI
	tplinkMgmt	          
				FROM TPLINK-MIB; 
						
tplinkSysToolMIB MODULE-IDENTITY
    LAST-UPDATED  "201211290000Z"
    ORGANIZATION  "TP-LINK"
    CONTACT-INFO  "www.tplink.com.cn"
    DESCRIPTION
         "This MIB module contain a collection of managed objects
          that apply to network devices."

    REVISION    "201211290000Z"
    DESCRIPTION
        "Initial version of this MIB module."
    ::= { tplinkMgmt 3 }

tplinkSysToolMIBObjects OBJECT IDENTIFIER ::= {tplinkSysToolMIB 1}
tplinkSysToolNotifications OBJECT IDENTIFIER ::= {tplinkSysToolMIB 2}

	
tpSysToolReBoot OBJECT-TYPE
	SYNTAX  INTEGER{
		notReBoot(0), 			--normal state
		reboot(1),
		reBootAndSave(2)						--reboot state
	}
	MAX-ACCESS  read-write
	STATUS  current
	DESCRIPTION
		  "this used to determine whether to reboot or not"
	::=	{tplinkSysToolMIBObjects 1}

tpSysToolReSet OBJECT-TYPE
	SYNTAX  INTEGER{
		notReSet(0), 					--normal state
		reSet(1)						--reset state
	}
	MAX-ACCESS  read-write
	STATUS  current
	DESCRIPTION
	  "this used to determine whether to reset or not"
	::=	{tplinkSysToolMIBObjects 2}
	
tpSysToolConfigSave		OBJECT-TYPE
	SYNTAX				
		INTEGER
		{
			commit(1)
		}
	MAX-ACCESS		read-write
	STATUS				current
	DESCRIPTION		
	"This object use to save the current config."
	::=	{tplinkSysToolMIBObjects 3}
	

	tpSysToolReBootSchedule  			OBJECT IDENTIFIER ::= {tplinkSysToolMIBObjects 4}
	scheduleStatus OBJECT-TYPE
		SYNTAX  INTEGER{
		disable(0), 		
		enable(1)				
		}
		MAX-ACCESS  read-only
		STATUS  	current
		DESCRIPTION
			  "Reboot Schedule Status"
		::=	{tpSysToolReBootSchedule 1}
	scheduleIn OBJECT-TYPE
		SYNTAX  	INTEGER (1..43200)
		MAX-ACCESS  read-create
		STATUS  	current
		DESCRIPTION
			  "this used to config the reboot schedule time interval"
		::=	{tpSysToolReBootSchedule 2}
	scheduleAt OBJECT-TYPE
		SYNTAX  	OCTET STRING(SIZE (0..255))
		MAX-ACCESS  read-create
		STATUS  	current
		DESCRIPTION
			  "this used to config the reboot schedule time
			  For example, Saturday Aug 18, 2015 at 08:18 would be
				given as:
						18/08/2015-08:18
			  "
		::=	{tpSysToolReBootSchedule 3}
	saveBeforeReboot OBJECT-TYPE
		SYNTAX  INTEGER{
		no(0), 					--save not before reboot
		yes(1)					--save before reboot
		}
		MAX-ACCESS  read-create
		STATUS  	current
		DESCRIPTION
			  "Save the user config before reboot"
		::=	{tpSysToolReBootSchedule 4}
	scheduleCancel OBJECT-TYPE
		SYNTAX  INTEGER{
			commit(1)
		}
		MAX-ACCESS  read-create
		STATUS  	current
		DESCRIPTION
			  "Cancel the reboot schedule"
		::=	{tpSysToolReBootSchedule 5}
	    
flash NOTIFICATION-TYPE    
	STATUS          current
	DESCRIPTION
	  "A flash notification is sented when the flash has been modified."
	::= {tplinkSysToolNotifications 1}
	    
power NOTIFICATION-TYPE    
	STATUS          current
	DESCRIPTION
	  "A power notification is sented when the Redundant Power Supply or the Power Supply Module status changed."
	::= {tplinkSysToolNotifications 2}	
 
fan NOTIFICATION-TYPE    
	STATUS          current
	DESCRIPTION
	  "A fan notification is sented when the Fan working mode or status changed."
	::= {tplinkSysToolNotifications 3}	  

temperature NOTIFICATION-TYPE    
	STATUS          current
	DESCRIPTION
	  "A temperature notification is sented when the temperature alarm happens or cancels."
	::= {tplinkSysToolNotifications 4}	

mCard NOTIFICATION-TYPE    
	STATUS          current
	DESCRIPTION
	  "A mCard notification is sented when the mCard is inserted or removed."
	::= {tplinkSysToolNotifications 5}					
END
