TIMETRA-SAS-GLOBAL-MIB DEFINITIONS ::= BEGIN

IMPORTS
    MODULE-IDENTITY, OBJECT-IDENTITY    FROM SNMPv2-SMI
    tmnxBasedProducts                   FROM TIMETRA-GLOBAL-MIB;

timetraSASGlobalMIBModule MODULE-IDENTITY
    LAST-UPDATED    "0801090000Z"

    ORGANIZATION    "Alcatel-Lucent"
    CONTACT-INFO    
        "Alcatel 7x50 Support
         Web: http://www.alcatel.com/comps/pages/carrier_support.jhtml"
    DESCRIPTION
        "This  document  is the SNMP MIB module for central registration
        of object identifiers defined under the Alcatel 'timetra' branch
        for the Alcatel 7210 SAS series SNMP MIBs.

        Copyright  2003-2013  Alcatel-Lucent. All rights reserved.
        Reproduction of  this document is  authorized  on  the condition
        that the foregoing copyright notice is included.

        This   SNMP   MIB   module  (Specification)  embodies  Alcatel's
        proprietary intellectual property. Alcatel retains all title and
        ownership in the Specification, including any revisions.

        Alcatel grants all interested parties a non-exclusive license to
        use  and  distribute an unmodified copy of this Specification in
        connection with management of Alcatel products, and without fee,
        provided this copyright notice and license appear on all copies.

        This  Specification  is  supplied  `as is', and Alcatel makes no
        warranty,  either  express or implied, as to the use, operation,
        condition, or performance of the Specification."
--
--  Revision History
--
        REVISION        "0801090000Z"
        DESCRIPTION     "Rev 1.0                09 Jan 2008 00:00
                This is the 1.0 release of the TIMETRA-SAS-GLOBAL-MIB."
        ::= { timetraSASModules 1 }

--
-- ----------------------------------------------------------------------------
-- timetraServiceAccessSwitches
-- ----------------------------------------------------------------------------
--
timetraServiceAccessSwitches OBJECT IDENTIFIER ::= { tmnxBasedProducts 2 }

--
-- ----------------------------------------------------------------------------
-- timetraServiceAccessSwitches 1  : SAS registry
-- ----------------------------------------------------------------------------
--  Sub-tree for registrations
timetraSASRegistry      OBJECT IDENTIFIER ::= { timetraServiceAccessSwitches 1 }

--
-- ----------------------------------------------
-- timetraSASRegistry 1  : SAS MIB Modules
-- ----------------------------------------------
--  
    timetraSASModules  OBJECT IDENTIFIER ::= { timetraSASRegistry 1 }
        timetraSASMIBModules                OBJECT IDENTIFIER ::= { timetraSASModules 3 }
        timetraSASCapabilityModule          OBJECT IDENTIFIER ::= { timetraSASModules 4 }

          timetraSASE7210CapModule          OBJECT IDENTIFIER ::= { timetraSASCapabilityModule 1 }

          timetraSASM7210CapModule          OBJECT IDENTIFIER ::= { timetraSASCapabilityModule 2 }

          timetraSASX7210CapModule          OBJECT IDENTIFIER ::= { timetraSASCapabilityModule 3 }

          timetraSASD7210CapModule          OBJECT IDENTIFIER ::= { timetraSASCapabilityModule 4 }

          timetraSAST7210CapModule          OBJECT IDENTIFIER ::= { timetraSASCapabilityModule 5 }

          timetraSASR7210CapModule          OBJECT IDENTIFIER ::= { timetraSASCapabilityModule 6 }

--
-- ----------------------------------------------
-- timetraSASRegistry 2  : SAS Hardware Products
-- ----------------------------------------------
--  Sub-trees for registration of Alcatel-Lucent SAS series hardware products
--
    timetraSAS7210ServiceAccessSwitches   OBJECT IDENTIFIER ::= { timetraSASRegistry 2 }
        timetraSASModel7210SASEReg    OBJECT-IDENTITY
            STATUS  current
            DESCRIPTION 
                "This objectID is to be used as the mib-2 sysObjID to
                 identify the Alcatel-Lucent 7210 SAS-E device."
        ::= { timetraSAS7210ServiceAccessSwitches 1 }

        timetraSASModel7210SASM  OBJECT IDENTIFIER ::= { timetraSAS7210ServiceAccessSwitches 2 }

        timetraSASModel7210SASMReg    OBJECT-IDENTITY
            STATUS  current
            DESCRIPTION
                "This objectID is to be used as the mib-2 sysObjID to
                 identify the Alcatel-Lucent 7210 SAS-M device."
        ::= { timetraSASModel7210SASM 1 }
        
        timetraSASModel7210SASM24F2XPReg    OBJECT-IDENTITY
            STATUS  current
            DESCRIPTION
                "This objectID is to be used as the mib-2 sysObjID to
                 identify the Alcatel-Lucent 7210 SAS-M 24F 2XP device."
        ::= { timetraSASModel7210SASM 2 }
        
        timetraSASModel7210SASM24F2XPETRReg    OBJECT-IDENTITY
            STATUS  current
            DESCRIPTION
                "This objectID is to be used as the mib-2 sysObjID to
                 identify the Alcatel-Lucent 7210 SAS-M 24F 2XP ETR device."
        ::= { timetraSASModel7210SASM 3 } 

        timetraSASModel7210SASX  OBJECT IDENTIFIER ::= { timetraSAS7210ServiceAccessSwitches 3 }

        timetraSASModel7210SASX24F2XPReg    OBJECT-IDENTITY
            STATUS  current
            DESCRIPTION
                "This objectID is to be used as the mib-2 sysObjID to
                 identify the Alcatel-Lucent 7210 SAS-X device."
        ::= { timetraSASModel7210SASX 1 }


        timetraSASModel7210SASD  OBJECT IDENTIFIER ::= { timetraSAS7210ServiceAccessSwitches 4 }

        timetraSASModel7210SASDReg    OBJECT-IDENTITY
            STATUS  current
            DESCRIPTION
                "This objectID is to be used as the mib-2 sysObjID to
                 identify the Alcatel-Lucent 7210 SAS-D device."
        ::= { timetraSASModel7210SASD 1 }

        timetraSASModel7210SASDETRReg    OBJECT-IDENTITY
            STATUS  current
            DESCRIPTION
                "This objectID is to be used as the mib-2 sysObjID to
                 identify the Alcatel-Lucent 7210 SAS-D ETR device."
        ::= { timetraSASModel7210SASD 2 }

        timetraSASModel7210SAST  OBJECT IDENTIFIER ::= { timetraSAS7210ServiceAccessSwitches 5 }

        timetraSASModel7210SASTReg    OBJECT-IDENTITY
            STATUS  current
            DESCRIPTION
                "This objectID is to be used as the mib-2 sysObjID to
                 identify the Alcatel-Lucent 7210 SAS-T device."
        ::= { timetraSASModel7210SAST 1 }


        timetraSASModel7210SASTETRReg    OBJECT-IDENTITY
            STATUS  current
            DESCRIPTION
                "This objectID is to be used as the mib-2 sysObjID to
                 identify the Alcatel-Lucent 7210 SAS-T ETR device."
        ::= { timetraSASModel7210SAST 2 }

        timetraSASModel7210SASR  OBJECT IDENTIFIER ::= { timetraSAS7210ServiceAccessSwitches 6 }

        timetraSASModel7210SASR6Reg    OBJECT-IDENTITY
            STATUS  current
            DESCRIPTION
                "This objectID is to be used as the mib-2 sysObjID to
                 identify the Alcatel-Lucent 7210 SAS-R six slot device."
        ::= { timetraSASModel7210SASR 1 }
        
--
-- ----------------------------------------------
-- timetraServiceAccessSwitches 2  : SAS objects
-- ----------------------------------------------
    timetraSASMIB           OBJECT IDENTIFIER ::= { timetraServiceAccessSwitches 2 }
        timetraSASConfs          OBJECT IDENTIFIER ::= { timetraSASMIB 1 }

        timetraSASObjs           OBJECT IDENTIFIER ::= { timetraSASMIB 2 }

--      Sub-tree for Notifications (events)
        timetraSASNotifyPrefix   OBJECT IDENTIFIER ::= { timetraSASMIB 3 }

        
--
-- ----------------------------------------------------------------------------
-- timetraServiceAccessSwitches 3  : Product Capabilities
-- ----------------------------------------------------------------------------
--
timetraSASProductCapability      OBJECT IDENTIFIER ::= { timetraServiceAccessSwitches 3 }
    timetraSAS7210Capability         OBJECT IDENTIFIER ::= { timetraSASProductCapability 1 }
        timetraSAS7210V1v0               OBJECT IDENTIFIER ::= { timetraSAS7210Capability 1 }
        timetraSAS7210V1v1               OBJECT IDENTIFIER ::= { timetraSAS7210Capability 2 }
        timetraSAS7210V2v0               OBJECT IDENTIFIER ::= { timetraSAS7210Capability 3 }
        timetraSAS7210V3v0               OBJECT IDENTIFIER ::= { timetraSAS7210Capability 4 }
        timetraSAS7210V4v0               OBJECT IDENTIFIER ::= { timetraSAS7210Capability 5 }
        timetraSAS7210V5v0               OBJECT IDENTIFIER ::= { timetraSAS7210Capability 6 }        
        timetraSAS7210V6v0               OBJECT IDENTIFIER ::= { timetraSAS7210Capability 7 }        

END
