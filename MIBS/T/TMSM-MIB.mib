-- extracted from draft-ietf-isms-tmsm-03.txt
-- at Wed Jun 28 06:06:35 2006

   TMSM-MIB DEFINITIONS ::= BEGIN
   IMPORTS
       MODULE-IDENTITY, OBJECT-TYPE,
       mib-2, Integer32, Unsigned32, Gauge32, Counter32
         FROM SNMPv2-SMI
       TestAndIncr, StorageType, RowStatus
         FROM SNMPv2-TC
       MODULE-COMPLIANCE, OBJECT-GROUP
         FROM SNMPv2-CONF
       SnmpSecurityModel,
       SnmpAdminString,  SnmpSecurityLevel, SnmpEngineID
          FROM SNMP-FRAMEWORK-MIB
       TransportAddress, TransportAddressType
         FROM TRANSPORT-ADDRESS-MIB
       ;

   tmsmMIB MODULE-IDENTITY
       LAST-UPDATED "200604200000Z"
       ORGANIZATION "ISMS Working Group"
       CONTACT-INFO "WG-EMail:   isms@lists.ietf.org
                     Subscribe:  isms-request@lists.ietf.org

                  Chairs:
                    Juergen Quittek
                    NEC Europe Ltd.
                    Network Laboratories
                    Kurfuersten-Anlage 36
                    69115 Heidelberg
                    Germany
                    +49 6221 90511-15
                     quittek@netlab.nec.de

                     Juergen Schoenwaelder
                     International University Bremen
                     Campus Ring 1
                     28725 Bremen
                     Germany
                     +49 421 200-3587
                     j.schoenwaelder@iu-bremen.de

                  Editor:
                     David Harrington
                     FutureWei Technologies
                     1700 Alma Drive, Suite 100
                     Plano, Texas 75075
                     USA
                     +1 603-436-8634
                     dharrington@huawei.com
                       "

          DESCRIPTION  "The Transport Mapping Security Model
                                    MIB Module

                        Copyright (C) The Internet Society (2006). This
                        version of this MIB module is part of RFC XXXX;
                        see the RFC itself for full legal notices.
   -- NOTE to RFC editor: replace XXXX with actual RFC number
   --                     for this document and remove this note
                       "

          REVISION     "200604200000Z"         -- 20 April 2006
          DESCRIPTION  "The initial version, published in RFC XXXX.
   -- NOTE to RFC editor: replace XXXX with actual RFC number
   --                     for this document and remove this note
                       "

       ::= { mib-2 1 }
   -- RFC Ed.: replace xxxx with IANA-assigned number and
   --          remove this note

   -- ---------------------------------------------------------- --
   -- subtrees in the TMSM-MIB
   -- ---------------------------------------------------------- --

   tmsmNotifications OBJECT IDENTIFIER ::= { tmsmMIB 0 }
   tmsmObjects       OBJECT IDENTIFIER ::= { tmsmMIB 1 }
   tmsmConformance   OBJECT IDENTIFIER ::= { tmsmMIB 2 }

   -- -------------------------------------------------------------
   -- Objects
   -- -------------------------------------------------------------

   -- Textual Conventions

   -- Notifications for the Transport Model Security Model extension

   -- Statistics for the Transport Model Security Model extension


   tmsmStats         OBJECT IDENTIFIER ::= { tmsmObjects 1 }

   tmsmSessionOpenErrors  OBJECT-TYPE
       SYNTAX       Counter32
       MAX-ACCESS   read-only
       STATUS       current
       DESCRIPTION "The number of times an openSession() request
                  failed to open a Session.
                   "
       ::= { tmsmStats 1 }

   tmsmSessionNoAvailableSessions  OBJECT-TYPE
       SYNTAX       Counter32
       MAX-ACCESS   read-only
       STATUS       current
       DESCRIPTION "The number of times a Response message
                  was dropped because the corresponding
                  session was no longer available.
                   "
       ::= { tmsmStats 2 }

   -- The tmsmSession Group

   tmsmSession          OBJECT IDENTIFIER ::= { tmsmObjects 2 }

   tmsmSessionCurrent  OBJECT-TYPE
       SYNTAX       Gauge32
       MAX-ACCESS   read-only
       STATUS       current
       DESCRIPTION "The current number of open sessions.
                   "
       ::= { tmsmSession 1 }

   tmsmSessionMaxSupported  OBJECT-TYPE
       SYNTAX       Unsigned32
       MAX-ACCESS   read-only
       STATUS       current
       DESCRIPTION "The maximum number of open sessions supported.
                    The value zero indicates the maximum is dynamic.
                   "
       ::= { tmsmSession 2 }

   tmsmSessionOpenErrors  OBJECT-TYPE
       SYNTAX       Counter32
       MAX-ACCESS   read-only
       STATUS       current
       DESCRIPTION "The number of times an openSession() request
                  failed to open a Session.
                   "
       ::= { tmsmSession 3 }

   tmsmSessionSecurityLevelNotAvailableErrors  OBJECT-TYPE
       SYNTAX       Counter32
       MAX-ACCESS   read-only
       STATUS       current
       DESCRIPTION "The number of times an outgoing message was
                  discarded because a requested securityLevel could not
                  provided.
                   "
       ::= { tmsmSession 4 }


   -- -------------------------------------------------------------
   -- tmsmMIB - Conformance Information
   -- -------------------------------------------------------------

   tmsmGroups OBJECT IDENTIFIER ::= { tmsmConformance 1 }

   tmsmCompliances OBJECT IDENTIFIER ::= { tmsmConformance 2 }

   -- -------------------------------------------------------------
   -- Units of conformance
   -- -------------------------------------------------------------
   tmsmGroup OBJECT-GROUP
       OBJECTS {
           tmsmSessionOpenErrors,
           tmsmSessionSecurityLevelNotAvailableErrors,
           tmsmSessionCurrent,
           tmsmSessionMaxSupported
       }
       STATUS      current
       DESCRIPTION "A collection of objects for maintaining session
                    information of an SNMP engine which implements the
                    TMSM architectural extension.
                   "

       ::= { tmsmGroups 2 }

   -- -------------------------------------------------------------
   -- Compliance statements
   -- -------------------------------------------------------------

   tmsmCompliance MODULE-COMPLIANCE
       STATUS      current
       DESCRIPTION
           "The compliance statement for SNMP engines that support the
           TMSM-MIB"
       MODULE
           MANDATORY-GROUPS { tmsmGroup }
       ::= { tmsmCompliances 1 }

   END

-- 
--    Copyright (C) The Internet Society (2006).
-- 
--    This document is subject to the rights, licenses and restrictions
--    contained in BCP 78, and except as set forth therein, the authors
--    retain all their rights.
-- 
--    This document and the information contained herein are provided on an
--    "AS IS" basis and THE CONTRIBUTOR, THE ORGANIZATION HE/SHE REPRESENTS
--    OR IS SPONSORED BY (IF ANY), THE INTERNET SOCIETY AND THE INTERNET
--    ENGINEERING TASK FORCE DISCLAIM ALL WARRANTIES, EXPRESS OR IMPLIED,
--    INCLUDING BUT NOT LIMITED TO ANY WARRANTY THAT THE USE OF THE
--    INFORMATION HEREIN WILL NOT INFRINGE ANY RIGHTS OR ANY IMPLIED
--    WARRANTIES OF MERCHANTABILITY OR FITNESS FOR A PARTICULAR PURPOSE.
-- 
-- Intellectual Property
-- 
--    The IETF takes no position regarding the validity or scope of any
--    Intellectual Property Rights or other rights that might be claimed to
--    pertain to the implementation or use of the technology described in
--    this document or the extent to which any license under such rights
--    might or might not be available; nor does it represent that it has
--    made any independent effort to identify any such rights.  Information
--    on the procedures with respect to rights in RFC documents can be
--    found in BCP 78 and BCP 79.
-- 
--    Copies of IPR disclosures made to the IETF Secretariat and any
--    assurances of licenses to be made available, or the result of an
--    attempt made to obtain a general license or permission for the use of
--    such proprietary rights by implementers or users of this
--    specification can be obtained from the IETF on-line IPR repository at
--    http://www.ietf.org/ipr.
-- 
--    The IETF invites any interested party to bring to its attention any
--    copyrights, patents or patent applications, or other proprietary
--    rights that may cover technology that may be required to implement
--    this standard.  Please address the information to the IETF at
--    ietf-ipr@ietf.org.
--
