TIMETRA-CAPABILITY-7210-SAS-M-V6v0 DEFINITIONS ::= BEGIN

IMPORTS
    MODULE-IDENTITY,
    Unsigned32, Integer32                   FROM SNMPv2-SMI

    RowStatus                               FROM SNMPv2-TC

    AGENT-CAPABILITIES,
    MODULE-COMPLIANCE                       FROM SNMPv2-CONF

    DisplayString,
    TruthValue                              FROM SNMPv2-TC

    SnmpAdminString                         FROM SNMP-FRAMEWORK-MIB

    InterfaceIndex                          FROM IF-MIB

    DefaultMetric                           FROM ISIS-MIB

    Dot1agCfmMhfCreation,
    Dot1agCfmIdPermission                   FROM IEEE8021-CFM-MIB

    InetAddress                             FROM INET-ADDRESS-MIB

    TQueueId                                FROM TIMETRA-TC-MIB

    TmnxOtuAlarms                           FROM TIMETRA-OTU-MIB

    timetraSASM7210CapModule,
    timetraSAS7210V6v0                     FROM TIMETRA-SAS-GLOBAL-MIB;

--
-- Capability statements for SAS-M 7210 release 6.0
--
timetraSASM7210V6v0CapModule   MODULE-IDENTITY
    LAST-UPDATED "1203010000Z"
    ORGANIZATION "Alcatel-Lucent"
    CONTACT-INFO
        "Alcatel-Lucent Support
         Web: http://www.alcatel-lucent.com/wps/portal/support"
    DESCRIPTION
        "This document is the SNMP MIB module for agent capability clauses
         defined under the Alcatel timetra object identifier branch for
         the Alcatel SAS-M 7210 release R6.0. These capability clauses specify
         details about the SNMP agent implementation for this release.

         Copyright 2005-2014 Alcatel-Lucent. All rights reserved.
         Reproduction of this document is authorized on the condition
         that the foregoing copyright notice is included.

         This SNMP MIB module (Specification) embodies Alcatel's
         proprietary intellectual property. Alcatel retains
         all title and ownership in the Specification, including any
         revisions.

         Alcatel grants all interested parties a non-exclusive
         license to use and distribute an unmodified copy of this
         Specification in connection with management of Alcatel
         products, and without fee, provided this copyright notice and
         license appear on all copies.

         This Specification is supplied as is, and Alcatel
         makes no warranty, either express or implied, as to the use,
         operation, condition, or performance of the Specification."

--
--  Revision History
--
    REVISION        "1303010000Z"
    DESCRIPTION     "Rev 0.0                01 Mar 2013 00:00
        This is the initial version of the TIMETRA-CAPABILITY-7210-SAS-M-V6v0
        mib for Alcatel SAS-M 7210 Release 6.0."
    ::= { timetraSASM7210CapModule 3 }

--
-- ----------------------------------------------------------------------------
-- timetraSASM7210V6v0
-- ----------------------------------------------------------------------------
--
tmnxSASM7210V6v0 OBJECT IDENTIFIER ::= { timetraSAS7210V6v0 2 }


--
--  IEEE 8021 PAE CAPABILITIES
--
tmnxIEEE8021PaeCapsSASM7210V6v0 AGENT-CAPABILITIES
    PRODUCT-RELEASE "Alcatel SAS-M 7210"
    STATUS current
    DESCRIPTION
        "Implementation of IEEE 8021 PAE protocol capabilities on
         Alcatel SAS-M 7210 release R6.0"

    SUPPORTS IEEE8021-PAE-MIB
        INCLUDES    {
            dot1xPaeSystemGroup,
            dot1xPaeAuthConfigGroup,
            dot1xPaeAuthStatsGroup,
            dot1xPaeAuthDiagGroup,
            dot1xPaeAuthSessionStatsGroup
            -- not supported: dot1xPaeSuppConfigGroup,
            -- not supported: dot1xPaeSuppStatsGroup
        }

        VARIATION   dot1xAuthAdminControlledDirections
            ACCESS  read-only
            DESCRIPTION
                    "read-only support."

        VARIATION   dot1xAuthKeyTxEnabled
            SYNTAX  TruthValue
            ACCESS  read-only
            DESCRIPTION
                    "read-only support. The value returned is always false."

    SUPPORTS ALCATEL-IEEE8021-PAE-MIB
        INCLUDES    {
            alxDot1xAuthConfigGroup,
            alxDot1xRadiusPlcyGroup
        }
    ::= { tmnxSASM7210V6v0 1 }

--
--  IGMP Snooping Capabilities
--
tmnxIgmpSnoopingCapsSASM7210V6v0 AGENT-CAPABILITIES
    PRODUCT-RELEASE "Alcatel SAS-M 7210"
    STATUS current
    DESCRIPTION
        "Implementation of igmp snooping on Alcatel SAS-M 7210 release R6.0"

    SUPPORTS ALCATEL-IGMP-SNOOPING-MIB
        INCLUDES    {
            alxTlsIgmpSnpgConfigV6v0Group,
            alxTlsIgmpSnpgQuerierV3v0Group,
            alxTlsIgmpSnpgProxyV3v0Group,
            alxTlsIgmpSnpgMRouterV3v0Group,
            -- alxTlsMvrConfigV3v0Group,
            alxTlsIgmpSnpgTimeStampGroup,
            alxSapIgmpSnpgConfigV5v0Group,
            alxSapIgmpSnpgGroupV3v0,
            alxSapIgmpSnpgStaticV3v0Group,
            alxSapIgmpSnpgStatsV6v0Group,
            alxSapMvrV3v0Group,
            alxSapIgmpSnpgNotV5v0Group,
            alxSapIgmpSnpgTimeStampGroup,
            alxSdpBindIgmpSnpgConfV5v0Group,
            alxSdpBindIgmpSnpgV3v0Group,
            alxSdpBindIgmpSnpgStatV3v0Group,
            alxSdpBindIgmpSnpgStatsV6v0Grp,
            alxSdpBindIgmpSnpgNotV5v0Group,
            alxSdpBindIgmpSnpgTimeStampGroup
        }

        VARIATION   sdpBndIgmpSnpgGrpFilterMode
            ACCESS  not-implemented
            DESCRIPTION
                    "Not supported."

        VARIATION sapIgmpSnpgCfgMcacAvailMandBw
            ACCESS  not-implemented
            DESCRIPTION
                "Not supported."

        VARIATION sapIgmpSnpgCfgMcacAvailOpnlBw
            ACCESS  not-implemented
            DESCRIPTION
                "Not supported."

        VARIATION sapIgmpSnpgCfgMcacConstAdmSt
            ACCESS  not-implemented
            DESCRIPTION
                "Not supported."

        VARIATION sapIgmpSnpgCfgMcacinUseMandBw
            ACCESS  not-implemented
            DESCRIPTION
                "Not supported."

        VARIATION sapIgmpSnpgCfgMcacinUseOpnlBw
            ACCESS  not-implemented
            DESCRIPTION
                "Not supported."

        VARIATION sapIgmpSnpgCfgMcacLagLastChangeT
            ACCESS  not-implemented
            DESCRIPTION
                "Not supported."

        VARIATION sapIgmpSnpgCfgMcacLagLevel
            ACCESS  not-implemented
            DESCRIPTION
                "Not supported."

        VARIATION sapIgmpSnpgCfgMcacLagRowStat
            ACCESS  not-implemented
            DESCRIPTION
                "Not supported."

        VARIATION sapIgmpSnpgCfgMcacLevelBW
            ACCESS  not-implemented
            DESCRIPTION
                "Not supported."

        VARIATION sapIgmpSnpgCfgMcacLevelLastChngT
            ACCESS  not-implemented
            DESCRIPTION
                "Not supported."

        VARIATION sapIgmpSnpgCfgMcacLevelRowStat
            ACCESS  not-implemented
            DESCRIPTION
                "Not supported."

        VARIATION sapIgmpSnpgCfgMcacPolicyName
            ACCESS  not-implemented
            DESCRIPTION
                "Not supported."

        VARIATION sapIgmpSnpgCfgMcacPrRsvMndBW
            ACCESS  not-implemented
            DESCRIPTION
                "Not supported."

        VARIATION sapIgmpSnpgCfgMcacUnconstBW
            ACCESS  not-implemented
            DESCRIPTION
                "Not supported."

        VARIATION sapIgmpSnpgCfgMcacValInTrans
            ACCESS  not-implemented
            DESCRIPTION
                "Not supported."

        VARIATION sapIgmpSnpgFwdSrcSpecQueries
            ACCESS  not-implemented
            DESCRIPTION
                "Not supported."

        VARIATION sapIgmpSnpgMcacPolicyDrops
            ACCESS  not-implemented
            DESCRIPTION
                "Not supported."

        VARIATION sapIgmpSnpgMcsFailures
            ACCESS  not-implemented
            DESCRIPTION
                "Not supported."
     
        VARIATION sdpBndIgmpSnpgCfgMcacAvailMndBw
            ACCESS  not-implemented
            DESCRIPTION
                "Not supported."

        VARIATION sdpBndIgmpSnpgCfgMcacAvailOplBw
            ACCESS  not-implemented
            DESCRIPTION
                "Not supported."

        VARIATION sdpBndIgmpSnpgCfgMcacinUseMndBw
            ACCESS  not-implemented
            DESCRIPTION
                "Not supported."

        VARIATION sdpBndIgmpSnpgCfgMcacinUseOplBw
            ACCESS  not-implemented
            DESCRIPTION
                "Not supported."

        VARIATION sdpBndIgmpSnpgCfgMcacPolicyName
            ACCESS  not-implemented
            DESCRIPTION
                "Not supported."

        VARIATION sdpBndIgmpSnpgCfgMcacPrRsvMndBW
            ACCESS  not-implemented
            DESCRIPTION
                "Not supported."

        VARIATION sdpBndIgmpSnpgCfgMcacUnconstBW
            ACCESS  not-implemented
            DESCRIPTION
                "Not supported."

        VARIATION sdpBndIgmpSnpgCfgMcacValInTrans
            ACCESS  not-implemented
            DESCRIPTION
                "Not supported."

        VARIATION sdpBndIgmpSnpgFwdSrcSpecQueries
            ACCESS  not-implemented
            DESCRIPTION
                "Not supported."

        VARIATION sdpBndIgmpSnpgFwdV3Reports
            ACCESS  not-implemented
            DESCRIPTION
                "Not supported."

        VARIATION sdpBndIgmpSnpgRxSrcSpecQueries
            ACCESS  not-implemented
            DESCRIPTION
                "Not supported."

        VARIATION sdpBndIgmpSnpgRxV3Reports
            ACCESS  not-implemented
            DESCRIPTION
                "Not supported."

        VARIATION sdpBndIgmpSnpgTxSrcSpecQueries
            ACCESS  not-implemented
            DESCRIPTION
                "Not supported."

        VARIATION sdpBndIgmpSnpgTxV3Reports
            ACCESS  not-implemented
            DESCRIPTION
                "Not supported."            

        VARIATION sdpBndIgmpSnpgMcacPolicyDrops
            ACCESS  not-implemented
            DESCRIPTION
                "Not supported."

        VARIATION sapIgmpSnpgRxRsvdScopePkts
            ACCESS  not-implemented
            DESCRIPTION
                "Not supported."

        VARIATION sdpBndIgmpSnpgRxRsvdScopePkts
            ACCESS  not-implemented
            DESCRIPTION
                "Not supported."


    ::= { tmnxSASM7210V6v0 2 }

--
--  Ethernet Wan Interface Sublayer Capabilities
--

tmnxEtherWisCapsSASM7210V6v0 AGENT-CAPABILITIES
    PRODUCT-RELEASE "Alcatel SAS-M 7210"
    STATUS current
    DESCRIPTION
        "The compliance statement for interfaces that include
         the Ethernet WIS on Alcatel SAS-M 7210 release R6.0"

    SUPPORTS ETHER-WIS
        INCLUDES    {
            etherWisDeviceGroupBasic,
            etherWisDeviceGroupExtra,
            etherWisSectionGroup,
            etherWisPathGroup,
            etherWisFarEndPathGroup
        }

        VARIATION   etherWisDeviceTxTestPatternMode
            ACCESS  read-only
            DESCRIPTION
                    "read-only support."

        VARIATION   etherWisDeviceRxTestPatternMode
            ACCESS  read-only
            DESCRIPTION
                    "read-only support."

        VARIATION   etherWisDeviceRxTestPatternErrors
            ACCESS  read-only
            DESCRIPTION
                    "read-only support."

        VARIATION   etherWisSectionCurrentJ0Transmitted
            ACCESS  read-only
            DESCRIPTION
                    "read-only implementation."

        VARIATION   etherWisPathCurrentJ1Transmitted
            ACCESS  read-only
            DESCRIPTION
                    "read-only implementation."

    ::= { tmnxSASM7210V6v0 3 }

--
--  EtherLike MIB Capabilities
--
tmnxEtherLikeCapsSASM7210V6v0 AGENT-CAPABILITIES
    PRODUCT-RELEASE "Alcatel SAS-M 7210"
    STATUS current
    DESCRIPTION
        "Implementation of Ethernet-like network interfaces
         capabilities for Alcatel SAS-M 7210 release R6.0"

    SUPPORTS EtherLike-MIB
        INCLUDES    {
            etherCollisionTableGroup,
            etherStatsLowSpeedGroup,
            etherStatsHighSpeedGroup,
            etherStatsBaseGroup2,
            etherStatsHalfDuplexGroup,
            etherDuplexGroup
            -- EXCLUDE dot3CollTable
            -- EXCLUDE dot3ControlTable
            -- EXCLUDE dot3PauseTable
            -- EXCLUDE dot3Tests
            -- EXCLUDE dot3Errors
            -- EXCLUDE dot3StatsRateControlAbility
            -- EXCLUDE dot3StatsRateControlStatus
            -- EXCLUDE dot3HCStatsTable
        }
    ::= { tmnxSASM7210V6v0 4 }

--
--  REMOTE MONITORING, RMON, CAPABILITIES
--
tmnxRmonCapsSASM7210V6v0 AGENT-CAPABILITIES
    PRODUCT-RELEASE "Alcatel SAS-M 7210"
    STATUS current
    DESCRIPTION
        "Implementation of Remote Monitoring, RMON,
         capabilities for Alcatel SAS-M 7210 release R6.0"

    SUPPORTS RMON-MIB
        INCLUDES    {
            rmonEtherStatsGroup,
            rmonHistoryControlGroup,
            rmonEthernetHistoryGroup,
            rmonAlarmGroup,
            rmonEventGroup
            -- rmonHostGroup :
            --   EXCLUDE hostControlTable
            --   EXCLUDE hosts
            -- rmonHostTopNGroup
            --   EXCLUDE hostTopN
            -- rmonMatrixGroup
            --   EXCLUDE matrix
            -- rmonFilterGroup
            --   EXCLUDE filter
            -- rmonPacketCaptureGroup
            --   EXCLUDE capture
            -- rmonNotificationGroup
            --   EXCLUDE rmonConformance
        }

        VARIATION   etherStatsIndex
            SYNTAX  InterfaceIndex
            DESCRIPTION
                    "The agent creates a row entry in the etherStatsTable for
                    each ethernet port in the system that is indexed by the
                    port-id or ifIndex value which has a larger value range
                    than that specified for etherStatsIndex in the RMON-MIB."

        VARIATION   etherStatsDataSource
            ACCESS  read-only
            DESCRIPTION
                    "read-only implementation. The agent creates a row entry
                     in the etherStatsTable for each ethernet port in the
                     system, indexed by the port-id."

        VARIATION   etherStatsOwner
            ACCESS  read-only
            DESCRIPTION
                    "read-only implementation."

        VARIATION   etherStatsStatus
            ACCESS  read-only
            DESCRIPTION
                    "etherStatsTable is read-only on SAS-M 7210. Rows cannot
                    be created by SNMP SET requests. The agent creates a row
                    entry in the etherStatsTable for each ethernet port in
                    the system, indexed by the port-id."

        VARIATION   etherStatsOversizePkts
            DESCRIPTION
                    "etherStatsOversizePkts indicates the total number of
                    packets received that were longer than the maximum frame
                    size for the particular media, usually 12287 octets
                    (excluding framing bits, but including FCS octets), and
                    were otherwise well formed.

                    TIMETRA-PORT-MIB::tmnxPortEtherPkts1519toMax,
                    TIMETRA-PORT-MIB::tmnxPortEtherHCOverPkts1519toMax and
                    TIMETRA-PORT-MIB::tmnxPortEtherHCPkts1519toMax are used
                    to indicate the total number of packets received that were
                    longer than 1518 octets but less than the maximum frame
                    size for the particular media, usually 12287 octets
                    (excluding framing bits, but including FCS octets)."

    SUPPORTS HC-RMON-MIB
        INCLUDES    {
            mediaIndependentGroup,
            etherStatsHighCapacityGroup,
            etherHistoryHighCapacityGroup,
            hcRMONInformationGroup
        }

        VARIATION   mediaIndependentIndex
            SYNTAX  InterfaceIndex
            DESCRIPTION
                    "The agent creates a row entry in the
                    mediaIndependentTable for each physical port in
                    the system, indexed by the port-id which is also
                    the ifIndex which has a larger value range than
                    that specified for mediaIndependentIndex in the
                    HC-RMON-MIB."

        VARIATION   mediaIndependentDataSource
            ACCESS  read-only
            DESCRIPTION
                    "mediaIndependentTable is read-only on SAS-M 7210.
                    The agent creates a row entry in the mediaIndependentTable
                    for each physical port in the system, indexed by the
                    port-id."

        VARIATION   mediaIndependentOwner
            ACCESS  read-only
            DESCRIPTION
                    "read-only implementation."

        VARIATION   mediaIndependentStatus
            ACCESS  read-only
            DESCRIPTION
                    "mediaIndependentTable is read-only on SAS-M 7210.
                    Rows cannot be created in the table by SNMP SET requests.
                    The agent creates a row entry in the mediaIndependentTable
                    for each physical port in the system, indexed by the
                    port-id."

    ::= { tmnxSASM7210V6v0 6 }

--
--  LAG
--
tmnxLagCapsSASM7210V6v0 AGENT-CAPABILITIES
    PRODUCT-RELEASE "Alcatel SAS-M 7210"
    STATUS current
    DESCRIPTION
        "Implementation of Link Aggregation, LAG, capabilities for Alcatel
         SAS-M 7210 release R6.0"

    SUPPORTS IEEE8023-LAG-MIB
        INCLUDES    {
            dot3adAggGroup,
            dot3adAggPortGroup
            -- dot3adTablesLastChangedGroup: EXCLUDE dot3adTablesLastChanged
            -- dot3adAggPortListGroup      : EXCLUDE dot3adAggPortListTable
            -- dot3adAggPortStatsGroup     : EXCLUDE dot3adAggPortStatsTable
            -- dot3adAggPortDebugGroup     : EXCLUDE dot3adAggPortDebugTable
        }

        --
        -- dot3adAggGroup
        --
        VARIATION   dot3adAggActorAdminKey
            ACCESS  read-write
            DESCRIPTION
                    "The value of dot3adAggActorAdminKey cannot be changed
                    after the row entry has been created. A set to the same
                    value succeeds."

        VARIATION   dot3adAggActorSystemPriority
            ACCESS  read-only
            DESCRIPTION
                    "read-only implementation."

        VARIATION   dot3adAggCollectorMaxDelay
            ACCESS  read-only
            DESCRIPTION
                    "read-only implementation."

        VARIATION   dot3adAggEntry
            CREATION-REQUIRES { tLagRowStatus }
            DESCRIPTION
                    "An entry in the dot3adAggTable is created when an entry
                    is created in the tLagConfigTable in TIMETRA-LAG-MIB."

        --
        -- dot3adAggPortGroup
        --
        VARIATION   dot3adAggPortActorSystemPriority
            ACCESS  read-only
            DESCRIPTION
                    "read-only implementation."

        VARIATION   dot3adAggPortActorAdminKey
            ACCESS  read-only
            DESCRIPTION
                    "read-only implementation."

        VARIATION   dot3adAggPortActorOperKey
            ACCESS  read-only
            DESCRIPTION
                    "read-only implementation."

        VARIATION   dot3adAggPortPartnerAdminSystemPriority
            ACCESS  read-only
            DESCRIPTION
                    "read-only implementation."

        VARIATION   dot3adAggPortPartnerAdminSystemID
            ACCESS  read-only
            DESCRIPTION
                    "read-only implementation."

        VARIATION   dot3adAggPortPartnerAdminKey
            ACCESS  read-only
            DESCRIPTION
                    "read-only implementation."

        VARIATION   dot3adAggPortPartnerAdminPort
            ACCESS  read-only
            DESCRIPTION
                    "read-only implementation."

        VARIATION   dot3adAggPortPartnerAdminPortPriority
            ACCESS  read-only
            DESCRIPTION
                    "read-only implementation."

        VARIATION   dot3adAggPortActorAdminState
            ACCESS  read-only
            DESCRIPTION
                    "read-only implementation."

        VARIATION   dot3adAggPortPartnerAdminState
            ACCESS  read-only
            DESCRIPTION
                    "read-only implementation."

    SUPPORTS TIMETRA-LAG-MIB
        INCLUDES    {
            tmnxLagInstanceV7v0Group,
            tmnxLagV6v0NotifGroup
            -- tmnxLagHsmdaV6v0Group
        }
        VARIATION   tLagAccessAdaptQos
            ACCESS  not-implemented
            DESCRIPTION
                    "tLagAccessAdaptQos is not supported on 7210 SAS-M."

        VARIATION   tLagPortThreshold
            SYNTAX  INTEGER (0..3)
            DESCRIPTION
                    "tLagPortThreshold range for SAS-M is (0..3)."

        VARIATION   tLagPortSubgroup
            SYNTAX  INTEGER (1..2)
            DESCRIPTION
                    "tLagPortSubgroup range for SAS-M is (1..2)."

    ::= { tmnxSASM7210V6v0 7 }

--
--  INTERFACE CAPABILITIES
--
tmnxIfCapsSASM7210V6v0 AGENT-CAPABILITIES
    PRODUCT-RELEASE "Alcatel SAS-M 7210"
    STATUS current
    DESCRIPTION
        "Implementation of interface capabilities for Alcatel SAS-M 7210 release R6.0"

    SUPPORTS IF-MIB
        INCLUDES    {
            ifGeneralInformationGroup,
            linkUpDownNotificationsGroup,
            ifPacketGroup,
            ifHCPacketGroup,
            ifVHCPacketGroup,
            ifCounterDiscontinuityGroup,
            ifStackGroup2
            -- ifFixedLengthGroup
            -- ifHCFixedLengthGroup
            -- ifRcvAddressGroup
            -- EXCLUDE ifRcvAddressTable
            -- EXCLUDE ifTestTable (obsolete)
        }

        VARIATION   ifAdminStatus
            SYNTAX  INTEGER {
                        up      (1),       -- ready to pass packets
                        down    (2)
                    }
            DESCRIPTION
                    "Write access using value 'testing (3)' is not supported."

        VARIATION   linkDown
            DESCRIPTION
                    "The linkDown notification has ifDescr appended to the 
                     variable list."

        VARIATION   linkUp
            DESCRIPTION
                    "The linkUp trap has ifDescr appended to the variable list."

        VARIATION   ifLinkUpDownTrapEnable
            ACCESS  read-only
            DESCRIPTION
                    "read-only implementation."

        VARIATION   ifPromiscuousMode
            ACCESS  read-only
            DESCRIPTION
                    "read-only implementation."

        VARIATION   ifAlias
            ACCESS  read-only
            DESCRIPTION
                    "read-only implementation."

        VARIATION   ifStackStatus
            ACCESS  read-only
            DESCRIPTION
                    "read-only implementation."

    SUPPORTS IF-INVERTED-STACK-MIB
        INCLUDES    {
            ifInvStackGroup
        }
    ::= { tmnxSASM7210V6v0 8 }

--
--  IP CAPABILITIES
--
tmnxIPCapabilitySASM7210V6v0 AGENT-CAPABILITIES
    PRODUCT-RELEASE "Alcatel SAS-M 7210"
    STATUS current
    DESCRIPTION
        "Base implementation of Internet Protocol, IP
         capabilities for Alcatel SAS-M 7210 release R6.0"

    SUPPORTS IP-MIB
        INCLUDES    {
            ipGroup,
            -- EXCLUDE ipAddressPrefixGroup (not supported)
            -- EXCLUDE ipAddressGroup (not supported)
            ipNetToPhysicalGroup,
            ipv6RouterAdvertGroup,
            icmpGroup
            -- EXCLUDE ipv6GeneralGroup2 (not supported)
            -- EXCLUDE ipLastChangeGroup (not supported)
            -- EXCLUDE ipv4InterfaceTable (not supported)
            -- EXCLUDE ipv6InterfaceTable (not supported)
            -- EXCLUDE ipTrafficStats (not supported)
            -- EXCLUDE ipAddressSpinLock (not supported)
            -- EXCLUDE ipv6ScopeZoneIndexTable (not supported)
            -- EXCLUDE ipDefaultRouterTable (not supported)
            -- EXCLUDE ipv6RouterAdvertSpinLock (not supported)
            -- EXCLUDE icmpStatsTable (not supported)
            -- EXCLUDE icmpMsgStatsTable (not supported)
        }

        VARIATION   ipNetToMediaType
            SYNTAX  INTEGER {
                        other   (1),      -- none of the following
                        invalid (2),      -- an invalidated mapping
                        dynamic (3),
                        static  (4),
                        managed (5)       -- added for 7x50
                    }
            DESCRIPTION
                    "The value 'managed (5)' is used to indicate that the
                    ARP entry has been added by:

                    - a static host; or
                    - by a DHCP lease state if
                      TIMETRA-VRTR-MIB::vRtrIfArpPopulate is set to enabled.

                    An attempt to explicitly set the value of ipNetToMediaType
                    to 'managed' results in an 'inconsistentValue' error."

        VARIATION   ipForwarding
            ACCESS  read-only
            DESCRIPTION
                    "ipForwarding is read-only on SAS-M 7210. It always
                     returns the value 'forwarding (1)'."

        VARIATION   ipDefaultTTL
            ACCESS  read-only
            DESCRIPTION
                    "ipDefaultTTL is read-only on SAS-M 7210. It always
                     returns the value '64'."

        VARIATION   ipv6RouterAdvertSpinLock
            ACCESS  not-implemented
            DESCRIPTION
                    "Not supported."

        VARIATION   ipNetToPhysicalType
            SYNTAX  INTEGER {
                        other   (1),      -- none of the following
                        invalid (2),      -- an invalidated mapping
                        dynamic (3),
                        static  (4),
                        local   (5),      -- local interface
                        managed (100)     -- added for 7x50
                    }
            DESCRIPTION
                    "The value 'managed (100)' is used to indicate that the
                    ARP entry has been added by:

                    - a static host; or
                    - by a DHCP lease state if
                      TIMETRA-VRTR-MIB::vRtrIfArpPopulate is set to enabled.

                    An attempt to explicitly set the value of
                    ipNetToPhysicalType to 'managed' results in an
                    'inconsistentValue' error."


    SUPPORTS IP-FORWARD-MIB
        INCLUDES    {
            ipForwardCidrRouteGroup,
            inetForwardCidrRouteGroup
            -- EXCLUDE ipForwardNumber (obsolete object)
            -- EXCLUDE ipForwardTable  (obsolete table)
            -- EXCLUDE inetCidrRouteNumber   (not supported)
            -- EXCLUDE inetCidrRouteDiscards (not supported)
        }

        VARIATION   ipCidrRouteIfIndex
            ACCESS  read-only
            DESCRIPTION
                    "read-only implementation."

        VARIATION   ipCidrRouteType
            ACCESS  read-only
            DESCRIPTION
                    "read-only implementation."

        VARIATION   ipCidrRouteInfo
            ACCESS  read-only
            DESCRIPTION
                    "read-only implementation."

        VARIATION   ipCidrRouteNextHopAS
            ACCESS  read-only
            DESCRIPTION
                    "read-only implementation."

        VARIATION   ipCidrRouteMetric1
            ACCESS  read-only
            DESCRIPTION
                    "read-only implementation."

        VARIATION   ipCidrRouteMetric2
            ACCESS  read-only
            DESCRIPTION
                    "read-only implementation."

        VARIATION   ipCidrRouteMetric3
            ACCESS  read-only
            DESCRIPTION
                    "read-only implementation."

        VARIATION   ipCidrRouteMetric4
            ACCESS  read-only
            DESCRIPTION
                    "read-only implementation."

        VARIATION   ipCidrRouteMetric5
            ACCESS  read-only
            DESCRIPTION
                    "read-only implementation."

        VARIATION   ipCidrRouteStatus
            ACCESS  read-only
            DESCRIPTION
                    "read-only implementation."

        VARIATION   inetCidrRouteDestType
            DESCRIPTION
                    "inetCidrRouteDestType can only be ipv4 on SAS-M 7210."

        VARIATION   inetCidrRouteNextHopType
           DESCRIPTION
                    "inetCidrRouteNextHopType can only be ipv4 on SAS-M 7210."

        VARIATION   inetCidrRouteIfIndex
            ACCESS  read-only
            DESCRIPTION
                    "read-only implementation."   

        VARIATION   inetCidrRouteType
            ACCESS  read-only
            DESCRIPTION
                    "read-only implementation."

        VARIATION   inetCidrRouteNextHopAS
            ACCESS  read-only
            DESCRIPTION
                    "read-only implementation."

        VARIATION   inetCidrRouteMetric1
            ACCESS  read-only
            DESCRIPTION
                    "read-only implementation."

        VARIATION   inetCidrRouteMetric2
            ACCESS  read-only
            DESCRIPTION
                    "read-only implementation."

        VARIATION   inetCidrRouteMetric3
            ACCESS  read-only
            DESCRIPTION
                    "read-only implementation."

        VARIATION   inetCidrRouteMetric4
            ACCESS  read-only
            DESCRIPTION
                    "read-only implementation."

        VARIATION   inetCidrRouteMetric5
            ACCESS  read-only
            DESCRIPTION
                    "read-only implementation."

        VARIATION   inetCidrRouteStatus
            ACCESS  read-only
            DESCRIPTION
                    "read-only implementation."

        VARIATION   inetCidrRouteNumber
            ACCESS  not-implemented
            DESCRIPTION
                    "Not supported."

        VARIATION   inetCidrRouteDiscards
            ACCESS  not-implemented
            DESCRIPTION
                    "Not supported."

    SUPPORTS TCP-MIB
        INCLUDES    {
            tcpBaseGroup,
            tcpConnectionGroup,
            tcpListenerGroup
            -- EXCLUDE tcpHCGroup (not supported)
        }

        VARIATION   tcpConnectionState
            ACCESS  read-only
            DESCRIPTION
                    "read-only implementation."

    SUPPORTS UDP-MIB
        INCLUDES    {
            udpGroup,
            udpEndpointGroup
            -- EXCLUDE udpHCGroup (not supported)
        }
    ::= { tmnxSASM7210V6v0 9 }

--
--  ISIS CAPABILITIES
--
tmnxIsisCapsSASM7210V6v0 AGENT-CAPABILITIES
    PRODUCT-RELEASE "Alcatel SAS-M 7210"
    STATUS current
    DESCRIPTION
        "Implementation of ISIS protocol capabilities
         capabilities for Alcatel SAS-M 7210 release R6.0"

    SUPPORTS ISIS-MIB
        INCLUDES    {
            isisSystemGroup,       -- EXCLUDE isisSummAddrTable
            isisCircuitGroup,
            isisISAdjGroup
            -- isisISPDUCounterGroup,
            -- isisRATableGroup    : EXCLUDE isisRATable
            -- isisISIPRADestGroup : EXCLUDE isisIPRATable
        }

        --
        --  isisSystemGroup
        --
        VARIATION   isisSysEntry
            CREATION-REQUIRES { vRtrIsIsStatus }
            DESCRIPTION
                    "Row entries in the isisSysTable are created by setting
                    TIMETRA-VRTR-MIB::vRtrIsIsStatus to true."

        VARIATION   isisSysExistState
            SYNTAX  INTEGER {
                        active (1)
                    }
            ACCESS  read-only
            DESCRIPTION
                    "RowStatus object. read-only implementation."

        VARIATION   isisSysID
            ACCESS  read-only
            DESCRIPTION
                    "read-only implementation."

        VARIATION   isisSysOrigL1LSPBuffSize
            ACCESS  not-implemented
            DESCRIPTION
                    "No longer supported. It has been replaced by
                     TIMETRA-ISIS-MIB::vRtrIsisSysOrigL1LSPBuffSize."

        VARIATION   isisSysMaxAreaAddresses
            ACCESS  read-only
            DESCRIPTION
                    "read-only implementation."

        VARIATION   isisSysMinL1LSPGenInt
            ACCESS  read-only
            DESCRIPTION
                    "read-only implementation."

        VARIATION   isisSysMinL2LSPGenInt
            ACCESS  read-only
            DESCRIPTION
                    "read-only implementation."

        VARIATION   isisSysPollESHelloRate
            ACCESS  read-only
            DESCRIPTION
                    "read-only implementation."   

        VARIATION   isisSysOrigL2LSPBuffSize
            ACCESS  not-implemented
            DESCRIPTION
                    "No longer supported. It has been replaced by
                     TIMETRA-ISIS-MIB::vRtrIsisSysOrigL2LSPBuffSize."

        VARIATION   isisSysLSPIgnoreErrors
            ACCESS  read-only
            DESCRIPTION
                    "read-only implementation."

        VARIATION   isisSysLogAdjacencyChanges
            ACCESS  read-only
            DESCRIPTION
                    "read-only implementation."

        VARIATION   isisSysL2toL1Leaking
            ACCESS  read-only
            DESCRIPTION
                    "read-only implementation."

        VARIATION   isisSysProtSuppExistState
            ACCESS  read-only
            DESCRIPTION
                    "read-only implementation."

        VARIATION   isisSummAddrExistState
            ACCESS  not-implemented
            DESCRIPTION
                    "Not supported."

        VARIATION   isisSummAddrAdminState
            ACCESS  not-implemented
            DESCRIPTION
                    "Not supported."

        VARIATION   isisSummAddrDefaultMetric
            ACCESS  not-implemented
            DESCRIPTION
                    "Not supported."

        --
        --  isisCircuitGroup
        --
        --  isisCircTable
        --
        VARIATION   isisCircEntry
            CREATION-REQUIRES { vRtrIsisIfRowStatus }
            DESCRIPTION
                    "Row entries in the isisCircTable are created by setting
                    TIMETRA-ISIS-MIB::vRtrIsisIfRowStatus."

        VARIATION   isisCircExistState
            SYNTAX  INTEGER {
                        active (1)
                    }
            ACCESS  read-only
            DESCRIPTION
                    "RowStatus object. read-only implementation."

        VARIATION   isisCircIfIndex
            ACCESS  read-only
            DESCRIPTION
                    "read-only implementation."

        VARIATION   isisCircIfSubIndex
            ACCESS  read-only
            DESCRIPTION
                    "read-only implementation."

        --
        --  isisCircLevelTable
        --
        VARIATION   isisCircLevelDefaultMetric
            SYNTAX  DefaultMetric (0..63)
            ACCESS  read-only
            DESCRIPTION
                    "read-only implementation. isisCircLevelDefaultMetric
                     can have a value of 0 for loopback and system interfaces."

        VARIATION   isisCircLevelISPriority
            ACCESS  read-only
            DESCRIPTION
                    "read-only implementation."

        VARIATION   isisCircLevelHelloTimer
            ACCESS  read-only
            DESCRIPTION
                    "read-only implementation."

        VARIATION   isisCircLevelDRHelloTimer
            ACCESS  read-only
            DESCRIPTION
                    "read-only implementation."

        VARIATION   isisCircLevelLSPThrottle
            ACCESS  read-only
            DESCRIPTION
                    "read-only implementation."

        VARIATION   isisCircLevelMinLSPRetransInt
            ACCESS  read-only
            DESCRIPTION
                    "read-only implementation."

        VARIATION   isisCircLevelCSNPInterval
            ACCESS  read-only
            DESCRIPTION
                    "read-only implementation."

        VARIATION   isisCircLevelPartSNPInterval
            ACCESS  read-only
            DESCRIPTION
                    "read-only implementation."

        VARIATION   isisCircLevelHelloMultiplier
            DEFVAL { 3 }
            DESCRIPTION
                    "The default hello multiplier value is 3 instead of 10
                    since the value of 10 results in a long holding time."

        VARIATION   isisSysMaxPathSplits
            ACCESS  read-only
            DESCRIPTION
                    "read-only implementation."

    SUPPORTS TIMETRA-ISIS-MIB
        INCLUDES    {
            vRtrIsisV5v0Group,
            vRtrIsisHostGroup,
            vRtrIsisRouteV5v0Group,
            vRtrIsisPathV5v0Group,
            vRtrIsisLSPGroup,
            vRtrIsisIfV5v0Group,
            vRtrIsisAdjV5v0Group,
            vRtrIsisNotificationV3v0Group,
            vRtrIsisSpfGroup,
            vRtrIsisSummaryV4v0Group,
            vRtrIsisIfV6v0Group,
            vRtrIsisIfV6v1Group,
            vRtrIsisSummaryV6v1Group,
            vRtrIsisRouteV6v1Group,
            vRtrIsisV6v0Group,
            vRtrIsisV6v1Group,
            vRtrIsisNotificationV6v0Group,
            vRtrIsisLspMtuV6v0Group,
            vRtrIsisV8v0Group,
            vRtrIsisV9v0R4Group,
            vRtrIsisIfV9v0Group
        }

        VARIATION   vRtrIsisIfIpv6EnableBfd
            ACCESS  not-implemented
            DESCRIPTION
                    "Not supported."
                    
        VARIATION   vRtrIsisGRRestartDuration
            ACCESS  not-implemented
            DESCRIPTION
                    "Not supported."

        VARIATION   vRtrIsisUnicastImport
            ACCESS  not-implemented
            DESCRIPTION
                    "Not supported."


        VARIATION   vRtrIsisMulticastImport
            ACCESS  not-implemented
            DESCRIPTION
                    "Not supported." 


        VARIATION   vRtrIsisIfLevelOperMetric
            SYNTAX  Unsigned32 (0..16777215)
            DESCRIPTION
                    "vRtrIsisIfLevelOperMetric can have a value of 0 for
                    loopback and system interfaces."

        VARIATION   vRtrIsisOverloadOnBoot
            SYNTAX  INTEGER {
                    disabled (1),
                    enabled (2)
                    -- enabledWaitForBgp (3)
                }
            DESCRIPTION
                    "vRtrIsisOverloadOnBoot only supports disabled (1)' and
                    'enabled (2)'.  'enabledWaitForBgp (3) is not implemented."

        VARIATION vRtrIsisIfLdpSyncState
            ACCESS  not-implemented
            DESCRIPTION
                "Not supported."

        VARIATION vRtrIsisIfLdpSyncMaxMetric
            ACCESS  not-implemented
            DESCRIPTION
                "Not supported."

        VARIATION vRtrIsisIfLdpSyncTimerState
            ACCESS  not-implemented
            DESCRIPTION
                "Not supported."

        VARIATION vRtrIsisIfLdpSyncTimeLeft
            ACCESS  not-implemented
            DESCRIPTION
                "Not supported."


        VARIATION vRtrIsisInetMtRouteLevel
            ACCESS  not-implemented
            DESCRIPTION
                "Not supported."

        VARIATION vRtrIsisInetMtRouteMetric
            ACCESS  not-implemented
            DESCRIPTION
                "Not supported."

        VARIATION vRtrIsisInetMtRouteNHopSysID
            ACCESS  not-implemented
            DESCRIPTION
                "Not supported."

        VARIATION vRtrIsisInetMtRouteSpfRunNumber
            ACCESS  not-implemented
            DESCRIPTION
                "Not supported."

        VARIATION vRtrIsisInetMtRouteTag
            ACCESS  not-implemented
            DESCRIPTION
                "Not supported."

        VARIATION vRtrIsisInetMtRouteType
            ACCESS  not-implemented
            DESCRIPTION
                "Not supported."


        VARIATION vRtrIsisLoopfreeAlternate  
            ACCESS  not-implemented
            DESCRIPTION
                "Not supported."
                
        VARIATION vRtrIsisMtPathMetric
            ACCESS  not-implemented
            DESCRIPTION
                "Not supported."

        VARIATION vRtrIsisMtPathSNPA
            ACCESS  not-implemented
            DESCRIPTION
                "Not supported."

        VARIATION vRtrIsisRsvpShortcut    
            ACCESS  not-implemented
            DESCRIPTION
                "Not supported."
                
        VARIATION vRtrIsisShortCuts
            ACCESS  not-implemented
            DESCRIPTION
                "Not supported."

        VARIATION vRtrIsisIPv6UnicastImport
            ACCESS  not-implemented
            DESCRIPTION
                "Not supported."

        VARIATION vRtrIsisIPv6MulticastImport
            ACCESS  not-implemented
            DESCRIPTION
                "Not supported."

    ::= { tmnxSASM7210V6v0 10 }
--
--  LDP CAPABILITIES
--
tmnxLdpCapsSASM7210V6v0 AGENT-CAPABILITIES
    PRODUCT-RELEASE "Alcatel SAS-M 7210"
    STATUS current
    DESCRIPTION
        "Implementation of LDP capabilities
         capabilities for Alcatel SAS-M 7210 release R6.0"

    SUPPORTS MPLS-LDP-MIB
        INCLUDES    {
            mplsLdpGeneralGroup,
            mplsLdpNotificationsGroup
            -- EXCLUDE mplsLdpEntityIndexNext
            -- EXCLUDE mplsLdpEntityGenericObjects
            -- EXCLUDE mplsLdpEntityStatsTable
            -- EXCLUDE mplsLdpSessionStatsTable
            -- EXCLUDE mplsLdpSessionUpDownTrapEnable
            -- EXCLUDE mplsFecIndexNext
            -- EXCLUDE mplsFecTable
            -- EXCLUDE mplsLdpSessionInLabelMapTable
            -- EXCLUDE mplsLdpSessionOutLabelMapTable
            -- EXCLUDE mplsLdpSessionXCMapTable
            -- EXCLUDE mplsXCsFecsTable
            -- EXCLUDE mplsLdpSessionPeerAddressTable
            -- EXCLUDE mplsLdpEntityAtmObjects
            -- EXCLUDE mplsLdpAtmSessionTable
            -- EXCLUDE mplsLdpAtmGroup
            -- EXCLUDE mplsLdpEntityFrameRelayObjects
            -- EXCLUDE mplsLdpFrameRelaySessionTable
            -- EXCLUDE mplsLdpFrameRelayGroup
        }

        VARIATION   mplsLdpEntityIndexNext
            ACCESS  not-implemented
            DESCRIPTION
                    "read-only implementation."

        VARIATION   mplsLdpEntityEntry
            CREATION-REQUIRES   { vRtrLdpStatus }
            DESCRIPTION
                    "Row entries cannot be created by SNMP SET requests.

                    Row entries in the mplsLdpEntityTable are created by
                    setting TIMETRA-VRTR-MIB::vRtrLdpStatus to 'create'."

        VARIATION   mplsLdpEntityProtocolVersion
            ACCESS  read-only
            DESCRIPTION
                    "read-only implementation."

        VARIATION   mplsLdpEntityAdminStatus
            ACCESS  read-only
            DESCRIPTION
                    "read-only implementation."

        VARIATION   mplsLdpEntityWellKnownTcpDiscoveryPort
            ACCESS  read-only
            DESCRIPTION
                    "read-only implementation."

        VARIATION   mplsLdpEntityWellKnownUdpDiscoveryPort
            ACCESS  read-only
            DESCRIPTION
                    "read-only implementation."

        VARIATION   mplsLdpEntityMaxPduLength
            ACCESS  read-only
            DESCRIPTION
                    "read-only implementation."

        VARIATION   mplsLdpEntityKeepAliveHoldTimer
            ACCESS  read-only
            DESCRIPTION
                    "read-only implementation."

        VARIATION   mplsLdpEntityHelloHoldTimer
            ACCESS  read-only
            DESCRIPTION
                    "read-only implementation."

        VARIATION   mplsLdpEntityFailedInitSessionTrapEnable
            ACCESS  read-only
            DESCRIPTION
                    "read-only implementation."

        VARIATION   mplsLdpEntityFailedInitSessionThreshold
            ACCESS  read-only
            DESCRIPTION
                    "read-only implementation."

        VARIATION   mplsLdpEntityLabelDistributionMethod
            ACCESS  read-only
            DESCRIPTION
                    "read-only implementation."

        VARIATION   mplsLdpEntityLabelRetentionMode
            ACCESS  read-only
            DESCRIPTION
                    "read-only implementation."

        VARIATION   mplsLdpEntityPVLimitMismatchTrapEnable
            ACCESS  read-only
            DESCRIPTION
                    "read-only implementation."

        VARIATION   mplsLdpEntityPathVectorLimit
            ACCESS  read-only
            DESCRIPTION
                    "read-only implementation."

        VARIATION   mplsLdpEntityHopCountLimit
            ACCESS  read-only
            DESCRIPTION
                    "read-only implementation."

        VARIATION   mplsLdpEntityTargetedPeer
            ACCESS  read-only
            DESCRIPTION
                    "read-only implementation."

        VARIATION   mplsLdpEntityTargetedPeerAddrType
            ACCESS  read-only
            DESCRIPTION
                    "read-only implementation."

        VARIATION   mplsLdpEntityTargetedPeerAddr
            ACCESS  read-only
            DESCRIPTION
                    "read-only implementation."

        VARIATION   mplsLdpEntityOptionalParameters
            ACCESS  read-only
            DESCRIPTION
                    "read-only implementation."

        VARIATION   mplsLdpEntityStorageType
            ACCESS  read-only
            DESCRIPTION
                    "read-only implementation."

        VARIATION   mplsLdpEntityRowStatus
            ACCESS  read-only
            DESCRIPTION
                    "read-only implementation. Row entries cannot be
                     created by SNMP SET requests. LDP Entities are created
                     in TIMETRA-LDP-MIB and this table when
                     TIMETRA-VRTR-MIB::vRtrLdpStatus is set to 'create'."

        VARIATION   mplsLdpAttemptedSessions
            ACCESS  not-implemented
            DESCRIPTION
                    "Not supported. It is implemented through
                     vRtrLdpStatsAttemptedSessions in TIMETRA-LDP-MIB."

        VARIATION   mplsLdpSessionRejectedNoHelloErrors
            ACCESS  not-implemented
            DESCRIPTION
                    "Not supported. It is implemented through
                     vRtrLdpStatsSessRejNoHelloErrors in TIMETRA-LDP-MIB."

        VARIATION   mplsLdpSessionRejectedAdvertisementErrors
            ACCESS  not-implemented
            DESCRIPTION
                    "Not supported. It is implemented through
                     vRtrLdpStatsSessRejAdvErrors in TIMETRA-LDP-MIB."

        VARIATION   mplsLdpSessionRejectedMaxPduErrors
            ACCESS  not-implemented
            DESCRIPTION
                    "Not supported. It is implemented through
                     vRtrLdpStatsSessRejMaxPduErrors in TIMETRA-LDP-MIB."

        VARIATION   mplsLdpSessionRejectedLabelRangeErrors
            ACCESS  not-implemented
            DESCRIPTION
                    "Not supported. It is implemented through
                     vRtrLdpStatsSessRejLabelRangeErrors in TIMETRA-LDP-MIB."

        VARIATION   mplsLdpBadLdpIdentifierErrors
            ACCESS  not-implemented
            DESCRIPTION
                    "Not supported.  It is implemented through
                     vRtrLdpStatsBadLdpIdentifierErrors in TIMETRA-LDP-MIB."

        VARIATION   mplsLdpBadPduLengthErrors
            ACCESS  not-implemented
            DESCRIPTION
                    "Not supported. It is implemented through
                     vRtrLdpStatsBadPduLengthErrors in TIMETRA-LDP-MIB."

        VARIATION   mplsLdpBadMessageLengthErrors
            ACCESS  not-implemented
            DESCRIPTION
                    "Not supported. It is implemented through
                     vRtrLdpStatsBadMessageLengthErrors in TIMETRA-LDP-MIB."

        VARIATION   mplsLdpBadTlvLengthErrors
            ACCESS  not-implemented
            DESCRIPTION
                    "Not supported. It is implemented through
                     vRtrLdpStatsBadTlvLengthErrors in TIMETRA-LDP-MIB."

        VARIATION   mplsLdpMalformedTlvValueErrors
            ACCESS  not-implemented
            DESCRIPTION
                    "Not supported. It is implemented through
                     vRtrLdpStatsMalformedTlvValueErrors in TIMETRA-LDP-MIB."

        VARIATION   mplsLdpKeepAliveTimerExpiredErrors
            ACCESS  not-implemented
            DESCRIPTION
                    "Not supported.  It is implemented through
                     vRtrLdpStatsKeepAliveExpiredErrors in TIMETRA-LDP-MIB."

        VARIATION   mplsLdpShutdownNotifReceived
            ACCESS  not-implemented
            DESCRIPTION
                    "Not supported. It is implemented through
                     vRtrLdpStatsShutdownNotifRecv in TIMETRA-LDP-MIB."

        VARIATION   mplsLdpShutdownNotifSent
            ACCESS  not-implemented
            DESCRIPTION
                    "Not supported. It is implemented through
                     vRtrLdpStatsShutdownNotifSent in TIMETRA-LDP-MIB."

        VARIATION   mplsLdpSessionStatsUnknownMessageTypeErrors
            ACCESS  not-implemented
            DESCRIPTION
                    "Not supported."

        VARIATION   mplsLdpSessionStatsUnknownTlvErrors
            ACCESS  not-implemented
            DESCRIPTION
                    "Not supported."

        VARIATION   mplsFecIndexNext
            ACCESS  not-implemented
            DESCRIPTION
                    "Not supported."

        VARIATION   mplsFecType
            ACCESS  not-implemented
            DESCRIPTION
                    "Not supported."

        VARIATION   mplsFecAddressLength
            ACCESS  not-implemented
            DESCRIPTION
                    "Not supported."

        VARIATION   mplsFecAddressFamily
            ACCESS  not-implemented
            DESCRIPTION
                    "Not supported."

        VARIATION   mplsFecAddress
            ACCESS  not-implemented
            DESCRIPTION
                    "Not supported."

        VARIATION   mplsFecStorageType
            ACCESS  not-implemented
            DESCRIPTION
                    "Not supported."

        VARIATION   mplsFecRowStatus
            ACCESS  not-implemented
            DESCRIPTION
                    "Not supported."

        VARIATION   mplsLdpSessionPeerNextHopAddressType
            ACCESS  not-implemented
            DESCRIPTION
                    "Not supported."

        VARIATION   mplsLdpSessionPeerNextHopAddress
            ACCESS  not-implemented
            DESCRIPTION
                    "Not supported."

        VARIATION   mplsLdpSessionUpDownTrapEnable
            ACCESS  not-implemented
            DESCRIPTION
                    "generation of MPLS LDP traps is controled by the
                    tmnxEventTable in TIMETRA-LOG-MIB."

        VARIATION   mplsLdpFailedInitSessionThresholdExceeded
            ACCESS  not-implemented
            DESCRIPTION
                    "Not supported."

        VARIATION   mplsLdpPathVectorLimitMismatch
            ACCESS  not-implemented
            DESCRIPTION
                    "Not supported."

        VARIATION   mplsLdpSessionUp
            ACCESS  not-implemented
            DESCRIPTION
                    "Not supported."

        VARIATION   mplsLdpSessionDown
            ACCESS  not-implemented
            DESCRIPTION
                    "Not supported."

    SUPPORTS TIMETRA-LDP-MIB
        INCLUDES    {
            tmnxLdpGlobalV5v0Group,
            tmnxLdpIfV5v0Group,
            tmnxLdpAdjR2r1Group,
            tmnxLdpSessionV5v0Group,
            tmnxLdpServFecV6v0Group,
            tmnxLdpAddrFecV5v0Group,
            tmnxLdpNotificationGroup,
            -- tmnxLdpStaticFecV3v0Group,
            -- EXCLUDE vRtrLdpPolicyTable
            -- EXCLUDE vRtrLdpIfTableSpinlock
            -- EXCLUDE vRtrLdpAdjBackoffTable
            -- tmnxLdpAdjBackoffGroup
            -- tmnxLdpCepTdmFecV6v0Group,
            -- tmnxLdpServFec129V6v0Group,
            -- tmnxLdpStatsV7v0Group
            tmnxLdpAggrPreMatchV7v0Group,
            tmnxLdpPeerV7v0Group,
            tmnxLdpGlobalV8v0Group
         -- EXCLUDE vRtrLdpServFecMapTable (obsoleted table)
         -- EXCLUDE vLdpServFec129MapTable (obsoleted table)
        }


        VARIATION   vRtrLdpGenLoopDetectCapable
            ACCESS  read-only
            DESCRIPTION
                    "read-only implementation."

        VARIATION   vRtrLdpGenHopLimit
            ACCESS  read-only
            DESCRIPTION
                    "read-only implementation."

        VARIATION   vRtrLdpGenPathVectorLimit
            ACCESS  read-only
            DESCRIPTION
                    "read-only implementation."

        VARIATION   vRtrLdpGenBackoffTime
            ACCESS  read-only
            DESCRIPTION
                    "read-only implementation."

        VARIATION   vRtrLdpGenMaxBackoffTime
            ACCESS  read-only
            DESCRIPTION
                    "read-only implementation."

        VARIATION   vRtrLdpGenTargPassiveMode
            ACCESS  read-only
            DESCRIPTION
                    "read-only implementation."

        VARIATION   vRtrLdpIfTableSpinlock
            ACCESS  not-implemented
            DESCRIPTION
                    "read-only implementation."

        VARIATION   vRtrLdpIfBackoffTime
            ACCESS  read-only
            DESCRIPTION
                    "read-only implementation."

        VARIATION   vRtrLdpIfMaxBackoffTime
            ACCESS  read-only
            DESCRIPTION
                    "read-only implementation."

        VARIATION   vRtrLdpIfPassiveMode
            ACCESS  read-only
            DESCRIPTION
                    "read-only implementation."

        VARIATION   vRtrLdpPeerTTLLogId
            ACCESS  not-implemented
            DESCRIPTION
                    "vRtrLdpPeerTTLLogId is not implemented."

        VARIATION   vRtrLdpGenTrustList
            ACCESS  not-implemented
            DESCRIPTION
                    "vRtrLdpGenTrustList is not implemented."

        VARIATION   vRtrLdpEgrStatFecPfxRowStatus
            DESCRIPTION
                    "vRtrLdpEgrStatFecPfxRowStatus supports only 'ipv4' indices.
                     If an attempt is made to create a row entry with the 
                     vRtrLdpEgrStatFecPfxAddrType index set to a value other
                     than 'ipv4', a 'noCreation' error will be returned."


        VARIATION   vRtrLdpStatsEgrFecPfxCount
            ACCESS  not-implemented
            DESCRIPTION
                    "Not supported."

        VARIATION   vRtrLdpEgrStatFecPfxTblLastChgd
            ACCESS  not-implemented
            DESCRIPTION
                    "Not supported."

        VARIATION   vRtrLdpTargImportPolicy1
            ACCESS  not-implemented
            DESCRIPTION
                    "Not supported."

        VARIATION   vRtrLdpTargImportPolicy2
            ACCESS  not-implemented
            DESCRIPTION
                    "Not supported."

        VARIATION   vRtrLdpTargImportPolicy3
            ACCESS  not-implemented
            DESCRIPTION
                    "Not supported."

        VARIATION   vRtrLdpTargImportPolicy4
            ACCESS  not-implemented
            DESCRIPTION
                    "Not supported."

        VARIATION   vRtrLdpTargImportPolicy5
            ACCESS  not-implemented
            DESCRIPTION
                    "Not supported."

        VARIATION   vRtrLdpTargExportPolicy1
            ACCESS  not-implemented
            DESCRIPTION
                    "Not supported."

        VARIATION   vRtrLdpTargExportPolicy2
            ACCESS  not-implemented
            DESCRIPTION
                    "Not supported."

        VARIATION   vRtrLdpTargExportPolicy3
            ACCESS  not-implemented
            DESCRIPTION
                    "Not supported."

        VARIATION   vRtrLdpTargExportPolicy4
            ACCESS  not-implemented
            DESCRIPTION
                    "Not supported."

        VARIATION   vRtrLdpTargExportPolicy5
            ACCESS  not-implemented
            DESCRIPTION
                    "Not supported."

        VARIATION   vRtrLdpGenShortTTLPropLocal
            ACCESS  not-implemented
            DESCRIPTION
                    "Not supported."       

        VARIATION   vRtrLdpGenShortTTLPropTransit
            ACCESS  not-implemented
            DESCRIPTION
                    "Not supported."       
                    
    ::= { tmnxSASM7210V6v0 11 }

--
--  MPLS CAPABILITIES
--
tmnxMplsCapsSASM7210V6v0 AGENT-CAPABILITIES
    PRODUCT-RELEASE "Alcatel SAS-M 7210"
    STATUS current
    DESCRIPTION
        "Implementation of MPLS capabilities
         capabilities for Alcatel SAS-M 7210 release R6.0"

    SUPPORTS MPLS-LSR-MIB
        INCLUDES    {
            mplsInSegmentGroup,
            mplsOutSegmentGroup,
            mplsXCGroup,
            mplsInterfaceGroup,
            -- mplsPerfGroup,
            -- mplsSegmentDiscontinuityGroup,
            -- mplsHCInSegmentPerfGroup,
            -- mplsHCOutSegmentPerfGroup,
            mplsTrafficParamGroup,
            -- mplsLabelStackGroup
            mplsXCIsPersistentGroup,
            mplsXCIsNotPersistentGroup,
            mplsLsrNotificationGroup
            -- EXCLUDE mplsInSegmentPerfTable
            -- EXCLUDE mplsOutSegmentPerfTable
            -- EXCLUDE mplsLabelStackTable
            -- EXCLUDE mplsOutSegmentNextHopIpv6Addr
            -- EXCLUDE mplsXCTrapEnable
        }

        VARIATION   mplsTrafficParamMaxRate
            ACCESS  read-only
            DESCRIPTION
                    "read-only implementation."

        VARIATION   mplsTrafficParamMeanRate
            ACCESS  read-only
            DESCRIPTION
                    "read-only implementation."

        VARIATION   mplsTrafficParamMaxBurstSize
            ACCESS  read-only
            DESCRIPTION
                    "read-only implementation."

        VARIATION   mplsTrafficParamRowStatus
            ACCESS  read-only
            DESCRIPTION
                    "read-only implementation."

        VARIATION   mplsTrafficParamStorageType
            ACCESS  read-only
            DESCRIPTION
                    "read-only implementation."

        VARIATION   mplsOutSegmentNextHopIpv6Addr
            ACCESS  not-implemented
            DESCRIPTION
                    "Not supported. No IPv6."

        VARIATION   mplsXCLspId
            ACCESS  read-only
            DESCRIPTION
                    "read-only implementation."

        VARIATION   mplsXCTrapEnable
            ACCESS  not-implemented
            DESCRIPTION
                    "Generation of MPLS traps is controled by the
                    TIMETRA-LOG-MIB tmnxEventTable."

        VARIATION   mplsInSegmentDiscards
            ACCESS  not-implemented
            DESCRIPTION
                    "Not supported."

        VARIATION   mplsInSegmentOctets
            ACCESS  not-implemented
            DESCRIPTION
                    "Not supported."

        VARIATION   mplsOutSegmentDiscards
            ACCESS  not-implemented
            DESCRIPTION
                    "Not supported."

        VARIATION   mplsOutSegmentErrors
            ACCESS  not-implemented
            DESCRIPTION
                    "Not supported."

        VARIATION   mplsOutSegmentOctets
            ACCESS  not-implemented
            DESCRIPTION
                    "Not supported."

    SUPPORTS MPLS-TE-MIB
        INCLUDES    {
            mplsTunnelGroup,
            mplsTunnelManualGroup,
            mplsTunnelSignaledGroup,
            mplsTunnelIsNotIntfcGroup,
            mplsTunnelIsIntfcGroup,
            mplsTunnelOptionalGroup
            -- mplsTeNotificationGroup
            -- EXCLUDE mplsTunnelResourceTable
            -- EXCLUDE mplsTunnelHopIpv6Addr
            -- EXCLUDE mplsTunnelHopIpv6PrefixLen
            -- EXCLUDE mplsTunnelHopAsNumber
            -- EXCLUDE mplsTunnelHopLspId
            -- EXCLUDE mplsTunnelARHopIpv6Addr
            -- EXCLUDE mplsTunnelARHopIpv6PrefixLen
            -- EXCLUDE mplsTunnelTrapEnable           
        }

        VARIATION   mplsTunnelResourcePointer
            ACCESS  read-only
            DESCRIPTION
                    "mplsTunnelResourceTable is not implemented and
                    mplsTunnelResourcePointer always returns the null
                    identifier value { ccitt 0 }."

        VARIATION   mplsTunnelResourceIndexNext
            ACCESS  not-implemented
            DESCRIPTION
                    "Not supported."

        VARIATION   mplsTunnelResourceMaxRate
            ACCESS  not-implemented
            DESCRIPTION
                    "Not supported."

        VARIATION   mplsTunnelResourceMeanRate
            ACCESS  not-implemented
            DESCRIPTION
                    "Not supported."

        VARIATION   mplsTunnelResourceMaxBurstSize
            ACCESS  not-implemented
            DESCRIPTION
                    "Not supported."

        VARIATION   mplsTunnelResourceRowStatus
            ACCESS  not-implemented
            DESCRIPTION
                    "Not supported."

        VARIATION   mplsTunnelResourceStorageType
            ACCESS  not-implemented
            DESCRIPTION
                    "Not supported."

        VARIATION   mplsTunnelEntry
            CREATION-REQUIRES {
                    mplsTunnelRowStatus,
                    mplsTunnelName
            }
            DESCRIPTION
                    "mplsTunnelName must be set for row creation to succeed.
                    The value of these objects cannot be changed after the
                    row entry has been created:
                        mplsTunnelDescr, mplsTunnelIsIf,
                        mplsTunnelSignallingProto, mplsTunnelSetupPrio,
                        mplsTunnelHoldingPrio, mplsTunnelOwner,
                        mplsTunnelLocalProtectInUse, mplsTunnelResourcePointer,
                        mplsTunnelSessionAttributes,
                        mplsTunnelInstancePriority."

        VARIATION   mplsTunnelRowStatus
            SYNTAX  INTEGER {
                        active      (1),
                        createAndGo (4),
                        destroy     (6)
                    }
            DESCRIPTION
                    "mplsTunnelRowStatus supports only the values
                    'active (1)', 'createAndGo (4)' and 'destroy (6)'."

        VARIATION   mplsTunnelHopIpv6Addr
            ACCESS  not-implemented
            DESCRIPTION
                    "Not supported. No IPv6 MPLS."

        VARIATION   mplsTunnelHopIpv6PrefixLen
            ACCESS  not-implemented
            DESCRIPTION
                    "Not supported. No IPv6 MPLS."

        VARIATION   mplsTunnelHopAsNumber
            ACCESS  not-implemented
            DESCRIPTION
                    "Not supported."

        VARIATION   mplsTunnelHopLspId
            ACCESS  not-implemented
            DESCRIPTION
                    "Not supported."

        VARIATION   mplsTunnelARHopIpv6Addr
            ACCESS  not-implemented
            DESCRIPTION
                    "Not supported. No IPv6 MPLS."

        VARIATION   mplsTunnelARHopIpv6PrefixLen
            ACCESS  not-implemented
            DESCRIPTION
                    "Not supported. No IPv6 MPLS."

        VARIATION   mplsTunnelTrapEnable
            ACCESS  not-implemented
            DESCRIPTION
                    "Not supported. Control of MPLS traps is managed using
                     the tmnxEventTable in the TIMETRA-LOG-MIB."

        VARIATION   mplsTunnelHopTableIndex
            ACCESS  read-only
            DESCRIPTION
                    "read-only implementation. The value of
                     mplsTunnelHopTableIndex is the same as mplsTunnelIndex."

        VARIATION   mplsTunnelIsIf
            ACCESS  read-only
            DESCRIPTION
                    "read-only implementation."

        VARIATION   mplsTunnelSignallingProto
            ACCESS  read-only
            DESCRIPTION
                    "read-only implementation."

        VARIATION   mplsTunnelSetupPrio
            ACCESS  read-only
            DESCRIPTION
                    "read-only implementation."

        VARIATION   mplsTunnelHoldingPrio
            ACCESS  read-only
            DESCRIPTION
                    "read-only implementation."

        VARIATION   mplsTunnelSessionAttributes
            ACCESS  read-only
            DESCRIPTION
                    "read-only implementation."

        VARIATION   mplsTunnelOwner
            ACCESS  read-only
            DESCRIPTION
                    "read-only implementation."

        VARIATION   mplsTunnelLocalProtectInUse
            ACCESS  read-only
            DESCRIPTION
                    "read-only implementation."

        VARIATION   mplsTunnelInstancePriority
            ACCESS  read-only
            DESCRIPTION
                    "read-only implementation."
        
        VARIATION   mplsTunnelName
            SYNTAX  DisplayString (SIZE(0..32))
            DESCRIPTION
                    "The maximum length supported for the mplsTunnelName is 32
                     characters."  

    SUPPORTS TIMETRA-MPLS-MIB
        INCLUDES    {
            tmnxMplsGlobalV6v0Group,
            tmnxMplsLspV5v0Group,
            -- tmnxMplsLspPathV6v0Group,
            tmnxMplsXCGroup,
            tmnxMplsIfGroup,
            tmnxMplsTunnelARHopGroup,
            tmnxMplsTunnelCHopGroup,
            tmnxMplsAdminGroupGroup,
            -- tmnxMplsFSGroupGroup,
            tmnxMplsNotificationR2r1Group,
            tmnxMplsLabelRangeGroup,
            -- tmnxMplsSrlgV6v0Group,
            tmnxMplsLspPathV6v1Group,
            tmnxMplsIfV6v0Group,
            tmnxMplsLspV6v0Group,
            tmnxMplsLspV7v0Group,
            tmnxMplsGlobalV7v0Group,
            tmnxMplsNotificationV7v0Group,
            tmnxMplsLspPathV7v0Group
            -- tmnxMplsSrlgV7v0Group
        }

        VARIATION   vRtrMplsLspPathTableSpinlock
            ACCESS  not-implemented
            DESCRIPTION
                    "vRtrMplsLspPathTableSpinlock was intended to be used
                    for control of changes to inherited attributes. There
                    are no inherited attributes in the base version of
                    MPLS on Alcatel SAS-M 7210 systems."

        VARIATION   vRtrMplsLspDecrementTtl
            ACCESS  read-only
            DESCRIPTION
                    "read-only implementation."

        VARIATION   vRtrMplsLspClassOfService
            ACCESS  read-only
            DESCRIPTION
                    "read-only implementation."

        VARIATION   vRtrMplsLspSetupPriority
            ACCESS  read-only
            DESCRIPTION
                    "read-only implementation."

        VARIATION   vRtrMplsLspHoldPriority
            ACCESS  read-only
            DESCRIPTION
                    "read-only implementation."

        VARIATION   vRtrMplsLspRecord
            ACCESS  read-only
            DESCRIPTION
                    "read-only implementation."

        VARIATION   vRtrMplsLspBandwidth
            ACCESS  read-only
            DESCRIPTION
                    "read-only implementation."

        VARIATION   vRtrMplsLspOptimizeTimer
            ACCESS  read-only
            DESCRIPTION
                    "read-only implementation."

        VARIATION   vRtrMplsLspFRObject
            ACCESS  read-only
            DESCRIPTION
                    "read-only implementation."

        VARIATION   vRtrMplsLspPathCos
            ACCESS  read-only
            DESCRIPTION
                    "read-only implementation."

        VARIATION   vRtrMplsLspPathCosSource
            ACCESS  read-only
            DESCRIPTION
                    "read-only implementation."

        VARIATION   vRtrMplsLspPathClassOfService
            ACCESS  read-only
            DESCRIPTION
                    "read-only implementation."

        VARIATION   vRtrMplsLspPathOptimizeTimer
            ACCESS  read-only
            DESCRIPTION
                    "read-only implementation."

        VARIATION   vRtrMplsGeneralPropagateTtl
            ACCESS  read-only
            DESCRIPTION
                    "read-only implementation."

        VARIATION   vRtrMplsGeneralTE
            ACCESS  read-only
            DESCRIPTION
                    "read-only implementation."

        VARIATION   vRtrMplsGeneralOptimizeTimer
            ACCESS  read-only
            DESCRIPTION
                    "read-only implementation."

        VARIATION   vRtrMplsLspBwProtect
            ACCESS  read-only
            DESCRIPTION
                    "read-only implementation."

        VARIATION   vRtrMplsLspPathBwProtect
            ACCESS  read-only
            DESCRIPTION
                    "read-only implementation."

        VARIATION   vRtrMplsLspPreference
            ACCESS  read-only
            DESCRIPTION
                    "read-only implementation."

        VARIATION   vRtrMplsLspPathPreference
            ACCESS  read-only
            DESCRIPTION
                    "read-only implementation."

        VARIATION   vRtrMplsLspPathSharing
            ACCESS  read-only
            DESCRIPTION
                    "read-only implementation."

        VARIATION   vRtrMplsLspOctets
            ACCESS  not-implemented
            DESCRIPTION
                    "Not supported."

        VARIATION   vRtrMplsLspPackets
            ACCESS  not-implemented
            DESCRIPTION
                    "Not supported."    

        VARIATION   vRtrMplsLspP2mpId
            ACCESS  not-implemented
            DESCRIPTION 
                    "Not supported."

        VARIATION   vRtrMplsLspClassType
            ACCESS  not-implemented
            DESCRIPTION 
                    "Not supported."

        VARIATION   vRtrMplsLspLeastFill
            ACCESS  not-implemented
            DESCRIPTION 
                    "Not supported."

        VARIATION   vRtrMplsLspConfP2mpInstances
            ACCESS  not-implemented
            DESCRIPTION 
                    "Not supported."

        VARIATION   vRtrMplsGeneralNewP2mpInstIndex
            ACCESS  not-implemented
            DESCRIPTION 
                    "Not supported."

        VARIATION   vRtrMplsGeneralS2lOriginate
            ACCESS  not-implemented
            DESCRIPTION 
                    "Not supported."

        VARIATION   vRtrMplsGeneralS2lTransit
            ACCESS  not-implemented
            DESCRIPTION 
                    "Not supported."

        VARIATION   vRtrMplsGeneralS2lTerminate
            ACCESS  not-implemented
            DESCRIPTION 
                    "Not supported."

        VARIATION   vRtrMplsInSegmentNumS2ls
            ACCESS  not-implemented
            DESCRIPTION 
                    "Not supported."

        VARIATION   vRtrMplsOutSegmentNumS2ls
            ACCESS  not-implemented
            DESCRIPTION 
                    "Not supported."

        VARIATION   vRtrMplsGeneralP2mpResigTimer
            ACCESS  not-implemented
            DESCRIPTION 
                    "Not supported."

        VARIATION   vRtrMplsGeneralP2mpNextResignal
            ACCESS  not-implemented
            DESCRIPTION 
                    "Not supported."

        VARIATION   vRtrMplsLspP2mpId
            ACCESS  not-implemented
            DESCRIPTION 
                    "Not supported."

        VARIATION   vRtrMplsLspConfP2mpInstances
            ACCESS  not-implemented
            DESCRIPTION 
                    "Not supported."

        VARIATION   vRtrMplsGeneralNewP2mpInstIndex
            ACCESS  not-implemented
            DESCRIPTION 
                    "Not supported."

        VARIATION   vRtrMplsGeneralS2lOriginate
            ACCESS  not-implemented
            DESCRIPTION 
                    "Not supported."

        VARIATION   vRtrMplsGeneralS2lTransit
            ACCESS  not-implemented
            DESCRIPTION 
                    "Not supported."

        VARIATION   vRtrMplsGeneralS2lTerminate
            ACCESS  not-implemented
            DESCRIPTION 
                    "Not supported."

        VARIATION   vRtrMplsInSegmentNumS2ls
            ACCESS  not-implemented
            DESCRIPTION 
                    "Not supported."

        VARIATION   vRtrMplsOutSegmentNumS2ls
            ACCESS  not-implemented
            DESCRIPTION 
                    "Not supported."

        VARIATION   vRtrMplsGeneralP2mpResigTimer
            ACCESS  not-implemented
            DESCRIPTION 
                    "Not supported."

        VARIATION   vRtrMplsGeneralP2mpNextResignal
            ACCESS  not-implemented
            DESCRIPTION 
                    "Not supported."

        VARIATION   vRtrMplsLspPathClassType
            ACCESS  not-implemented
            DESCRIPTION 
                    "Not supported."

         VARIATION   vRtrMplsLspTemplateName 
            ACCESS  not-implemented
            DESCRIPTION 
                    "Not supported."            

         VARIATION   vRtrMplsLspTemplateRowStatus 
            ACCESS  not-implemented
            DESCRIPTION 
                    "Not supported."          

         VARIATION   vRtrMplsLspTemplateLastChanged 
            ACCESS  not-implemented
            DESCRIPTION 
                    "Not supported."          

         VARIATION   vRtrMplsLspTemplateAdminState
            ACCESS  not-implemented
            DESCRIPTION 
                    "Not supported."          

         VARIATION   vRtrMplsLspTemplateType
            ACCESS  not-implemented
            DESCRIPTION 
                    "Not supported."          

         VARIATION   vRtrMplsLspTemplateAdaptive 
            ACCESS  not-implemented
            DESCRIPTION 
                    "Not supported."          

          VARIATION    vRtrMplsLspTemplateBandwidth 
            ACCESS  not-implemented
            DESCRIPTION 
                    "Not supported."          

          VARIATION   vRtrMplsLspTemplateCspf 
            ACCESS  not-implemented
            DESCRIPTION 
                    "Not supported."   

          VARIATION   vRtrMplsLspTemplateDefaultPath
            ACCESS  not-implemented
            DESCRIPTION 
                    "Not supported."            

         VARIATION   vRtrMplsLspTemplateAdmGrpIncl
            ACCESS  not-implemented
            DESCRIPTION 
                    "Not supported."       
        
        VARIATION   vRtrMplsLspTemplateAdmGrpExcl 
            ACCESS  not-implemented
            DESCRIPTION 
                    "Not supported."            

            VARIATION   vRtrMplsLspTemplateFastReroute
            ACCESS  not-implemented
            DESCRIPTION 
                    "Not supported."            

         VARIATION    vRtrMplsLspTemplateFRMethod 
            ACCESS  not-implemented
            DESCRIPTION 
                    "Not supported."          

         VARIATION    vRtrMplsLspTemplateFRHopLimit
            ACCESS  not-implemented
            DESCRIPTION 
                    "Not supported."          

         VARIATION   vRtrMplsLspTemplateHopLimit
            ACCESS  not-implemented
            DESCRIPTION 
                    "Not supported."          

         VARIATION   vRtrMplsLspTemplateRecord 
            ACCESS  not-implemented
            DESCRIPTION 
                    "Not supported."          

         VARIATION    vRtrMplsLspTemplateRecordLabel
            ACCESS  not-implemented
            DESCRIPTION 
                    "Not supported."          

          VARIATION   vRtrMplsLspTemplateRetryLimit 
            ACCESS  not-implemented
            DESCRIPTION 
                    "Not supported."          

          VARIATION    vRtrMplsLspTemplateRetryTimer 
            ACCESS  not-implemented
            DESCRIPTION 
                    "Not supported."   

          VARIATION   vRtrMplsLspTemplateCspfTeMetric
            ACCESS  not-implemented
            DESCRIPTION 
                    "Not supported."            

         VARIATION    vRtrMplsLspTemplateLspCount
            ACCESS  not-implemented
            DESCRIPTION 
                    "Not supported."       
        
        VARIATION   vRtrMplsLspTemplateMvpnRefCount 
            ACCESS  not-implemented
            DESCRIPTION 
                    "Not supported."                        


        VARIATION   vRtrMplsGeneralLeastFillMinThd
            ACCESS  not-implemented
            DESCRIPTION 
                    "Not supported."

        VARIATION   vRtrMplsGenLeastFillReoptiThd
            ACCESS  not-implemented
            DESCRIPTION 
                    "Not supported."


    ::= { tmnxSASM7210V6v0 12 }

--
--  NOTIFICATION LOG CAPABILITIES
--
tmnxNotificationCapsSASM7210V6v0 AGENT-CAPABILITIES
    PRODUCT-RELEASE "Alcatel SAS-M 7210"
    STATUS current
    DESCRIPTION
        "Implementation of DISMAN Notification Log
         capabilities for Alcatel SAS-M 7210 release R6.0"

    SUPPORTS NOTIFICATION-LOG-MIB
        INCLUDES    {
            notificationLogConfigGroup,
            notificationLogStatsGroup,
            notificationLogLogGroup,
            notificationLogDateGroup
        }

        VARIATION   nlmConfigGlobalEntryLimit
            ACCESS  read-only
            DESCRIPTION
                    "read-only implementation."

        VARIATION   nlmConfigGlobalAgeOut
            ACCESS  read-only
            DESCRIPTION
                    "read-only implementation."

        VARIATION   nlmConfigLogStorageType
            ACCESS  read-only
            DESCRIPTION
                    "read-only implementation."

        VARIATION   nlmConfigLogEntryStatus
            SYNTAX  INTEGER {
                        active (1)
                    }
            ACCESS  read-only
            DESCRIPTION
                    "read-only implementation. Row entries cannot be created
                     by SNMP SET requests. Notification logs are created using
                     the TIMETRA-LOG-MIB."

    ::= { tmnxSASM7210V6v0 13 }

--
--  OSPF CAPABILITIES
--
tmnxOspfCapsSASM7210V6v0 AGENT-CAPABILITIES
    PRODUCT-RELEASE "Alcatel SAS-M 7210"
    STATUS current
    DESCRIPTION
        "Implementation of OSPF
         capabilities for Alcatel SAS-M 7210 release R6.0"

    SUPPORTS OSPF-MIB
        INCLUDES    {
            ospfBasicGroup2,
            ospfAreaGroup2,
            ospfStubAreaGroup,
            ospfIfGroup2,
            ospfIfMetricGroup,
            ospfVirtIfGroup2,
            ospfNbrGroup2,
            ospfVirtNbrGroup2,
            ospfAreaAggregateGroup2,
            ospfHostGroup2,
            ospfLsdbGroup,
            ospfLocalLsdbGroup,
            ospfVirtLocalLsdbGroup,
            ospfAsLsdbGroup
            -- EXCLUDE ospfAuthType  (obsolete)
            -- EXCLUDE ospfAreaRangeTable (obsolete)
            -- EXCLUDE ospfExtLsdbTable (replaced with ospfAsLsdbTable)
            -- EXCLUDE ospfAreaLsaCountTable (not supported)
        }

        VARIATION   ospfRouterId
            ACCESS  read-only
            DESCRIPTION
                    "read-only implementation."

        VARIATION   ospfAdminStat
            ACCESS  read-only
            DESCRIPTION
                    "read-only implementation."

        VARIATION   ospfVersionNumber
            ACCESS  read-only
            DESCRIPTION
                    "read-only implementation."

        VARIATION   ospfAreaBdrRtrStatus
            ACCESS  read-only
            DESCRIPTION
                    "read-only implementation."

        VARIATION   ospfASBdrRtrStatus
            ACCESS  read-only
            DESCRIPTION
                    "read-only implementation."

        VARIATION   ospfExternLsaCount
            ACCESS  read-only
            DESCRIPTION
                    "read-only implementation."

        VARIATION   ospfExternLsaCksumSum
            ACCESS  read-only
            DESCRIPTION
                    "read-only implementation."

        VARIATION   ospfTOSSupport
            ACCESS  read-only
            DESCRIPTION
                    "read-only implementation."

        VARIATION   ospfOriginateNewLsas
            ACCESS  read-only
            DESCRIPTION
                    "read-only implementation."

        VARIATION   ospfRxNewLsas
            ACCESS  read-only
            DESCRIPTION
                    "read-only implementation."

        VARIATION   ospfExtLsdbLimit
            ACCESS  read-only
            DESCRIPTION
                    "read-only implementation."

        VARIATION   ospfMulticastExtensions
            ACCESS  read-only
            DESCRIPTION
                    "read-only implementation."

        VARIATION   ospfExitOverflowInterval
            ACCESS  read-only
            DESCRIPTION
                    "read-only implementation."   

        VARIATION   ospfDemandExtensions
            ACCESS  read-only
            DESCRIPTION
                    "read-only implementation."

        VARIATION   ospfRFC1583Compatibility
            ACCESS  read-only
            DESCRIPTION
                    "read-only implementation."

        VARIATION   ospfOpaqueLsaSupport
            ACCESS  read-only
            DESCRIPTION
                    "read-only implementation."

        VARIATION   ospfReferenceBandwidth
            ACCESS  read-only
            DESCRIPTION
                    "read-only implementation."

        VARIATION   ospfRestartSupport
            ACCESS  read-only
            DESCRIPTION
                    "read-only implementation."

        VARIATION   ospfRestartInterval
            ACCESS  read-only
            DESCRIPTION
                    "read-only implementation."

        VARIATION   ospfRestartStrictLsaChecking
            ACCESS  read-only
            DESCRIPTION
                    "read-only implementation."

        VARIATION   ospfRestartStatus
            ACCESS  read-only
            DESCRIPTION
                    "read-only implementation."

        VARIATION   ospfRestartAge
            ACCESS  read-only
            DESCRIPTION
                    "read-only implementation."

        VARIATION   ospfRestartExitReason
            ACCESS  read-only
            DESCRIPTION
                    "read-only implementation."   

        VARIATION   ospfAsLsaCount
            ACCESS  read-only
            DESCRIPTION
                    "read-only implementation."

        VARIATION   ospfAsLsaCksumSum
            ACCESS  read-only
            DESCRIPTION
                    "read-only implementation."

        VARIATION   ospfStubRouterSupport
            ACCESS  read-only
            DESCRIPTION
                    "read-only implementation."

        VARIATION   ospfStubRouterAdvertisement
            ACCESS  read-only
            DESCRIPTION
                    "read-only implementation."

        VARIATION   ospfDiscontinuityTime
            ACCESS  read-only
            DESCRIPTION
                    "read-only implementation."

        VARIATION   ospfAreaId
            ACCESS  read-only
            DESCRIPTION
                    "read-only implementation."

        VARIATION   ospfImportAsExtern
            ACCESS  read-only
            DESCRIPTION
                    "read-only implementation."

        VARIATION   ospfSpfRuns
            ACCESS  read-only
            DESCRIPTION
                    "read-only implementation."

        VARIATION   ospfAreaBdrRtrCount
            ACCESS  read-only
            DESCRIPTION
                    "read-only implementation."

        VARIATION   ospfAsBdrRtrCount
            ACCESS  read-only
            DESCRIPTION
                    "read-only implementation."

        VARIATION   ospfAreaLsaCount
            ACCESS  read-only
            DESCRIPTION
                    "read-only implementation."

        VARIATION   ospfAreaLsaCksumSum
            ACCESS  read-only
            DESCRIPTION
                    "read-only implementation."

        VARIATION   ospfAreaSummary
            ACCESS  read-only
            DESCRIPTION
                    "read-only implementation."

        VARIATION   ospfAreaStatus
            ACCESS  read-only
            DESCRIPTION
                    "read-only implementation."

        VARIATION   ospfAreaNssaTranslatorRole
            ACCESS  read-only
            DESCRIPTION
                    "read-only implementation."

        VARIATION   ospfAreaNssaTranslatorState
            ACCESS  read-only
            DESCRIPTION
                    "read-only implementation."

        VARIATION   ospfAreaNssaTranslatorStabilityInterval
            ACCESS  read-only
            DESCRIPTION
                    "read-only implementation."

        VARIATION   ospfAreaNssaTranslatorEvents
            ACCESS  read-only
            DESCRIPTION
                    "read-only implementation."

        VARIATION   ospfStubAreaId
            ACCESS  read-only
            DESCRIPTION
                    "read-only implementation."

        VARIATION   ospfStubTOS
            ACCESS  read-only
            DESCRIPTION
                    "read-only implementation."

        VARIATION   ospfStubMetric
            ACCESS  read-only
            DESCRIPTION
                    "read-only implementation."

        VARIATION   ospfStubStatus
            ACCESS  read-only
            DESCRIPTION
                    "read-only implementation."

        VARIATION   ospfStubMetricType
            ACCESS  read-only
            DESCRIPTION
                    "read-only implementation."

        VARIATION   ospfLsdbAreaId
            ACCESS  read-only
            DESCRIPTION
                    "read-only implementation."

        VARIATION   ospfLsdbType
            ACCESS  read-only
            DESCRIPTION
                    "read-only implementation."

        VARIATION   ospfLsdbLsid
            ACCESS  read-only
            DESCRIPTION
                    "read-only implementation."

        VARIATION   ospfLsdbRouterId
            ACCESS  read-only
            DESCRIPTION
                    "read-only implementation."

        VARIATION   ospfLsdbSequence
            ACCESS  read-only
            DESCRIPTION
                    "read-only implementation."

        VARIATION   ospfLsdbAge
            ACCESS  read-only
            DESCRIPTION
                    "read-only implementation."

        VARIATION   ospfLsdbChecksum
            ACCESS  read-only
            DESCRIPTION
                    "read-only implementation."

        VARIATION   ospfLsdbAdvertisement
            ACCESS  read-only
            DESCRIPTION
                    "read-only implementation."

        VARIATION   ospfAreaRangeAreaId
            ACCESS  read-only
            DESCRIPTION
                    "read-only implementation."

        VARIATION   ospfAreaRangeNet
            ACCESS  read-only
            DESCRIPTION
                    "read-only implementation."

        VARIATION   ospfAreaRangeMask
            ACCESS  read-only
            DESCRIPTION
                    "read-only implementation."

        VARIATION   ospfAreaRangeStatus
            ACCESS  read-only
            DESCRIPTION
                    "read-only implementation."

        VARIATION   ospfAreaRangeEffect
            ACCESS  read-only
            DESCRIPTION
                    "read-only implementation."

        VARIATION   ospfHostIpAddress
            ACCESS  read-only
            DESCRIPTION
                    "read-only implementation."

        VARIATION   ospfHostTOS
            ACCESS  read-only
            DESCRIPTION
                    "read-only implementation."

        VARIATION   ospfHostMetric
            ACCESS  read-only
            DESCRIPTION
                    "read-only implementation."

        VARIATION   ospfHostStatus
            ACCESS  read-only
            DESCRIPTION
                    "read-only implementation."

        VARIATION   ospfHostAreaID
            ACCESS  read-only
            DESCRIPTION
                    "read-only implementation."

        VARIATION   ospfHostCfgAreaID
            ACCESS  read-only
            DESCRIPTION
                    "read-only implementation."

        VARIATION   ospfIfIpAddress
            ACCESS  read-only
            DESCRIPTION
                    "read-only implementation."

        VARIATION   ospfAddressLessIf
            ACCESS  read-only
            DESCRIPTION
                    "read-only implementation."

        VARIATION   ospfIfAreaId
            ACCESS  read-only
            DESCRIPTION
                    "read-only implementation."

        VARIATION   ospfIfType
            ACCESS  read-only
            DESCRIPTION
                    "read-only implementation."

        VARIATION   ospfIfAdminStat
            ACCESS  read-only
            DESCRIPTION
                    "read-only implementation."

        VARIATION   ospfIfRtrPriority
            ACCESS  read-only
            DESCRIPTION
                    "read-only implementation."

        VARIATION   ospfIfTransitDelay
            ACCESS  read-only
            DESCRIPTION
                    "read-only implementation."

        VARIATION   ospfIfRetransInterval
            ACCESS  read-only
            DESCRIPTION
                    "read-only implementation."

        VARIATION   ospfIfHelloInterval
            ACCESS  read-only
            DESCRIPTION
                    "read-only implementation."

        VARIATION   ospfIfRtrDeadInterval
            ACCESS  read-only
            DESCRIPTION
                    "read-only implementation."

        VARIATION   ospfIfPollInterval
            ACCESS  read-only
            DESCRIPTION
                    "read-only implementation."

        VARIATION   ospfIfState
            ACCESS  read-only
            DESCRIPTION
                    "read-only implementation."

        VARIATION   ospfIfDesignatedRouter
            ACCESS  read-only
            DESCRIPTION
                    "read-only implementation."

        VARIATION   ospfIfBackupDesignatedRouter
            ACCESS  read-only
            DESCRIPTION
                    "read-only implementation."

        VARIATION   ospfIfEvents
            ACCESS  read-only
            DESCRIPTION
                    "read-only implementation."

        VARIATION   ospfIfAuthType
            ACCESS  read-only
            DESCRIPTION
                    "read-only implementation."

        VARIATION   ospfIfAuthKey
            ACCESS  read-only
            DESCRIPTION
                    "read-only implementation."

        VARIATION   ospfIfStatus
            ACCESS  read-only
            DESCRIPTION
                    "read-only implementation."

        VARIATION   ospfIfMulticastForwarding
            ACCESS  read-only
            DESCRIPTION
                    "read-only implementation."

        VARIATION   ospfIfDemand
            ACCESS  read-only
            DESCRIPTION
                    "read-only implementation."

        VARIATION   ospfIfLsaCount
            ACCESS  read-only
            DESCRIPTION
                    "read-only implementation."

        VARIATION   ospfIfLsaCksumSum
            ACCESS  read-only
            DESCRIPTION
                    "read-only implementation."

        VARIATION   ospfIfMetricIpAddress
            ACCESS  read-only
            DESCRIPTION
                    "read-only implementation."

        VARIATION   ospfIfMetricAddressLessIf
            ACCESS  read-only
            DESCRIPTION
                    "read-only implementation."

        VARIATION   ospfIfMetricTOS
            ACCESS  read-only
            DESCRIPTION
                    "read-only implementation."

        VARIATION   ospfIfMetricValue
            ACCESS  read-only
            DESCRIPTION
                    "read-only implementation."

        VARIATION   ospfIfMetricStatus
            ACCESS  read-only
            DESCRIPTION
                    "read-only implementation."

        VARIATION   ospfVirtIfAreaId
            ACCESS  read-only
            DESCRIPTION
                    "read-only implementation."

        VARIATION   ospfVirtIfNeighbor
            ACCESS  read-only
            DESCRIPTION
                    "read-only implementation."

        VARIATION   ospfVirtIfTransitDelay
            ACCESS  read-only
            DESCRIPTION
                    "read-only implementation."

        VARIATION   ospfVirtIfRetransInterval
            ACCESS  read-only
            DESCRIPTION
                    "read-only implementation."

        VARIATION   ospfVirtIfHelloInterval
            ACCESS  read-only
            DESCRIPTION
                    "read-only implementation."

        VARIATION   ospfVirtIfRtrDeadInterval
            ACCESS  read-only
            DESCRIPTION
                    "read-only implementation."

        VARIATION   ospfVirtIfState
            ACCESS  read-only
            DESCRIPTION
                    "read-only implementation."

        VARIATION   ospfVirtIfEvents
            ACCESS  read-only
            DESCRIPTION
                    "read-only implementation."

        VARIATION   ospfVirtIfAuthType
            ACCESS  read-only
            DESCRIPTION
                    "read-only implementation."

        VARIATION   ospfVirtIfAuthKey
            ACCESS  read-only
            DESCRIPTION
                    "read-only implementation."

        VARIATION   ospfVirtIfStatus
            ACCESS  read-only
            DESCRIPTION
                    "read-only implementation."

        VARIATION   ospfVirtIfLsaCount
            ACCESS  read-only
            DESCRIPTION
                    "read-only implementation."

        VARIATION   ospfVirtIfLsaCksumSum
            ACCESS  read-only
            DESCRIPTION
                    "read-only implementation."

        VARIATION   ospfIfDesignatedRouterId
            ACCESS  read-only
            DESCRIPTION
                    "read-only implementation."

        VARIATION   ospfIfBackupDesignatedRouterId
            ACCESS  read-only
            DESCRIPTION
                    "read-only implementation."

        VARIATION   ospfNbrIpAddr
            ACCESS  read-only
            DESCRIPTION
                    "read-only implementation."

        VARIATION   ospfNbrAddressLessIndex
            ACCESS  read-only
            DESCRIPTION
                    "read-only implementation."

        VARIATION   ospfNbrRtrId
            ACCESS  read-only
            DESCRIPTION
                    "read-only implementation."

        VARIATION   ospfNbrOptions
            ACCESS  read-only
            DESCRIPTION
                    "read-only implementation."

        VARIATION   ospfNbrPriority
            ACCESS  read-only
            DESCRIPTION
                    "read-only implementation."

        VARIATION   ospfNbrState
            ACCESS  read-only
            DESCRIPTION
                    "read-only implementation."

        VARIATION   ospfNbrEvents
            ACCESS  read-only
            DESCRIPTION
                    "read-only implementation."

        VARIATION   ospfNbrLsRetransQLen
            ACCESS  read-only
            DESCRIPTION
                    "read-only implementation."

        VARIATION   ospfNbmaNbrStatus
            ACCESS  read-only
            DESCRIPTION
                    "read-only implementation."

        VARIATION   ospfNbmaNbrPermanence
            ACCESS  read-only
            DESCRIPTION
                    "read-only implementation."

        VARIATION   ospfNbrHelloSuppressed
            ACCESS  read-only
            DESCRIPTION
                    "read-only implementation."

        VARIATION   ospfNbrRestartHelperStatus
            ACCESS  read-only
            DESCRIPTION
                    "read-only implementation."

        VARIATION   ospfNbrRestartHelperAge
            ACCESS  read-only
            DESCRIPTION
                    "read-only implementation."

        VARIATION   ospfNbrRestartHelperExitReason
            ACCESS  read-only
            DESCRIPTION
                    "read-only implementation."

        VARIATION   ospfVirtNbrArea
            ACCESS  read-only
            DESCRIPTION
                    "read-only implementation."

        VARIATION   ospfVirtNbrRtrId
            ACCESS  read-only
            DESCRIPTION
                    "read-only implementation."

        VARIATION   ospfVirtNbrIpAddr
            ACCESS  read-only
            DESCRIPTION
                    "read-only implementation."

        VARIATION   ospfVirtNbrOptions
            ACCESS  read-only
            DESCRIPTION
                    "read-only implementation."

        VARIATION   ospfVirtNbrState
            ACCESS  read-only
            DESCRIPTION
                    "read-only implementation."

        VARIATION   ospfVirtNbrEvents
            ACCESS  read-only
            DESCRIPTION
                    "read-only implementation."

        VARIATION   ospfVirtNbrLsRetransQLen
            ACCESS  read-only
            DESCRIPTION
                    "read-only implementation."

        VARIATION   ospfVirtNbrHelloSuppressed
            ACCESS  read-only
            DESCRIPTION
                    "read-only implementation."

        VARIATION   ospfVirtNbrRestartHelperStatus
            ACCESS  read-only
            DESCRIPTION
                    "read-only implementation."

        VARIATION   ospfVirtNbrRestartHelperAge
            ACCESS  read-only
            DESCRIPTION
                    "read-only implementation."

        VARIATION   ospfVirtNbrRestartHelperExitReason
            ACCESS  read-only
            DESCRIPTION
                    "read-only implementation."

        VARIATION   ospfExtLsdbType
            ACCESS  read-only
            DESCRIPTION
                    "read-only implementation."

        VARIATION   ospfExtLsdbLsid
            ACCESS  read-only
            DESCRIPTION
                    "read-only implementation."

        VARIATION   ospfExtLsdbRouterId
            ACCESS  read-only
            DESCRIPTION
                    "read-only implementation."

        VARIATION   ospfExtLsdbSequence
            ACCESS  read-only
            DESCRIPTION
                    "read-only implementation."

        VARIATION   ospfExtLsdbAge
            ACCESS  read-only
            DESCRIPTION
                    "read-only implementation."

        VARIATION   ospfExtLsdbChecksum
            ACCESS  read-only
            DESCRIPTION
                    "read-only implementation."

        VARIATION   ospfExtLsdbAdvertisement
            ACCESS  read-only
            DESCRIPTION
                    "read-only implementation."

        VARIATION   ospfAreaAggregateAreaID
            ACCESS  read-only
            DESCRIPTION
                    "read-only implementation."

        VARIATION   ospfAreaAggregateLsdbType
            ACCESS  read-only
            DESCRIPTION
                    "read-only implementation."

        VARIATION   ospfAreaAggregateNet
            ACCESS  read-only
            DESCRIPTION
                    "read-only implementation."

        VARIATION   ospfAreaAggregateMask
            ACCESS  read-only
            DESCRIPTION
                    "read-only implementation."

        VARIATION   ospfAreaAggregateStatus
            ACCESS  read-only
            DESCRIPTION
                    "read-only implementation."

        VARIATION   ospfAreaAggregateEffect
            ACCESS  read-only
            DESCRIPTION
                    "read-only implementation."

        VARIATION   ospfAreaAggregateExtRouteTag
            ACCESS  read-only
            DESCRIPTION
                    "read-only implementation."

        VARIATION   ospfLocalLsdbSequence
            ACCESS  read-only
            DESCRIPTION
                    "read-only implementation."

        VARIATION   ospfLocalLsdbAge
            ACCESS  read-only
            DESCRIPTION
                    "read-only implementation."

        VARIATION   ospfLocalLsdbChecksum
            ACCESS  read-only
            DESCRIPTION
                    "read-only implementation."

        VARIATION   ospfLocalLsdbAdvertisement
            ACCESS  read-only
            DESCRIPTION
                    "read-only implementation."

        VARIATION   ospfVirtLocalLsdbSequence
            ACCESS  read-only
            DESCRIPTION
                    "read-only implementation."

        VARIATION   ospfVirtLocalLsdbAge
            ACCESS  read-only
            DESCRIPTION
                    "read-only implementation."

        VARIATION   ospfVirtLocalLsdbChecksum
            ACCESS  read-only
            DESCRIPTION
                    "read-only implementation."

        VARIATION   ospfVirtLocalLsdbAdvertisement
            ACCESS  read-only
            DESCRIPTION
                    "read-only implementation."

        VARIATION   ospfAsLsdbSequence
            ACCESS  read-only
            DESCRIPTION
                    "read-only implementation."

        VARIATION   ospfAsLsdbAge
            ACCESS  read-only
            DESCRIPTION
                    "read-only implementation."

        VARIATION   ospfAsLsdbChecksum
            ACCESS  read-only
            DESCRIPTION
                    "read-only implementation."

        VARIATION   ospfAsLsdbAdvertisement
            ACCESS  read-only
            DESCRIPTION
                    "read-only implementation."

        VARIATION   ospfAreaLsaCountNumber
            ACCESS  read-only
            DESCRIPTION
                    "read-only implementation."

    SUPPORTS OSPF-TRAP-MIB
        INCLUDES    {
            ospfTrapControlGroup,
            ospfTrapEventGroup
        }

        VARIATION   ospfSetTrap
            ACCESS  read-only
            DESCRIPTION
                    "ospfSetTrap is implemented as read-only. The generation
                    of OSPF notifications is controled by tmnxEventTable
                    in the TIMETRA-LOG-MIB."

    SUPPORTS TIMETRA-OSPF-NG-MIB
        INCLUDES    {
            tmnxOspfGeneralV5v0Group,
            tmnxOspfAreaGroup,
            tmnxOspfHostGroup,
            tmnxOspfIfV5v0Group,
            tmnxOspfVirtIfGroup,
            tmnxOspfNbrGroup,
            tmnxOspfVirtNbrGroup,
            tmnxOspfAreaAggrGroup,
            tmnxOspfMD5KeyGroup,
            tmnxOspfNotifyObjsGroup,
            tmnxOspfNotificationGroup,
            tmnxOspfIfV6v0Group,
            tmnxOspfGeneralV6v0Group,
            tmnxOspfGeneralV6v1Group,
            tmnxOspfNotificationV6v0Group
        }

        VARIATION tmnxOspfAdvertiseTunnelLink
         ACCESS  not-implemented
         DESCRIPTION
                 "Not supported."

        VARIATION tmnxOspfIfAdvtSubnet
         ACCESS  not-implemented
         DESCRIPTION
                 "Obsolete object."
                 
        VARIATION tmnxOspfMulticastExtensions
         ACCESS  not-implemented
         DESCRIPTION
                 "Not supported."

        VARIATION tmnxOspfDemandExtensions
         ACCESS  read-only
         DESCRIPTION
                 "read-only implementation."

        VARIATION tmnxOspfStrictLsaChecking
         ACCESS  read-only
         DESCRIPTION
                 "read-only implementation."

        VARIATION tmnxOspfRestartSupport
         ACCESS  read-only
         DESCRIPTION
                 "read-only implementation."

        VARIATION tmnxOspfRestartInterval
         ACCESS  read-only
         DESCRIPTION
                 "read-only implementation."

        VARIATION tmnxOspfAreaStubMetricType
         ACCESS  read-only
         DESCRIPTION
                 "read-only implementation."

        VARIATION tmnxOspfAreaNssaTranslatorRole
         ACCESS  read-only
         DESCRIPTION
                 "read-only implementation."

        VARIATION tmnxOspfAreaNssaTranslatorStabInt
         ACCESS  read-only
         DESCRIPTION
                 "read-only implementation."

        VARIATION tmnxOspfIfMulticastForwarding
         ACCESS  not-implemented
         DESCRIPTION
                 "Not supported."

        VARIATION tmnxOspfIfDemand
         ACCESS  read-only
         DESCRIPTION
                 "read-only implementation."

        VARIATION tmnxOspfAreaAggrRouteTag
         ACCESS  read-only
         DESCRIPTION
                 "read-only implementation."

        VARIATION tmnxOspfMulticastImport
         ACCESS  not-implemented
         DESCRIPTION
                 "Not supported."

        VARIATION tmnxOspfRsvpShortcut
         ACCESS  not-implemented
         DESCRIPTION
                 "Not supported."                 

        VARIATION tmnxOspfNbrBfdTracking
         ACCESS  not-implemented
         DESCRIPTION
                 "Not supported."

        VARIATION tmnxOspfUnicastImport
         ACCESS  not-implemented
         DESCRIPTION
                 "Not supported."

        VARIATION tmnxOspfBootOverloadAdmState
         SYNTAX  INTEGER {
                 disabled (1),
                 enabled (2)
                 -- enabledWaitForBgp (3)
             }
         DESCRIPTION
                 "tmnxOspfBootOverloadAdmState only supports
                 'disabled (1)' and 'enabled (2)'.  'enabledWaitForBgp (3) is not
                  implemented."

    ::= { tmnxSASM7210V6v0 14 }

--
--  RSVP CAPABILITIES
--

tmnxRsvpCapsSASM7210V6v0 AGENT-CAPABILITIES
    PRODUCT-RELEASE "Alcatel SAS-M 7210"
    STATUS current
    DESCRIPTION
        "Implementation of RSVP
         capabilities for Alcatel SAS-M 7210 release R6.0"

    SUPPORTS RSVP-MIB
        INCLUDES    {
            -- rsvpSessionGroup,
            -- rsvpSenderGroup,
            -- rsvpResvGroup,
            -- rsvpResvFwdGroup,
            rsvpIfGroup,
            rsvpNbrGroup,
            rsvpNotificationGroup
            -- EXCLUDE rsvpGenObjects
            -- EXCLUDE rsvpSessionTable
            -- EXCLUDE rsvpSenderTable
            -- EXCLUDE rsvpSenderOutInterfaceTable
            -- EXCLUDE rsvpResvTable
            -- EXCLUDE rsvpResvFwdTable
        }

        VARIATION   rsvpNbrProtocol
            ACCESS  read-only
            DESCRIPTION
                    "read-only implementation."

        VARIATION   rsvpNbrStatus
            ACCESS  read-only
            DESCRIPTION
                    "rsvpNbrTable is implemented as read-only.  Row entries
                    cannot be created by SNMP SET requests."

        VARIATION   newFlow
            ACCESS  not-implemented
            DESCRIPTION
                    "Not supported."

        VARIATION   lostFlow
            ACCESS  not-implemented
            DESCRIPTION
                    "Not supported."

    SUPPORTS TIMETRA-RSVP-MIB
        INCLUDES    {
            tmnxRsvpGeneralGroup,
            tmnxRsvpIfV5v0Group,
            tmnxRsvpSessionGroup,
            tmnxRsvpNotificationGroup,
            tmnxRsvpSessionV5v0Group,
            tmnxRsvpGeneralV6v0Group,
            tmnxRsvpGeneralV6v1Group,
            tmnxRsvpIfV6v0Group,
            tmnxRsvpSessionV6v0Group,
            tmnxRsvpNbrV6v0Group,
            tmnxRsvpSessionV6v0Group,
            tmnxRsvpGeneralV6v1Group,
            -- tmnxRsvpIfV7v0Group,
            -- tmnxRsvpDSTEV7v0Group,
            tmnxRsvpGeneralV7v0Group
            -- tmnxRsvpSessionV7v0Group
        }

        VARIATION   vRtrRsvpIfKeepMultiplier
            ACCESS  not-implemented
            DESCRIPTION
                    "vRtrRsvpIfKeepMultiplier is obsolete."

        VARIATION   vRtrRsvpIfRefreshTime
            ACCESS  not-implemented
            DESCRIPTION
                    "vRtrRsvpIfRefreshTime is obsolete."

        VARIATION   vRtrRsvpIfAggregate
            ACCESS  read-only
            DESCRIPTION
                    "read-only implementation."

        VARIATION   vRtrRsvpIfAuthChallenge
            ACCESS  not-implemented
            DESCRIPTION
                    "vRtrRsvpIfAuthChallenge is not supported."

        VARIATION   vRtrRsvpDSTEAdmCtlModel
           SYNTAX   INTEGER {
                    basic (0), 
                    mam (1)   
                    -- rdm (2)  
                    }
           DESCRIPTION
                    "vRtrRsvpDSTEAdmCtlModel does not support the value 'rdm'."

        VARIATION   vRtrRsvpGeneralRefreshBypass
            ACCESS  not-implemented
            DESCRIPTION
                    "Not supported."

    ::= { tmnxSASM7210V6v0 16 }

--
--  SNMP CAPABILITIES
--
tmnxSnmpCapsSASM7210V6v0 AGENT-CAPABILITIES
    PRODUCT-RELEASE "Alcatel SAS-M 7210"
    STATUS current
    DESCRIPTION
        "Implementation of SNMP
         capabilities for Alcatel SAS-M 7210 release R6.0"

    SUPPORTS SNMPv2-MIB
        INCLUDES    {
            snmpGroup,
            snmpCommunityGroup,
            -- snmpSetGroup,
            systemGroup,
            snmpBasicNotificationsGroup,
            snmpWarmStartNotificationGroup,
            snmpNotificationGroup,
            snmpObsoleteGroup
            -- EXCLUDE SNMPv2-MIB.snmpMIB
            -- EXCLUDE SNMPv2-MIB.snmpTrap
            -- EXCLUDE SNMPv2-MIB.snmpSet
            -- EXCLUDE SNMPv2-MIB.sysORLastChange
            -- EXCLUDE SNMPv2-MIB.sysORTable
            -- EXCLUDE SNMPv2-MIB.snmpSilentDrops
            -- EXCLUDE SNMPv2-MIB.snmpProxyDrops
        }

        VARIATION   sysName
            SYNTAX  DisplayString (SIZE(0..32))
            DESCRIPTION
                    "The maximum length supported for the system name is 32
                    characters.  Setting sysName to the empty string, ''H,
                    resets sysName to the TiMOS default value."

        VARIATION   sysContact
            SYNTAX  DisplayString (SIZE(0..80))
            DESCRIPTION
                    "The maximum length supported for the system contact is
                    80 characters."

        VARIATION   sysLocation
            SYNTAX  DisplayString (SIZE(0..80))
            DESCRIPTION
                    "The maximum length supported for the system location is
                    80 characters."

        VARIATION   sysORTable
            ACCESS  not-implemented
            DESCRIPTION
                    "sysORTable is not supported on Alcatel SAS-M 7210
                    systems."

        VARIATION   coldStart
            DESCRIPTION
                    "coldStart notification is generated on all system
                    reboots - not only for power cycle reboots."

        VARIATION   warmStart
            DESCRIPTION
                    "warmStart notification is generated by the new active
                    CPM following a CPM switchover. This notification has
                    been supported starting with the 7450 3.0 release.

                    When the standby CPM card takes over following a failure
                    or reboot of the active CPM card, tmnxRedPrimaryCPMFail,
                    sbiBootConfig and sbiBootSnmpd events from the
                    TIMETRA-SYSTEM-MIB are generated to indicate the
                    secondary CPM has successfully taken control of the
                    system."

        VARIATION   snmpOutPkts
            DESCRIPTION
                    "This object was defined in RFC1213 for SNMPv1 agents
                    but it was made obsolete in SNMPv2-MIB.  However, 
                    many customers and NMS developers find this counter 
                    useful so this agent continues to support it."

        VARIATION   snmpInTooBigs
            DESCRIPTION
                    "This object was defined in RFC1213 for SNMPv1 agents
                    but it was made obsolete in SNMPv2-MIB.  However, 
                    many customers and NMS developers find this counter 
                    useful so this agent continues to support it."

        VARIATION   snmpInNoSuchNames
            DESCRIPTION
                    "This object was defined in RFC1213 for SNMPv1 agents
                    but it was made obsolete in SNMPv2-MIB.  However, 
                    many customers and NMS developers find this counter 
                    useful so this agent continues to support it."

        VARIATION   snmpInBadValues
            DESCRIPTION
                    "This object was defined in RFC1213 for SNMPv1 agents
                    but it was made obsolete in SNMPv2-MIB.  However, 
                    many customers and NMS developers find this counter 
                    useful so this agent continues to support it."

        VARIATION   snmpInReadOnlys
            DESCRIPTION
                    "This object was defined in RFC1213 for SNMPv1 agents
                    but it was made obsolete in SNMPv2-MIB.  However, 
                    many customers and NMS developers find this counter 
                    useful so this agent continues to support it."

        VARIATION   snmpInGenErrs
            DESCRIPTION
                    "This object was defined in RFC1213 for SNMPv1 agents
                    but it was made obsolete in SNMPv2-MIB.  However, 
                    many customers and NMS developers find this counter 
                    useful so this agent continues to support it."

        VARIATION   snmpInTotalReqVars
            DESCRIPTION
                    "This object was defined in RFC1213 for SNMPv1 agents
                    but it was made obsolete in SNMPv2-MIB.  However, 
                    many customers and NMS developers find this counter 
                    useful so this agent continues to support it."

        VARIATION   snmpInTotalSetVars
            DESCRIPTION
                    "This object was defined in RFC1213 for SNMPv1 agents
                    but it was made obsolete in SNMPv2-MIB.  However, 
                    many customers and NMS developers find this counter 
                    useful so this agent continues to support it."

        VARIATION   snmpInGetRequests
            DESCRIPTION
                    "This object was defined in RFC1213 for SNMPv1 agents
                    but it was made obsolete in SNMPv2-MIB.  However, 
                    many customers and NMS developers find this counter 
                    useful so this agent continues to support it."

        VARIATION   snmpInGetNexts
            DESCRIPTION
                    "This object was defined in RFC1213 for SNMPv1 agents
                    but it was made obsolete in SNMPv2-MIB.  However, 
                    many customers and NMS developers find this counter 
                    useful so this agent continues to support it."

        VARIATION   snmpInSetRequests
            DESCRIPTION
                    "This object was defined in RFC1213 for SNMPv1 agents
                    but it was made obsolete in SNMPv2-MIB.  However, 
                    many customers and NMS developers find this counter 
                    useful so this agent continues to support it."

        VARIATION   snmpInGetResponses
            DESCRIPTION
                    "This object was defined in RFC1213 for SNMPv1 agents
                    but it was made obsolete in SNMPv2-MIB.  However, 
                    many customers and NMS developers find this counter 
                    useful so this agent continues to support it."

        VARIATION   snmpInTraps
            DESCRIPTION
                    "This object was defined in RFC1213 for SNMPv1 agents
                    but it was made obsolete in SNMPv2-MIB.  However, 
                    many customers and NMS developers find this counter 
                    useful so this agent continues to support it."

        VARIATION   snmpOutTooBigs
            DESCRIPTION
                    "This object was defined in RFC1213 for SNMPv1 agents
                    but it was made obsolete in SNMPv2-MIB.  However, 
                    many customers and NMS developers find this counter 
                    useful so this agent continues to support it."

        VARIATION   snmpOutNoSuchNames
            DESCRIPTION
                    "This object was defined in RFC1213 for SNMPv1 agents
                    but it was made obsolete in SNMPv2-MIB.  However, 
                    many customers and NMS developers find this counter 
                    useful so this agent continues to support it."

        VARIATION   snmpOutBadValues
            DESCRIPTION
                    "This object was defined in RFC1213 for SNMPv1 agents
                    but it was made obsolete in SNMPv2-MIB.  However, 
                    many customers and NMS developers find this counter 
                    useful so this agent continues to support it."

        VARIATION   snmpOutGenErrs
            DESCRIPTION
                    "This object was defined in RFC1213 for SNMPv1 agents
                    but it was made obsolete in SNMPv2-MIB.  However, 
                    many customers and NMS developers find this counter 
                    useful so this agent continues to support it."

        VARIATION   snmpOutGetRequests
            DESCRIPTION
                    "This object was defined in RFC1213 for SNMPv1 agents
                    but it was made obsolete in SNMPv2-MIB.  However, 
                    many customers and NMS developers find this counter 
                    useful so this agent continues to support it."

        VARIATION   snmpOutGetNexts
            DESCRIPTION
                    "This object was defined in RFC1213 for SNMPv1 agents
                    but it was made obsolete in SNMPv2-MIB.  However, 
                    many customers and NMS developers find this counter 
                    useful so this agent continues to support it."

        VARIATION   snmpOutSetRequests
            DESCRIPTION
                    "This object was defined in RFC1213 for SNMPv1 agents
                    but it was made obsolete in SNMPv2-MIB.  However, 
                    many customers and NMS developers find this counter 
                    useful so this agent continues to support it."

        VARIATION   snmpOutGetResponses
            DESCRIPTION
                    "This object was defined in RFC1213 for SNMPv1 agents
                    but it was made obsolete in SNMPv2-MIB.  However, 
                    many customers and NMS developers find this counter 
                    useful so this agent continues to support it."

        VARIATION   snmpOutTraps
            DESCRIPTION
                    "This object was defined in RFC1213 for SNMPv1 agents
                    but it was made obsolete in SNMPv2-MIB.  However, 
                    many customers and NMS developers find this counter 
                    useful so this agent continues to support it."


    SUPPORTS SNMP-COMMUNITY-MIB
        INCLUDES    {
            snmpCommunityTableGroup
        }

        VARIATION   snmpCommunityContextEngineID
            ACCESS  read-only
            DESCRIPTION
                    "snmpCommunityContextEngineID is implemented as
                    read-only because only one SNMP Engine ID is supported.
                    The engine ID may change when a redundancy failover from
                    active to standby CPM happens."

    SUPPORTS SNMP-FRAMEWORK-MIB
        INCLUDES    {
            snmpEngineGroup
        }

    SUPPORTS SNMP-MPD-MIB
        INCLUDES    {
            snmpMPDGroup
        }

    SUPPORTS SNMP-NOTIFICATION-MIB
        INCLUDES    {
            snmpNotifyGroup,
            snmpNotifyFilterGroup
        }

        VARIATION   snmpNotifyRowStatus
            DESCRIPTION
                    "The only values allowed for the snmpNotifyName index is
                    the ASCII numerical value of the TiMOS event log ID that
                    the notification group is associated with.  Event log
                    IDs have a range of [1..100].  Leading zero, '0',
                    characters are not allowed."

    SUPPORTS SNMP-TARGET-MIB
        INCLUDES    {
            snmpTargetBasicGroup
            -- snmpTargetResponseGroup
            -- snmpTargetCommandResponderGroup,
        }

    SUPPORTS SNMP-USER-BASED-SM-MIB
        INCLUDES    {
            usmMIBBasicGroup
        }

        VARIATION   usmUserStorageType
            SYNTAX  INTEGER {
                        nonVolatile (3)
                    }
            DESCRIPTION
                    "Only the StorageType TC value 'nonVolatile (3)' is
                    supported for usmUserStorageType."

    SUPPORTS SNMP-VIEW-BASED-ACM-MIB
        INCLUDES    {
            vacmBasicGroup
        }

    ::= { tmnxSASM7210V6v0 17 }

--
--  CHASSIS CAPABILITIES
--

tmnxChassisCapsSASM7210V6v0 AGENT-CAPABILITIES
    PRODUCT-RELEASE "Alcatel SAS-M 7210"
    STATUS current
    DESCRIPTION
        "Implementation of chassis or hardware
         capabilities for Alcatel SAS-M 7210 release R6.0"

    SUPPORTS TIMETRA-CHASSIS-MIB
        INCLUDES    {
            tmnxChassisV5v0Group,
            tmnxChassisV6v1Group,
            tmnxCardV3v0Group,
            tmnxMDAV6v1Group,
            tmnxMDAMcPathMgmtV6v0Group,
            tmnxChassisNotificationV7v0Group,
            tmnxCardV6v0NamedPoolPlcyGroup,
            tmnxCardV7v0Group,
            -- tmnx77x0CESMDAV6v0Group
            -- tmnxIPsecIsaGrpV6v0Group     no IPsec on SAS-M 7210
            -- tmnx7710HwV3v0Group
            tmnx7710SETSRefSrcHwV6v0Group,
            -- tmnxChassisHsmdaV6v0Group,
            -- tmnxFPMcPathMgmtV6v1Group,
            tmnxMDACcagV6v1Group
        }

        VARIATION   tmnxChassisRedForcedSingleSfm
            ACCESS  not-implemented
            DESCRIPTION
                    "Not supported."

        -- no modeC for SAS-M 7210 : start
        VARIATION   tmnxChassisAdminMode
            SYNTAX  INTEGER {
                        modeA     (1),
                        modeB     (2),
                        -- modeC  (3)      No modeC on SAS-M 7210
                        modeD     (4)
                    }
            DESCRIPTION
                    "The value 'modeC (3)' is invalid on a 7450 system,
                    because scaling and features corresponding to the
                    IOM2-20g card are not supported on Alcatel 7450 systems."
        -- no modeC for SAS-M 7210 : end

        VARIATION   tmnxChassisRowStatus
            ACCESS  read-only
            DESCRIPTION
                    "tmnxChassisRowStatus is supported as read-only.
                    Row entries cannot be created by SNMP SET requests.
                    Multiple chassises are not supported on Alcatel
                    SAS-M 7210 systems."

        VARIATION   tmnxChassisMinorLEDState
            ACCESS  not-implemented
            DESCRIPTION
                    "Not supported."                                   

        VARIATION   tmnxHwContainedIndex
            ACCESS  not-implemented
            DESCRIPTION
                    "Not supported."

        VARIATION   tmnxCpmCardAssignedType
            ACCESS  read-only
            DESCRIPTION
                    "tmnxCpmCardAssignedType is supported as read-only.
                    Multiple CPM card types are not supported on Alcatel
                    SAS-M 7210 systems."

        VARIATION   tmnxEqBackdoorBusFailure
            ACCESS  not-implemented
            DESCRIPTION
                    "tmnxEqBackdoorBusFailure notification is not implemented.
                    This notification was made obsolete in the 2.1 release."

        VARIATION   tmnxPeOutOfMemory
            ACCESS  not-implemented
            DESCRIPTION
                    "tmnxPeOutOfMemory notification is not implemented.
                    This notification was made obsolete in the 2.1 release.

                    The tmnxPeOutOfMemory notification has been replaced
                    with the module specific notification from the
                    TIMETRA-SYSTEM-MIB: tmnxModuleMallocFailed."

        VARIATION   tmnxPeConfigurationError
            ACCESS  not-implemented
            DESCRIPTION
                    "tmnxPeConfigurationError notification is not implemented.
                    This notification was made obsolete in the 2.1 release.

                    Many other notifications more specifically indicate
                    detection of a configuration error. In most cases the
                    SNMP SET request that tries to make an invalid
                    configuration results in an error response.

                    In some cases the configuration parameters are valid
                    and the SNMP SET request succeeds but the system cannot
                    successfully apply the new parameters. The affected
                    object may then put into an operational 'down' state.
                    A state change notification such as tmnxStateChange or
                    a more specific notification is sent to alert about the
                    problem.

                    For example, an attempt to create an event log with a
                    file-type destination when the specified cflash media is
                    full or not present results in TIMETRA-LOG-MIB
                    notifications tmnxLogSpaceContention,
                    tmnxLogAdminLocFailed, or tmnxLogBackupLocFailed."

        VARIATION   tmnxPeStorageProblem
            ACCESS  not-implemented
            DESCRIPTION
                    "tmnxPeStorageProblem notification is not implemented.
                    This notification was made obsolete in the 2.1 release.

                    The only 'storage' devices on the SAS-M 7210 are the cflash
                    drives. Cflash write errors cause a tmnxEqFlashDataLoss
                    notification to be sent. The tmnxEqFlashDiskFull
                    notification is sent when the driver detects that the
                    cflash device is full."

        VARIATION   tmnxPeCpuCyclesExceeded
            ACCESS  not-implemented
            DESCRIPTION
                    "tmnxPeCpuCyclesExceeded notification is not implemented.
                    This notification was made obsolete in the 2.1 release.

                    It does not apply. The SAS-M 7210 software architecture does
                    not restrict CPU cycles used by a specific code module."

        VARIATION   tmnxRedSecondaryCPMStatusChange
            ACCESS  not-implemented
            DESCRIPTION
                    "tmnxRedSecondaryCPMStatusChange notification is not
                    implemented.  This notification was made obsolete in
                    the 2.1 release.

                    There is no way to administratively enable or disable
                    CPM cards so there is no need for a status change event
                    for administrative state changes.

                    Operational changes detected about the Secondary CPM
                    card are indicated by more specific notifications such
                    as tmnxEqCardFailure, tmnxEqCardRemoved, and
                    tmnxEqCardInserted."

        VARIATION   tmnxRedRestoreSuccess
            ACCESS  not-implemented
            DESCRIPTION
                    "tmnxRedRestoreSuccess notification is not implemented.
                    This notification was made obsolete in the 2.1 release.

                    It does not apply. This event was originally created
                    for an early redundancy mechanism that was never
                    released. This event should be removed.

                    When the secondary CPM card takes over following a
                    reboot or failure of the active CPM, sbiBootConfig
                    and sbiBootSnmpd events from the TIMETRA-SYSTEM-MIB
                    are generated to indicate that the secondary card
                    has successfully taken control of the system."

        VARIATION   tmnxRedRestoreFail
            ACCESS  not-implemented
            DESCRIPTION
                    "tmnxRedRestoreFail notification is not implemented.
                    This notification was made obsolete in the 2.1 release.

                    It does not apply. This event was originally created
                    for an early redundancy mechanism that was never
                    released. This event should be removed."

        VARIATION   tmnxCardAllowedTypes
            ACCESS  not-implemented
            DESCRIPTION
                    "tmnxCardAllowedTypes object is not implemented.
                    This object was made obsolete in the 3.0 release.

                    A bit-mask that specifies what IOM card types the
                    administrator has designated be allowed to be inserted
                    into this slot.If the slot has not-been pre-provisioned
                    and a card that does not match one of the allowed types
                    is inserted into this slot, a mis-match alarm will be
                    raised. If a specific value has not yet been SET by the
                    manager, tmnxCardAllowedTypes will return the same
                    value to a GET request as tmnxCardSupportedTypes."

        VARIATION   tmnxCpmCardAllowedTypes
            ACCESS  not-implemented
            DESCRIPTION
                    "tmnxCpmCardAllowedTypes object is not implemented.
                    This object was made obsolete in the 3.0 release.

                    A bit-mask that specifies what CPM card types the
                    administrator has designated be allowed to be inserted into
                    this slot. If the slot has not-been pre-provisioned and a
                    card that does not match one of the allowed types is
                    inserted into this slot, a mis-match alarm will be raised.
                    IfEntry a specific value has not yet been SET by the
                    manager, tmnxCpmCardAllowedTypes will return the same
                    value to a GET request as tmnxCpmCardSupportedTypes."

        VARIATION   tmnxMDAAllowedTypes
            ACCESS  not-implemented
            DESCRIPTION
                    "tmnxMDAAllowedTypes object is not implemented.
                    This object was made obsolete in the 3.0 release.

                    A bit-mask that specified what MDA card types the
                    administrator has designated be allowed to be inserted
                    into this slot. If the slot has not-been pre-provisioned
                    and a MDA card that does not match one of the allowed
                    types is inserted into this slot, a mis-match alarm will
                    be raised. If a specific value has not yet been SET by
                    the manager, a GET to tmnxMDAAllowedTypes returns the
                    same value as tmnxMDASupportedTypes."

        VARIATION   tmnxMDAEquippedPorts
            DESCRIPTION
                    "The value of tmnxMDAEquippedPorts indicates the number
                    of ports equipped on this MDA card. Previous to the 3.0
                    release this object was defined to be a bit-mask of
                    equipped ports.  However, the code implementation has
                    always returned a value this is just the total number of
                    equipped ports."

        VARIATION   tmnxHwOperState
            SYNTAX  INTEGER {
                        unknown         (1),
                        inService       (2),
                        outOfService    (3),
                        diagnosing      (4),
                        failed          (5),
                        booting         (6),
                        empty           (7),
                        provisioned     (8),
                        unprovisioned   (9),
                        upgrade         (10),
                        downgrade       (11)
                        -- inServiceUpgrage     (12),
                        -- inServiceDowngrade   (13),
                        -- resetPending         (14)
                    }
            DESCRIPTION
                    "The enumerations 'inServiceUpgrade (12)',
                    'inServiceDowngrade (13)', and 'resetPending (14)' are no
                    longer supported."

        VARIATION   tmnxChassisPowerSupplyPemType
            ACCESS  not-implemented
            DESCRIPTION
                    "Not supported."

        VARIATION   tmnxCpmCardSwitchToRedundantCard
            ACCESS  not-implemented
            DESCRIPTION
                    "Not supported."

        VARIATION   tmnxCpmCardSyncFileNotPresent
            ACCESS  not-implemented
            DESCRIPTION
                    "Not supported."

        VARIATION   tmnxSyncIfTimingFreqOffset
            ACCESS  not-implemented
            DESCRIPTION
                    "Not supported."

        VARIATION   tmnxSyncIfTimingRefOrder3
            ACCESS  not-implemented
            DESCRIPTION
                    "Not supported."

        VARIATION   tmnxSyncIfTimingBITSIfType
            ACCESS  not-implemented
            DESCRIPTION
                    "Not supported."

        VARIATION   tmnxSyncIfTimingBITSAdminStatus
            ACCESS  not-implemented
            DESCRIPTION
                    "Not supported."

        VARIATION   tmnxSyncIfTimingBITSInUse
            ACCESS  not-implemented
            DESCRIPTION
                    "Not supported."

        VARIATION   tmnxSyncIfTimingBITSQualified
            ACCESS  not-implemented
            DESCRIPTION
                    "Not supported."

        VARIATION   tmnxSyncIfTimingBITSAlarm
            ACCESS  not-implemented
            DESCRIPTION
                    "Not supported."

        VARIATION   tSyncIfTimingAdmRefOrder3
            ACCESS  not-implemented
            DESCRIPTION
                    "Not supported."

        VARIATION   tSyncIfTimingAdmBITSIfType
            ACCESS  not-implemented
            DESCRIPTION
                    "Not supported."

        VARIATION   tSyncIfTimingAdmBITSAdminStatus
            ACCESS  not-implemented
            DESCRIPTION
                    "Not supported."

        VARIATION   tmnxChassisPowerSupplyAssignedType
            ACCESS  read-only
            DESCRIPTION
                    "This object is read-only."

        VARIATION   tmnxCardFailOnError
            ACCESS  not-implemented
            DESCRIPTION
                    "Not supported."

    ::= { tmnxSASM7210V6v0 19 }

--
--  CLEAR CAPABILITIES
--
tmnxClearCapsSASM7210V6v0 AGENT-CAPABILITIES
    PRODUCT-RELEASE "Alcatel SAS-M 7210"
    STATUS current
    DESCRIPTION
        "Implementation of clear and reset
         capabilities for Alcatel SAS-M 7210 release R6.0"

    SUPPORTS TIMETRA-CLEAR-MIB
        INCLUDES    {
            tmnxClearGroup,
            tmnxClearNotificationGroup
        }
    ::= { tmnxSASM7210V6v0 20 }

--
--  QoS FILTER CAPABILITIES
--
tmnxFilterCapsSASM7210V6v0 AGENT-CAPABILITIES
    PRODUCT-RELEASE "Alcatel SAS-M 7210"
    STATUS current
    DESCRIPTION
        "Implementation of Qos filters
         capabilities for Alcatel SAS-M 7210 release R6.0"
    SUPPORTS TIMETRA-FILTER-MIB
        INCLUDES    {
            tFilterScalarGroup,
            tIPFilterV6v0Group,
            tMacFilterV6v0Group,
            -- tFilterLogGroup,
            -- tFilterLogV5v0Group,
            -- tFilterRedirectPolicyGroup,
            tFilterNotificationsGroup,
            -- tIPv6FilterV6v0Group (no ipv6 on SAS-M 7210)
            tTodPolicies77450V5v0Group,
            -- tTodPolicies77x0V5v0Group
            tToDPoliciesV5v0NotifyGroup,
            tIPv6FilterV8v0Group,
            tFilterPrefixListV10v0Group
        }

        -- no CFLOWD on SAS-M 7210: begin
        VARIATION   tIPFilterParamsCflowdSample
            ACCESS  not-implemented
            DESCRIPTION
                    "Not supported. No CFLOWD."

        VARIATION   tIPFilterParamsCflowdIfSample
            ACCESS  not-implemented
            DESCRIPTION
                    "Not supported. No CFLOWD."
        -- no CFLOWD on SAS-M 7210: end

        VARIATION   tAutoIPFilterEntryTable
            ACCESS  not-implemented
            DESCRIPTION
                    "Not supported."

        VARIATION   tIPFilterParamsIngrHitByteCount
            ACCESS  not-implemented
            DESCRIPTION
                    "Not supported."

        VARIATION   tIPFilterParamsEgrHitByteCount
            ACCESS  not-implemented
            DESCRIPTION
                    "Not supported."

        VARIATION   tIPv6FilterParamsLogId
            ACCESS  not-implemented
            DESCRIPTION
                    "Not supported."               

        VARIATION  tIPv6FilterParamsSourcePortValue2
            ACCESS  not-implemented
            DESCRIPTION
                    "Not supported."

       VARIATION   tIPv6FilterParamsSourcePortOperator    
            SYNTAX  INTEGER {
                         none    (0),
                         eq       (1),
                         range  (2),
                         lt        (3),
                         gt       (4)
                    }
            DESCRIPTION
                    "The values range(2),lt(3),gt(4) are not supported on MTU,SASX,STU,SASD"

        VARIATION  tIPv6FilterParamsDestPortValue2 
            ACCESS  not-implemented
            DESCRIPTION
                    "Not supported."    

       VARIATION  tIPv6FilterParamsDestPortOperator       
            SYNTAX  INTEGER {
                         none    (0),
                         eq       (1),
                         range  (2),
                         lt        (3),
                         gt       (4)
                    }
            DESCRIPTION
                    "The values range(2),lt(3),gt(4) are not supported on MTU,SASX,STU,SASD." 

        VARIATION   tMacFilterParamsIngrHitByteCount
            ACCESS  not-implemented
            DESCRIPTION
                    "Not supported."

        VARIATION   tMacFilterParamsEgrHitByteCount
            ACCESS  not-implemented
            DESCRIPTION
                    "Not supported."

        VARIATION  tMacFilterParamsLowISID
            ACCESS  not-implemented
            DESCRIPTION
                    "Not supported."

        VARIATION   tMacFilterParamsHighISID
            ACCESS  not-implemented
            DESCRIPTION
                    "Not supported."            

        VARIATION   tIPFilterParamsActiveDest
            ACCESS  not-implemented
    DESCRIPTION
                    "Not supported."

        VARIATION   tIPFilterParamsDestPortValue2
            ACCESS  not-implemented
            DESCRIPTION
                    "Not supported."

        VARIATION   tIPFilterParamsDestPortOperator  
            SYNTAX  INTEGER {
                         none    (0),
                         eq       (1),
                         range  (2),
                         lt        (3),
                         gt       (4)
                    }
            DESCRIPTION
                    "The values range(2),lt(3),gt(4) are not supported on MTU,SASX,STU,SASD"

        VARIATION   tIPFilterParamsForwardNH
            ACCESS  not-implemented
            DESCRIPTION
                    "Not supported."

        VARIATION   tIPFilterParamsForwardNHIndirect
            ACCESS  not-implemented
            DESCRIPTION
                    "Not supported."

        VARIATION   tIPFilterParamsForwardNHInterface
            ACCESS  not-implemented
            DESCRIPTION
                    "Not supported."

        VARIATION   tIPFilterParamsForwardRedPlcy
            ACCESS  not-implemented
            DESCRIPTION
                    "Not supported."

        VARIATION   tIPFilterParamsFwdSapEncapVal
            ACCESS  not-implemented
            DESCRIPTION
                    "Not supported."

        VARIATION   tIPFilterParamsFwdSapPortId
            ACCESS  not-implemented
            DESCRIPTION
                    "Not supported."

        VARIATION   tIPFilterParamsFwdSdpBind
            ACCESS  not-implemented
            DESCRIPTION
                    "Not supported."

        VARIATION   tIPFilterParamsFwdSvcId
            ACCESS  not-implemented
            DESCRIPTION
                    "Not supported."

        VARIATION   tIPFilterParamsIpOptionMask
            ACCESS  not-implemented
            DESCRIPTION
                    "Not supported."

        VARIATION   tIPFilterParamsIpOptionValue
            ACCESS  not-implemented
            DESCRIPTION
                    "Not supported."

        VARIATION   tIPFilterParamsLogId
            ACCESS  not-implemented
            DESCRIPTION
                    "Not supported."

        VARIATION   tIPFilterParamsLogInstantiated
            ACCESS  not-implemented
            DESCRIPTION
                    "Not supported."

        VARIATION   tIPFilterParamsMultipleOption
            ACCESS  not-implemented
            DESCRIPTION
                    "Not supported."

        VARIATION   tIPFilterParamsRedirectURL
            ACCESS  not-implemented
            DESCRIPTION
                    "Not supported."

        VARIATION   tIPFilterParamsRemarkDot1p
            ACCESS  not-implemented
            DESCRIPTION
                    "Not supported."

        VARIATION   tIPFilterParamsRemarkDSCP
            ACCESS  not-implemented
            DESCRIPTION
                    "Not supported."

        VARIATION   tIPFilterParamsRemarkDSCPMask
            ACCESS  not-implemented
            DESCRIPTION
                    "Not supported."

        VARIATION   tIPFilterParamsSourcePortValue2
            ACCESS  not-implemented
            DESCRIPTION
                    "Not supported."

        VARIATION   tIPFilterParamsSourcePortOperator  
            SYNTAX  INTEGER {
                         none    (0),
                         eq       (1),
                         range  (2),
                         lt        (3),
                         gt       (4)
                    }
            DESCRIPTION
                    "The values range(2),lt(3),gt(4) are not supported on MTU,SASX,STU,SASD"

        VARIATION   tMacFilterParamsDsap
            ACCESS  not-implemented
            DESCRIPTION
                    "Not supported."

        VARIATION   tMacFilterParamsDsapMask
            ACCESS  not-implemented
            DESCRIPTION
                    "Not supported."

        VARIATION   tMacFilterParamsFrameType
            ACCESS  not-implemented
            DESCRIPTION
                    "Not supported."

        VARIATION   tMacFilterParamsFwdSapEncapVal
            ACCESS  not-implemented
            DESCRIPTION
                    "Not supported."

        VARIATION   tMacFilterParamsFwdSapPortId
            ACCESS  not-implemented
            DESCRIPTION
                    "Not supported."

        VARIATION   tMacFilterParamsFwdSdpBind
            ACCESS  not-implemented
            DESCRIPTION
                    "Not supported."

        VARIATION   tMacFilterParamsFwdSvcId
            ACCESS  not-implemented
            DESCRIPTION
                    "Not supported."

        VARIATION   tMacFilterParamsLogId
            ACCESS  not-implemented
            DESCRIPTION
                    "Not supported."

        VARIATION   tMacFilterParamsLogInstantiated
            ACCESS  not-implemented
            DESCRIPTION
                    "Not supported."

        VARIATION   tMacFilterParamsRedirectURL
            ACCESS  not-implemented
            DESCRIPTION
                    "Not supported."

        VARIATION   tMacFilterParamsSnapOui
            ACCESS  not-implemented
            DESCRIPTION
                    "Not supported."

        VARIATION   tMacFilterParamsSnapPid
            ACCESS  not-implemented
            DESCRIPTION
                    "Not supported."

        VARIATION   tMacFilterParamsSsap
            ACCESS  not-implemented
            DESCRIPTION
                    "Not supported."

        VARIATION   tMacFilterParamsSsapMask
            ACCESS  not-implemented
            DESCRIPTION
                    "Not supported."

         VARIATION tFilterPrefixListTableLstChng
            ACCESS  not-implemented
            DESCRIPTION
                "Not supported."

           VARIATION  tFilterPrefixListType
            ACCESS  not-implemented
            DESCRIPTION
                "Not supported."

        VARIATION   tFilterPrefixListName            
            ACCESS  not-implemented
            DESCRIPTION
                "Not supported."

        VARIATION  tFilterPrefixListRowStatus
            ACCESS  not-implemented
            DESCRIPTION
                "Not supported."

        VARIATION  tFilterPrefixListLastChanged
            ACCESS  not-implemented
            DESCRIPTION
                "Not supported."

        VARIATION  tFilterPrefixListDescription
            ACCESS  not-implemented
            DESCRIPTION
                "Not supported."

        VARIATION  tFilterPrefixListEntryTblLstChg
            ACCESS  not-implemented
            DESCRIPTION
                "Not supported."

        VARIATION  tFilterPrefixListEntryPrefixType 
            ACCESS  not-implemented
            DESCRIPTION
                "Not supported."

        VARIATION  tFilterPrefixListEntryPrefix     
            ACCESS  not-implemented
            DESCRIPTION
                "Not supported."

        VARIATION  tFilterPrefixListEntryPrefixLen  
            ACCESS  not-implemented
            DESCRIPTION
                "Not supported."

        VARIATION  tFilterPrefixListEntryRowStatus
            ACCESS  not-implemented
            DESCRIPTION
                "Not supported."
                
    ::= { tmnxSASM7210V6v0 21 }

--
--  LOG CAPABILITIES
--
tmnxLogCapsSASM7210V6v0 AGENT-CAPABILITIES
    PRODUCT-RELEASE "Alcatel SAS-M 7210"
    STATUS current
    DESCRIPTION
        "Implementation of event logging
         capabilities for Alcatel SAS-M 7210 release R6.0"

    SUPPORTS TIMETRA-LOG-MIB
        INCLUDES    {
            tmnxLogGlobalGroup,
            tmnxLogV5v0Group,
            tmnxLogAccountingPolicyGroup,
            tmnxLogFileIdGroup,
            tmnxLogSyslogV5v0Group,
            tmnxSnmpTrapV5v0Group,
            tmnxSnmpSetErrsGroup,
            tmnxLogEventsV5v0Group,
            tmnxLogNotificationV6v0Group
        }

    ::= { tmnxSASM7210V6v0 22 }

--
--  MIRROR CAPABILITIES
--
tmnxMirrorCapsSASM7210V6v0 AGENT-CAPABILITIES
    PRODUCT-RELEASE "Alcatel SAS-M 7210"
    STATUS current
    DESCRIPTION
        "Implementation of port mirroring
         capabilities for Alcatel SAS-M 7210 release R6.0"

    SUPPORTS TIMETRA-MIRROR-MIB
        INCLUDES    {
            tMirrorDestinationV6v0Group,
            -- tMirrorDestinationR2r1RemoteSourceGroup,
            tMirrorSourceV6v0Group,
            tMirrorNotificationsGroup,
            tMirrorSourceNotificationsV6v0Group
            -- tMirrorBsxV6v0Group
        }

        -- No ATM mirroring for SAS-M 7210 : start
        -- No CPIPE mirroring for SAS-M 7210 : start
        VARIATION   tMirrorDestinationEncapsulation
            SYNTAX  INTEGER {
                        ether          (1),
                        frameRelay     (2),
                        ppp            (3)
                        -- atmSdu      (4),
                        -- satopE1     (5),
                        -- satopT1     (6),
                        -- satopE3     (7),
                        -- satopT3     (8),
                        -- cesopsn     (9),
                        -- cesopsnCas  (10)
                    }
            DESCRIPTION
                    "The values
                        - 'atmSdu     (4)',
                        - 'satopE1    (5)',
                        - 'satopT1    (6)',
                        - 'satopE3    (7)',
                        - 'satopT3    (8)',
                        - 'cesopsn    (9)',
                        - 'cesopsnCas (10)'
                        are invalid on a SAS-M 7210 system, as ATM and CEM are
                        not implemented."
        -- No ATM mirroring for SAS-M 7210 : end
        -- No CPIPE mirroring for SAS-M 7210 : end

        VARIATION   tMirrorSourceRemovedBySystem
            ACCESS  not-implemented
            DESCRIPTION
                    "Not supported."

        VARIATION   tMirrorSourceSubIpAddrType
            SYNTAX  INTEGER {
                        unknown     (0),
                        ipv4        (1)
                        -- ipv6     (2),
                        -- ipv4z    (3),
                        -- ipv6z    (4),
                        -- dns      (16)
                    }
            DESCRIPTION
                    "tMirrorSourceSubIpAddrType supports only InetAddressType
                    values 'unknown' and 'ipv4'."

        VARIATION   tMirrorSourceSubIpAddr
            SYNTAX  InetAddress (SIZE (0|4))
            DESCRIPTION
                    "tMirrorSourceSubIpAddr supports only InetAddressType
                    values 'unknown' and 'ipv4'."

        VARIATION tMirrorDestinationSapEgressQosPolicyId
            ACCESS not-implemented
            DESCRIPTION
                "Not supported."

        VARIATION tMirrorDestinationSdpEgrSvcLabel
            ACCESS not-implemented
            DESCRIPTION
                "Not supported."

        VARIATION tMirrorDestinationSdpNumber
            ACCESS not-implemented
            DESCRIPTION
                "Not supported."

        VARIATION tMirrorDestinationSdpOperEgrSvcLabel
            ACCESS not-implemented
            DESCRIPTION
                "Not supported."

        VARIATION tMirrorDestinationSliceSize
            ACCESS not-implemented
            DESCRIPTION
                "Not supported."

        VARIATION tMirrorDestRemoteSrcLastChgd
            ACCESS not-implemented
            DESCRIPTION
                "Not supported."
                
        VARIATION tMirrorSourceSapEgressEnabled
            ACCESS  not-implemented
            DESCRIPTION
                "Not supported."
                
        VARIATION tMirrorSourceSubEgressEnabled
            ACCESS  not-implemented
            DESCRIPTION
                "Not supported."

        VARIATION tMirrorSourceSubEncapValue
            ACCESS  not-implemented
            DESCRIPTION
                "Not supported."

        VARIATION tMirrorSourceSubFC
            ACCESS  not-implemented
            DESCRIPTION
                "Not supported."

        VARIATION tMirrorSourceSubIngressEnabled
            ACCESS  not-implemented
            DESCRIPTION
                "Not supported."

        VARIATION tMirrorSourceSubIpAddr
            ACCESS  not-implemented
            DESCRIPTION
                "Not supported."

        VARIATION tMirrorSourceSubIpAddrType
            ACCESS  not-implemented
            DESCRIPTION
                "Not supported."

        VARIATION tMirrorSourceSubLastChanged
            ACCESS  not-implemented
            DESCRIPTION
                "Not supported."

        VARIATION tMirrorSourceSubMacAddr
            ACCESS  not-implemented
            DESCRIPTION
                "Not supported."

        VARIATION tMirrorSourceSubPortId
            ACCESS  not-implemented
            DESCRIPTION
                "Not supported."

        VARIATION tMirrorSourceSubRowStatus
            ACCESS  not-implemented
            DESCRIPTION
                "Not supported."

        VARIATION tMirrorSourceSubSLAProfName
            ACCESS  not-implemented
            DESCRIPTION
                "Not supported."

        VARIATION tMirrorSourceSubTableLastChnged
            ACCESS  not-implemented
            DESCRIPTION
                "Not supported."

        VARIATION tMirrorSourceIngLabelLastChgd
            ACCESS  not-implemented
            DESCRIPTION
                "Not supported."

        VARIATION tMirrorSourceIngressLabelRowStatus
            ACCESS  not-implemented
            DESCRIPTION
                "Not supported."

        VARIATION tMirrorDestSapEgrIpMirrorSA
            ACCESS  not-implemented
            DESCRIPTION
                "Not supported."

        VARIATION tMirrorDestSapEgrIpMirrorDA
            ACCESS  not-implemented
            DESCRIPTION
                "Not supported."
                
    ::= { tmnxSASM7210V6v0 23 }

--
--  OAM TEST CAPABILITIES
--
tmnxOamTestCapsSASM7210V6v0 AGENT-CAPABILITIES
    PRODUCT-RELEASE "Alcatel SAS-M 7210"
    STATUS current
    DESCRIPTION
        "Implementation of OAM Test capabilities
         for Alcatel SAS-M 7210 release R6.0"

    SUPPORTS TIMETRA-SAS-OAM-TEST-MIB
        INCLUDES    {
            tmnxTestHdObjsV5v0Group,
            tmnxTestHdNotifyV5v0Group
        }
       
    SUPPORTS TIMETRA-OAM-TEST-MIB
        INCLUDES    {
         -- tmnxOamAtmPingR2r1Group,         no ATM on SAS-M 7210
            tmnxOamCpePingV4v0Group,
            tmnxOamIcmpPingGroup,
         -- tmnxOamAncpTestV5v0Group,
            tmnxOamLspPingV6v0Group,
            tmnxOamLspTrV6v0Group,
            tmnxOamMacPingV4v0Group,
            tmnxOamVccvPingV5v0Group,
            tmnxOamMacTrV3v0Group,
         -- tmnxOamMcastTrV4v0Group,            no PIM on SAS-M 7210
         -- tmnxOamMRInfoV4v0Group,         no PIM on SAS-M 7210
            tmnxOamMfibPingV6v0Group,
            tmnxOamPingGeneralV7v0Group,
            tmnxOamPingNotificationV7v0Group,
            tmnxOamSaaGeneralV7v0Group,
            tmnxOamSaaThresholdV3v0Group,
            tmnxOamSaaNotificationV3v0Group,
            tmnxOamTrGeneralV7v0Group,
            tmnxOamTrHopsV4v0Group,
            tmnxOamTrNotificationV5v0Group,
            tmnxOamVccvTrV6v0Group
         -- tmnxOamVprnPingV4v0Group,             no VPRN on SAS-M 7210
         -- tmnxOamVprnTrV6v0Group,               no VPRN on SAS-M 7210
         -- EXCLUDE tmnxOamMacPingL2MapGroup
        }

        -- No VPRN for SAS-M 7210 : start
        -- No ATM for SAS-M 7210 : start
        VARIATION   tmnxOamPingCtlTestMode
            SYNTAX  INTEGER {
                        sdpPing     (1),
                        mtuPing     (2),
                        svcPing     (3),
                        -- macQuery (4),  obsolete
                        macPing     (5),
                        macPopulate (6),
                        macPurge    (7),
                        lspPing     (8),
                        -- vprnPing (9),      no VPRN on SAS-M 7210
                        -- atmPing  (10),     no ATM on SAS-M 7210
                        mfibPing    (11),
                        cpePing     (12),
                        -- mrInfo   (13)      no PIM on SAS-M 7210
                        vccvPing    (14),
                        icmpPing    (15),
                        dnsPing     (16),
                        ancpLoopback (17)
                        -- p2mpLspPing (18)   no P2MP LSP on SAS-M 7210
                    }
            DESCRIPTION
                    "The values 'vprnPing (9)', 'atmPing (10)', and
                    'mrInfo (13)' are invalid on a SAS-M 7210 system,
                    as ATM is not implemented.  The value 'p2mpLspPing (18)'
                    is invalid on a SAS-M 7210 system."
        -- No ATM for SAS-M 7210 : end

        VARIATION   tmnxOamLspPingCtlReturnLsp
            ACCESS  read-only
            DESCRIPTION
                    "The LSP return option is not supported for configuration
                    of OAM lspPing tests."

        VARIATION   tmnxOamSaaTThreshold
            DESCRIPTION
                    "The value of tmnxOamSaaTThreshold must be a multiple of
                     1000 when specifying a tmnxOamSaaTType with units of
                     microseconds."

        -- No PIM for SAS-M 7210 : begin
        VARIATION   tmnxOamTrCtlTestMode
            SYNTAX  INTEGER {
                        macTraceRoute      (1),
                        lspTraceRoute      (2)
                        -- vprnTraceRoute  (3),    no VPRN on SAS-M 7210
                        -- mcastTraceRoute (4)     no PIM on SAS-M 7210
                    }
            DESCRIPTION
                    "The values 'vprnTraceRoute (3)' and  'mcastTraceRoute (4)'
                    are invalid on a SAS-M 7210 system, as VPRN and PIM are not
                    implemented."
        -- No PIM for SAS-M 7210 : end
        -- No VPRN for SAS-M 7210 : end

        VARIATION tmnxOamTrCtlTrapGeneration
            SYNTAX BITS {
                        -- pathChange(0),  not supported
                        testFailure(1),
                        testCompletion(2)
            }
            DESCRIPTION
                "pathChange bit is not supported."      

        VARIATION tmnxOamLTtraceAutoAdminState
            ACCESS  not-implemented
            DESCRIPTION
                "Not supported."

        VARIATION tmnxOamLTtraceAutoDiscIntvl
            ACCESS  not-implemented
            DESCRIPTION
                "Not supported."

        VARIATION tmnxOamLTtraceAutoDiscoveryState
            ACCESS  not-implemented
            DESCRIPTION
                "Not supported."

        VARIATION tmnxOamLTtraceAutoDisFecs
            ACCESS  not-implemented
            DESCRIPTION
                "Not supported."

        VARIATION tmnxOamLTtraceAutoFcName
            ACCESS  not-implemented
            DESCRIPTION
                "Not supported."

        VARIATION tmnxOamLTtraceAutoLastChanged
            ACCESS  not-implemented
            DESCRIPTION
                "Not supported."

        VARIATION tmnxOamLTtraceAutoLastDisDur
            ACCESS  not-implemented
            DESCRIPTION
                "Not supported."

        VARIATION tmnxOamLTtraceAutoLastDisEnd
            ACCESS  not-implemented
            DESCRIPTION
                "Not supported."

        VARIATION tmnxOamLTtraceAutoLastDisStart
            ACCESS  not-implemented
            DESCRIPTION
                "Not supported."

        VARIATION tmnxOamLTtraceAutoMaxPath
            ACCESS  not-implemented
            DESCRIPTION
                "Not supported."

        VARIATION tmnxOamLTtraceAutoPolicy1
            ACCESS  not-implemented
            DESCRIPTION
                "Not supported."

        VARIATION tmnxOamLTtraceAutoPolicy2
            ACCESS  not-implemented
            DESCRIPTION
                "Not supported."

        VARIATION tmnxOamLTtraceAutoPolicy3
            ACCESS  not-implemented
            DESCRIPTION
                "Not supported."

        VARIATION tmnxOamLTtraceAutoPolicy4
            ACCESS  not-implemented
            DESCRIPTION
                "Not supported."

        VARIATION tmnxOamLTtraceAutoPolicy5
            ACCESS  not-implemented
            DESCRIPTION
                "Not supported."

        VARIATION tmnxOamLTtraceAutoPrMaxFailures
            ACCESS  not-implemented
            DESCRIPTION
                "Not supported."

        VARIATION tmnxOamLTtraceAutoProbeIntvl
            ACCESS  not-implemented
            DESCRIPTION
                "Not supported."

        VARIATION tmnxOamLTtraceAutoProfile
            ACCESS  not-implemented
            DESCRIPTION
                "Not supported."

        VARIATION tmnxOamLTtraceAutoPrTimeOut
            ACCESS  not-implemented
            DESCRIPTION
                "Not supported."

        VARIATION tmnxOamLTtraceAutoRowStatus
            ACCESS  not-implemented
            DESCRIPTION
                "Not supported."

        VARIATION tmnxOamLTtraceAutoStorageType
            ACCESS  not-implemented
            DESCRIPTION
                "Not supported."

        VARIATION tmnxOamLTtraceAutoTotalFecs
            ACCESS  not-implemented
            DESCRIPTION
                "Not supported."

        VARIATION tmnxOamLTtraceAutoTrMaxFailures
            ACCESS  not-implemented
            DESCRIPTION
                "Not supported."

        VARIATION tmnxOamLTtraceAutoTrMaxTtl
            ACCESS  not-implemented
            DESCRIPTION
                "Not supported."

        VARIATION tmnxOamLTtraceAutoTrTimeOut
            ACCESS  not-implemented
            DESCRIPTION
                "Not supported."

        VARIATION tmnxOamLTtraceCtlLdpPrefix
            ACCESS  not-implemented
            DESCRIPTION
                "Not supported."

        VARIATION tmnxOamLTtraceCtlLdpPrefixLen
            ACCESS  not-implemented
            DESCRIPTION
                "Not supported."

        VARIATION tmnxOamLTtraceCtlLdpPrefixType
            ACCESS  not-implemented
            DESCRIPTION
                "Not supported."

        VARIATION tmnxOamLTtraceCtlMaxPath
            ACCESS  not-implemented
            DESCRIPTION
                "Not supported."

        VARIATION tmnxOamLTtraceFecDiscoveryState
            ACCESS  not-implemented
            DESCRIPTION
                "Not supported."

        VARIATION tmnxOamLTtraceFecDisPaths
            ACCESS  not-implemented
            DESCRIPTION
                "Not supported."

        VARIATION tmnxOamLTtraceFecDisStatusBits
            ACCESS  not-implemented
            DESCRIPTION
                "Not supported."

        VARIATION tmnxOamLTtraceFecFailedHops
            ACCESS  not-implemented
            DESCRIPTION
                "Not supported."

        VARIATION tmnxOamLTtraceFecFailedProbes
            ACCESS  not-implemented
            DESCRIPTION
                "Not supported."

        VARIATION tmnxOamLTtraceFecLastDisEnd
            ACCESS  not-implemented
            DESCRIPTION
                "Not supported."

        VARIATION tmnxOamLTtraceFecProbeState
            ACCESS  not-implemented
            DESCRIPTION
                "Not supported."

        VARIATION tmnxOamLTtraceHopAddr
            ACCESS  not-implemented
            DESCRIPTION
                "Not supported."

        VARIATION tmnxOamLTtraceHopAddrType
            ACCESS  not-implemented
            DESCRIPTION
                "Not supported."

        VARIATION tmnxOamLTtraceHopDiscoveryState
            ACCESS  not-implemented
            DESCRIPTION
                "Not supported."

        VARIATION tmnxOamLTtraceHopDiscoveryTime
            ACCESS  not-implemented
            DESCRIPTION
                "Not supported."

        VARIATION tmnxOamLTtraceHopDisTtl
            ACCESS  not-implemented
            DESCRIPTION
                "Not supported."

        VARIATION tmnxOamLTtraceHopDstAddr
            ACCESS  not-implemented
            DESCRIPTION
                "Not supported."

        VARIATION tmnxOamLTtraceHopDstAddrType
            ACCESS  not-implemented
            DESCRIPTION
                "Not supported."

        VARIATION tmnxOamLTtraceHopEgrNhAddr
            ACCESS  not-implemented
            DESCRIPTION
                "Not supported."

        VARIATION tmnxOamLTtraceHopEgrNhAddrType
            ACCESS  not-implemented
            DESCRIPTION
                "Not supported."

        VARIATION tmnxOamLTtraceHopLastRc
            ACCESS  not-implemented
            DESCRIPTION
                "Not supported."

        VARIATION tmnxOamLTtraceMaxConRequests
            ACCESS  not-implemented
            DESCRIPTION
                "Not supported."

        VARIATION tmnxOamLTtracePathDisTtl
            ACCESS  not-implemented
            DESCRIPTION
                "Not supported."

        VARIATION tmnxOamLTtracePathEgrNhAddr
            ACCESS  not-implemented
            DESCRIPTION
                "Not supported."

        VARIATION tmnxOamLTtracePathEgrNhAddrType
            ACCESS  not-implemented
            DESCRIPTION
                "Not supported."

        VARIATION tmnxOamLTtracePathLastDisTime
            ACCESS  not-implemented
            DESCRIPTION
                "Not supported."

        VARIATION tmnxOamLTtracePathLastRc
            ACCESS  not-implemented
            DESCRIPTION
                "Not supported."

        VARIATION tmnxOamLTtracePathProbeState
            ACCESS  not-implemented
            DESCRIPTION
                "Not supported."

        VARIATION tmnxOamLTtracePathProbeTmOutCnt
            ACCESS  not-implemented
            DESCRIPTION
                "Not supported."

        VARIATION tmnxOamLTtracePathRemAddrType
            ACCESS  not-implemented
            DESCRIPTION
                "Not supported."

        VARIATION tmnxOamLTtracePathRemoteAddr
            ACCESS  not-implemented
            DESCRIPTION
                "Not supported."

        VARIATION tmnxOamLTtraceResultsDisPaths
            ACCESS  not-implemented
            DESCRIPTION
                "Not supported."

        VARIATION tmnxOamLTtraceResultsDisState
            ACCESS  not-implemented
            DESCRIPTION
                "Not supported."

        VARIATION tmnxOamLTtraceResultsDisStatus
            ACCESS  not-implemented
            DESCRIPTION
                "Not supported."

        VARIATION tmnxOamLTtraceResultsFailedHops
            ACCESS  not-implemented
            DESCRIPTION
                "Not supported."

        VARIATION tmnxOamLTtraceUpStreamHopIndex
            ACCESS  not-implemented
            DESCRIPTION
                "Not supported."

        VARIATION tmnxOamPingCtlProfile
            ACCESS  not-implemented
            DESCRIPTION
                "Not supported."

        VARIATION tmnxOamTrCtlProfile
            ACCESS  not-implemented
            DESCRIPTION
                "Not supported."

        VARIATION tmnxOamVccvTrNextPwID
            ACCESS  not-implemented
            DESCRIPTION
                "Not supported."

        VARIATION tmnxOamVccvTrNextPwType
            ACCESS  not-implemented
            DESCRIPTION
                "Not supported."

        VARIATION tmnxOamVccvTrNextSenderAddrType
            ACCESS  not-implemented
            DESCRIPTION
                "Not supported."

        VARIATION tmnxOamVccvTrNextSenderAddr
            ACCESS  not-implemented
            DESCRIPTION
                "Not supported."

        VARIATION tmnxOamVccvTrNextRemoteAddrType
            ACCESS  not-implemented
            DESCRIPTION
                "Not supported."

        VARIATION tmnxOamVccvTrNextRemoteAddr
            ACCESS  not-implemented
            DESCRIPTION
                "Not supported."

    ::= { tmnxSASM7210V6v0 24 }

--
--  PORT CAPABILITIES
--
tmnxPortCapsSASM7210V6v0 AGENT-CAPABILITIES
    PRODUCT-RELEASE "Alcatel SAS-M 7210"
    STATUS current
            DESCRIPTION
        "Implementation of hardware port capabilities
         for Alcatel SAS-M 7210 release R6.0"

    SUPPORTS TIMETRA-PORT-MIB
        INCLUDES    {
            tmnxPortGroupV7v0,
            tmnxPortEthernetV7v0Group,
            -- tmnxPortSonetV3v0Group,
            -- tmnxPortTDMGroupV6v0,
            tmnxPortTDMGroupV7v0,
            -- tmnxPortFRGroup,
            tmnxQosAppObjsGroup,
            -- EXCLUDE tmnxPortTestGroup,            (not implemented)
            tmnxPortNotificationGroupV7v0,
            -- tmnxPortIngrMdaQosStatR2r1Group,
            -- tmnxPortATMGroupV4v0,                  no ATM on SAS-M 7210
            tmnxPortStatsR2r1Group,
            -- tmnxCiscoHDLCGroup,                    no CISCO-HDLC on SAS-M 7210
            tmnxScalarPortV3v0Group,
            -- tmnxMlBundleGroupV6v0                  no MLBundle on SAS-M 7210
            -- tmnxMlImaBundleGroup                   no IMABundle on SAS-M 7210
            -- tmnxPortSchedV5v0Group
            -- tmnxMcMlpppBundleGroup                 no McMlppp on SAS-M 7210
            tmnx7710PortTDMGroupV5v0,
            tmnxPortCemGroupV6v0,
            -- tmnxMlpppBundleGroup                   no MLPPP Bundles on SAS-M 7210
            -- tmnxNamedPoolGroupV6v0,
            -- tmnxHsmdaGroupV6v0,
            tmnxDigitalDiagMonitorGroup
            -- tmnxPortTDME1GroupV6v1
                    }

        VARIATION   tmnxPortEntry
            DESCRIPTION
                    "Vports are created by routed TLS and cannot be modified.
                    Management ports cannot be modified."

        VARIATION   tmnxPortClearAlarms
            ACCESS  read-only
            DESCRIPTION
                    "read-only implementation."

        VARIATION   tmnxPortMode
            DESCRIPTION
                    "tmnxPortMode is implemented as read-only for LAG ports
                    channelized interfaces, Multi-Link PPP (MLPPP) and IMA
                    bundles, ATM ports."

        VARIATION   tmnxPortAlias
            DESCRIPTION
                    "tmnxPortAlias is implemented as read-only for LAG ports."

        
        VARIATION   tmnxPortEtherDot1qEtype
            DESCRIPTION
                    "Not Supported."                         

        VARIATION   tmnxPortDescription
            DESCRIPTION
                    "tmnxPortDescription is implemented as read-only for
                    LAG ports."

        -- no ATM on SAS-M 7210: begin
        -- no CISCO-HDLC on SAS-M 7210: begin
        -- no CEM on SAS-M 7210: begin
        VARIATION   tmnxPortEncapType
            SYNTAX  INTEGER {
                        unknown            (0),
                        nullEncap          (1),
                        qEncap             (2),
                        mplsEncap          (3),
                        bcpNullEncap       (4),
                        bcpDot1qEncap      (5),
                        ipcpEncap          (6),
                        frEncap            (7),
                        pppAutoEncap       (8),
                        -- atmEncap        (9),     no ATM on SAS-M 7210
                        qinqEncap          (10),
                        wanMirrorEncap     (11)
                        -- ciscoHDLCEncap  (12),    no Cisco HDLC on SAS-M 7210
                        -- cemEncap        (13)     no CEM on SAS-M 7210
                    }
            DESCRIPTION
                    "tmnxPortEncapType is implemented as read-only for
                    Multi-Link PPP (MLPPP) bundles and IMA bundles.
                    Also the values 'atmEncap (9)', 'ciscoHDLCEncap (12)' and
                    'cemEncap (13)' are not suported on SAS-M 7210."
        -- no CEM on SAS-M 7210: end
        -- no CISCO-HDLC on SAS-M 7210: end
        -- no ATM on SAS-M 7210: end

        VARIATION   tmnxPortHoldTimeUp
            DESCRIPTION
                    "tmnxPortHoldTimeUp is implemented as read-only for
                    LAG ports, Multi-Link PPP (MLPPP) bundles, and
                    IMA bundles."

        VARIATION   tmnxPortHoldTimeDown
            DESCRIPTION
                    "tmnxPortHoldTimeDown is implemented as read-only for
                    LAG ports, Multi-Link PPP (MLPPP) bundles, and
                    IMA bundles."

        VARIATION   tmnxPortNetworkEgrQueues
    DESCRIPTION
                    "tmnxPortNetworkEgrQueues is implemented as read-only for
                    LAG ports, Multi-Link PPP (MLPPP) bundles and IMA bundles.

                    tmnxPortNetworkEgrQueues can only be modified for
                    channels and ethernet ports."

        VARIATION   tmnxPortEtherMTU
            DESCRIPTION
                    "tmnxPortEtherMTU is implemented as read-only for
                    LAG ports."

        VARIATION   tmnxPortEtherDuplex
            DESCRIPTION
                    "tmnxPortEtherDuplex is implemented as read-only for
                    LAG ports that are not the primary LAG port."

        VARIATION   tmnxPortEtherSpeed
            DESCRIPTION
                    "tmnxPortEtherSpeed is implemented as read-only for
                    LAG ports that are not the primary LAG port."

        VARIATION   tmnxPortEtherAutoNegotiate
            DESCRIPTION
                    "tmnxPortEtherAutoNegotiate is implemented as read-only for
                    LAG ports that are not the primary LAG port."

        VARIATION   tmnxPortEtherAcctPolicyId
            DESCRIPTION
                    "tmnxPortEtherAcctPolicyId is implemented as read-only for
                    LAG ports that are not the primary LAG port."

        VARIATION   tmnxPortEtherCollectStats
            DESCRIPTION
                    "tmnxPortEtherCollectStats is implemented as read-only
                    for LAG ports that are not the primary LAG port."

        VARIATION   tmnxPortEtherXGigMode
            DESCRIPTION
                    "tmnxPortEtherXGigMode is implemented as read-only
                    for LAG ports that are not the primary LAG port."

        VARIATION   tmnxPortEtherEgressRate
            DESCRIPTION
                    "tmnxPortEtherEgressRate is implemented as read-only
                    for LAG ports that are not the primary LAG port."

        VARIATION   tmnxDS3ChannelChannelized
            SYNTAX  INTEGER {
                    none   (1),
                    ds1    (2),
                    e1     (3)
                    -- j1  (4)
                }
            DESCRIPTION
                    "tmnxDS3ChannelChannelized value of 'j1 (4)' is not
                    supported."

        VARIATION  tmnxSonetPathRowStatus
            SYNTAX  INTEGER {
                        active      (1),
                        createAndGo (4),
                        destroy     (6)
                    }
            DESCRIPTION
                    "tmnxSonetPathRowStatus supports only the values
                    'active (1)', 'createAndGo (4)' and 'destroy (6)'."

        VARIATION   tmnxDS3Buildout
            ACCESS not-implemented
            DESCRIPTION
                "tmnxDS3Buildout is not supported"

        VARIATION   tmnxDS3ChannelAcctPolicyId
            ACCESS not-implemented
            DESCRIPTION
                "tmnxDS3ChannelAcctPolicyId is not supported"

        VARIATION   tmnxDS3ChannelBERTDuration
            ACCESS not-implemented
            DESCRIPTION
                "tmnxDS3ChannelBERTDuration is not supported"

        VARIATION   tmnxDS3ChannelBERTErrors
            ACCESS not-implemented
            DESCRIPTION
                "tmnxDS3ChannelBERTErrors is not supported"

        VARIATION   tmnxDS3ChannelBERTOperStatus
            ACCESS not-implemented
            DESCRIPTION
                "tmnxDS3ChannelBERTOperStatus is not supported"

        VARIATION   tmnxDS3ChannelBERTPattern
            ACCESS not-implemented
            DESCRIPTION
                "tmnxDS3ChannelBERTPattern is not supported"

        VARIATION   tmnxDS3ChannelBERTSynched
            ACCESS not-implemented
            DESCRIPTION
                "tmnxDS3ChannelBERTSynched is not supported"

        VARIATION   tmnxDS3ChannelBERTTotalBits
            ACCESS not-implemented
            DESCRIPTION
                "tmnxDS3ChannelBERTTotalBits is not supported"

        VARIATION   tmnxDS3ChannelBitErrorInsertionRate
            ACCESS not-implemented
            DESCRIPTION
                "tmnxDS3ChannelBitErrorInsertionRate is not supported"

        VARIATION   tmnxDS3ChannelCRC
            ACCESS not-implemented
            DESCRIPTION
                "tmnxDS3ChannelCRC is not supported"

        VARIATION   tmnxDS3ChannelChannelized
            ACCESS not-implemented
            DESCRIPTION
                "tmnxDS3ChannelChannelized is not supported"

        VARIATION   tmnxDS3ChannelClockMasterPortId
            ACCESS not-implemented
            DESCRIPTION
                "tmnxDS3ChannelClockMasterPortId is not supported"

        VARIATION   tmnxDS3ChannelClockSource
            ACCESS not-implemented
            DESCRIPTION
                "tmnxDS3ChannelClockSource is not supported"

        VARIATION   tmnxDS3ChannelClockSyncState
            ACCESS not-implemented
            DESCRIPTION
                "tmnxDS3ChannelClockSyncState is not supported"

        VARIATION   tmnxDS3ChannelCollectStats
            ACCESS not-implemented
            DESCRIPTION
                "tmnxDS3ChannelCollectStats is not supported"

        VARIATION   tmnxDS3ChannelFEACLoopRespond
            ACCESS not-implemented
            DESCRIPTION
                "tmnxDS3ChannelFEACLoopRespond is not supported"

        VARIATION   tmnxDS3ChannelFraming
            ACCESS not-implemented
            DESCRIPTION
                "tmnxDS3ChannelFraming is not supported"

        VARIATION   tmnxDS3ChannelIdleCycleFlags
            ACCESS  not-implemented
            DESCRIPTION
                "tmnxDS3ChannelIdleCycleFlags is not supported"

        VARIATION   tmnxDS3ChannelInFEACLoop
            ACCESS not-implemented
            DESCRIPTION
                "tmnxDS3ChannelInFEACLoop is not supported"

        VARIATION   tmnxDS3ChannelLastChangeTime
        ACCESS  not-implemented
        DESCRIPTION
                "tmnxDS3ChannelLastChangeTime is not supported"

        VARIATION   tmnxDS3ChannelLoopback
        ACCESS  not-implemented
        DESCRIPTION
                "tmnxDS3ChannelLoopback is not supported"

        VARIATION   tmnxDS3ChannelMDLEicString
        ACCESS  not-implemented
        DESCRIPTION
                "tmnxDS3ChannelMDLEicString is not supported"

        VARIATION   tmnxDS3ChannelMDLFicString
        ACCESS  not-implemented
        DESCRIPTION
                "tmnxDS3ChannelMDLFicString is not supported"

        VARIATION   tmnxDS3ChannelMDLGenString
        ACCESS  not-implemented
        DESCRIPTION
                "tmnxDS3ChannelMDLGenString is not supported"

        VARIATION   tmnxDS3ChannelMDLLicString
        ACCESS  not-implemented
        DESCRIPTION
                "tmnxDS3ChannelMDLLicString is not supported"

        VARIATION   tmnxDS3ChannelMDLMessageType
        ACCESS  not-implemented
        DESCRIPTION
                "tmnxDS3ChannelMDLMessageType is not supported"

        VARIATION   tmnxDS3ChannelMDLMonGenString
        ACCESS  not-implemented
        DESCRIPTION
                "tmnxDS3ChannelMDLMonGenString is not supported"

        VARIATION   tmnxDS3ChannelMDLMonPortString
        ACCESS  not-implemented
        DESCRIPTION
                "tmnxDS3ChannelMDLMonPortString is not supported"

        VARIATION   tmnxDS3ChannelMDLPfiString
        ACCESS  not-implemented
        DESCRIPTION
                "tmnxDS3ChannelMDLPfiString is not supported"

        VARIATION   tmnxDS3ChannelMDLPortString
        ACCESS  not-implemented
        DESCRIPTION
                "tmnxDS3ChannelMDLPortString is not supported"

        VARIATION   tmnxDS3ChannelMDLUnitString
        ACCESS  not-implemented
        DESCRIPTION
                "tmnxDS3ChannelMDLUnitString is not supported"

        VARIATION   tmnxDS3ChannelMTU
        ACCESS  not-implemented
        DESCRIPTION
                "tmnxDS3ChannelMTU is not supported"

        VARIATION   tmnxDS3ChannelOperMTU
        ACCESS  not-implemented
        DESCRIPTION
                "tmnxDS3ChannelOperMTU is not supported"

        VARIATION   tmnxDS3ChannelReportAlarm
        ACCESS  not-implemented
        DESCRIPTION
                "tmnxDS3ChannelReportAlarm is not supported"

        VARIATION   tmnxDS3ChannelReportAlarmStatus
            ACCESS  not-implemented
    DESCRIPTION
                "tmnxDS3ChannelReportAlarmStatus is not supported"

        VARIATION   tmnxDS3ChannelRowStatus
            ACCESS  not-implemented
            DESCRIPTION
                "tmnxDS3ChannelRowStatus is not supported"

        VARIATION   tmnxDS3ChannelScramble
            ACCESS  not-implemented
            DESCRIPTION
                "tmnxDS3ChannelScramble is not supported"

        VARIATION   tmnxDS3ChannelSubrate
            ACCESS  not-implemented
            DESCRIPTION
                "tmnxDS3ChannelSubrate is not supported"

        VARIATION   tmnxDS3ChannelSubrateCSUMode
            ACCESS  not-implemented
            DESCRIPTION
                "tmnxDS3ChannelSubrateCSUMode is not supported"

        VARIATION   tmnxDS3ChannelType
            ACCESS  not-implemented
            DESCRIPTION
                "tmnxDS3ChannelType is not supported"

        VARIATION   tmnxDS3LastChangeTime
            ACCESS  not-implemented
            DESCRIPTION
                "tmnxDS3LastChangeTime is not supported"

        VARIATION   tmnxDS3Type
            ACCESS  not-implemented
            DESCRIPTION
                "tmnxDS3Type is not supported"

        VARIATION   tmnxDS1InvertData
            ACCESS  not-implemented
            DESCRIPTION
                "Not supported."

        VARIATION   tmnxDS1BitErrorInsertionRate
            ACCESS  not-implemented
            DESCRIPTION
                "Not supported."

        VARIATION   tmnxDS1BERTPattern
            ACCESS  not-implemented
            DESCRIPTION
                "Not supported."

        VARIATION   tmnxDS1BERTDuration
            ACCESS  not-implemented
            DESCRIPTION
                "Not supported."

        VARIATION   tmnxDS1BERTOperStatus
            ACCESS  not-implemented
            DESCRIPTION
                "Not supported."

        VARIATION   tmnxDS1BERTSynched
            ACCESS  not-implemented
            DESCRIPTION
                "Not supported."

        VARIATION   tmnxDS1BERTErrors
            ACCESS  not-implemented
            DESCRIPTION
                "Not supported."

        VARIATION   tmnxDS1BERTTotalBits
            ACCESS  not-implemented
            DESCRIPTION
                "Not supported."

        VARIATION   tmnxDS1InRemoteLoop
            ACCESS  not-implemented
            DESCRIPTION
                "Not supported."

        VARIATION   tmnxDS1InsertSingleBitError
            ACCESS  not-implemented
            DESCRIPTION
                "Not supported."

        VARIATION   tmnxDS1BerSdThreshold
            ACCESS  not-implemented
            DESCRIPTION
                    "Not supported."

        VARIATION   tmnxDS1BerSfThreshold
            ACCESS  not-implemented
            DESCRIPTION
                    "Not supported."

        VARIATION   tmnxDS0ChanGroupScramble
            ACCESS  not-implemented
            DESCRIPTION
                "Not supported."

        VARIATION   tmnxDS0ChanGroupBerSfLinkDown
            ACCESS  not-implemented
            DESCRIPTION
                "Not supported."

        VARIATION   tmnxOpticalPortHasRxAmplifier
            ACCESS  not-implemented
            DESCRIPTION
                "Not supported."
                
        VARIATION   tmnxOpticalPortHasRxTdcm
            ACCESS  not-implemented
            DESCRIPTION
                "Not supported."

        VARIATION   tmnxOpticalPortAmpPowerIn
            ACCESS  not-implemented
            DESCRIPTION
                "Not supported."

        VARIATION   tmnxOpticalPortAmpGain
            ACCESS  not-implemented
            DESCRIPTION
                "Not supported."

        VARIATION   tmnxOpticalPortAmpPowerOut
            ACCESS  not-implemented
            DESCRIPTION
                "Not supported."

        VARIATION   tmnxOpticalPortAmpPumpTemp
            ACCESS  not-implemented
            DESCRIPTION
                "Not supported."

        VARIATION   tmnxOpticalPortAmpModuleTemp
            ACCESS  not-implemented
            DESCRIPTION
                "Not supported."

        VARIATION   tmnxOpticalPortAmpPumpCurrent
            ACCESS  not-implemented
            DESCRIPTION
                "Not supported."

        VARIATION   tmnxOpticalPortAmpAlarmState
            ACCESS  not-implemented
            DESCRIPTION
                "Not supported."

        VARIATION   tmnxOpticalPortAmpSerialNum
            ACCESS  not-implemented
            DESCRIPTION
                "Not supported."

        VARIATION   tmnxOpticalPortAmpCtrlState
            ACCESS  not-implemented
            DESCRIPTION
                "Not supported."

        VARIATION   tmnxOpticalPortTdcmPowerIn
            ACCESS  not-implemented
            DESCRIPTION
                "Not supported."

        VARIATION   tmnxOpticalPortTdcmLoss
            ACCESS  not-implemented
            DESCRIPTION
                "Not supported."

        VARIATION   tmnxOpticalPortTdcmPowerOut
            ACCESS  not-implemented
            DESCRIPTION
                "Not supported."

        VARIATION   tmnxOpticalPortTdcmRtd1Temp
            ACCESS  not-implemented
            DESCRIPTION
                "Not supported."

        VARIATION   tmnxOpticalPortTdcmRtd2Temp
            ACCESS  not-implemented
            DESCRIPTION
                "Not supported."

        VARIATION   tmnxOpticalPortTdcmRtd3Temp
            ACCESS  not-implemented
            DESCRIPTION
                "Not supported."

        VARIATION   tmnxOpticalPortTdcmRtd4Temp
            ACCESS  not-implemented
            DESCRIPTION
                "Not supported."

        VARIATION   tmnxOpticalPortTdcmModuleTemp
            ACCESS  not-implemented
            DESCRIPTION
                "Not supported."

        VARIATION   tmnxOpticalPortTdcmMinDisp
            ACCESS  not-implemented
            DESCRIPTION
                "Not supported."

        VARIATION   tmnxOpticalPortTdcmMaxDisp
            ACCESS  not-implemented
            DESCRIPTION
                "Not supported."

        VARIATION   tmnxOpticalPortTdcmAutoDisp
            ACCESS  not-implemented
            DESCRIPTION
                "Not supported."

        VARIATION   tmnxOpticalPortTdcmMeasDisp
            ACCESS  not-implemented
            DESCRIPTION
                "Not supported."

        VARIATION   tmnxOpticalPortTdcmPresRxChan
            ACCESS  not-implemented
            DESCRIPTION
                "Not supported."

        VARIATION   tmnxOpticalPortTdcmAlarmState
            ACCESS  not-implemented
            DESCRIPTION
                "Not supported."

        VARIATION   tmnxOpticalPortTdcmSerialNum
            ACCESS  not-implemented
            DESCRIPTION
                "Not supported."

        VARIATION   tmnxOpticalPortTdcmCtrlState
            ACCESS  not-implemented
            DESCRIPTION
                "Not supported."


        VARIATION  tmnxDS1Type
            SYNTAX  INTEGER {
                        ds1(1),
                        e1 (2)
                     -- j1 (3)
                    }
            DESCRIPTION
                    "Only ds1 and e1 supported."

        VARIATION  tmnxDS1Loopback
            SYNTAX  INTEGER {
                       none (0),
                       line (1),
                       internal (2)
                    -- fdlAnsi (3),
                    -- fdlBellcore (4),
                    -- payloadAnsi (5),
                    -- inbandAnsi  (6),
                    -- inbandBellcore (7)
                    }
            DESCRIPTION
                    "Only none(0), line(1) and internal(2) supported."

        VARIATION  tmnxDS1ClockSource
            SYNTAX  INTEGER {
                       loopTimed    (1),
                       nodeTimed    (2),
                       adaptive     (3)
                    -- differential (4)
                    }
            DESCRIPTION
                    "differential(4) not supported."

        VARIATION   tmnxDS0ChanGroupAcctPolicyId
            ACCESS  not-implemented
            DESCRIPTION
                "Not supported."

        VARIATION   tmnxDS0ChanGroupCollectStats
            ACCESS  not-implemented
            DESCRIPTION
                "Not supported."

        VARIATION   tmnxL4LoadBalancing
            ACCESS  not-implemented
            DESCRIPTION
                "Not supported."

        VARIATION   tmnxPortLoadBalanceAlgorithm
            ACCESS  not-implemented
            DESCRIPTION
                "Not supported."

        VARIATION   tmnxSonetSuppressLoOrderAlarm
            ACCESS  not-implemented
            DESCRIPTION
                "Not supported."

        VARIATION   tmnxObjectType
            SYNTAX  INTEGER {
                    mda (1),
                    port (2),
                    channel (3),
                    bundle (4)
                    -- mpointQueues (51)      added for 7210
                    }
            DESCRIPTION
                    "The value 'mpointQueues (51)' is not supported."

        VARIATION   tmnxObjectAppType
            SYNTAX  INTEGER {
                    accessIngress (1),
                    accessEgress (2),
                    networkIngress (3),
                    networkEgress (4)
                    -- system (51)      added for 7210
                    }
            DESCRIPTION
                    "The value 'system (51)' is not supported."

    SUPPORTS TIMETRA-SAS-PORT-MIB
        INCLUDES    {
            tmnxSASPortV1v0Group,
            tmnxSASPortV1v1Group,
            tmnxSASPortV2v0Group,
            tmnxSASPortV3v0Group,
            tmnxSASPortV6v0Group
        }

     VARIATION   tmnxPortEtherClockConfig
         ACCESS  not-implemented
         DESCRIPTION
             "Not supported."

    VARIATION tmnxSASPortNetIngressFwdInProfPkts
        ACCESS not-implemented
        DESCRIPTION
            "Not supported."

    VARIATION tmnxSASPortNetIngressFwdOutProfPkts
        ACCESS not-implemented
        DESCRIPTION
            "Not supported."

    VARIATION tmnxSASPortNetIngressFwdInProfOcts
        ACCESS not-implemented
        DESCRIPTION
            "Not supported."

    VARIATION tmnxSASPortNetIngressFwdOutProfOcts
        ACCESS not-implemented
        DESCRIPTION
            "Not supported."

    VARIATION tmnxPortStatsQueue1PktsFwd
        ACCESS not-implemented
        DESCRIPTION
            "Not supported."

    VARIATION tmnxPortStatsQueue2PktsFwd
        ACCESS not-implemented
        DESCRIPTION
            "Not supported."

    VARIATION tmnxPortStatsQueue3PktsFwd
        ACCESS not-implemented
        DESCRIPTION
            "Not supported."

    VARIATION tmnxPortStatsQueue4PktsFwd
        ACCESS not-implemented
        DESCRIPTION
            "Not supported."

    VARIATION tmnxPortStatsQueue5PktsFwd
        ACCESS not-implemented
        DESCRIPTION
            "Not supported."

    VARIATION tmnxPortStatsQueue6PktsFwd
        ACCESS not-implemented
        DESCRIPTION
            "Not supported."

    VARIATION tmnxPortStatsQueue7PktsFwd
        ACCESS not-implemented
        DESCRIPTION
            "Not supported."

    VARIATION tmnxPortStatsQueue8PktsFwd
        ACCESS not-implemented
        DESCRIPTION
            "Not supported."

    VARIATION tmnxPortNetEgressQueueStatsInProfDroPkts
        ACCESS not-implemented
        DESCRIPTION
            "Not supported."

    VARIATION tmnxPortNetEgressQueueStatsInProfDroOcts
        ACCESS not-implemented
        DESCRIPTION
            "Not supported."

    VARIATION tmnxPortNetEgressQueueStatsOutProfDroPkts
        ACCESS not-implemented
        DESCRIPTION
            "Not supported."

    VARIATION tmnxPortNetEgressQueueStatsOutProfDroOcts
        ACCESS not-implemented
        DESCRIPTION
            "Not supported."

        VARIATION tmnxPortEtherNwAggRateLimit
            ACCESS  not-implemented
            DESCRIPTION
                "Not supported."                                

    ::= { tmnxSASM7210V6v0 25 }

--
--  QOS Capabilities
--
tmnxQosCapsSASM7210V6v0 AGENT-CAPABILITIES
    PRODUCT-RELEASE "Alcatel SAS-M 7210"
    STATUS current
    DESCRIPTION
        "Implementation of Quality of Service, QoS, capabilities
         for Alcatel SAS-M 7210 release R6.0"

    SUPPORTS TIMETRA-QOS-MIB
        INCLUDES    {
            tmnxQosGlobalGroup,
            tmnxQosDSCPGroup,
            tmnxQosFCGroup,
            tmnxQosSapIngressV6v0Group,
         -- tmnxQosSapEgressV6v0Group,
            tmnxQosNetworkV7v0Group,
            tmnxQosSlopeGroup,
            tmnxQosSchedulerV5v0Group,
         -- tmnxQosAtmTdpV5v0Group,       no ATM on SAS-M 7210
         -- tmnxQosQueueV4v0Group,
         -- tmnxQosSapIpv6FilterR4r0Group  no ipv6 on SAS-M 7210
         -- tmnxQosHsmdaV7v0Group,
         -- tmnxQosFrameBasedV6v0Group
         -- tmnxQosNamedPoolPolicyV6v0Group,
         -- tmnxQosMcMlpppIngrGroup,
         -- tmnxQosMcMlpppEgrGroup,
            tQosQGrpFCGroup,
            tmnxQosQueueGrpPolcrV10v0Group,
            tmnxQosPolicyV10v0Group,
            tmnxQosHsmdaV9v0Group,
            tmnxQosAdvConfigV10v0Group
        }

       VARIATION  tAdvCfgPolicyName           
            ACCESS not-implemented
            DESCRIPTION
                "Not supported."

        VARIATION  tAdvCfgPolicyRowStatus      
            ACCESS not-implemented
            DESCRIPTION
                "Not supported."

        VARIATION  tAdvCfgLastChanged          
            ACCESS not-implemented
            DESCRIPTION
                "Not supported."

        VARIATION  tAdvCfgDescription          
            ACCESS not-implemented
            DESCRIPTION
                "Not supported."

        VARIATION  tAdvCfgChildAdmnPirPrcnt    
            ACCESS not-implemented
            DESCRIPTION
                "Not supported."

        VARIATION  tAdvCfgChildAdminRate       
            ACCESS not-implemented
            DESCRIPTION
                "Not supported."

        VARIATION  tAdvCfgOMGranPirPrcnt       
            ACCESS not-implemented
            DESCRIPTION
                "Not supported."

        VARIATION  tAdvCfgOMGranRate           
            ACCESS not-implemented
            DESCRIPTION
                "Not supported."

        VARIATION  tAdvCfgMaxDecPirPrcnt       
            ACCESS not-implemented
            DESCRIPTION
                "Not supported."

        VARIATION  tAdvCfgMaxDecRate           
            ACCESS not-implemented
            DESCRIPTION
                "Not supported."

        VARIATION  tAdvCfgHiRateHoldTime       
            ACCESS not-implemented
            DESCRIPTION
                "Not supported."

        VARIATION  tAdvCfgTimeAvgFactor        
            ACCESS not-implemented
            DESCRIPTION
                "Not supported."

        VARIATION  tAdvCfgSampleInterval       
            ACCESS not-implemented
            DESCRIPTION
                "Not supported."

        VARIATION  tAdvCfgFastStart            
            ACCESS not-implemented
            DESCRIPTION
                "Not supported."

        VARIATION  tAdvCfgFastStop             
            ACCESS not-implemented
            DESCRIPTION
                "Not supported."

        VARIATION  tAdvCfgAbvOffCapPirPrcnt    
            ACCESS not-implemented
            DESCRIPTION
                "Not supported."

        VARIATION  tAdvCfgAbvOffCapRate        
            ACCESS not-implemented
            DESCRIPTION
                "Not supported."

        VARIATION  tAdvCfgBWDGranPirPrcnt      
            ACCESS not-implemented
            DESCRIPTION
                "Not supported."

        VARIATION  tAdvCfgBWDGranRate          
            ACCESS not-implemented
            DESCRIPTION
                "Not supported."

        VARIATION  tAdvCfgMinOnly              
            ACCESS not-implemented
            DESCRIPTION
                "Not supported."

        VARIATION  tAdvCfgDecOnly 
            ACCESS not-implemented
            DESCRIPTION
                "Not supported."

        VARIATION   tSapEgressMatchCriteria
            SYNTAX  INTEGER {
                        ip(1),
                        -- mac(2),
                        none(3)
                    }
            DESCRIPTION
                    "tSapEgressMatchCriteria does not support the value
                    'mac' as defined by the TMatchCriteria
                    textual convention."

        VARIATION   tSapEgrIPCritSourceIpAddrType
            SYNTAX  INTEGER {
                        unknown     (0),
                        ipv4        (1)
                        -- ipv6     (2),
                        -- ipv4z    (3),
                        -- ipv6z    (4),
                        -- dns      (16)
                    }
            DESCRIPTION
                    "tSapEgrIPCritSourceIpAddrType only supports the values
                    'none' and 'ipv4' as defined by the InetAddressType
                    textual convention."

        VARIATION   tSapEgrIPCritDestIpAddrType
            SYNTAX  INTEGER {
                        unknown     (0),
                        ipv4        (1)
                        -- ipv6     (2),
                        -- ipv4z    (3),
                        -- ipv6z    (4),
                        -- dns      (16)
        }
            DESCRIPTION
                    "tSapEgrIPCritDestIpAddrType only supports the values
                    'none' and 'ipv4' as defined by the InetAddressType
                    textual convention."

         VARIATION   tHsmdaWrrPolicyName                 
            ACCESS  not-implemented
            DESCRIPTION
                "Not supported."

        VARIATION   tHsmdaWrrPolicyRowStatus            
            ACCESS  not-implemented
            DESCRIPTION
                "Not supported."

        VARIATION  tHsmdaWrrPolicyLastChanged          
            ACCESS  not-implemented
            DESCRIPTION
                "Not supported."

        VARIATION  tHsmdaWrrPolicyDescription          
            ACCESS  not-implemented
            DESCRIPTION
                "Not supported."

        VARIATION  tHsmdaWrrPolicyIncludeQueues        
            ACCESS  not-implemented
            DESCRIPTION
                "Not supported."

        VARIATION   tHsmdaWrrPolicySchedUsingClass      
            ACCESS  not-implemented
            DESCRIPTION
                "Not supported."

        VARIATION  tHsmdaWrrPolicyAggWeightAtClass
            ACCESS  not-implemented
            DESCRIPTION
                "Not supported."

       VARIATION   tSapEgressPolicyName
            ACCESS  not-implemented
            DESCRIPTION
                "Not supported."

        VARIATION  tNetworkQueuePoolName 
            ACCESS not-implemented
            DESCRIPTION
                   "tNetworkQueuePoolName is not supported on SAS-M."

        VARIATION  tNetworkQueue
            SYNTAX TQueueId (1..8)
            DESCRIPTION
                   "Only 8 queues on the network port."

        VARIATION tPortSchedulerPlcyLvl1CIR
            ACCESS  not-implemented
            DESCRIPTION
                "Not supported."

        VARIATION tPortSchedulerPlcyLvl1PIR
            ACCESS  not-implemented
            DESCRIPTION
                "Not supported."

        VARIATION tPortSchedulerPlcyLvl2CIR
            ACCESS  not-implemented
            DESCRIPTION
                "Not supported."

        VARIATION tPortSchedulerPlcyLvl2PIR
            ACCESS  not-implemented
            DESCRIPTION
                "Not supported."

        VARIATION tPortSchedulerPlcyLvl3CIR
            ACCESS  not-implemented
            DESCRIPTION
                "Not supported."

        VARIATION tPortSchedulerPlcyLvl3PIR
            ACCESS  not-implemented
            DESCRIPTION
                "Not supported."

        VARIATION tPortSchedulerPlcyLvl4CIR
            ACCESS  not-implemented
            DESCRIPTION
                "Not supported."

        VARIATION tPortSchedulerPlcyLvl4PIR
            ACCESS  not-implemented
            DESCRIPTION
                "Not supported."

        VARIATION tPortSchedulerPlcyLvl5CIR
            ACCESS  not-implemented
            DESCRIPTION
                "Not supported."

        VARIATION tPortSchedulerPlcyLvl5PIR
            ACCESS  not-implemented
            DESCRIPTION
                "Not supported."

        VARIATION tPortSchedulerPlcyLvl6CIR
            ACCESS  not-implemented
            DESCRIPTION
                "Not supported."

        VARIATION tPortSchedulerPlcyLvl6PIR
            ACCESS  not-implemented
            DESCRIPTION
                "Not supported."

        VARIATION tPortSchedulerPlcyLvl7CIR
            ACCESS  not-implemented
            DESCRIPTION
                "Not supported."

        VARIATION tPortSchedulerPlcyLvl7PIR
            ACCESS  not-implemented
            DESCRIPTION
                "Not supported."

        VARIATION tPortSchedulerPlcyLvl8CIR
            ACCESS  not-implemented
            DESCRIPTION
                "Not supported."

        VARIATION tPortSchedulerPlcyLvl8PIR
            ACCESS  not-implemented
            DESCRIPTION
                "Not supported."

        VARIATION tPortSchedulerPlcyMaxRate
            ACCESS  not-implemented
            DESCRIPTION
                "Not supported."

        VARIATION tPortSchedulerPlcyOrphanCIRLvl
            ACCESS  not-implemented
            DESCRIPTION
                "Not supported."

        VARIATION tPortSchedulerPlcyOrphanCIRWght
            ACCESS  not-implemented
            DESCRIPTION
                "Not supported."

        VARIATION tPortSchedulerPlcyOrphanLvl
            ACCESS  not-implemented
            DESCRIPTION
                "Not supported."

        VARIATION tPortSchedulerPlcyOrphanWeight
            ACCESS  not-implemented
            DESCRIPTION
                "Not supported."

        VARIATION tSapIngressDefaultFCPriority
            ACCESS  not-implemented
            DESCRIPTION
                "Not supported."

        VARIATION tSapIngressDot1pFC
            ACCESS  not-implemented
            DESCRIPTION
                "Not supported."

        VARIATION tSapIngressDot1pLastChanged
            ACCESS  not-implemented
            DESCRIPTION
                "Not supported."

        VARIATION tSapIngressDot1pPriority
            ACCESS  not-implemented
            DESCRIPTION
                "Not supported."

        VARIATION tSapIngressDot1pRowStatus
            ACCESS  not-implemented
            DESCRIPTION
                "Not supported."

        VARIATION tSapIngressDot1pTableLastChanged
            ACCESS  not-implemented
            DESCRIPTION
                "Not supported."

        VARIATION tSapIngressDSCPFC
            ACCESS  not-implemented
            DESCRIPTION
                "Not supported."

        VARIATION tSapIngressDSCPLastChanged
            ACCESS  not-implemented
            DESCRIPTION
                "Not supported."

        VARIATION tSapIngressDSCPPriority
            ACCESS  not-implemented
            DESCRIPTION
                "Not supported."

        VARIATION tSapIngressDSCPRowStatus
            ACCESS  not-implemented
            DESCRIPTION
                "Not supported."

        VARIATION tSapIngressDSCPTableLastChanged
            ACCESS  not-implemented
            DESCRIPTION
                "Not supported."

        VARIATION tSapIngressFCBCastQueue
            ACCESS  not-implemented
            DESCRIPTION
                "Not supported."

        VARIATION tSapIngressFCDE1OutOfProfile
            ACCESS  not-implemented
            DESCRIPTION
                "Not supported."

        VARIATION tSapIngressFCInProfDscp
            ACCESS  not-implemented
            DESCRIPTION
                "Not supported."

        VARIATION tSapIngressFCInProfPrec
            ACCESS  not-implemented
            DESCRIPTION
                "Not supported."

        VARIATION tSapIngressFCInProfRemark
            ACCESS  not-implemented
            DESCRIPTION
                "Not supported."

        VARIATION tSapIngressFCMCastQueue
            ACCESS  not-implemented
            DESCRIPTION
                "Not supported."

        VARIATION tSapIngressFCOutProfDscp
            ACCESS  not-implemented
            DESCRIPTION
                "Not supported."

        VARIATION tSapIngressFCOutProfPrec
            ACCESS  not-implemented
            DESCRIPTION
                "Not supported."

        VARIATION tSapIngressFCOutProfRemark
            ACCESS  not-implemented
            DESCRIPTION
                "Not supported."

        VARIATION tSapIngressFCProfile
            ACCESS  not-implemented
            DESCRIPTION
                "Not supported."

        VARIATION tSapIngressFCQueue
            ACCESS  not-implemented
            DESCRIPTION
                "Not supported."

        VARIATION tSapIngressFCUnknownQueue
            ACCESS  not-implemented
            DESCRIPTION
                "Not supported."

       VARIATION tSapIngressFCPolicer
            ACCESS  not-implemented
            DESCRIPTION
                "Not supported."

        VARIATION tSapIngressFCMCastPolicer
            ACCESS  not-implemented
            DESCRIPTION
                "Not supported."

        VARIATION tSapIngressFCBCastPolicer
            ACCESS  not-implemented
            DESCRIPTION
                "Not supported."

        VARIATION tSapIngressFCUnknownPolicer
            ACCESS  not-implemented
            DESCRIPTION
                "Not supported."

        VARIATION tSapIngressIPCriteriaActionPriority
            ACCESS  not-implemented
            DESCRIPTION
                "Not supported."            

        VARIATION tSapIngressIPCriteriaFragment
            ACCESS  not-implemented
            DESCRIPTION
                "Not supported."
                
        VARIATION tSapIngressMacCriteriaActionPriority
            ACCESS  not-implemented
            DESCRIPTION
                "Not supported."

        VARIATION tSapIngressMacCriteriaDSAP
            ACCESS  not-implemented
            DESCRIPTION
                "Not supported."

        VARIATION tSapIngressMacCriteriaDSAPMask
            ACCESS  not-implemented
            DESCRIPTION
                "Not supported."

        VARIATION tSapIngressMacCriteriaFrameType
            ACCESS  not-implemented
            DESCRIPTION
                "Not supported."

        VARIATION tSapIngressMacCriteriaSnapOui
            ACCESS  not-implemented
            DESCRIPTION
                "Not supported."

        VARIATION tSapIngressMacCriteriaSnapPid
            ACCESS  not-implemented
            DESCRIPTION
                "Not supported."

        VARIATION tSapIngressMacCriteriaSSAP
            ACCESS  not-implemented
            DESCRIPTION
                "Not supported."

        VARIATION tSapIngressMacCriteriaSSAPMask
            ACCESS  not-implemented
            DESCRIPTION
                "Not supported."

        VARIATION tSapIngressPrecFC
            ACCESS  not-implemented
            DESCRIPTION
                "Not supported."

        VARIATION tSapIngressPrecFCPriority
            ACCESS  not-implemented
            DESCRIPTION
                "Not supported."

        VARIATION tSapIngressPrecLastChanged
            ACCESS  not-implemented
            DESCRIPTION
                "Not supported."

        VARIATION tSapIngressPrecRowStatus
            ACCESS  not-implemented
            DESCRIPTION
                "Not supported."

        VARIATION tSapIngressPrecTableLastChanged
            ACCESS  not-implemented
            DESCRIPTION
                "Not supported."

        VARIATION tSapIngressQueueAdminCIR
            ACCESS  not-implemented
            DESCRIPTION
                "Not supported."

        VARIATION tSapIngressQueueAdminPIR
            ACCESS  not-implemented
            DESCRIPTION
                "Not supported."

        VARIATION tSapIngressQueueCBS
            ACCESS  not-implemented
            DESCRIPTION
                "Not supported."

        VARIATION tSapIngressQueueCIRAdaptation
            ACCESS  not-implemented
            DESCRIPTION
                "Not supported."

        VARIATION tSapIngressQueueCIRLevel
            ACCESS  not-implemented
            DESCRIPTION
                "Not supported."

        VARIATION tSapIngressQueueCIRWeight
            ACCESS  not-implemented
            DESCRIPTION
                "Not supported."

        VARIATION tSapIngressQueueExpedite
            ACCESS  not-implemented
            DESCRIPTION
                "Not supported."

        VARIATION tSapIngressQueueHiPrioOnly
            ACCESS  not-implemented
            DESCRIPTION
                "Not supported."

        VARIATION tSapIngressQueueLastChanged
            ACCESS  not-implemented
            DESCRIPTION
                "Not supported."

        VARIATION tSapIngressQueueLevel
            ACCESS  not-implemented
            DESCRIPTION
                "Not supported."

        VARIATION tSapIngressQueueMBS
            ACCESS  not-implemented
            DESCRIPTION
                "Not supported."

        VARIATION tSapIngressQueueMCast
            ACCESS  not-implemented
            DESCRIPTION
                "Not supported."

        VARIATION tSapIngressQueueMode
            ACCESS  not-implemented
            DESCRIPTION
                "Not supported."

        VARIATION tSapIngressQueueParent
            ACCESS  not-implemented
            DESCRIPTION
                "Not supported."

        VARIATION tSapIngressQueuePIRAdaptation
            ACCESS  not-implemented
            DESCRIPTION
                "Not supported."

        VARIATION tSapIngressQueuePoliced
            ACCESS  not-implemented
            DESCRIPTION
                "Not supported."

        VARIATION tSapIngressQueuePoolName
            ACCESS  not-implemented
            DESCRIPTION
                "Not supported."

        VARIATION tSapIngressQueueRowStatus
            ACCESS  not-implemented
            DESCRIPTION
                "Not supported."

        VARIATION tSapIngressQueueTableLastChanged
            ACCESS  not-implemented
            DESCRIPTION
                "Not supported."

        VARIATION tSapIngressQueueWeight
            ACCESS  not-implemented
            DESCRIPTION
                "Not supported."

        VARIATION tSlopeHiAdminStatus
            ACCESS  not-implemented
            DESCRIPTION
                "Not supported."

        VARIATION tSlopeHiMaxAverage
            ACCESS  not-implemented
            DESCRIPTION
                "Not supported."

        VARIATION tSlopeHiMaxProbability
            ACCESS  not-implemented
            DESCRIPTION
                "Not supported."

        VARIATION tSlopeHiStartAverage
            ACCESS  not-implemented
            DESCRIPTION
                "Not supported."

        VARIATION tSlopeLoAdminStatus
            ACCESS  not-implemented
            DESCRIPTION
                "Not supported."

        VARIATION tSlopeLoMaxAverage
            ACCESS  not-implemented
            DESCRIPTION
                "Not supported."

        VARIATION tSlopeLoMaxProbability
            ACCESS  not-implemented
            DESCRIPTION
                "Not supported."

        VARIATION tSlopeLoStartAverage
            ACCESS  not-implemented
            DESCRIPTION
                "Not supported."

        VARIATION tSlopeTimeAvgFactor
            ACCESS  not-implemented
            DESCRIPTION
                "Not supported."

        VARIATION tVirtualSchedulerCIR
            ACCESS  not-implemented
            DESCRIPTION
                "Not supported."

        VARIATION tVirtualSchedulerCIRLevel
            ACCESS  not-implemented
            DESCRIPTION
                "Not supported."

        VARIATION tVirtualSchedulerCIRWeight
            ACCESS  not-implemented
            DESCRIPTION
                "Not supported."

        VARIATION tVirtualSchedulerDescription
            ACCESS  not-implemented
            DESCRIPTION
                "Not supported."

        VARIATION tVirtualSchedulerLastChanged
            ACCESS  not-implemented
            DESCRIPTION
                "Not supported."

        VARIATION tVirtualSchedulerLevel
            ACCESS  not-implemented
            DESCRIPTION
                "Not supported."

        VARIATION tVirtualSchedulerParent
            ACCESS  not-implemented
            DESCRIPTION
                "Not supported."

        VARIATION tVirtualSchedulerPIR
            ACCESS  not-implemented
            DESCRIPTION
                "Not supported."

        VARIATION tVirtualSchedulerPortCIRLvl
            ACCESS  not-implemented
            DESCRIPTION
                "Not supported."

        VARIATION tVirtualSchedulerPortCIRWght
            ACCESS  not-implemented
            DESCRIPTION
                "Not supported."

        VARIATION tVirtualSchedulerPortLvl
            ACCESS  not-implemented
            DESCRIPTION
                "Not supported."

        VARIATION tVirtualSchedulerPortWght
            ACCESS  not-implemented
            DESCRIPTION
                "Not supported."

        VARIATION tVirtualSchedulerRowStatus
            ACCESS  not-implemented
            DESCRIPTION
                "Not supported."

        VARIATION tVirtualSchedulerSummedCIR
            ACCESS  not-implemented
            DESCRIPTION
                "Not supported."

        VARIATION tVirtualSchedulerTableLastChanged
            ACCESS  not-implemented
            DESCRIPTION
                "Not supported."

        VARIATION tVirtualSchedulerUsePortParent
            ACCESS  not-implemented
            DESCRIPTION
                "Not supported."

        VARIATION tVirtualSchedulerWeight
            ACCESS  not-implemented
            DESCRIPTION
                "Not supported."

      

        VARIATION tNetworkPolicyEgressRemarkDscp
            ACCESS  not-implemented
            DESCRIPTION
                "Not supported."

        VARIATION tNetworkPolicyIngressLerUseDscp
            ACCESS  not-implemented
            DESCRIPTION
                "Not supported."

        VARIATION tNetworkQueueCIRLevel
            ACCESS  not-implemented
            DESCRIPTION
                "Not supported."

        VARIATION tNetworkQueueCIRWeight
            ACCESS  not-implemented
            DESCRIPTION
                "Not supported."

        VARIATION tNetworkQueueExpedite
            ACCESS  not-implemented
            DESCRIPTION
                "Not supported."

        VARIATION tNetworkQueueFCMCast
            ACCESS  not-implemented
            DESCRIPTION
                "Not supported."

        VARIATION tNetworkQueueHiPrioOnly
            ACCESS  not-implemented
            DESCRIPTION
                "Not supported."

        VARIATION tNetworkQueueLevel
            ACCESS  not-implemented
            DESCRIPTION
                "Not supported."

        VARIATION tNetworkQueueMBS
            ACCESS  not-implemented
            DESCRIPTION
                "Not supported."

        VARIATION tNetworkQueueMCast
            ACCESS  not-implemented
            DESCRIPTION
                "Not supported."

        VARIATION tNetworkQueueParent
            ACCESS  not-implemented
            DESCRIPTION
                "Not supported."

        VARIATION tNetworkQueuePortAvgOverhead
            ACCESS  not-implemented
            DESCRIPTION
                "Not supported."

        VARIATION tNetworkQueuePortCIRLvl
            ACCESS  not-implemented
            DESCRIPTION
                "Not supported."

        VARIATION tNetworkQueuePortCIRWght
            ACCESS  not-implemented
            DESCRIPTION
                "Not supported."

        VARIATION tNetworkQueuePortLvl
            ACCESS  not-implemented
            DESCRIPTION
                "Not supported."

        VARIATION tNetworkQueuePortWght
            ACCESS  not-implemented
            DESCRIPTION
                "Not supported."

        VARIATION tNetworkQueueUsePortParent
            ACCESS  not-implemented
            DESCRIPTION
                "Not supported."

        VARIATION tNetworkQueueWeight
            ACCESS  not-implemented
            DESCRIPTION
                "Not supported."

        VARIATION tNetworkEgressFCQGrpQueue
            ACCESS  not-implemented
            DESCRIPTION
                "Not supported." 

       VARIATION tNetworkEgressFCQGrpPolicer
            ACCESS  not-implemented
            DESCRIPTION
                "Not supported."           


    SUPPORTS TIMETRA-SAS-QOS-MIB
        INCLUDES    {
            tmnxSASQoSV2v0Group,
            tmnxSASMQoSV1v0Group,
            tmnxSASQoSV7v0Group
        }

        VARIATION   tNetworkIngressMeterCBS
            DESCRIPTION
                    "Not supported."

        VARIATION   tNetworkIngressMeterColorMode
            DESCRIPTION
                    "Not supported."

        VARIATION   tSapIngressMeterCBS
            DESCRIPTION
                    "Not supported."

        VARIATION   tPortSchedulerPlcyQuanta
            ACCESS  not-implemented
            DESCRIPTION
                        "Not supported."

        VARIATION tSlopeHiQueue1DropRate
            ACCESS not-implemented
            DESCRIPTION
                "Not supported."

        VARIATION tSlopeHiQueue2DropRate
            ACCESS not-implemented
            DESCRIPTION
                "Not supported."

        VARIATION tSlopeHiQueue3DropRate
            ACCESS not-implemented
            DESCRIPTION
                "Not supported."

        VARIATION tSlopeHiQueue4DropRate
            ACCESS not-implemented
            DESCRIPTION
                "Not supported."

        VARIATION tSlopeHiQueue5DropRate
            ACCESS not-implemented
            DESCRIPTION
                "Not supported."

        VARIATION tSlopeHiQueue6DropRate
            ACCESS not-implemented
            DESCRIPTION
                "Not supported."

        VARIATION tSlopeHiQueue7DropRate
            ACCESS not-implemented
            DESCRIPTION
                "Not supported."

        VARIATION tSlopeHiQueue8DropRate
            ACCESS not-implemented
            DESCRIPTION
                "Not supported."

        VARIATION tSlopeLoQueue1DropRate
            ACCESS not-implemented
            DESCRIPTION
                "Not supported."

        VARIATION tSlopeLoQueue2DropRate
            ACCESS not-implemented
            DESCRIPTION
                "Not supported."

        VARIATION tSlopeLoQueue3DropRate
            ACCESS not-implemented
            DESCRIPTION
                "Not supported."

        VARIATION tSlopeLoQueue4DropRate
            ACCESS not-implemented
            DESCRIPTION
                "Not supported."

        VARIATION tSlopeLoQueue5DropRate
            ACCESS not-implemented
            DESCRIPTION
                "Not supported."

        VARIATION tSlopeLoQueue6DropRate
            ACCESS not-implemented
            DESCRIPTION
                "Not supported."

        VARIATION tSlopeLoQueue7DropRate
            ACCESS not-implemented
            DESCRIPTION
                "Not supported."

        VARIATION tSlopeLoQueue8DropRate
            ACCESS not-implemented
            DESCRIPTION
                "Not supported."

        VARIATION tSlopeHiStartThreshold
            ACCESS not-implemented
            DESCRIPTION
                "Not supported."

        VARIATION tSlopeLoStartThreshold
            ACCESS not-implemented
            DESCRIPTION
                "Not supported."  

        VARIATION tAccessEgressQueueCBS
            ACCESS read-only
            DESCRIPTION
                "Not supported."

        VARIATION tAccessEgressQueueMBS
            ACCESS not-implemented
            DESCRIPTION
                "Not supported."

        VARIATION tNetworkQueuePolicyName
        ACCESS  not-implemented
        DESCRIPTION
                "Not supported."

        VARIATION tSapEgressQueuePolicyName
        ACCESS  not-implemented
        DESCRIPTION
                "Not supported."

        VARIATION tQueueMgmtPolicyRowStatus
        ACCESS  not-implemented
        DESCRIPTION
                "Not supported."

        VARIATION tQueueMgmtPolicyLastChanged
        ACCESS  not-implemented
        DESCRIPTION
                "Not supported."

        VARIATION tQueueMgmtPolicyHiAdminStatus
        ACCESS  not-implemented
        DESCRIPTION
                "Not supported."

        VARIATION tQueueMgmtPolicyHiStartAverage
        ACCESS  not-implemented
        DESCRIPTION
                "Not supported."

        VARIATION tQueueMgmtPolicyHiMaxAverage
        ACCESS  not-implemented
        DESCRIPTION
                "Not supported."

        VARIATION tQueueMgmtPolicyHiMaxProbability
        ACCESS  not-implemented
        DESCRIPTION
                "Not supported."

        VARIATION tQueueMgmtPolicyLoAdminStatus
        ACCESS  not-implemented
        DESCRIPTION
                "Not supported."

        VARIATION tQueueMgmtPolicyLoStartAverage
        ACCESS  not-implemented
        DESCRIPTION
                "Not supported."

        VARIATION tQueueMgmtPolicyLoMaxAverage
        ACCESS  not-implemented
        DESCRIPTION
                "Not supported."

        VARIATION tQueueMgmtPolicyLoMaxProbability
        ACCESS  not-implemented
        DESCRIPTION
                "Not supported."

        VARIATION tQueueMgmtPolicyCBS
        ACCESS  not-implemented
        DESCRIPTION
                "Not supported."

        VARIATION tQueueMgmtPolicyMBS
        ACCESS  not-implemented
        DESCRIPTION
                "Not supported."

        VARIATION tQueueMgmtPolicyTimeAvgFactor
        ACCESS  not-implemented
        DESCRIPTION
                "Not supported."

        VARIATION tSASRemarkPolicyId                
        ACCESS  not-implemented
        DESCRIPTION
                "Not supported." 

        VARIATION tSASRemarkPolicyRowStatus
        ACCESS  not-implemented
        DESCRIPTION
                "Not supported."

        VARIATION tSASRemarkPolicyDescription
        ACCESS  not-implemented
        DESCRIPTION
                "Not supported."

        VARIATION tSASRemarkPolicyType
        ACCESS  not-implemented
        DESCRIPTION
                "Not supported."

        VARIATION tSASRemarkPolicyLastChanged
        ACCESS  not-implemented
        DESCRIPTION
                "Not supported."

        VARIATION tSASRemarkPolicyFCName                 
        ACCESS  not-implemented
        DESCRIPTION
                "Not supported."

        VARIATION tSASRemarkPolicyDot1PInProfile
        ACCESS  not-implemented
        DESCRIPTION
                "Not supported."

        VARIATION tSASRemarkPolicyDot1POutProfile
        ACCESS  not-implemented
        DESCRIPTION
                "Not supported."

        VARIATION tSASRemarkPolicyDSCPInProfile
        ACCESS  not-implemented
        DESCRIPTION
                "Not supported."

        VARIATION tSASRemarkPolicyDSCPOutProfile
        ACCESS  not-implemented
        DESCRIPTION
                "Not supported."

        VARIATION tSASRemarkPolicyLspExpInProfile
        ACCESS  not-implemented
        DESCRIPTION
                "Not supported."

        VARIATION tSASRemarkPolicyLspExpOutProfile
        ACCESS  not-implemented
        DESCRIPTION
                "Not supported."

        VARIATION tSASRemarkPolicyDot1PLspExpInProfile
        ACCESS  not-implemented
        DESCRIPTION
                "Not supported."

        VARIATION tSASRemarkPolicyDot1PLspExpOutProfile
        ACCESS  not-implemented
        DESCRIPTION
                "Not supported."

    ::= { tmnxSASM7210V6v0 27 }

--
--  Route Policy Capabilities
--
tmnxRoutePolicyCapsSASM7210V6v0 AGENT-CAPABILITIES
    PRODUCT-RELEASE "Alcatel SAS-M 7210"
    STATUS current
    DESCRIPTION
        "Implementation of Route Policy capabilities
         for Alcatel SAS-M 7210 release R6.0"

    SUPPORTS TIMETRA-ROUTE-POLICY-MIB
        INCLUDES    {
            tmnxRPAdminControlObjectsGroup,
            -- tmnxRPASPathObjectsV5v0Group,     no BGP on SAS-M 7210
            -- tmnxRPCommunityObjectsV5v0Group,  no BGP on SAS-M 7210
            -- tmnxRPDampingObjectsV5v0Group,    no BGP on SAS-M 7210
            -- tmnxRPPrefixListObjectsV5v0Group, replaced by
                                          -- tmnxRPInetPrefixListObjectsGroup
            tmnxRPInetPrefixListObjectsV5v0Group,
            tmnxRPPolicyObjectsV7v0Group,
            tmnxRPPolicyEntryObjectsV7v0Group
        }

        VARIATION   tRPAdminPolicyStatementDefaultAction
            DESCRIPTION
                    "In 7210 platforms, next-policy and next-entry
                    are not supported."
                    
        

        -- no IGMP on SAS-M 7210: begin
        -- no PIM on SAS-M 7210: begin
        VARIATION   tRPAdminPSFromCriteriaProtocol
            SYNTAX  INTEGER {
                        none       (1),
                        direct     (2),
                        static     (3),
                        bgp     (4),
                        isis       (5),
                        ospf       (6),
                        rip        (7),
                        aggregate  (8),
                        bgpVpn     (9)
                        -- igmp    (10),      no IGMP on SAS-M 7210
                        -- pim     (11),      no PIM on SAS-M 7210
                        -- ospf3   (12)       no IPv6 on SAS-M 7210
                        -- mld     (15)       no MLD on SAS-M 7210
                        -- managed (16)       no Routed Subscriber Host on SAS-M 7210
                    }
            DESCRIPTION
                    "The values 'igmp (10)', 'mld (15)'
                     'managed (16)' and 'pim (11)' are not allowed on SAS-M 7210
                     systems, as IGMP, MLD, Routed Subscriber Host and PIM
                     are not available on SAS-M 7210 systems.
                     The value 'ospf3 (12)' is not allowed on a SAS-M 7210 system,
                     as IPv6 is not supported on a SAS-M 7210 system."

        VARIATION   tRPAdminPSToCriteriaProtocol
            SYNTAX  INTEGER {
                        none       (1),
                        direct     (2),
                        static     (3),
                        bgp     (4),
                        isis       (5),
                        ospf       (6),
                        rip        (7),
                        aggregate  (8),
                        bgpVpn     (9)
                        -- igmp    (10),      no IGMP on SAS-M 7210
                        -- pim     (11),      no PIM on SAS-M 7210
                        -- ospf3   (12)       no IPv6 on SAS-M 7210
                    }
            DESCRIPTION
                    "The values 'igmp (10)', and
                    'pim (11)' are not allowed on SAS-M 7210 systems,
                    as IGMP, and PIM are not available on SAS-M 7210
                    systems. The value 'ospf3 (12)' is not allowed on a
                    SAS-M 7210 system, as IPv6 is not supported on a SAS-M 7210 system."
        -- no IGMP on SAS-M 7210: end
        -- no PIM on SAS-M 7210: end

        VARIATION   tRPOperPolicyStatementTableLastChanged
            DESCRIPTION
                    "Obsolete. TIMETRA-SYSTEM-MIB::tmnxConfigModify
                     notification is used instead."

        VARIATION   tRPOperPolicyStatementEntryLastChanged
            DESCRIPTION
                    "Obsolete. TIMETRA-SYSTEM-MIB::tmnxConfigModify
                     notification is used instead."

        VARIATION   tRPOperPSDefaultActionParamsTableLastChanged
            DESCRIPTION
                    "Obsolete. TIMETRA-SYSTEM-MIB::tmnxConfigModify
                     notification is used instead."

        VARIATION   tRPOperPSDefaultActionParamsEntryLastChanged
            DESCRIPTION
                    "Obsolete. TIMETRA-SYSTEM-MIB::tmnxConfigModify
                     notification is used instead."

        VARIATION   tRPOperPSParamsTableLastChanged
            DESCRIPTION
                    "Obsolete. TIMETRA-SYSTEM-MIB::tmnxConfigModify
                     notification is used instead."

        VARIATION   tRPOperPSParamsEntryLastChanged
            DESCRIPTION
                    "Obsolete. TIMETRA-SYSTEM-MIB::tmnxConfigModify
                     notification is used instead."

        VARIATION   tRPOperPSAcceptActionParamsTableLastChanged
            DESCRIPTION
                    "Obsolete. TIMETRA-SYSTEM-MIB::tmnxConfigModify
                     notification is used instead."

        VARIATION   tRPOperPSAcceptActionParamsEntryLastChanged
            DESCRIPTION
                    "Obsolete. TIMETRA-SYSTEM-MIB::tmnxConfigModify
                     notification is used instead."

        VARIATION   tRPOperPSToCriteriaTableLastChanged
            DESCRIPTION
                    "Obsolete. TIMETRA-SYSTEM-MIB::tmnxConfigModify
                     notification is used instead."

        VARIATION   tRPOperPSToCriteriaEntryLastChanged
            DESCRIPTION
                    "Obsolete. TIMETRA-SYSTEM-MIB::tmnxConfigModify
                     notification is used instead."

        VARIATION   tRPOperPSFromCriteriaTableLastChanged
            DESCRIPTION
                    "Obsolete. TIMETRA-SYSTEM-MIB::tmnxConfigModify
                     notification is used instead."

        VARIATION   tRPOperPSFromCriteriaEntryLastChanged
            DESCRIPTION
                    "Obsolete. TIMETRA-SYSTEM-MIB::tmnxConfigModify
                     notification is used instead."

        VARIATION   tRPOperInetPrefixListTblLastChg
            DESCRIPTION
                    "OBsolete. TIMETRA-SYSTEM-MIB::tmnxConfigModify
                     notification is used instead."

        VARIATION   tRPOperInetPrefixListLastChg
            DESCRIPTION
                    "Obsolete. TIMETRA-SYSTEM-MIB::tmnxConfigModify
                     notification is used instead."

        
    ::= { tmnxSASM7210V6v0 28 }

--
--  SECURITY CAPABILITIES
--
tmnxSecurityCapsSASM7210V6v0 AGENT-CAPABILITIES
    PRODUCT-RELEASE "Alcatel SAS-M 7210"
    STATUS current
    DESCRIPTION
        "Implementation of Security capabilities
         for Alcatel SAS-M 7210 release R6.0"

    SUPPORTS TIMETRA-SECURITY-MIB
        INCLUDES    {
            tmnxSecurityUserV6v0Group,
            tmnxSecurityMafV6v0Group,
            tmnxSecurityPasswordsV6v0Group,
            tmnxSecurityRadiusV5v0Group,
            tmnxSecurityTacPlusV6v0Group,
            tmnxSecurityServerCtlV4v0Group,
            -- tmnxSecurityCpmGroup,
            tmnxSecurityPasswordHashGroup,
            tmnxSSHServerV4v0Group,
            tmnxSecurityNotificationV5v0Group,
            tmnxSecuritySourceIpV4v0Group,
            tmnxSecurityKeyChainV5v0Group,
            -- tmnxSecurityCpmIPv6FilterV4v0Group  no IPv6 on SAS-M 7210
            -- tmnxSecurityCpmIpFilterV5v0Group,
            -- tmnxSecurityCpmProtectGroup,
            -- tmnxSecurityLiGroup,
            -- tmnxSecurityCpmProtNotificationGroup,
            -- tmnxSecurityCpmMacFilterGroup,
            -- tmnxSecurityMafMacFilterGroup,
            -- tmnxSecurityV7v0Group,
            -- tmnxSecurityCpmProtNotifyV7v0Grp
            tmnxSecurityNwExceptionsGroup
        }

        VARIATION   tCpmIpFilterEntryVRtrId
            ACCESS  not-implemented
            DESCRIPTION
                    "Not supported."

        VARIATION   tmnxRadiusServerInetAddressType
            SYNTAX  INTEGER {
                        unknown     (0),
                        ipv4        (1)
                        -- ipv6     (2)
                        -- ipv4z    (3),
                        -- ipv6z    (4),
                        -- dns      (16)
                    }
            DESCRIPTION
                    "tmnxRadiusServerInetAddressType object supports
                    address of type 'ipv4'."

        VARIATION   tmnxRadiusServerInetAddress
            SYNTAX  InetAddress (SIZE(0|4))
            DESCRIPTION
                    "tmnxRadiusServerInetAddress supports only address of type
                    'ipv4'."

        VARIATION   tmnxTacPlusServerInetAddressType
            SYNTAX  INTEGER {
                        unknown     (0),
                        ipv4        (1)
                        -- ipv6     (2)
                        -- ipv4z    (3),
                        -- ipv6z    (4),
                        -- dns      (16)
                    }
            DESCRIPTION
                    "tmnxTacPlusServerInetAddressType object supports only
                    address of type 'ipv4'."

        VARIATION   tmnxTacPlusServerInetAddress
           SYNTAX  InetAddress (SIZE(0|4))
           DESCRIPTION
                    "tmnxTacPlusServerInetAddress supports only address of type
                    'ipv4'."

        VARIATION   tmnxCpmProtPolRowStatus
            SYNTAX  INTEGER {
                        active      (1),
                        createAndGo (4),
                        destroy     (6)
                     }
            DESCRIPTION
                    "tmnxCpmProtPolRowStatus supports only the values
                    'active (1)', 'createAndGo (4)' and 'destroy (6)'."

        VARIATION   tmnxCpmProtViolVdoSvcEntry
           ACCESS   not-implemented
           DESCRIPTION
                    "tmnxCpmProtViolVdoSvcEntry is not implemented on SR-1,
                     where the value of TIMETRA-CHASSIS-MIB::tmnxChassisType
                     is '5'."
        
        VARIATION   tmnxCpmProtViolVdoVrtrEntry
           ACCESS   not-implemented
           DESCRIPTION
                    "tmnxCpmProtViolVdoVrtrEntry is not implemented on
                     SR-1, where the value of
                     TIMETRA-CHASSIS-MIB::tmnxChassisType is '5'."
        
        VARIATION   tmnxCpmProtViolVdoSvcClient
           ACCESS   not-implemented
           DESCRIPTION
                    "tmnxCpmProtViolVdoSvcClient is not implemented on SR-1,
                     where the value of TIMETRA-CHASSIS-MIB::tmnxChassisType
                     is '5'."
        
        VARIATION   tmnxCpmProtViolVdoVrtrClient
           ACCESS   not-implemented
           DESCRIPTION
                    "tmnxCpmProtViolVdoVrtrClient is not implemented on SR-1,
                     where the value of TIMETRA-CHASSIS-MIB::tmnxChassisType
                     is '5'."

        VARIATION   tmnxRadiusPEForceDiscovery
           ACCESS   not-implemented
           DESCRIPTION
                    "Not supported."

        VARIATION   tmnxRadiusPEForceDiscoverySvcId
           ACCESS   not-implemented
           DESCRIPTION
                    "Not supported."

        VARIATION   tmnxCpmVprnNwExceptions
           ACCESS   not-implemented
           DESCRIPTION
                    "Not supported."

        VARIATION   tmnxCpmNumVprnNwExceptions
           ACCESS   not-implemented
           DESCRIPTION
                    "Not supported."

        VARIATION   tmnxCpmVprnNwExceptionsTime
           ACCESS   not-implemented
           DESCRIPTION
                    "Not supported."
                    
    ::= { tmnxSASM7210V6v0 29 }

--
--  SERVICES CAPABILITIES
--
tmnxServicesCapsSASM7210V6v0 AGENT-CAPABILITIES
    PRODUCT-RELEASE "Alcatel SAS-M 7210"
    STATUS current
    DESCRIPTION
        "Implementation of Services capabilities
         for Alcatel SAS-M 7210 release R6.0"

    SUPPORTS TIMETRA-SERV-MIB
        INCLUDES    {
            tmnxCustV6v0Group,
            tmnxSvcV6v0Group,
            tmnxSvcTlsV6v0Group,
            tmnxSvcTlsFdbV7v0Group,
            tmnxSvcIesIfV6v0Group,
            -- tmnxSvcTlsShgV6v0Group,
            tmnxSvcTlsMFibV6v0Group,
            -- tmnxSvcRdntV6v0Group,
            -- tmnxSvcTlsMstiV6v0Group,
            -- tmnxSvcTlsEgrV6v0Group,
            -- tmnxSvcDhcpV7v0Group,
            tmnxSvcEndPointV6v0Group,
            -- tmnxSvcPEV6v0Group,
            -- tmnxSvcIfDHCP6V6v0Group,
            tmnxSvcTlsBackbone6v1Group,
            -- tmnxSvcTlsBgpV6v0Group,
            tmnxSvcEpipeV6v0Group,
            -- tmnxSvcTlsPipV7v0Group,
            tmnxSvcNotifyObjsV7v0Group,
            tmnxSvcNotifyV7v0Group
            -- tmnxApipeV3v0Group,
            -- tmnxSvcRoutedCOV7v0Group,
            -- tmnxApipeV3v0Group,             no ATM on SAS-M 7210
            -- tmnxSvcRoutedCOV5v0Group,  no routed-CO on SAS-M 7210
            -- tmnxSvcBsxV6v0Group
            -- tmnxArpHostGroup,
            -- tmnxArpHostNotifyGroup,
            -- svcIgmpTrkGroup,
            -- tmnxSvcPbbMacV7v0Group
         }

        -- No ATM for SAS-M 7210 : start
        -- No BGP for SAS-M 7210 : start
        -- No FPIPE for SAS-M 7210 : start
        -- No CPIPE for SAS-M 7210 : start
        VARIATION   svcType
            SYNTAX  INTEGER {
                        epipe    (1),   -- Ethernet pipe
                        p3pipe   (2),   -- POS pipe
                        tls      (3),   -- Virtual private LAN service
                        vprn  (4),      --Virtual private routed network                       
                        ies      (5),   -- Internet enhanced service
                        mirror   (6),   -- Mirror service
                        -- apipe (7)    ATM pipe service
                        --              no aPIPE on SAS-M 7210
                        -- fpipe (8)    FR pipe service
                        --              no FPIPE on SAS-M 7210
                        ipipe    (9)    -- IP interworking pipe service
                        -- cpipe (10)   Circuit Emulation pipe service
                        --              no CPIPE on SAS-M 7210
                    }
            DESCRIPTION
                    "The values
                        - 'apipe (7)',
                        - 'fpipe (8)',
                        - 'cpipe (10)'
                     are invalid on a SAS-M 7210 system."
        -- end

        VARIATION   svcVllType
            SYNTAX  INTEGER {
                        undef         (1)
                        -- atmSdu     (6),
                        -- atmCell    (7),
                        -- atmVcc     (8),
                        -- atmVpc     (9),
                        -- frDlci     (10),
                        -- satopE3    (14),
                        -- satopT3    (15),
                        -- cesopsn    (16),
                        -- cesopsnCas (17)
            }
            DESCRIPTION
                    "The values
                        - 'atmSdu     (6)',
                        - 'atmCell    (7)',
                        - 'atmVcc     (8)',
                        - 'atmVpc     (9)',
                        - 'frDlci     (10)',
                        - 'satopE3    (14)',
                        - 'satopT3    (15)',
                        - 'cesopsn    (16)',
                        - 'cesopsnCas (17)'
                     are not supported on a SAS-M 7210 system."

        -- No FPIPE for SAS-M 7210 : end

        -- No ATM for SAS-M 7210 : end
        -- No CPIPE for SAS-M 7210 : end

        VARIATION   svcApipeInterworking
            DESCRIPTION
                    "Not supported."

        VARIATION   iesIfType
            SYNTAX  INTEGER {
                        service       (1),
                        -- subscriber (2),
                        -- group      (3),
                        -- redundant  (4),
                        -- cem        (5),
                        -- ipsec      (6),
                        ipMirror      (7)
                    }
            DESCRIPTION
                    "The values
                        - 'subscriber (2)',
                        - 'group      (3)',
                        - 'redundant  (4)'
                    are not supported on SAS-M 7210 systems, as the routed-co
                    feature is not implemented.

                    Also the values
                        - 'cem        (5)',
                        - 'ipsec      (6)'
                    are not supported on SAS-M 7210 systems."

        VARIATION   iesIfParentIf
            ACCESS  not-implemented
            DESCRIPTION
                    "Not supported (No routed-co feature)."

        VARIATION   iesIfFwdServId
            ACCESS  not-implemented
            DESCRIPTION
                    "Not supported. (No routed-co feature)."

        VARIATION tlsEgrMcGrpQinqFixedTagPosition
            ACCESS  read-only
            DESCRIPTION
                    "read-only implementation."

                    
        VARIATION   svcEndPointStandbySigSlave
            ACCESS  not-implemented
            DESCRIPTION
                    "Not supported."                 

        VARIATION   svcDhcpManagedRouteStatus
            ACCESS  not-implemented
            DESCRIPTION
                    "Not supported. (No Routed Subscriber Host feature)."

        VARIATION   svcTlsMcPathMgmtPlcyName
            ACCESS  not-implemented
            DESCRIPTION
                    "Not supported."

        VARIATION   svcTlsMrpAdminStatus
            ACCESS  not-implemented
            DESCRIPTION
                    "Not supported."

        VARIATION   svcTlsMrpAttrTblHighWatermark
            ACCESS  not-implemented
            DESCRIPTION
                    "Not supported."

        VARIATION   svcTlsMrpAttrTblLowWatermark
            ACCESS  not-implemented
            DESCRIPTION
                    "Not supported."

        VARIATION   svcTlsMrpAttributeCount
            ACCESS  not-implemented
            DESCRIPTION
                    "Not supported."

        VARIATION   svcTlsMrpFailedRegisterCount
            ACCESS  not-implemented
            DESCRIPTION
                    "Not supported."

        VARIATION   svcTlsMrpFloodTime
            ACCESS  not-implemented
            DESCRIPTION
                    "Not supported."

        VARIATION   svcTlsMrpMaxAttributes
            ACCESS  not-implemented
            DESCRIPTION
                    "Not supported."

        VARIATION custEgrQosPortSchedFwdOctets
            ACCESS  not-implemented
            DESCRIPTION
                "Not supported."

        VARIATION custEgrQosPortSchedFwdPkts
            ACCESS  not-implemented
            DESCRIPTION
                "Not supported."

        VARIATION custEgrQosSchedStatsForwardedOctets
            ACCESS  not-implemented
            DESCRIPTION
                "Not supported."

        VARIATION custEgrQosSchedStatsForwardedPackets
            ACCESS  not-implemented
            DESCRIPTION
                "Not supported."

        VARIATION custEgrSchedPlcyPortStatsFwdOct
            ACCESS  not-implemented
            DESCRIPTION
                "Not supported."

        VARIATION custEgrSchedPlcyPortStatsFwdPkt
            ACCESS  not-implemented
            DESCRIPTION
                "Not supported."

        VARIATION custEgrSchedPlcyStatsFwdOct
            ACCESS  not-implemented
            DESCRIPTION
                "Not supported."

        VARIATION custEgrSchedPlcyStatsFwdPkt
            ACCESS  not-implemented
            DESCRIPTION
                "Not supported."

        VARIATION custIngQosPortSchedFwdOctets
            ACCESS  not-implemented
            DESCRIPTION
                "Not supported."

        VARIATION custIngQosPortSchedFwdPkts
            ACCESS  not-implemented
            DESCRIPTION
                "Not supported."

        VARIATION custIngQosSchedStatsForwardedOctets
            ACCESS  not-implemented
            DESCRIPTION
                "Not supported."

        VARIATION custIngQosSchedStatsForwardedPackets
            ACCESS  not-implemented
            DESCRIPTION
                "Not supported."

        VARIATION custIngSchedPlcyPortStatsFwdOct
            ACCESS  not-implemented
            DESCRIPTION
                "Not supported."

        VARIATION custIngSchedPlcyPortStatsFwdPkt
            ACCESS  not-implemented
            DESCRIPTION
                "Not supported."

        VARIATION custIngSchedPlcyStatsFwdOct
            ACCESS  not-implemented
            DESCRIPTION
                "Not supported."

        VARIATION custIngSchedPlcyStatsFwdPkt
            ACCESS  not-implemented
            DESCRIPTION
                "Not supported."

        VARIATION custMssEgrQosSCIR
            ACCESS  not-implemented
            DESCRIPTION
                "Not supported."

        VARIATION custMssEgrQosSLastMgmtChange
            ACCESS  not-implemented
            DESCRIPTION
                "Not supported."

        VARIATION custMssEgrQosSOverrideFlags
            ACCESS  not-implemented
            DESCRIPTION
                "Not supported."

        VARIATION custMssEgrQosSPIR
            ACCESS  not-implemented
            DESCRIPTION
                "Not supported."

        VARIATION custMssEgrQosSRowStatus
            ACCESS  not-implemented
            DESCRIPTION
                "Not supported."

        VARIATION custMssEgrQosSSummedCIR
            ACCESS  not-implemented
            DESCRIPTION
                "Not supported."

        VARIATION custMssIngQosSCIR
            ACCESS  not-implemented
            DESCRIPTION
                "Not supported."

        VARIATION custMssIngQosSLastMgmtChange
            ACCESS  not-implemented
            DESCRIPTION
                "Not supported."

        VARIATION custMssIngQosSOverrideFlags
            ACCESS  not-implemented
            DESCRIPTION
                "Not supported."

        VARIATION custMssIngQosSPIR
            ACCESS  not-implemented
            DESCRIPTION
                "Not supported."

        VARIATION custMssIngQosSRowStatus
            ACCESS  not-implemented
            DESCRIPTION
                "Not supported."

        VARIATION custMssIngQosSSummedCIR
            ACCESS  not-implemented
            DESCRIPTION
                "Not supported."

        VARIATION custMultSvcSiteAssignment
            ACCESS  not-implemented
            DESCRIPTION
                "Not supported."

        VARIATION custMultSvcSiteCurrentEgrSchedPlcy
            ACCESS  not-implemented
            DESCRIPTION
                "Not supported."

        VARIATION custMultSvcSiteCurrentIngrSchedPlcy
            ACCESS  not-implemented
            DESCRIPTION
                "Not supported."

        VARIATION custMultSvcSiteDescription
            ACCESS  not-implemented
            DESCRIPTION
                "Not supported."

        VARIATION custMultSvcSiteEgressAggRateLimit
            ACCESS  not-implemented
            DESCRIPTION
                "Not supported."

        VARIATION custMultSvcSiteEgressSchedulerPolicy
            ACCESS  not-implemented
            DESCRIPTION
                "Not supported."

        VARIATION custMultSvcSiteFrameBasedAccnt
            ACCESS  not-implemented
            DESCRIPTION
                "Not supported."

        VARIATION custMultSvcSiteIngressSchedulerPolicy
            ACCESS  not-implemented
            DESCRIPTION
                "Not supported."

        VARIATION custMultSvcSiteIntendedEgrSchedPlcy
            ACCESS  not-implemented
            DESCRIPTION
                "Not supported."

        VARIATION custMultSvcSiteIntendedIngrSchedPlcy
            ACCESS  not-implemented
            DESCRIPTION
                "Not supported."

        VARIATION custMultSvcSiteLastMgmtChange
            ACCESS  not-implemented
            DESCRIPTION
                "Not supported."

        VARIATION custMultSvcSiteName
            ACCESS  not-implemented
            DESCRIPTION
                "Not supported."

        VARIATION custMultSvcSiteRowStatus
            ACCESS  not-implemented
            DESCRIPTION
                "Not supported."

        VARIATION custMultSvcSiteTodSuite
            ACCESS  not-implemented
            DESCRIPTION
                "Not supported."

        VARIATION svcIpRouting
            ACCESS  not-implemented
            DESCRIPTION
                "Not supported."

        VARIATION svcRadiusDiscovery
            ACCESS  not-implemented
            DESCRIPTION
                "Not supported."

        VARIATION svcRadiusDiscoveryShutdown
            ACCESS  not-implemented
            DESCRIPTION
                "Not supported."

        VARIATION svcRadiusPEDiscPolicy
            ACCESS  not-implemented
            DESCRIPTION
                "Not supported."

        VARIATION svcRadiusUserName
            ACCESS  not-implemented
            DESCRIPTION
                "Not supported."

        VARIATION svcRadiusUserNameType
            ACCESS  not-implemented
            DESCRIPTION
                "Not supported."

        VARIATION svcRestoreHostProblem
            ACCESS  not-implemented
            DESCRIPTION
                "Not supported."

        VARIATION svcVcSwitching
            ACCESS  not-implemented
            DESCRIPTION
                    "Not supported."               

        VARIATION svcTlsFdbNumDhcpEntries
            ACCESS  not-implemented
            DESCRIPTION
                "Not supported."

        VARIATION svcTlsFdbNumHostEntries
            ACCESS  not-implemented
            DESCRIPTION
                "Not supported."

        VARIATION svcTlsShcvAction
            ACCESS  not-implemented
            DESCRIPTION
                "Not supported."

        VARIATION svcTlsShcvInterval
            ACCESS  not-implemented
           DESCRIPTION
                "Not supported."

        VARIATION svcTlsShcvSrcIp
            ACCESS  not-implemented
            DESCRIPTION
                "Not supported."

        VARIATION svcTlsShcvSrcMac
           ACCESS   not-implemented
           DESCRIPTION
                "Not supported."
        
        VARIATION svcTotalFdbMimDestIdxEntries
            ACCESS  not-implemented
            DESCRIPTION
                "Not supported."

        VARIATION tlsEgrMcGrpAdminQinqFixedTagVal
            ACCESS  not-implemented
            DESCRIPTION
                "Not supported."

        VARIATION tlsFdbProtected
            ACCESS  not-implemented
            DESCRIPTION
                "Not supported."

        VARIATION tlsProtMacImplCount
            ACCESS  not-implemented
            DESCRIPTION
                "Not supported."

        VARIATION tlsProtMacLastMgmtChange
            ACCESS  not-implemented
            DESCRIPTION
                "Not supported."

        VARIATION tlsProtMacRowStatus
            ACCESS  not-implemented
            DESCRIPTION
                "Not supported."

        VARIATION custMultSvcSiteScope
            ACCESS  not-implemented
            DESCRIPTION
                "Not supported."

        VARIATION iesGrpIfOperUpWhileEmpty
            ACCESS  not-implemented
            DESCRIPTION
                "Not supported."

        VARIATION tlsMFibStatsForwardedPkts
            ACCESS  not-implemented
            DESCRIPTION
                "Not supported."

        VARIATION tlsMFibStatsForwardedOctets
            ACCESS  not-implemented
            DESCRIPTION
                "Not supported."
                
        VARIATION tlsShgResidential
            ACCESS  not-implemented
            DESCRIPTION
                "Not supported." 
                
         VARIATION tlsShgRestProtSrcMac
            ACCESS  not-implemented
            DESCRIPTION
                "Not supported."    

         VARIATION tlsShgRestUnprotDstMac
            ACCESS  not-implemented
            DESCRIPTION
                "Not supported."    

         VARIATION tlsShgRestProtSrcMacAction
            ACCESS  not-implemented
            DESCRIPTION
                "Not supported."    

         VARIATION svcTlsBackboneLDPMacFlush
            ACCESS  not-implemented
            DESCRIPTION
                "Not supported."    

         VARIATION svcTlsBackboneLDPMacFlushNotMine
            ACCESS  not-implemented
            DESCRIPTION
                "Not supported."    

         VARIATION  svcTlsBackboneVplsStp 
            ACCESS  not-implemented
            DESCRIPTION
                "Not supported." 

    SUPPORTS TIMETRA-SAS-SERV-MIB
        INCLUDES    {
            tmnxSapGlobalV1v0Group,
            tmnxSasSapQosV2v0Group
         }

        VARIATION   svcUplinkType
            ACCESS  not-implemented
            DESCRIPTION
                    "Not supported."

         VARIATION   svcbVplsVid
            ACCESS  not-implemented
            DESCRIPTION
                    "Not supported."

        VARIATION   sapBaseInfoEgressStatsPktsMode
            ACCESS  not-implemented
            DESCRIPTION
                    "Not supported."

        VARIATION   sapBaseInfoIngressCounterMode
            ACCESS  not-implemented
            DESCRIPTION
                    "Not supported."

        VARIATION   sapBaseInfoIngressWithAggregateMeter
            ACCESS  not-implemented
            DESCRIPTION
                    "Not supported."

        VARIATION   sapBaseInfoEgressStatsEnable
            ACCESS  not-implemented
            DESCRIPTION
                    "Not supported."

        VARIATION   sapBaseInfoIngressStatsEnable
            ACCESS  not-implemented
            DESCRIPTION
                    "Not supported."

        VARIATION   sapBaseInfoIngressFabricPath
            ACCESS  not-implemented
            DESCRIPTION
                    "Not supported." 
                    
        VARIATION   sapEgrQosQueueStatsExtnTable
            ACCESS  not-implemented
            DESCRIPTION
                    "Not supported."

        VARIATION   sapIngQosQueueStatsExtnTable
            ACCESS  not-implemented
            DESCRIPTION
                    "Not supported."

    ::= { tmnxSASM7210V6v0 30 }

--
--  SYSTEM CAPABILITIES
--

tmnxSystemCapsSASM7210V6v0 AGENT-CAPABILITIES
    PRODUCT-RELEASE "Alcatel SAS-M 7210"
    STATUS current
            DESCRIPTION
        "Implementation of System capabilities
         for Alcatel SAS-M 7210 release R6.0"

    SUPPORTS TIMETRA-SYSTEM-MIB
        INCLUDES    {
            tmnxSysGeneralV3v0Group,
            tmnxSysTimeV4v0Group,
            tmnxSysConfigV3v0Group,
            tmnxSysRadiusServerV5v0Group,
            tmnxSysTacPlusServerV5v0Group,
            tmnxSysNotificationV6v0Group,
            tmnxSysBofV6v0Group,
            tmnxSysLoginControlSecGroup,
            tmnxSysGeneralV7v0Group,
            tmnxSysIcmpVSV6v1Group
            -- tmnxPersistenceV6v0Group
            -- tmnxSysIpv6MgmtItfV6v0Group,
            -- tmnxSysLiV6v0Group
          }

        VARIATION   sntpTimeDiffExceedsThreshold
            ACCESS  not-implemented
            DESCRIPTION
                    "Not supported."

        VARIATION   spiDhcpSrvPersistenceFileLoc
            ACCESS  not-implemented
            DESCRIPTION
                    "Not supported."

        VARIATION   spiDhcpSrvPersistenceDescr
            ACCESS  not-implemented
            DESCRIPTION
                    "Not supported."

        VARIATION   sbiLiLocalSave
            ACCESS  not-implemented
            DESCRIPTION
                    "Not supported."

        VARIATION   sbiLiSeparate
            ACCESS  not-implemented
            DESCRIPTION
                    "Not supported."

        VARIATION   sbiRedSwitchoverScript
            ACCESS  not-implemented
            DESCRIPTION
                    "Not supported."

        VARIATION   sbiRedSwitchoverScriptStatus
            ACCESS  not-implemented
            DESCRIPTION
                    "Not supported."

        VARIATION   ssiRedCpmActive
            ACCESS  not-implemented
            DESCRIPTION
                    "Not supported."

        VARIATION   ssiRedFailoverReason
            ACCESS  not-implemented
            DESCRIPTION
                    "Not supported."

        VARIATION   ssiRedFailoverTime
            ACCESS  not-implemented
            DESCRIPTION
                    "Not supported."

        VARIATION   ssiRedSingleCpm
            ACCESS  not-implemented
            DESCRIPTION
                    "Not supported."

        VARIATION   ssiRedStandbyReady
            ACCESS  not-implemented
            DESCRIPTION
                    "Not supported."

        VARIATION   ssiRedStandbySyncing
            ACCESS  not-implemented
            DESCRIPTION
                    "Not supported."

        VARIATION   ssiRedStandbySyncLost
            ACCESS  not-implemented
            DESCRIPTION
                    "Not supported."

        VARIATION   ssiRedSwitchover
            ACCESS  not-implemented
            DESCRIPTION
                    "Not supported."

        VARIATION   ssiSyncBootEnvLastTime
            ACCESS  not-implemented
            DESCRIPTION
                    "Not supported."

        VARIATION   ssiSyncConfigLastTime
            ACCESS  not-implemented
            DESCRIPTION
                    "Not supported."

        VARIATION   ssiSyncForce
            ACCESS  not-implemented
            DESCRIPTION
                    "Not supported."

        VARIATION   ssiSyncMode
            ACCESS  not-implemented
            DESCRIPTION
                    "Not supported."

        VARIATION   ssiSyncStatus
            ACCESS  not-implemented
            DESCRIPTION
                    "Not supported."

        VARIATION   sbiStandbyIpAddr
            ACCESS  not-implemented
            DESCRIPTION
                    "Not supported."

        VARIATION   sbiStandbyIpMask
            ACCESS  not-implemented
            DESCRIPTION
                    "Not supported."

        VARIATION   sbiStaticRouteNextHop
            ACCESS  not-implemented
            DESCRIPTION
                    "Not supported."

        VARIATION   sbiStaticRouteRowStatus
            ACCESS  not-implemented
            DESCRIPTION
                    "Not supported."

       VARIATION   slcTelnetMinTTLValue
            ACCESS  not-implemented
            DESCRIPTION
                    "Not supported."

        VARIATION   slcSSHMinTTLValue
            ACCESS  not-implemented
            DESCRIPTION
                    "Not supported."

        VARIATION   sgiKbMemoryUsed
            ACCESS  not-implemented
            DESCRIPTION
                    "Not supported."                    

        VARIATION   sgiKbMemoryAvailable
            ACCESS  not-implemented
            DESCRIPTION
                    "Not supported."                    

        VARIATION   sgiKbMemoryPoolAllocated
            ACCESS  not-implemented
            DESCRIPTION
                    "Not supported."

        VARIATION   sysIcmpVSEnhancement
            ACCESS  not-implemented
            DESCRIPTION
                    "Not supported."
                    
    SUPPORTS TIMETRA-SAS-SYSTEM-MIB
          INCLUDES {
              tmnxSASSysV2v0Group,
              tmnxSASSysV3v0Group,
              tmnxSASSysV4v0Group,
              tmnxSASSysV5v0Group,
              tmnxSASSysQosV5v0Group,
              tmnxSASSysV6v0Group,
              tmnxSASChassisGroup,
              tmnxSASSysConsoleV6v0Group
          }

       VARIATION   tmnxChassisSystemLEDState
            ACCESS  not-implemented
            DESCRIPTION
                    "Not supported."            


       VARIATION   tmnxFabricPolicyIndex 
            ACCESS  not-implemented
            DESCRIPTION
                    "Not supported."

        VARIATION   tmnxFabricPolicyRowStatus
            ACCESS  not-implemented
            DESCRIPTION
                    "Not supported."
                    
        VARIATION   tmnxFabricPolicyCIR 
            ACCESS  not-implemented
            DESCRIPTION
                    "Not supported."

        VARIATION   sysDhcpSnoopingSdpEnable
            ACCESS  not-implemented
            DESCRIPTION
                    "Not supported."
                    
        VARIATION   sysDhcpSnoopingEnable
            ACCESS  not-implemented
            DESCRIPTION
                    "Not supported."
                    
         VARIATION   tmnxFabricPolicyPIR
            ACCESS  not-implemented
            DESCRIPTION
                    "Not supported."

         VARIATION   tmnxFabricPolicyCBS
            ACCESS  not-implemented
            DESCRIPTION
                    "Not supported."

         VARIATION   tmnxFabricPolicyMBS 
            ACCESS  not-implemented
            DESCRIPTION
                    "Not supported."

         VARIATION   tmnxFabricPolicyMpointFabricPort 
            ACCESS  not-implemented
            DESCRIPTION
                    "Not supported."

        VARIATION  sysResEgrSapEgrClass 
            ACCESS  not-implemented
            DESCRIPTION
                    "Not supported."

          VARIATION  sysResEgrSapEgrClassMac
            ACCESS  not-implemented
            DESCRIPTION
                    "Not supported."

          VARIATION  sysResEgrSapEgrClassIpv4 
            ACCESS  not-implemented
            DESCRIPTION
                    "Not supported."

          VARIATION  sysResEgrSapEgrClassIpv4Ipv6  
            ACCESS  not-implemented
            DESCRIPTION
                    "Not supported."

        VARIATION    sysResIngTcamIngAcl64bitIpv4Ipv6   
            ACCESS  not-implemented
            DESCRIPTION
                    "Not supported."            

         VARIATION   sysResQosSapIngQMode 
            ACCESS  not-implemented
            DESCRIPTION
                    "Not supported."   
                    
         VARIATION   sysResQosSapIngQOperMode 
            ACCESS  not-implemented
            DESCRIPTION
                    "Not supported."

         VARIATION   sysResFabricPathBandwidth 
            ACCESS  not-implemented
            DESCRIPTION
                    "Not supported."

        VARIATION   sysResRouterEcmpMaxRoutesDstOperVal 
            ACCESS  not-implemented
            DESCRIPTION
                    "Not supported."            
                    
         VARIATION   tmnxChassisFanCfgMode 
            ACCESS  not-implemented
            DESCRIPTION
                    "Not supported."                    

         VARIATION   tmnxChassisFanOperMode 
            ACCESS  not-implemented
            DESCRIPTION
                    "Not supported."  

          VARIATION   tmnxSysConsoleAlarmInput  
            ACCESS  not-implemented
            DESCRIPTION
                    "Not supported."
                    
    ::= { tmnxSASM7210V6v0 32 }

--
--  VIRTUAL ROUTER CAPABILITIES
--
tmnxVRtrCapsSASM7210V6v0 AGENT-CAPABILITIES
    PRODUCT-RELEASE "Alcatel SAS-M 7210"
    STATUS current
    DESCRIPTION
        "Implementation of Virtual Router capabilities
         for Alcatel SAS-M 7210 release R6.0"

    SUPPORTS TIMETRA-VRTR-MIB
        INCLUDES    {
            tmnxVRtrGlobalV6v0Group,
            tmnxVRtrV6v1Group,
            tmnxVRtrIfV5v0Group,
            tmnxVRtrNotificationV7v0Group,
            tmnxVRtrIfSubscrAuthV3v0Group,
            -- tmnxVRtrIfCpmProtectGroup,
            tmnxVRtrBfdV6v0Group,
            -- tmnxVRtrIPv6IfV4v0Group no IPv6 on SAS-M 7210
            -- tmnxVRtrIPv6MgtIfV7v0Group,
            -- tmnxVRtrIPv6V4v0Group   no IPv6 on SAS-M 7210
            -- tmnxVRtrIPv6IpV5v0Group no IPv6 on SAS-M 7210
            -- tmnxVRtrIfDhcpServerGroup no DHCP server on SAS-M 7210
            -- tmnxVRtrIfIpcpV6v0Group no IPCP Extensions on SAS-M 7210
            -- tmnxVRtrStaticRteCPEChkV6v0Group,
            tmnxDscpAppV6v0Group,
            -- tmnxVRtrIfDHCPRelayV7v0Group,
            tmnxVRtrV7v0Group,
            tmnxVRtrIpV7v0Group,
            tmnxVRtrDHCPIfLseStatesExceeded,
            tmnxVRtrIfDHCPRelayV6v1Group,
            tmnxVRtrIfDHCPRelayV9v0Group,
            tmnxVRtrQosQGrplV10v0Group
        }

         VARIATION  vRtrIfQosEgrPortRedirectQGrp
            DESCRIPTION
                    "Not supported ."
     
       
         VARIATION  vRtrIfQosEgrQGrpInstanceId
            DESCRIPTION
                    "Not supported. "
 
        
         VARIATION vRtrIfQosIngFpRedirectQGrp
            DESCRIPTION
                    "Not supported. "
         
         VARIATION  vRtrIfQosIngQGrpInstanceId
            DESCRIPTION
                    "Not supported. "               

        VARIATION   vRtrIfEgressFilterId
            DESCRIPTION
                    "Not supported in RVPLS."

        VARIATION   vRtrIfIPv6IngressFilterId
            DESCRIPTION
                    "Not supported in RVPLS."

        VARIATION   vRtrIfIPv6EgressFilterId
            DESCRIPTION
                    "Not supported in RVPLS."

        VARIATION   vRtrNextVRtrID
            ACCESS  read-only
            DESCRIPTION
                    "read-only implementation."

        VARIATION   vRtrRouteThresholdSoakTime
            ACCESS  read-only
            DESCRIPTION
                    "read-only implementation."

        VARIATION   vRtrIPv6RouteThresholdSoakTime
            ACCESS  not-implemented
            DESCRIPTION
                    "Not supported."

        VARIATION   vRtrIpCidrRoutePreference
            ACCESS  read-only
            DESCRIPTION
                    "read-only implementation."

        VARIATION   vRtrType
            ACCESS  read-only
            DESCRIPTION
                    "read-only implementation."

        VARIATION   vRtrIfDHCPLeasePopulate
            DESCRIPTION
                    "The default value of vRtrIfDHCPLeasePopulate is '1',
                    not '0', when the interface running DHCP has vRtrIfType
                    'serviceIesGroup'."

        VARIATION   vRtrIgnoreIcmpRedirect
            DESCRIPTION
                    "The default value of vRtrIgnoreIcmpRedirect is changed
                    to 'true' from 'false' in release 4.0-R13 and 5.0-R3."

                   
        --  VPRN on SAS-M 7210: begin
        

        VARIATION vRtrIfType
            SYNTAX  INTEGER {
                        network                  (1),
                        service                  (2),
                        serviceIes               (3),
                        -- serviceRtdVpls        (4)
                        serviceVprn           (5),
                        -- serviceIesSubscriber  (6),
                        -- serviceIesGroup       (7),
                        -- serviceVprnSubscriber (8),
                        -- serviceVprnGroup      (9),
                        -- serviceIesRedundant   (10),
                        -- serviceVprnRedundant  (11),
                        serviceVpls              (12),
                        -- serviceIesCem         (13),
                        -- serviceVprnCem        (14),
                        -- serviceVprnIPsec      (15)
                        serviceVprnIPMirror      (16)
                    }
            DESCRIPTION
                    "The values
                        - 'serviceRtdVpls        (4)'  (obsoleted)
                        - 'serviceIesSubscriber  (6)', (routed CO)
                        - 'serviceIesGroup       (7)', (routed CO)
                        - 'serviceVprnSubscriber (8)',
                        - 'serviceVprnGroup      (9)',
                        - 'serviceIesRedundant   (10)',
                        - 'serviceVprnRedundant  (11)',
                        - 'serviceIesCem         (13)',
                        - 'serviceVprnCem        (14)',
                        - 'serviceVprnIPsec      (15)' (IPsec Tunneling)
                    are not suppoted on SAS-M 7210 systems."

       
        --  VPRN on SAS-M 7210: end

        -- no CFLOWD on SAS-M 7210: begin
        VARIATION   vRtrIfCflowd
            ACCESS  not-implemented
            DESCRIPTION
                    "Not supported (No CFLOWD)."
        -- no CFLOWD on SAS-M 7210: end

        -- no IGMP on SAS-M 7210: begin

        -- no IGMP on SAS-M 7210: end

        -- no PIM on SAS-M 7210: begin
       
        VARIATION   vRtrMulticastRoutes
            ACCESS  not-implemented
            DESCRIPTION
                    "Not supported (No IPM)."
        -- no PIM on SAS-M 7210: end

        -- no MSDP on SAS-M 7210: begin
        VARIATION   vRtrMsdpStatus
            ACCESS  not-implemented
            DESCRIPTION
                    "Not supported (No MSDP)."

        -- no MSDP on SAS-M 7210: end

        -- no MLD on SAS-M 7210: begin
        VARIATION   vRtrMldStatus
            ACCESS  not-implemented
            DESCRIPTION
                    "Not supported (No MLD)."

        -- no MLD on SAS-M 7210: end

        VARIATION   vRtrSubMgmtRoutes
            ACCESS  not-implemented
            DESCRIPTION
                    "Not supported (No routed-CO)."

        VARIATION   vRtrSubMgmtActiveRoutes
            ACCESS  not-implemented
            DESCRIPTION
                    "Not supported (No routed-CO)."

        VARIATION   vRiaInetGwAddressType
            ACCESS  not-implemented
            DESCRIPTION
                    "Not supported."

        VARIATION   vRiaInetGwAddress
            ACCESS  not-implemented
            DESCRIPTION
                    "Not supported."

        VARIATION   vRtrInetStaticRouteCpeAddrType
            SYNTAX  INTEGER {
                        unknown     (0),
                        ipv4        (1)
                        -- ipv6     (2),
                        -- ipv4z    (3),
                        -- ipv6z    (4),
                        -- dns      (16)
                    }
            DESCRIPTION
                    "vRtrInetStaticRouteCpeAddrType supports only
                     InetAddressType values 'unknown' and 'ipv4'."

        VARIATION   vRtrInetStaticRouteCpeAddr
            SYNTAX  InetAddress (SIZE (0|4))
            DESCRIPTION
                    "vRtrInetStaticRouteCpeAddr supports only
                     InetAddressType values 'unknown' and 'ipv4'."


        VARIATION   vRtrManagedRoutes
            ACCESS  not-implemented
            DESCRIPTION
                    "Not supported (No Routed Subscriber Host)."

        VARIATION   vRtrManagedActiveRoutes
            ACCESS  not-implemented
            DESCRIPTION
                    "Not supported (No Routed Subscriber Host)."

        VARIATION   tmnxDscpAppId
            SYNTAX  INTEGER {
                    bgp                (1),
                    --cflowd             (2),
                    dhcp               (3),
                    dns                (4),
                    ftp                (5),
                    icmp               (6),
                    --igmp               (7),
                    --l2tp               (8),
                    ldp                (9),
                    --mld               (10),
                    --msdp              (11),
                    --ndis              (12),
                    ntp               (13),
                    ospf              (14),
                    --pim               (15),
                    radius            (16),
                    rip               (17),
                    rsvp              (18),
                    snmp              (19),
                    snmp-notification (20),
                    --srrp              (21),
                    ssh               (22),
                    syslog            (23),
                    tacplus           (24),
                    telnet            (25),
                    tftp              (26),
                    traceroute        (27),
                    vrrp              (28)
                    }
            DESCRIPTION
                    "tmnxDscpAppId does not support TDSCPAppId
                    values of 'srrp', 'cflowd', 'igmp',
                    'mld', 'msdp', 'ndis' and 'pim' as SRRP,
                    CFLOWD, IGMP, MLD, MSDP, IPv6 and PIM
                    are not available on SAS-M 7210 systems."

        VARIATION   tmnxDot1pAppId
            SYNTAX  INTEGER {
                    arp               (1),
                    isis              (2)
                    --pppoe             (3)
                    }
            DESCRIPTION
                    "tmnxDot1pAppId does not support value 'pppoe (3)'
                     as PPPoE is not available on SAS-M 7210 systems."

        VARIATION  vRtrMcPathMgmtPlcyName
             ACCESS  not-implemented
             DESCRIPTION
                    "Not supported (no way to join multicast streams)."

        VARIATION  vRtrMldStatus
             ACCESS  not-implemented
             DESCRIPTION
                    "Not supported."

       VARIATION vRtrIPv6HighRouteThreshold
           ACCESS  not-implemented
           DESCRIPTION
               "Not supported."

       VARIATION vRtrMcPathMgmtPlcyName
           ACCESS  not-implemented
           DESCRIPTION
               "Not supported."

       VARIATION vRtrMcPathMgmtPlcyName
           ACCESS  not-implemented
           DESCRIPTION
               "Not supported."

       VARIATION vRtrConfederationAS4Byte
           ACCESS  not-implemented
           DESCRIPTION
               "Not supported."

        VARIATION vRiaInetGwAddressType
            ACCESS  not-implemented
            DESCRIPTION
                "Not supported."

        VARIATION vRiaInetGwAddress
            ACCESS  not-implemented
            DESCRIPTION
                "Not supported."

        VARIATION vRtrInetCidrProtocolInstance
            ACCESS  not-implemented
            DESCRIPTION
                "Not supported."

        VARIATION vRtrInetCidrRouteTunnEndpntInfo
            ACCESS  not-implemented
            DESCRIPTION
                "Not supported."

        VARIATION vRtrHighRouteThreshold
            ACCESS  not-implemented
            DESCRIPTION
                "Not supported."

        VARIATION vRtrIfDelayUpTimer
            ACCESS  not-implemented
            DESCRIPTION
                "Not supported."

        VARIATION vRtrIfInitDelayEnable
            ACCESS  not-implemented
            DESCRIPTION
                "Not supported."

        VARIATION vRtrIgnoreNextHopMetric
            ACCESS  not-implemented
            DESCRIPTION
                "Not supported."

        VARIATION vRtrIllegalLabelThreshold
            ACCESS  not-implemented
            DESCRIPTION
                "Not supported."

        VARIATION vRtrInetStaticRouteDisallowIgp
            ACCESS  not-implemented
            DESCRIPTION
                "Not supported."

        VARIATION vRtrInetStaticRouteIgpShortcut
            ACCESS  not-implemented
            DESCRIPTION
                "Not supported."

      
        VARIATION vRtrInetStaticRouteNHTunnelName
            ACCESS  not-implemented
            DESCRIPTION
                "Not supported."

        VARIATION vRtrInetSvcIpRangeExclusive
            ACCESS  not-implemented
            DESCRIPTION
                "Not supported."

        VARIATION vRtrInetSvcIpRangeRowStatus
            ACCESS  not-implemented
            DESCRIPTION
                "Not supported."

        VARIATION vRtrRIPActiveRoutes
            ACCESS  not-implemented
            DESCRIPTION
                "Not supported."

        VARIATION vRtrRIPRoutes
            ACCESS  not-implemented
            DESCRIPTION
                "Not supported."

        VARIATION vRtrRipStatus
            ACCESS  not-implemented
            DESCRIPTION
                "Not supported."

        VARIATION vRtrSecondaryVrfId
            ACCESS  not-implemented
            DESCRIPTION
                "Not supported."

        VARIATION vRtrStatActiveRsvpTunnels
            ACCESS  not-implemented
            DESCRIPTION
                "Not supported."

        VARIATION vRtrStaticRouteDisallowIgp
            ACCESS  not-implemented
            DESCRIPTION
                "Not supported."

        VARIATION vRtrStaticRouteIgpShortcut
            ACCESS  not-implemented
            DESCRIPTION
                "Not supported."

        VARIATION vRtrStaticRouteNextHopUnnumberedIf
            ACCESS  not-implemented
            DESCRIPTION
                "Not supported."

        VARIATION vRtrStatTotalRsvpTunnels
            ACCESS  not-implemented
            DESCRIPTION
                "Not supported."

        VARIATION vRtrSvcIpRangeAddress
            ACCESS  not-implemented
            DESCRIPTION
                "Not supported."

        VARIATION vRtrSvcIpRangeExclusive
            ACCESS  not-implemented
            DESCRIPTION
                "Not supported."

        VARIATION vRtrSvcIpRangeMask
            ACCESS  not-implemented
            DESCRIPTION
                "Not supported."

        VARIATION vRtrSvcIpRangeRowStatus
            ACCESS  not-implemented
            DESCRIPTION
                "Not supported."

        VARIATION vRtrV6StatActiveRsvpTunnels
            ACCESS  not-implemented
            DESCRIPTION
                "Not supported."

        VARIATION vRtrV6StatTotalRsvpTunnels
            ACCESS  not-implemented
            DESCRIPTION
                "Not supported."


        VARIATION vRtrVprnType
            SYNTAX      INTEGER {
                    regular (1)
                }
                
            DESCRIPTION
                    "On 7210 SAS-M platforms only regular is supported for
                    vRtrVprnType."

        VARIATION vRtrDHCP6DropStatLastCleared
            ACCESS  not-implemented
            DESCRIPTION
                "Not supported."

        VARIATION vRtrDHCP6DropStatPktsDropped
            ACCESS  not-implemented
            DESCRIPTION
                "Not supported."

        VARIATION vRtrDHCP6MsgStatsDropped
            ACCESS  not-implemented
            DESCRIPTION
                "Not supported."

        VARIATION vRtrDHCP6MsgStatsLstClrd
            ACCESS  not-implemented
            DESCRIPTION
                "Not supported."

        VARIATION vRtrDHCP6MsgStatsRcvd
            ACCESS  not-implemented
            DESCRIPTION
                "Not supported."

        VARIATION vRtrDHCP6MsgStatsSent
            ACCESS  not-implemented
            DESCRIPTION
                "Not supported."

        VARIATION vRtrDHCP6MsgStatsSent
            ACCESS  not-implemented
            DESCRIPTION
                "Not supported."

        VARIATION   vRtrIfDHCPAuthPolicy
            ACCESS  not-implemented
            DESCRIPTION
                    "Not supported."
                    
        VARIATION   vRtrIfDHCPFilterId     
            ACCESS  not-implemented
            DESCRIPTION
                    "Not supported."
                    
        VARIATION   vRtrIfDHCPUseArpForReply    
            ACCESS  not-implemented
            DESCRIPTION
                    "Not supported."
                    
        VARIATION   vRtrIfDHCPUserDb   
            ACCESS  not-implemented
            DESCRIPTION
                    "Not supported."
                   
                    
        VARIATION   vRtrIfDHCPAntiSpoofMacAddr 
            ACCESS  not-implemented
            DESCRIPTION
                    "Not supported."
                    
        VARIATION   vRtrIfDHCPLayer2Header
            ACCESS  not-implemented
            DESCRIPTION
                    "Not supported."
                    
        VARIATION vRtrIfDHCPLeasePopulate
            ACCESS  not-implemented
            DESCRIPTION
                "Not supported."

        VARIATION vRtrIfDHCPMatchOption82
            ACCESS  not-implemented
            DESCRIPTION
                "Not supported."

        VARIATION vRtrIfDHCPOperLeasePopulate
            ACCESS  not-implemented
            DESCRIPTION
                "Not supported."

        VARIATION vRtrIfDHCPProxyAdminState
            ACCESS  not-implemented
            DESCRIPTION
                "Not supported."

        VARIATION vRtrIfDHCPProxyLeaseTime
            ACCESS  not-implemented
            DESCRIPTION
                "Not supported."

        VARIATION vRtrIfDHCPProxyLTRadiusOverride
            ACCESS  not-implemented
            DESCRIPTION
                "Not supported."

        VARIATION vRtrIfDHCPProxyServerAddr
            ACCESS  not-implemented
            DESCRIPTION
                "Not supported."

    ::= { tmnxSASM7210V6v0 34 }

--
--  CRON CAPABILITIES
--
tmnxCronCapsSASM7210V6v0 AGENT-CAPABILITIES
    PRODUCT-RELEASE "Alcatel SAS-M 7210"
    STATUS current
    DESCRIPTION
        "Implementation of CRON scheduling capabilities
         for Alcatel SAS-M 7210 release R6.0"

    SUPPORTS DISMAN-SCHEDULE-MIB
        INCLUDES    {
            schedGroup2,
            schedCalendarGroup,
            schedNotificationsGroup
        }

        VARIATION   schedOwner
            SYNTAX  SnmpAdminString (SIZE (1..32))
            DESCRIPTION
                    "The minimum length of schedOwner is 1 when creating
                     new entries in tables via SNMP SET requests."

        VARIATION   schedInterval
            SYNTAX  Unsigned32 (30..42949672)
            DESCRIPTION
                    "The values supported for schedInterval are between
                    30 and 42949672 seconds.  42949672 seconds creates
                    a maximum interval of 497 days, 2 hours, 27 minutes
                    and 52 seconds."


    SUPPORTS DISMAN-SCRIPT-MIB
        INCLUDES    {
            smLanguageGroup,
            smScriptGroup2,
            smLaunchGroup2,
            smRunGroup2,
            smNotificationsGroup2
        }

        VARIATION   smScriptEntry
            DESCRIPTION
                    "A maximum of 255 smScriptEntry rows are allowed to be
                    created."

        VARIATION   smScriptOwner
            SYNTAX  SnmpAdminString (SIZE (1..32))
            DESCRIPTION
                    "The minimum length of smScriptOwner is 1 when creating
                     new entries in tables via SNMP SET requests."

        VARIATION   smScriptDescr
            SYNTAX  SnmpAdminString (SIZE (0..80))
            DESCRIPTION
                    "The maximum size string supported for smScriptDescr
                    is 80 octets."

        VARIATION   smScriptLanguage
            SYNTAX  Integer32 (1)
            DESCRIPTION
                    "The only script language supported is the TiMOS CLI
                    that has an smLangIndex value equal 1.  smScriptLanguage
                    can only be set to the value 1."

        VARIATION   smScriptSource
            DESCRIPTION
                    "The mib requires that when smScriptAdminStatus is
                    set to 'enabled', the agent at that point should
                    'pull' the script from local cflash or remote URL
                    if one is specified.  This agent does not 'pull'
                    scripts to its local storage.  The URL specified in
                    smScriptSource is passed as an argument to the CLI
                    'exec' command when the smRunState transitions to
                    'executing'.

                    The mib states that an empty URL implies that the
                    script scource is already in local storage and are
                    located by some implementation specific mapping
                    scheme between the local storage file name and the
                    smScriptName index.  This agent does not support
                    this behavior.  An empty smScriptSource URL causes
                    an attempt to set a value to smLaunchStart to return
                    an 'inconsistentValue' error."

        VARIATION   smScriptAdminStatus
            SYNTAX  INTEGER {
                        enabled     (1),
                        disabled    (2)
                        -- editing  (3)
                    }
            DESCRIPTION
                    "The smScriptAdminStatus state 'editing (3)' is not
                    supported because smCodeTable is not supported."

        VARIATION   smScriptStorageType
            DEFVAL  { nonVolatile }
            DESCRIPTION
                    "This agent supports only 'nonVolatile' storage type.
                    This is interpreted to be the desired storage type
                    for the configuration of the script row entry.

                    When smLaunchStorageType has a value of 'nonVolatile'
                    its configuration is written to the configuration
                    file upon a 'save configuration' operation.  If the
                    system reboots between the time this row entry is
                    created and before a 'save configuration' operation is
                    made, this row entry will NOT be restored following
                    the reboot."

        VARIATION   smLaunchEntry
            DESCRIPTION
                    "A maximum of 255 smLaunchEntry rows are allowed to be
                    created."

        VARIATION   smLaunchOwner
            SYNTAX  SnmpAdminString (SIZE (1..32))
            DESCRIPTION
                    "The minimum length of smLaunchOwner is 1 when creating
                     new entries in tables via SNMP SET requests."

        VARIATION   smLaunchMaxRunning
            SYNTAX  Unsigned32 (1)
            DESCRIPTION
                    "Concurrently running scripts are not supported by
                    this agent. Scripts are queued and executed one
                    at a time. An attempt to set smLaunchMaxRunning
                    to any value other than 1 results in an
                    'inconsistentValue' error."

        VARIATION   smLaunchArgument
            DESCRIPTION
                    "This agent uses smLaunchArgument to specify the
                    URL of the file that is created to hold the CLI
                    session output from the 'exec' of the CLI script
                    specified in smScriptSource.  The script specified
                    in smScriptSource is executed as if the 'exec' '-echo'
                    switch was specified in a CLI CONSOLE/Telnet session
                    and the command echo and any display from CLI 'show'
                    commands specified in the script is redirected to the
                    results file specified in smLaunchArgument.

                    The smLaunchArgument URL should consist of the
                    path and a filename prefix.  It refer to either the
                    local cflash drives or a remote file accessed through
                    a remote ftp URL.  When the exec results file is created
                    for a specific run of the script, a timestamp of the
                    form '_yyyymmdd-hhmmss.out' is appended on the end of
                    the smLaunchArgument filename prefix.  For example,
                    setting smLaunchArgument to
                    'ftp://<user>:<passwd>@<a.b.c.d>/cron/results/test-res'
                    causes a script results file to be created named
                    'cron/results/test-res_yyyymmdd-hhmmss.out'.

                    NOTE: The agent does not have any capability to age out,
                    rotate, delete, or otherwise manage these script
                    results files.  It is up to the SR system operator or
                    manager to manage retrieval and cleanup of these files."

        VARIATION   smLaunchExpireTime
            DESCRIPTION
                    "Unlike smLaunchLifeTime, the mib does not specify a
                    value for smLaunchExpireTime that can be used to
                    indicate that an associated smRunEntry with a smRunState
                    equal to 'terminated' should be kept forever and
                    never aged out.  This agent uses the maximum value
                    (2147483647) to specify that a smRunEntry does not
                    age out after its smRunState transitions to
                    'terminated'.  A terminated smRunEntry with a maximum
                    smRunExpireTime value will never be removed from
                    the table."

        VARIATION   smLaunchStart
            DESCRIPTION
                    "In the 4.0 release there is no user access rights
                    checking to verify that the user setting smLaunchStart
                    has read-access to the script.  A user command
                    access profile with RADIUS/TACACS+ authentication will
                    be associated to the script in a later release.

                    The mib requires that in order for a set to smLaunchStart
                    to succede th number of concurrently executing scripts
                    must be less than the value of smLaunchMaxRunning.
                    This agent does not support execution of more than one
                    script at a time.  Instead, a smRunEntry is created
                    with smRunState equal to 'initializing' and sequentially
                    queued for later execution.  The maximum number of
                    smRunEntry rows is limited to 255 regardless of the value
                    of smRunState.

                    The mib specifies that when the smRunEntry is created
                    by setting smLaunchStart, the smRunStartTime should be
                    set to the current time.  Because of the one-at-a-time
                    queuing for execution there may be a long time between
                    entering the 'initializing' state and transitioning
                    to the 'executing' state, this agent does not set
                    smRunStartTime until smRunState transitions to
                    'executing'."

        VARIATION   smLaunchControl
            SYNTAX  INTEGER {
                        abort        (1),
                        -- suspend   (2),
                        -- resume    (3),
                        nop          (4)
                    }
            DESCRIPTION
                    "The 'suspend (2)' and 'resume (3)' controls are not
                    supported.  An attempt to set either value results
                    in an 'inconsistentValue' error."

        VARIATION   smLaunchAdminStatus
            SYNTAX  INTEGER {
                        enabled      (1),
                        disabled     (2)
                        -- autostart (3)
                    }
            DESCRIPTION
                    "The 'autostart (3)' state is not supported.

                    The mib is not clear if smLaunchAdminStatus can be
                    set to 'disabled (2)' if there are associated entries
                    in the smRunTable.  This agent does not allow
                    smLaunchAdminStatus to be set to 'disabled (2)' if there
                    are any associated entries in the smRunTable.  Any
                    associated smRunEntry must be aborted and aged out
                    before smLaunchAdminStatus can be set to 'disabled'."

        VARIATION   smLaunchRunIndexNext
            DESCRIPTION
                    "The mib requires that subsequent reads of
                    smLaunchRunIndexNext must return different values.
                    This agent does not increment the value with every
                    read.  A read always returns the next available
                    index value."

        VARIATION   smLaunchStorageType
            SYNTAX  INTEGER {
                        -- other        (1),
                        -- volatile     (2),
                        nonVolatile     (3)  -- e.g., in NVRAM
                        -- permanent    (4),
                        -- readOnly     (5)
                    }
            DEFVAL  { nonVolatile }
            DESCRIPTION
                    "This agent supports only 'nonVolatile (3)' storage type.
                    This is interpreted to be the desired storage type
                    for the configuration of the launch entry.

                    When smLaunchStorageType has a value of 'nonVolatile'
                    its configuration is written to the configuration
                    file upon a 'save configuration' operation.  If the
                    system reboots between the time this row entry is
                    created and before a 'save configuration' operation is
                    made, this row entry will NOT be restored following
                    the reboot."

        VARIATION   smLaunchRowExpireTime
            ACCESS  read-only
            DESCRIPTION
                    "smLaunchRowExpireTime functionality is not supported.
                    Its value cannot be modified.  The default value
                    2147483647 is always returned to indicate that the
                    smLaunchTable row entry will never be aged out."

        VARIATION   smRunEntry
            DESCRIPTION
                    "A maximum of 255 smRunEntry rows are allowed to be created
                    regardless of the value of smRunState."

        VARIATION   smRunArgument
            SYNTAX  OCTET STRING (SIZE (0..255))
            DESCRIPTION
                    "The maximum size string returned by a read of
                    smRunArgument is 255 octets."

        VARIATION   smRunLifeTime
            DESCRIPTION
                    "It is not clear from the mib if smRunLifeTime starts
                    to tick backwards when smRunState equals 'initializing'
                    or when smRunState equals 'executing'.  This agent
                    implementation starts to decrement smRunLifeTime
                    when smRunState transitions to 'executing'."

        VARIATION   smRunExpireTime
            DESCRIPTION
                    "Unlike smRunLifeTime, the mib does not specify a
                    value for smRunExpireTime that can be used to
                    indicate this smRunEntry should be kept forever and
                    never aged out.  This agent uses the maximum value
                    (2147483647) to specify that this smRunEntry does not
                    age out after its smRunState transitions to
                    'terminated'.

                    If smRunExpireTime is set to its maximum value
                    (2147483647), either by a set operation or by its
                    initialization from the smLaunchExpireTime object,
                    then it does not tick backwards. A terminated script
                    with a maximum smRunExpireTime value thus is never
                    be aged out and removed from the table."

        VARIATION   smRunResult
            SYNTAX  OCTET STRING (SIZE (0..255))
            DESCRIPTION
                    "The maximum size string returned by a read of
                    smRunResult is 255 octets."

        VARIATION   smRunControl
            SYNTAX  INTEGER {
                        abort       (1),
                        -- suspend  (2),
                        -- resume   (3),
                        nop         (4)
                    }
            DESCRIPTION
                    "The 'suspend (2)' and 'resume (3)' controls are not
                     supported.  An attempt to set either value results in
                     an 'inconsistentValue' error."

        VARIATION   smRunState
            SYNTAX INTEGER {
                        initializing    (1),
                        executing       (2),
                        -- suspending   (3),
                        -- suspended    (4),
                        -- resuming     (5),
                        aborting        (6),
                        terminated      (7)
                    }
            DESCRIPTION
                    "The 'suspending (3)', 'suspended (4)', and 'resuming (5)'
                    states are not supported."

        VARIATION   smRunStartTime
            DESCRIPTION
                    "It is not clear from the mib if smRunStartTime is
                    set when smRunState transitions to 'initializing' or
                    not until smRunState transitions to 'executing'.
                    This agent implementation sets smRunStartTime when
                    smRunState transitions to 'executing'."

    ::= { tmnxSASM7210V6v0 35 }  -- CRON DISMAN-SCHEDULE-MIB & DISMAN-SCRIPT-MIB

--
--  NTP CAPABILITIES
--
tmnxNtpCapsSASM7210V6v0 AGENT-CAPABILITIES
    PRODUCT-RELEASE "Alcatel 7740"
    STATUS current
    DESCRIPTION
        "Implementation of NTP capabilities for Alcatel SAS-M 7210 release R6.0"

    SUPPORTS TIMETRA-NTP-MIB
        INCLUDES    {
            tmnxNtpGlobalGroup,
            -- tmnxNtpMulticastGroup,
            tmnxNtpServersGroup,
            tmnxNtpPeersGroup,
            tmnxNtpAuthKeyGroup,
            tmnxNtpBroadcastGroup,
            tmnxNtpNotificationV6v0Group
-- EXCLUDE tmnxNtpUtcOffsetExThreshold (obsolete notification object)
-- EXCLUDE tmnxNtpUtcOffsetInThreshold (obsolete notification object)
        }

        VARIATION   tmnxNtpMulticastAddressType
            SYNTAX  INTEGER {
                        -- unknown  (0),
                        ipv4        (1)
                        -- ipv6     (2),
                        -- ipv4z    (3),
                        -- ipv6z    (4),
                        -- dns      (16)
                    }
            DESCRIPTION
                    "tmnxNtpMulticastAddressType supports only InetAddressType
                    'ipv4'."

        VARIATION   tmnxNtpMulticastAddress
            SYNTAX  InetAddress (SIZE (4))
            DESCRIPTION
                    "tmnxNtpMulticastAddress supports only InetAddressType
                    'ipv4'."

        VARIATION   tmnxNtpServersAddrType
            SYNTAX  INTEGER {
                        -- unknown  (0),
                        ipv4        (1)
                        -- ipv6     (2),
                        -- ipv4z    (3),
                        -- ipv6z    (4),
                        -- dns      (16)
                    }
            DESCRIPTION
                    "tmnxNtpServersAddrType supports only InetAddressType
                    'ipv4'."

        VARIATION   tmnxNtpServersAddress
            SYNTAX  InetAddress (SIZE (4))
            DESCRIPTION
                    "tmnxNtpServersAddress supports only InetAddressType
                    'ipv4'."

        VARIATION   tmnxNtpPeersAddrType
            SYNTAX  INTEGER {
                        -- unknown  (0),
                        ipv4        (1)
                        -- ipv6     (2),
                        -- ipv4z    (3),
                        -- ipv6z    (4),
                        -- dns      (16)
                    }
            DESCRIPTION
                    "tmnxNtpPeersAddrType supports only InetAddressType
                    'ipv4'."

        VARIATION   tmnxNtpPeersAddress
            SYNTAX  InetAddress (SIZE (4))
            DESCRIPTION
                    "tmnxNtpPeersAddress supports only InetAddressType
                    'ipv4'."

        VARIATION   tmnxNtpPeersPeerAddrType
            SYNTAX  INTEGER {
                        -- unknown  (0),
                        ipv4        (1)
                        -- ipv6     (2),
                        -- ipv4z    (3),
                        -- ipv6z    (4),
                        -- dns      (16)
                    }
            DESCRIPTION
                    "tmnxNtpPeersPeerAddrType supports only InetAddressType
                    'ipv4'."

        VARIATION   tmnxNtpPeersPeerAddress
            SYNTAX  InetAddress (SIZE (4))
            DESCRIPTION
                    "tmnxNtpPeersPeerAddress supports only InetAddressType
                    'ipv4'."

        VARIATION   tmnxNtpAuthKeyEntry
            CREATION-REQUIRES   { tmnxNtpAuthKeyType }
            DESCRIPTION
                    "A value must be set for tmnxNtpAuthKeyType in order for
                     tmnxNtpAuthKeyEntryStatus to successfully transition
                     to the 'active' state."

        VARIATION   tmnxNtpAuthKeyType
            SYNTAX  INTEGER {
                        -- des          (1),
                        messageDigest   (2)
                    }
            DESCRIPTION
                    "tmnxNtpAuthKeyType supports only 'messageDigest (2)'."

    ::= { tmnxSASM7210V6v0 36 }

--
--  TOD CAPABILITIES
--
tmnxSchedulerCapsSASM7210V6v0 AGENT-CAPABILITIES
    PRODUCT-RELEASE "Alcatel SAS-M 7210"
    STATUS current
    DESCRIPTION
        "Implementation of time of day (tod) policies on
         Alcatel SAS-M 7210 release R6.0"

    SUPPORTS TIMETRA-SCHEDULER-MIB
        INCLUDES    {
            tmnxTodPolicyV5v0Group,
            tmnxCronSchedV5v0Group
        }

        VARIATION tTodSuiteOprIngrIpv6FilterIndex
            ACCESS  not-implemented
            DESCRIPTION
                    "Not supported."

        VARIATION tTodSuiteOprEgrIpv6FilterIndex
            ACCESS  not-implemented
            DESCRIPTION
                    "Not supported."

        VARIATION tmnxTodToolRetryIPv6FltrDownload
            ACCESS  not-implemented
            DESCRIPTION
                    "Not supported."

    ::= { tmnxSASM7210V6v0 37 }

--
--  EFM OAM CAPABILITIES
--

tmnxDot3OamCapsSASM7210V6v0    AGENT-CAPABILITIES
    PRODUCT-RELEASE "Alcatel SAS-M 7210"
    STATUS          current
    DESCRIPTION
        "Implementation of Ethernet OAM (802.3ah) capabilities for Alcatel
        SAS-M 7210 release R6.0"

    SUPPORTS        DOT3-OAM-MIB
        INCLUDES    {
            dot3OamControlGroup,
            dot3OamPeerGroup,
            dot3OamStatsBaseGroup,
            dot3OamLoopbackGroup,
            dot3OamEventLogGroup,
            dot3OamNotificationGroup
        }

        VARIATION    dot3OamEventLogWindowHi
            ACCESS   not-implemented
            DESCRIPTION
                 "Not supported."

        VARIATION    dot3OamEventLogWindowLo
            ACCESS   not-implemented
            DESCRIPTION
                  "Not supported."

        VARIATION    dot3OamEventLogThresholdHi
            ACCESS   not-implemented
            DESCRIPTION
                  "Not supported."

        VARIATION    dot3OamEventLogThresholdLo
            ACCESS   not-implemented
            DESCRIPTION
                  "Not supported."

        VARIATION    dot3OamEventLogValue
            ACCESS   not-implemented
            DESCRIPTION
                  "Not supported."

        VARIATION    dot3OamEventLogRunningTotal
            ACCESS   not-implemented
            DESCRIPTION
                  "Not supported."

        VARIATION    dot3OamThresholdEvent
            ACCESS   not-implemented
            DESCRIPTION
                  "Not supported."

        VARIATION    dot3OamEventLogEventTotal
            ACCESS   not-implemented
            DESCRIPTION
                  "Not supported."

        VARIATION    dot3OamEventLogLocation
            ACCESS   not-implemented
            DESCRIPTION
                  "Not supported."

        VARIATION    dot3OamEventLogOui
            ACCESS   not-implemented
            DESCRIPTION
                  "Not supported."

        VARIATION    dot3OamEventLogTimestamp
            ACCESS   not-implemented
            DESCRIPTION
                  "Not supported."

        VARIATION    dot3OamEventLogType
            ACCESS   not-implemented
            DESCRIPTION
                  "Not supported."

    SUPPORTS        TIMETRA-DOT3-OAM-MIB
        INCLUDES    {
            tmnxDot3OamV6v0Group,
            tmnxDot3OamV6v1Group,
            tmnxDot3OamLoopbackGroup,
            tmnxDot3OamNotificationV6v0Group
        }

    ::= { tmnxSASM7210V6v0 41 }

--
-- Dot1ag CFM CAPABILITIES
--

tmnxDot1agCfmCapsSASM7210V6v0 AGENT-CAPABILITIES
    PRODUCT-RELEASE "Alcatel SAS-M 7210"
    STATUS          current
    DESCRIPTION     "Implementation of Dot1ag CFM capabilities
                     for Alcatel SRSAS-M 7210 release R6.0"

    SUPPORTS        TIMETRA-IEEE8021-CFM-MIB
        INCLUDES    {
            tmnxDot1agCfmSdpBindStackGroup,
            tmnxDot1agCfmMepGroupV7v0,
            tmnxDot1agCfmSapStackGroup,
            tmnxDot1agCfmNotificationGroup,
            -- tmnxDot1agCfmMipGroup,
            tmnxDot1agCfmMipNotifyGroup,
            tmnxY1731CfmNotificationGroup
        }

        VARIATION   tmnxDot1agCfmMepEthTestPattern
            SYNTAX  INTEGER {
                        allZerosNoCrc  (0),
                        allZerosCrc    (1),
                        -- prbsNoCrc   (2),
                        -- prbsCrc     (3),
                        allOnesNoCrc   (4),
                        allOnesCrc     (5)
                    }
            DESCRIPTION
                    "tmnxDot1agCfmMepEthTestPattern supports all zero and all one
                     patterns only."

        VARIATION   tmnxDot1agCfmMaMepListMacAddress
           ACCESS   not-implemented
           DESCRIPTION
                   "SNMP set and get are disabled.Only snmp walk is working." 

        VARIATION   tmnxDot1agCfmMepSvcId
           ACCESS   not-implemented
           DESCRIPTION
                   "Not supported."


    SUPPORTS        IEEE8021-CFM-MIB
        INCLUDES    {
            -- dot1agCfmStackGroup,
            -- dot1agCfmDefaultMdGroup,
            -- dot1agCfmVlanIdGroup,
            -- dot1agCfmConfigErrorListGroup,
            dot1agCfmMdGroup,
            dot1agCfmMaGroup,
            dot1agCfmMepGroup,
            dot1agCfmMepDbGroup,
            dot1agCfmNotificationsGroup
        }

        VARIATION   dot1agCfmMaComponentId
            DESCRIPTION
                    "dot1agCfmMaComponentId supports a smaller range than
                     specified in the IEEE-8021-CFM-MIB. The 7x50 series
                     supports the range of 1..2147483647."

        VARIATION   dot1agCfmMdMhfCreation
            SYNTAX  Dot1agCfmMhfCreation {
                        defMHFnone (1)
                        -- defMHFdefault (2),
                        -- defMHFexplicit (3)
                    }
            DESCRIPTION
                    "dot1agCfmMdMhfCreation only supports 'defMHFnone'."

        VARIATION   dot1agCfmMdMhfIdPermission
            SYNTAX  Dot1agCfmIdPermission {
                        sendIdNone (1)
                        -- sendIdChassis (2),
                        -- sendIdManage (3),
                        -- sendIdChassisManage (4),
                        -- sendIdDefer (5)
                    }
            DESCRIPTION
                    "dot1agCfmMdMhfIdPermission only supports 'sendIdNone'."

        VARIATION   dot1agCfmMaNetFormat
            DEFVAL  { unsignedInt16 }
            DESCRIPTION
                    "dot1agCfmMaNetFormat defaults to 'unsignedInt16' if not
                     specified."

        VARIATION   dot1agCfmMaNetCcmInterval
            SYNTAX  INTEGER {
                        -- intervalInvalid (0),
                        -- interval300Hz (1),
                        -- interval10ms (2),
                        interval100ms (3),
                        interval1s (4),
                        interval10s (5),
                        interval1min (6),
                        interval10min (7)
                    }
            DEFVAL  { interval10s }
            DESCRIPTION
                    "dot1agCfmMaNetCcmInterval defaults to 'interval10s' if not
                     specified, and does not support sub-second intervals."

        VARIATION   dot1agCfmMaCompMhfCreation
            SYNTAX  Dot1agCfmMhfCreation {
                        defMHFnone (1),
                        -- defMHFdefault (2),
                        defMHFexplicit (3)
                        -- defMHFdefer (4)
                    }
            DEFVAL  { defMHFnone }
            DESCRIPTION
                    "dot1agCfmMaCompMhfCreation defaults to 'defMHFnone' if not
                     specified."

        VARIATION   dot1agCfmMaCompIdPermission
            SYNTAX  Dot1agCfmIdPermission {
                        sendIdNone (1)
                        -- sendIdChassis (2),
                        -- sendIdManage (3),
                        -- sendIdChassisManage (4),
                        -- sendIdDefer (5)
                    }
            DEFVAL  { defMHFnone }
            DESCRIPTION
                    "dot1agCfmMaCompIdPermission defaults to, and only supports
                     the value 'defMHFnone'."

       VARIATION   dot1agCfmMepErrorCcmLastFailure
            SYNTAX  OCTET STRING (SIZE(0..1522))
            DESCRIPTION
                   "dot1agCfmMepErrorCcmLastFailure supports a size of 0 octets."

        VARIATION   dot1agCfmMepXconCcmLastFailure
            SYNTAX  OCTET STRING (SIZE(0..1522))
            DESCRIPTION
                   "dot1agCfmMepXconCcmLastFailure supports a size of 0 octets."

        VARIATION   dot1agCfmMepCcmLtmPriority
            DEFVAL  { 7 }
            DESCRIPTION
                    "dot1agCfmMepCcmLtmPriority defaults to 7, if not specified."

        VARIATION   dot1agCfmMepFngAlarmTime
            ACCESS  read-only
            DESCRIPTION
                    "read-only implementation."

        VARIATION   dot1agCfmMepFngResetTime
            ACCESS  read-only
            DESCRIPTION
                    "read-only implementation."

        VARIATION   dot1agCfmMepTransmitLbmStatus
            ACCESS  read-only
            DESCRIPTION
                    "read-only implementation."

        VARIATION   dot1agCfmMepTransmitLbmDestMepId
            DEFVAL  { 0 }
            DESCRIPTION
                    "dot1agCfmMepTransmitLbmDestMepId defaults to, and only
                     supports the value zero (0)."

        VARIATION   dot1agCfmMepTransmitLbmDestIsMepId
            DEFVAL  { false }
            DESCRIPTION
                    "dot1agCfmMepTransmitLbmDestIsMepId defaults to, and only
                     supports the value false."

        VARIATION   dot1agCfmMepTransmitLbmMessages
            SYNTAX  Integer32 (0..5)
            DEFVAL  { 0 }
            DESCRIPTION
                    "dot1agCfmMepTransmitLbmMessages supports a range from 0 to 5
                     messages and defaults to 0."

        VARIATION   dot1agCfmMepTransmitLtmTargetIsMepId
            DEFVAL  { false }
            DESCRIPTION
                    "dot1agCfmMepTransmitLtmTargetIsMepId defaults to, and only
                     supports the value false."

        VARIATION   dot1agCfmMepPrimaryVid
            SYNTAX  Unsigned32
            DESCRIPTION
                    "dot1agCfmMepPrimaryVid supports the entire Unsigned32 range
                     of values. This is to facilitate Q-in-Q encapsulation for SAPs."

        VARIATION   dot1agCfmMepTransmitLbmVlanDropEnable
           ACCESS   read-only
           DESCRIPTION
                   "dot1agCfmMepTransmitLbmVlanDropEnable is implemented as
                    read-only and only supports the value of false."

        VARIATION   dot1agCfmMepDbChassisIdSubtype
           ACCESS   not-implemented
           DESCRIPTION
                   "Not supported."

        VARIATION   dot1agCfmMepDbChassisId
           ACCESS   not-implemented
           DESCRIPTION
                   "Not supported."

        VARIATION   dot1agCfmMepDbManAddressDomain
           ACCESS   not-implemented
           DESCRIPTION
                   "Not supported."

        VARIATION   dot1agCfmMepDbManAddress
           ACCESS   not-implemented
           DESCRIPTION
                   "Not supported."

    ::= { tmnxSASM7210V6v0 43 }

--
--  SAP CAPABILITIES
--
tmnxSapCapsSASM7210V6v0    AGENT-CAPABILITIES
    PRODUCT-RELEASE "Alcatel SAS-M 7210"
    STATUS          current
    DESCRIPTION     "Implementation of SAP capabilities
                     for Alcatel SAS-M 7210 release R6.0"

    SUPPORTS        TIMETRA-SAP-MIB
        INCLUDES    {
           tmnxSapV7v0Group,
           tmnxSapTlsV6v1Group,
           tmnxSapBaseV6v0Group,
           -- tmnxSapAtmV6v0Group,            no ATM on SAS-M 7210
           -- tmnxSapQosV6v0Group,
           -- tmnxSapStaticHostV6v1Group,
           -- tmnxSapPortIdV6v0Group,
           -- tmnxSapSubMgmtV6v0Group,
           tmnxSapMstiV6v0Group,
           -- tmnxSapIpipeV7v0Group,
           tmnxSapPolicyV6v0Group,
           tmnxSapL2ptV6v0Group,
           -- tmnxSapMsapV6v0Group,
           -- tmnxSapMsapV6v1Group,
           -- tmnxSapHsmdaV6v0Group,
           tmnxSapNotifyGroup,
           -- tmnxSapDhcpV6v0Group,
           -- tmnxSapMrpV6v0Group,
           -- tmnxSapIpV6FilterV6v0Group
           -- tmnxSapIpv6FilterV5v0Group      no IPv6 on SAS-M 7210
           tmnxSapCemV6v0Group,
           tmnxSapCemNotificationV6v0Group,
           -- tmnxTlsMsapPppoeV6v0Group  no PPPoE on SAS-M 7210
           -- tmnxSapBsxV7v0Group,
           tmnxSapArpHostGroup,
           -- tmnxSapIgmpTrkGroup
           -- tmnxSapPbbGroup,
           tmnxSapDhcpV8v0Group,
           tmnxSapTlsV8v0Group,
           tmnxSapV10v0Group
        }

         VARIATION   sapTlsDhcpUserDb
            ACCESS  not-implemented
            DESCRIPTION
                    "Not supported."        
                    
        VARIATION   sapTlsStpBpduEncap
            SYNTAX  INTEGER {
                        dynamic (1)
                    }
            DESCRIPTION
                    "The only value that can be assigned to sapTlsStpBpduEncap
                    is 'dynamic (1)'. Additional values may be supported in a
                    later release."

        VARIATION   sapAntiSpoofing
            ACCESS  not-implemented
            DESCRIPTION
                    "Not supported."

        VARIATION   sapStaticHostMRtTblLastChgd
            ACCESS  not-implemented
            DESCRIPTION
                    "Not supported (No Routed Subscriber Host feature)."

        VARIATION   sapStaticHostMRtRowStatus
            ACCESS  not-implemented
            DESCRIPTION
                    "Not supported (No Routed Subscriber Host feature)."

        VARIATION   sapStaticHostMRtLastMgmtChange
            ACCESS  not-implemented
            DESCRIPTION
                    "Not supported (No Routed Subscriber Host feature)."

        VARIATION   sapStaticHostMRtStatus
            ACCESS  not-implemented
            DESCRIPTION
                    "Not supported (No Routed Subscriber Host feature)."

        VARIATION   sapCemDifferential
            ACCESS  not-implemented
            DESCRIPTION
                    "Not supported."

        VARIATION   sapCemTimestampFreq
            ACCESS  not-implemented
            DESCRIPTION
                    "Not supported."

        VARIATION   sapCemLocalEcid
            ACCESS  not-implemented
            DESCRIPTION
                    "Not supported."

        VARIATION   sapCemRemoteMacAddr
            ACCESS  not-implemented
            DESCRIPTION
                    "Not supported."

        VARIATION   sapCemRemoteEcid
            ACCESS  not-implemented
            DESCRIPTION
                    "Not supported."

        VARIATION   sapTlsL2ptForceBoundary
            ACCESS  not-implemented
            DESCRIPTION
                    "Not supported."

        VARIATION   sapTlsL2ptForceProtocols
            ACCESS  not-implemented
            DESCRIPTION
                    "Not supported."

        VARIATION   sapBaseStatsAuthenticationPktsDiscarded
            ACCESS  not-implemented
            DESCRIPTION
                    "Not supported."

        VARIATION   sapBaseStatsAuthenticationPktsSuccess
            ACCESS  not-implemented
            DESCRIPTION
                    "Not supported."

        VARIATION   sapCustMultSvcSite
            ACCESS  not-implemented
            DESCRIPTION
                    "Not supported."

        VARIATION   sapEgressAggRateLimit
            ACCESS  not-implemented
            DESCRIPTION
                    "Not supported."

        VARIATION   sapEgressQinQMarkTopOnly
            ACCESS  not-implemented
            DESCRIPTION
                    "Not supported."

        VARIATION   sapEgressFrameBasedAccounting
            ACCESS  not-implemented
            DESCRIPTION
                    "Not supported."

        VARIATION sapIngressMatchQinQDot1PBits 
            ACCESS  not-implemented
            DESCRIPTION
                "Not supported."

        VARIATION sapIngressSharedQueuePolicy 
            ACCESS  not-implemented
            DESCRIPTION
                "Not supported."

        VARIATION sapIngressVlanTranslation 
            ACCESS  not-implemented
            DESCRIPTION
                "Not supported."

        VARIATION sapIngressVlanTranslationId 
            ACCESS  not-implemented
            DESCRIPTION
                "Not supported."

        VARIATION sapIngUseMultipointShared 
            ACCESS  not-implemented
            DESCRIPTION
                "Not supported."

        VARIATION sapTlsArpReplyAgent 
            ACCESS  not-implemented
            DESCRIPTION
                "Not supported."

        VARIATION sapTlsAuthenticationPolicy 
            ACCESS  not-implemented
            DESCRIPTION
                "Not supported."

        VARIATION   sapTlsDhcpLeasePopulate
            ACCESS  not-implemented
            DESCRIPTION
                    "Not supported."

        VARIATION   sapTlsDhcpOperLeasePopulate
            ACCESS  not-implemented
            DESCRIPTION
                    "Not supported."

        VARIATION   sapTlsDhcpProxyAdminState
            ACCESS  not-implemented
            DESCRIPTION
                    "Not supported."

        VARIATION   sapTlsDhcpProxyServerAddr
            ACCESS  not-implemented
            DESCRIPTION
                    "Not supported."
                    
        VARIATION sapTlsDhcpProxyLeaseTime 
            ACCESS  not-implemented
            DESCRIPTION
                "Not supported."

        VARIATION   sapTlsDhcpProxyLTRadiusOverride
            ACCESS  not-implemented
            DESCRIPTION
                    "Not supported."                   

        VARIATION sapTlsEgressMcastGroup 
            ACCESS  not-implemented
            DESCRIPTION
                "Not supported."

        VARIATION sapTlsMvplsMgmtMsti 
            ACCESS  not-implemented
            DESCRIPTION
                "Not supported."

        VARIATION sapTlsRestProtSrcMac 
            ACCESS  not-implemented
            DESCRIPTION
                "Not supported."

        VARIATION sapTlsRestProtSrcMacAction 
            ACCESS  not-implemented
            DESCRIPTION
                "Not supported."

        VARIATION sapTlsRestUnprotDstMac 
            ACCESS  not-implemented
            DESCRIPTION
                "Not supported."

        VARIATION sapTlsShcvAction 
            ACCESS  not-implemented
            DESCRIPTION
                "Not supported."

        VARIATION sapTlsShcvInterval 
            ACCESS  not-implemented
            DESCRIPTION
                "Not supported."

        VARIATION sapTlsShcvSrcIp 
            ACCESS  not-implemented
            DESCRIPTION
                "Not supported."

        VARIATION sapTlsShcvSrcMac 
            ACCESS  not-implemented
            DESCRIPTION
                "Not supported."

        VARIATION sapTlsStpInMstBpdus 
            ACCESS  not-implemented
            DESCRIPTION
                "Not supported."

        VARIATION sapTlsStpInsideRegion 
            ACCESS  not-implemented
            DESCRIPTION
                "Not supported."

        VARIATION sapTlsStpOutMstBpdus 
            ACCESS  not-implemented
            DESCRIPTION
                "Not supported."

        VARIATION msapTlsPlcyArpHostMaxNumHosts 
            ACCESS  not-implemented
            DESCRIPTION
                "Not supported."

        VARIATION msapTlsPlcyArpHostMinAuthIntvl 
            ACCESS  not-implemented
            DESCRIPTION
                "Not supported."

        VARIATION sapBaseStatsIngressPchipDroppedPackets
            ACCESS  not-implemented
            DESCRIPTION
                "Not supported."

        VARIATION sapBaseStatsIngressPchipDroppedOctets
            ACCESS  not-implemented
            DESCRIPTION
                "Not supported."

        VARIATION sapBaseStatsIngressPchipOfferedHiPrioPackets
            ACCESS  not-implemented
            DESCRIPTION
                "Not supported."

        VARIATION sapBaseStatsIngressPchipOfferedHiPrioOctets
            ACCESS  not-implemented
            DESCRIPTION
                "Not supported."

        VARIATION sapBaseStatsIngressPchipOfferedLoPrioPackets
            ACCESS  not-implemented
            DESCRIPTION
                "Not supported."

        VARIATION sapBaseStatsIngressPchipOfferedLoPrioOctets
            ACCESS  not-implemented
            DESCRIPTION
                "Not supported."

        VARIATION sapBaseStatsIngressQchipDroppedHiPrioPackets
            ACCESS  not-implemented
            DESCRIPTION
                "Not supported."

        VARIATION sapBaseStatsIngressQchipDroppedHiPrioOctets
            ACCESS  not-implemented
            DESCRIPTION
                "Not supported."

        VARIATION sapBaseStatsIngressQchipDroppedLoPrioPackets
            ACCESS  not-implemented
            DESCRIPTION
                "Not supported."

        VARIATION sapBaseStatsIngressQchipDroppedLoPrioOctets
            ACCESS  not-implemented
            DESCRIPTION
                "Not supported."

        VARIATION sapBaseStatsIngressQchipForwardedInProfPackets
            ACCESS  not-implemented
            DESCRIPTION
                "Not supported."

        VARIATION sapBaseStatsIngressQchipForwardedInProfOctets
            ACCESS  not-implemented
            DESCRIPTION
                "Not supported."

        VARIATION sapBaseStatsIngressQchipForwardedOutProfPackets
            ACCESS  not-implemented
            DESCRIPTION
                "Not supported."

        VARIATION sapBaseStatsIngressQchipForwardedOutProfOctets
            ACCESS  not-implemented
            DESCRIPTION
                "Not supported."

        VARIATION sapBaseStatsEgressQchipDroppedInProfPackets
            ACCESS  not-implemented
            DESCRIPTION
                "Not supported."

        VARIATION sapBaseStatsEgressQchipDroppedInProfOctets
            ACCESS  not-implemented
            DESCRIPTION
                "Not supported."

        VARIATION sapBaseStatsEgressQchipDroppedOutProfPackets
            ACCESS  not-implemented
            DESCRIPTION
                "Not supported."

        VARIATION sapBaseStatsEgressQchipDroppedOutProfOctets
            ACCESS  not-implemented
            DESCRIPTION
                "Not supported."

        VARIATION sapBaseStatsEgressQchipForwardedInProfPackets
            ACCESS  not-implemented
            DESCRIPTION
                "Not supported."

        VARIATION sapBaseStatsEgressQchipForwardedInProfOctets
            ACCESS  not-implemented
            DESCRIPTION
                "Not supported."

        VARIATION sapBaseStatsEgressQchipForwardedOutProfPackets
            ACCESS  not-implemented
            DESCRIPTION
                "Not supported."

        VARIATION sapBaseStatsEgressQchipForwardedOutProfOctets
            ACCESS  not-implemented
            DESCRIPTION
                "Not supported."

        VARIATION sapBaseStatsIngressPchipOfferedUncoloredPackets
            ACCESS  not-implemented
            DESCRIPTION
                "Not supported."

        VARIATION sapBaseStatsIngressPchipOfferedUncoloredOctets
            ACCESS  not-implemented
            DESCRIPTION
                "Not supported."

        VARIATION sapBaseStatsAuthenticationPktsDiscarded
            ACCESS  not-implemented
            DESCRIPTION
                "Not supported."

        VARIATION sapBaseStatsAuthenticationPktsSuccess
            ACCESS  not-implemented
            DESCRIPTION
                "Not supported."

    ::= { tmnxSASM7210V6v0 46 }  -- SAP



--
--  SDP CAPABILITIES
--
tmnxSdpCapsSASM7210V6v0    AGENT-CAPABILITIES
    PRODUCT-RELEASE "Alcatel SAS-M 7210"
    STATUS          current
    DESCRIPTION     "Implementation of SDP capabilities
                     for Alcatel SAS-M 7210 release R6.0."

    SUPPORTS        TIMETRA-SDP-MIB
        INCLUDES    {
             tmnxSdpV6v0Group,
             tmnxSdpBindV6v0Group,
             tmnxSdpBindTlsV6v0Group,
             tmnxSdpBindMeshV6v0Group,
             -- tmnxSdpApipeV6v0Group,       no ATM on SAS-M 7210
             -- tmnxSdpBindDhcpV6v0Group,
             -- tmnxSdpBindIpipeV7v0Group,
             tmnxSdpBindTlsL2ptV6v0Group,
             -- tmnxSdpAutoBindV7v0Group,
             -- tmnxSdpBindTlsMrpV6v0Group,
             -- tmnxSdpTlsBgpV6v0Group,
             tmnxSdpNotifyV6v0Group,
             tmnxSdpL2V6v0Group,
             -- tmnxSdpFCV6v0Group,
             tmnxSdpBindCpipeV6v0Group,
             tmnxSdpMixedLspModeV9v0Group
             -- tmnxSdpL2V7v0Group
             -- tmnxSdpPbbGroup 
        }

        VARIATION   sdpBindVcType
            SYNTAX  INTEGER {
                        undef         (1),
                        ether         (2),
                        -- vpls       (3),
                        vlan          (4),
                        mirror        (5),
                        -- atmSdu     (6),
                        -- atmCell    (7),
                        -- atmVcc     (8),
                        -- atmVpc     (9),
                        -- frDlci     (10),
                        -- ipipe      (11)
                        satopE1       (12),
                        satopT1       (13),
                        -- satopE3    (14),
                        -- satopT3    (15),
                        cesopsn    (16),
                        cesopsnCas (17)
            }
            DESCRIPTION
                    "The enumeration 'vpls (3)' is no longer supported.
                     The values
                        - 'atmSdu     (6)',
                        - 'atmCell    (7)',
                        - 'atmVcc     (8)',
                        - 'atmVpc     (9)',
                        - 'frDlci     (10),
                        - 'ipipe      (11)
                        - 'satopE3    (14)',
                        - 'satopT3    (15)',
                     are not supported on a SAS-M 7210 system."

        VARIATION   sdpBindControlWordBit
            DESCRIPTION
                    "sdpBindControlWordBit is only supported for EPIPE service in SAS-M 7210."

        VARIATION   pwTemplateShgRestProtSrcMac
            ACCESS  not-implemented
            DESCRIPTION
                    "Not supported."

        VARIATION   pwTemplateShgRestUnprotDstMac
            ACCESS  not-implemented
            DESCRIPTION
                    "Not supported."

        VARIATION   sdpBandwidthBookingFactor
            ACCESS  not-implemented
            DESCRIPTION
                    "Not supported."

        VARIATION   sdpOperBandwidth
            ACCESS  not-implemented
            DESCRIPTION
                    "Not supported."

        VARIATION   sdpAvailableBandwidth
            ACCESS  not-implemented
            DESCRIPTION
                    "Not supported."

        VARIATION   sdpBindAdminBandwidth
            ACCESS  not-implemented
            DESCRIPTION
                    "Not supported."

        VARIATION   sdpBindOperBandwidth
            ACCESS  not-implemented
            DESCRIPTION
                    "Not supported."

        VARIATION   sdpBindOperGrp
            ACCESS  not-implemented
            DESCRIPTION
                    "Not supported."             

        VARIATION   sdpBindCpipeLocalSigPkts
            ACCESS  not-implemented
            DESCRIPTION
                    "Not supported."

        VARIATION   sdpBindCpipePeerSigPkts
            ACCESS  not-implemented
            DESCRIPTION
                    "Not supported."

        VARIATION   sdpBindCpipeLocalCasTrunkFraming
            ACCESS  not-implemented
            DESCRIPTION
                    "Not supported."

        VARIATION   sdpBindCpipePeerCasTrunkFraming
            ACCESS  not-implemented
            DESCRIPTION
                    "Not supported."

        VARIATION   sdpBindBaseStatsIngressDroppedPackets
            ACCESS  not-implemented
            DESCRIPTION
                    "Not supported."

        VARIATION   sdpBindClassFwdingOperState
            ACCESS  not-implemented
            DESCRIPTION
                    "Not supported."

        VARIATION   sdpBindEgressIpFilterId
            ACCESS  not-implemented
            DESCRIPTION
                    "Not supported."

        VARIATION   sdpBindEgressIpv6FilterId
            ACCESS  not-implemented
            DESCRIPTION
                    "Not supported."

        VARIATION   sdpBindEgressMacFilterId
            ACCESS  not-implemented
            DESCRIPTION
                    "Not supported."

        VARIATION   sdpBindIesIfIndex
            ACCESS  not-implemented
            DESCRIPTION
                    "Not supported."

        VARIATION   sdpBindIngressIpFilterId
            ACCESS  not-implemented
            DESCRIPTION
                    "Not supported."

        VARIATION   sdpBindIngressIpv6FilterId
            ACCESS  not-implemented
            DESCRIPTION
                    "Not supported."

        VARIATION   sdpBindIngressMacFilterId
            ACCESS  not-implemented
            DESCRIPTION
                    "Not supported."        

        VARIATION   sdpBindTlsStpInMstBpdus
            ACCESS  not-implemented
            DESCRIPTION
                    "Not supported."

        VARIATION   sdpBindTlsStpOutMstBpdus
            ACCESS  not-implemented
            DESCRIPTION
                    "Not supported."     

        VARIATION   sdpPBBEtype
            ACCESS  not-implemented
            DESCRIPTION
                    "Not supported."

        VARIATION  sdpClassFwdingDefaultLsp
            ACCESS  not-implemented
            DESCRIPTION
                "Not supported."

        VARIATION sdpClassFwdingEnabled
            ACCESS  not-implemented
            DESCRIPTION
                "Not supported."

        VARIATION sdpClassFwdingMcLsp
            ACCESS  not-implemented
            DESCRIPTION
                "Not supported."

        VARIATION sdpBindMeshTlsNotInMstRegion
            ACCESS  not-implemented
            DESCRIPTION
                "Not supported."

        VARIATION pwTemplateEgressMacFilterId
            ACCESS  not-implemented
            DESCRIPTION
                "Not supported."

        VARIATION pwTemplateEgressIpFilterId
            ACCESS  not-implemented
            DESCRIPTION
                "Not supported."

        VARIATION pwTemplateEgressIpv6FilterId
            ACCESS  not-implemented
            DESCRIPTION
                "Not supported."

        VARIATION pwTemplateIngressMacFilterId
            ACCESS  not-implemented
            DESCRIPTION
                "Not supported."

        VARIATION pwTemplateIngressIpFilterId
            ACCESS  not-implemented
            DESCRIPTION
                "Not supported."

        VARIATION pwTemplateIngressIpv6FilterId
            ACCESS  not-implemented
            DESCRIPTION
                "Not supported."

        VARIATION pwTemplateHashLabel
            ACCESS  not-implemented
            DESCRIPTION
                "Not supported."

        VARIATION pwTemplateHashLabelSignalCap
            ACCESS  not-implemented
            DESCRIPTION
                "Not supported."

    ::= { tmnxSASM7210V6v0 47 }  -- SDP

--
--  DS0 CAPABILITIES
--
tmnxDS0CapsSASM7210V6v0    AGENT-CAPABILITIES
    PRODUCT-RELEASE "Alcatel SAS-M 7210"
    STATUS          current
    DESCRIPTION     "Implementation of DS0 capabilities
                     for Alcatel SAS-M 7210 release R6.0."

    SUPPORTS        DS0-MIB
        INCLUDES    {
            ds0ConfigGroup
        }

        VARIATION   dsx0RobbedBitSignalling
            ACCESS  not-implemented
            DESCRIPTION
                    "Not supported."

        VARIATION   dsx0CircuitIdentifier
            ACCESS  not-implemented
            DESCRIPTION
                    "Not supported."

        VARIATION   dsx0IdleCode
            ACCESS  not-implemented
            DESCRIPTION
                    "Not supported."

        VARIATION   dsx0SeizedCode
            ACCESS  not-implemented
            DESCRIPTION
                    "Not supported."

        VARIATION   dsx0ReceivedCode
            ACCESS  not-implemented
            DESCRIPTION
                    "Not supported."

        VARIATION   dsx0TransmitCodesEnable
            ACCESS  not-implemented
            DESCRIPTION
                    "Not supported."

        VARIATION   dsx0Ds0BundleMappedIfIndex
            ACCESS  not-implemented
            DESCRIPTION
                    "Not supported."

    ::= { tmnxSASM7210V6v0 48 }

--
--  DS1 CAPABILITIES
--
tmnxDS1CapsSASM7210V6v0    AGENT-CAPABILITIES
    PRODUCT-RELEASE "Alcatel SAS-M 7210"
    STATUS          current
    DESCRIPTION     "Implementation of DS0 capabilities
                     for Alcatel SAS-M 7210 release R6.0."

    SUPPORTS        DS1-MIB
        INCLUDES    {
            ds1NearEndConfigGroup,
            ds1NearEndStatisticsGroup,
            -- ds1FarEndGroup,
            ds1NearEndOptionalConfigGroup,
            ds1TransStatsGroup,
            ds1ChanMappingGroup,
            ds1NearEndOptionalTrapGroup
-- EXCLUDE dsx1IfIndex (deprecated)
-- EXCLUDE dsx1FracTable (deprecated)
-- EXCLUDE dsx1LineMode (not supported)
-- EXCLUDE dsx1LineBuildOut (not supported)
        }

    ::= { tmnxSASM7210V6v0 49 }

--
--  LLDP CAPABILITIES
--
tmnxLLDPCapsSASM7210V6v0    AGENT-CAPABILITIES
    PRODUCT-RELEASE "Alcatel SAS-M 7210"
    STATUS          current
    DESCRIPTION     "Implementation of LLDP capabilities
                     for Alcatel SAS-M 7210 release R6.0."

    SUPPORTS        TIMETRA-LLDP-MIB
        INCLUDES    {
            tmnxLldpConfigGroup,
            tmnxLldpStatsRxGroup,
            tmnxLldpStatsTxGroup,
            tmnxLldpLocSysGroup,
            tmnxLldpRemSysGroup,
            tmnxLldpRemManAddrGroup
        }

    SUPPORTS        LLDP-MIB
        INCLUDES    {
             -- lldpConfigGroup,
             lldpConfigRxGroup,
             lldpConfigTxGroup,
             lldpStatsRxGroup,
             -- lldpStatsTxGroup,
             lldpLocSysGroup,
             -- lldpRemSysGroup,
             lldpNotificationsGroup
        }

        VARIATION   lldpPortConfigNotificationEnable
            ACCESS  not-implemented
            DESCRIPTION
                    "lldpPortConfigNotificationEnable has been replaced by
                     TIMETRA-LLDP-MIB::tmnxLldpPortCfgNotifyEnable."

        VARIATION   lldpTxDelay
            ACCESS  not-implemented
            DESCRIPTION
                    "lldpTxDelay is not implemented."
        VARIATION   lldpPortConfigTLVsTxEnable
            ACCESS  not-implemented
            DESCRIPTION
                    "lldpPortConfigTLVsTxEnable has been replaced by
                     TIMETRA-LLDP-MIB::tmnxLldpPortCfgTLVsTxEnable."

        VARIATION   lldpConfigManAddrPortsTxEnable
            ACCESS  not-implemented
            DESCRIPTION
                    "lldpConfigManAddrPortsTxEnable has been replaced by
                     TIMETRA-LLDP-MIB::tmnxLldpPortCfgManAddrTxEnabled."

        VARIATION   lldpStatsRxPortFramesDiscardedTotal
            ACCESS  not-implemented
            DESCRIPTION
                    "lldpStatsRxPortFramesDiscardedTotal has been replaced b
                     TIMETRA-LLDP-MIB::tmnxLldpStatsRxPortFrameDiscard."

        VARIATION   lldpStatsRxPortFramesErrors
            ACCESS  not-implemented
            DESCRIPTION
                    "lldpStatsRxPortFramesErrors has been replaced by
                     TIMETRA-LLDP-MIB::tmnxLldpStatsRxPortFrameErrs."

        VARIATION   lldpStatsRxPortFramesTotal
            ACCESS  not-implemented
            DESCRIPTION
                    "lldpStatsRxPortFramesTotal has been replaced by
                     TIMETRA-LLDP-MIB::tmnxLldpStatsRxPortFrames."

        VARIATION   lldpStatsRxPortTLVsDiscardedTotal
            ACCESS  not-implemented
            DESCRIPTION
                    "lldpStatsRxPortTLVsDiscardedTotal has been replaced by
                     TIMETRA-LLDP-MIB::tmnxLldpStatsRxPortTLVDiscard."

        VARIATION   lldpStatsRxPortTLVsUnrecognizedTotal
            ACCESS  not-implemented
            DESCRIPTION
                    "lldpStatsRxPortTLVsUnrecognizedTotal has been replaced
                     with TIMETRA-LLDP-MIB::tmnxLldpStatsRxPortTLVUnknown."

        VARIATION   lldpStatsRxPortAgeoutsTotal
            ACCESS  not-implemented
            DESCRIPTION
                    "lldpStatsRxPortAgeoutsTotal has been replaced by
                     TIMETRA-LLDP-MIB::tmnxLldpStatsRxPortAgeouts."

        VARIATION   lldpLocPortIdSubtype
            ACCESS  not-implemented
            DESCRIPTION
                    "lldpLocPortIdSubtype has been replaced by
                     TIMETRA-LLDP-MIB::tmnxLldpLocPortIdSubtype."

        VARIATION   lldpLocPortId
            ACCESS  not-implemented
            DESCRIPTION
                    "lldpLocPortId has been replaced by
                     TIMETRA-LLDP-MIB::tmnxLldpLocPortId."

        VARIATION   lldpLocPortDesc
            ACCESS  not-implemented
            DESCRIPTION
                    "lldpLocPortDesc has been replaced by
                     TIMETRA-LLDP-MIB::tmnxLldpLocPortDesc."

    ::= { tmnxSASM7210V6v0 51 }  -- LLDP

--
--  ALARM INPUT CAPABILITIES
--
tmnxAlarmInputCapsSASM7210V6v0    AGENT-CAPABILITIES
    PRODUCT-RELEASE "Alcatel SAS-M 7210"
    STATUS          current
    DESCRIPTION     "Implementation of alarm input capabilities
                     for Alcatel SAS-M 7210 release R6.0."

    SUPPORTS        TIMETRA-SAS-ALARM-INPUT-MIB
        INCLUDES    {
            tmnxSASAlarmInputV2v0Group,
            tmnxAlarmInputNotificationV2v0Group
        }

        VARIATION   tmnxSasAlarmOutputSeverity
            SYNTAX  INTEGER {
                        none(1),
                        major(3),
                        critical(4)
                    }
            DESCRIPTION
                    "SAS-E and SAS-M do not support minor(2)."

        VARIATION tmnxSasAlarmInputPowerStatus
            ACCESS  not-implemented
            DESCRIPTION
                "Not supported."
                
    ::= { tmnxSASM7210V6v0 52 }  -- Alarm Input

--
--  MC-REDUNDANCY CAPABILITIES
--
tmnxMcRedundancyCapsSASM7210V6v0 AGENT-CAPABILITIES
    PRODUCT-RELEASE "Alcatel SASM 7210"
    STATUS current
    DESCRIPTION
        "Implementation of the Multi-Chassis Redundancy feature
         on Alcatel SAS-M 7210 release R6.0."

    SUPPORTS TIMETRA-MC-REDUNDANCY-MIB
        INCLUDES    {
            tmnxMcRedundancyV6v0Group,
            tmnxSrrpV5v0Group,
            tmnxSrrpV6v1Group,
            tmnxSrrpNotifV6v1Group,
            tmnxMcRedundancyV5v0NotifGroup,
            tmnxMcRedundancySrrpNotifGroup,
            tmnxMcRingV6v0Group,
            tmnxMcRingV6v0NotifGroup,
            tmnxMcPeerSyncGroup,
            tmnxMcsDhcpsV6v0Group,
            tmnxMcsSubHostTrkGroup,
            tmnxMcL3RingGroup,
            tmnxMcLagPbbGroup,
            tmnxMcPeerEPGroup,
            tmnxMcPeerEPV7v0NotifGroup
        }

        VARIATION   tmnxMcLagConfigPeerAdminstate
            SYNTAX  INTEGER {
                        -- noop         (1),
                        inService       (2),
                        outOfService    (3)
                    }
            DESCRIPTION
                    "The only allowed values for this object are 'inService (2)'
                    and 'outOfService (3)'."

        VARIATION   tmnxMcLagConfigLagRowStatus
            SYNTAX  INTEGER {
                        active      (1),
                        createAndGo (4),
                        destroy     (6)
                     }
            DESCRIPTION
                    "tmnxMcLagConfigLagRowStatus supports only the values
                    'active (1)', 'createAndGo (4)' and 'destroy (6)'."

        VARIATION   tmnxSrrpOperRowStatus
            SYNTAX  INTEGER {
                        active      (1),
                        createAndGo (4),
                        destroy     (6)
                     }
            DESCRIPTION
                    "tmnxSrrpOperRowStatus supports only the values
                    'active (1)', 'createAndGo (4)' and 'destroy (6)'."

        VARIATION   tmnxMcRingRowStatus
            SYNTAX  INTEGER {
                        active      (1),
                        createAndGo (4),
                        destroy     (6)
                     }
            DESCRIPTION
                    "tmnxMcRingRowStatus supports only the values
                    'active (1)', 'createAndGo (4)' and 'destroy (6)'."

        VARIATION   tmnxMcRingAdminState
            SYNTAX  INTEGER {
                        -- noop         (1),
                        inService       (2),
                        outOfService    (3)
                    }
            DESCRIPTION
                    "The only allowed values for this object are 'inService (2)'
                     and 'outOfService (3)'."

        VARIATION   tmnxMcRingNodeRowStatus
            SYNTAX  INTEGER {
                        active      (1),
                        createAndGo (4),
                        destroy     (6)
                    }
            DESCRIPTION
                    "tmnxMcRingNodeRowStatus supports only the values
                    'active (1)', 'createAndGo (4)' and 'destroy (6)'."

        VARIATION   tmnxMcRingNodeRncvAdminState
            SYNTAX  INTEGER {
                        -- noop      (1),
                        inService    (2),
                        outOfService (3)
                    }
            DESCRIPTION
                    "The only allowed values for this object are 'inService (2)'
                     and 'outOfService (3)'."

        VARIATION   tmnxMcEpipeSapRowStatus
            SYNTAX  INTEGER {
                        active      (1),
                        createAndGo (4),
                        destroy     (6)
                    }
            DESCRIPTION
                    "tmnxMcEpipeSapRowStatus supports only the values
                    'active (1)', 'createAndGo (4)' and 'destroy (6)'."

        VARIATION   tmnxMcRingInbCtrlDestIpType
            SYNTAX  INTEGER {
                        unknown     (0),
                        ipv4        (1)
                        -- ipv6     (2),
                        -- ipv4z    (3),
                        -- ipv6z    (4),
                        -- dns      (16)
                    }
            DESCRIPTION
                    "tmnxMcRingInbCtrlDestIpType supports only InetAddressType
                    values 'unknown (0)' and 'ipv4 (1)'."

        VARIATION   tmnxMcRingInbCtrlDestIp
            SYNTAX  InetAddress (SIZE (0|4))
            DESCRIPTION
                    "tmnxMcRingInbCtrlDestIp supports only InetAddressType
                    values 'unknown (0)' and 'ipv4 (1)'."

        VARIATION   tmnxMcRingInfoInbCtrlSrcIpType
            SYNTAX  INTEGER {
                        unknown     (0),
                        ipv4        (1)
                        -- ipv6     (2),
                        -- ipv4z    (3),
                        -- ipv6z    (4),
                        -- dns      (16)
                    }
            DESCRIPTION
                    "tmnxMcRingInfoInbCtrlSrcIpType supports only
                    InetAddressType values 'unknown (0)' and 'ipv4 (1)'."

        VARIATION   tmnxMcRingInfoInbCtrlSrcIp
            SYNTAX  InetAddress (SIZE (0|4))
            DESCRIPTION
                    "tmnxMcRingInfoInbCtrlSrcIp supports only InetAddressType
                    values 'unknown (0)' and 'ipv4 (1)'."

        VARIATION   tmnxMcRingNodeRncvSrcIpType
            SYNTAX  INTEGER {
                        unknown     (0),
                        ipv4        (1)
                        -- ipv6     (2),
                        -- ipv4z    (3),
                        -- ipv6z    (4),
                        -- dns      (16)
                    }
            DESCRIPTION
                    "tmnxMcRingNodeRncvSrcIpType supports only
                    InetAddressType values 'unknown (0)' and 'ipv4 (1)'."

        VARIATION   tmnxMcRingNodeRncvSrcIp
            SYNTAX  InetAddress (SIZE (0|4))
            DESCRIPTION
                    "tmnxMcRingNodeRncvSrcIp supports only InetAddressType
                    values 'unknown (0)' and 'ipv4 (1)'."

        VARIATION   tmnxMcRingNodeRncvDestIpType
            SYNTAX  INTEGER {
                        unknown     (0),
                        ipv4        (1)
                        -- ipv6     (2),
                        -- ipv4z    (3),
                        -- ipv6z    (4),
                        -- dns      (16)
                    }
            DESCRIPTION
                    "tmnxMcRingNodeRncvDestIpType supports only
                    InetAddressType values 'unknown (0)' and 'ipv4 (1)'."

        VARIATION   tmnxMcRingNodeRncvDestIp
            SYNTAX  InetAddress (SIZE (0|4))
            DESCRIPTION
                    "tmnxMcRingNodeRncvDestIp supports only InetAddressType
                    values 'unknown (0)' and 'ipv4 (1)'."

        VARIATION   tmnxMcTlsCfgDefGwIpType
            SYNTAX  INTEGER {
                        unknown     (0),
                        ipv4        (1)
                        -- ipv6     (2),
                        -- ipv4z    (3),
                        -- ipv6z    (4),
                        -- dns      (16)
                    }
            DESCRIPTION
                    "tmnxMcTlsCfgDefGwIpType supports only
                    InetAddressType values 'unknown (0)' and 'ipv4 (1)'."

        VARIATION   tmnxMcTlsCfgDefGwIp
            SYNTAX  InetAddress (SIZE (0|4))
            DESCRIPTION
                    "tmnxMcTlsCfgDefGwIp supports only InetAddressType
                    values 'unknown (0)' and 'ipv4 (1)'."

    ::= { tmnxSASM7210V6v0 53 }

--
--  BGP CAPABILITIES
--
tmnxBgpCaps7210V5v0    AGENT-CAPABILITIES
    PRODUCT-RELEASE "Alcatel 7210"
    STATUS          current
    DESCRIPTION     "Implementation of BGP protocol capabilities for
                     Alcatel 7210 release R6.0."

    SUPPORTS        BGP4-MIB
        INCLUDES    {
            bgp4MIBGlobalsGroup,
            bgp4MIBPeerGroup,
            bgp4MIBPathAttrGroup,
            bgp4MIBNotificationGroup
-- EXCLUDE bgpRcvdPathAttrTable (obsolete)
        }

        VARIATION  bgpBackwardTransition 
            DESCRIPTION
                    "The bgpBackwardTransition notification has vRtrID 
                     appended to the variable list."

        VARIATION  bgpEstablished 
            DESCRIPTION
                    "The bgpEstablished notification has vRtrID 
                     appended to the variable list."

        VARIATION  bgpPeerMinRouteAdvertisementInterval
            SYNTAX     INTEGER (1..255)
            DESCRIPTION
                    "The maximum supported value for 
                     bgpPeerMinRouteAdvertisementInterval is 255 seconds."
        
        VARIATION  bgpPeerMinASOriginationInterval
                SYNTAX     INTEGER (1..255)
                DESCRIPTION
                    "The maximum supported value for 
                     bgpPeerMinASOriginationInterval is 255 seconds."

    SUPPORTS        TIMETRA-BGP-MIB
        INCLUDES    {
            tmnxBgpInstanceParamsV5v0Group,
            tmnxBgpPeerGroupParamsV5v0Group,
            tmnxBgpPeerParamsV5v0Group,
            tmnxBgp4PathAttrGroup,
            tmnxBgpNotificationV5v0Group,
            tmnxBgpNotificationV7v0Group,
            tmnxBgpInstanceParamsV6v0Group,
            tmnxBgpPeerGroupParamsV6v0Group,
            tmnxBgpPeerParamsV6v0Group,
            tmnxBgp4ByteASNV7v0Group,
            tmnxBgpPeeringPolicyV7v0Group,
            tmnxBgpInstanceV10v0Group,
            tmnxBgpPeerGroupV10v0Group,
            tmnxBgpPeerV10v0Group,
            tmnxBgpGlobalV10v0Group,
            tmnxBgpRTConstraintV10v0Group
-- EXCLUDE tBgpPeerTable (obsolete table)
-- EXCLUDE tBgpPeerParamsTable  (obsolete table)
-- EXCLUDE tBgpPeerOperTable   (obsolete table)
-- EXCLUDE tBgpPeerSendOrfRouteTargetTable (obsolete table)
-- EXCLUDE tBgpPeerGroupLocalAddress (obsolete object)
-- EXCLUDE tBgpMaxPrefix90 (obsolete notification object)
-- EXCLUDE tBgpMaxPrefix100 (obsolete notification object)
-- EXCLUDE tBgpPeerGRStatusChange (obsolete notification object)
-- EXCLUDE tBgpPeerNgOperPathsSupByDamping (obsolete object)
-- EXCLUDE tBgpPeerNgOperV6ReceivedPaths (obsolete object)
-- EXCLUDE tBgpPeerNgOperV6SuppPathsDamping (obsolete object)
-- EXCLUDE tBgpPeerNgOperVpnReceivedPaths (obsolete object)
        }

        VARIATION   tBgpInstanceGRAdminState
            ACCESS  read-only
            DESCRIPTION
                    "tBgpInstanceGRAdminState is implemented as read only."

        VARIATION   tBgpPeerGroupGRAdminState
            ACCESS  read-only
            DESCRIPTION
                    "tBgpPeerGroupGRAdminState is implemented as read only."

        VARIATION   tBgpPeerGRAdminState
            ACCESS  read-only
            DESCRIPTION
                    "tBgpPeerNgGRAdminState is implemented as read only."

        VARIATION   tBgpInstanceIBgpMultipath
            ACCESS  not-implemented
            DESCRIPTION
                    "tBgpInstanceIBgpMultipath is not implemented."

        VARIATION   tBgpInstanceMultipath
            ACCESS  not-implemented
            DESCRIPTION
                    "tBgpInstanceMultipath is not implemented."

        VARIATION   tBgpInstanceIgpShortcut
            ACCESS  not-implemented
            DESCRIPTION
                    "tBgpInstanceIgpShortcut is not implemented."

        VARIATION   tBgpInstanceClusterId
            ACCESS  not-implemented
            DESCRIPTION
                    "tBgpInstanceClusterId is not implemented."

        VARIATION   tBgpInstanceDisableClientReflect
            ACCESS  not-implemented
            DESCRIPTION
                    "tBgpInstanceDisableClientReflect is not implemented."

        VARIATION   tBgpInstanceIBgpMultipath
            ACCESS  not-implemented
            DESCRIPTION
                    "tBgpInstanceIBgpMultipath is not implemented."

        VARIATION   tBgpInstanceDisallowIgp
            ACCESS  not-implemented
            DESCRIPTION
                    "tBgpInstanceDisallowIgp is not implemented."

        VARIATION   tBgpInstanceConfederationAS4Byte
            ACCESS  not-implemented
            DESCRIPTION
                    "tBgpInstanceConfederationAS4Byte is not implemented."

        VARIATION   tBgpInstanceMultipathEiBgpState
            ACCESS  not-implemented
            DESCRIPTION
                    "tBgpInstanceMultipathEiBgpState is not implemented."

        VARIATION   tBgpPeerGroupClusterId
            ACCESS  not-implemented
            DESCRIPTION
                    "tBgpPeerGroupClusterId is not implemented."

        VARIATION   tBgpPeerGroupDisableClientReflect
            ACCESS  not-implemented
            DESCRIPTION
                    "tBgpPeerGroupDisableClientReflect is not implemented."

        VARIATION   tBgpPGBfdEnabled
            ACCESS  not-implemented
            DESCRIPTION
                    "tBgpPGBfdEnabled is not implemented."

        VARIATION  tBgpPGDefaultRouteTarget   
            ACCESS   not-implemented
            DESCRIPTION
                 "Not supported."

        VARIATION  tBgpPGAigp   
            ACCESS   not-implemented
            DESCRIPTION
                  "Not supported."

        VARIATION  tBgpPGRemovePrivateSkipPeerAs   
            ACCESS   not-implemented
            DESCRIPTION
                  "Not supported."

        VARIATION   tBgpPeerNgClusterId
            ACCESS  not-implemented
            DESCRIPTION
                    "tBgpPeerNgClusterId is not implemented."

        VARIATION   tBgpPeerNgDisableClientReflect
            ACCESS  not-implemented
            DESCRIPTION
                    "tBgpPeerNgDisableClientReflect is not implemented."

        VARIATION   tBgpPeerNgOperV6ReceivedPrefixes
            ACCESS  not-implemented
            DESCRIPTION
                    "tBgpPeerNgOperV6ReceivedPrefixes is not implemented."

        VARIATION   tBgpPeerNgOperV6SentPrefixes
            ACCESS  not-implemented
            DESCRIPTION
                    "tBgpPeerNgOperV6SentPrefixes is not implemented."

        VARIATION   tBgpPeerNgOperV6ActivePrefixes
            ACCESS  not-implemented
            DESCRIPTION
                    "tBgpPeerNgOperV6ActivePrefixes is not implemented."

        VARIATION   tBgpPeerNgOperV6ReceivedPaths
            ACCESS  not-implemented
            DESCRIPTION
                    "tBgpPeerNgOperV6ReceivedPaths is not implemented."

        VARIATION   tBgpPeerNgOperV6SuppPathsDamping
            ACCESS  not-implemented
            DESCRIPTION
                    "tBgpPeerNgOperV6SuppPathsDamping is not implemented."

        VARIATION   tBgpPeerNgOperV6SuppPfxDamp
            ACCESS  not-implemented
            DESCRIPTION
                    "tBgpPeerNgOperV6SuppPfxDamp is not implemented."

        VARIATION   tBgpPeerNgOperMCastV4SuppPfxDamp
            ACCESS  not-implemented
            DESCRIPTION
                    "tBgpPeerNgOperMCastV4SuppPfxDamp is not implemented."

        VARIATION   tBgpPeerNgOperMCastV4RecvPfxs
            ACCESS  not-implemented
            DESCRIPTION
                    "tBgpPeerNgOperMCastV4RecvPfxs is not implemented."

        VARIATION   tBgpPeerNgOperMCastV4SentPfxs
            ACCESS  not-implemented
            DESCRIPTION
                    "tBgpPeerNgOperMCastV4SentPfxs is not implemented."

        VARIATION   tBgpPeerNgOperMCastV4ActivePfxs
            ACCESS  not-implemented
            DESCRIPTION
                    "tBgpPeerNgOperMCastV4ActivePfxs is not implemented."

        VARIATION   tBgpPeerNgOperVpnIpv6RecvPfxs
            ACCESS  not-implemented
            DESCRIPTION
                    "tBgpPeerNgOperVpnIpv6RecvPfxs is not implemented."

        VARIATION   tBgpPeerNgOperVpnIpv6SentPfxs
            ACCESS  not-implemented
            DESCRIPTION
                    "tBgpPeerNgOperVpnIpv6SentPfxs is not implemented."

        VARIATION   tBgpPeerNgOperVpnIpv6ActivePfxs
            ACCESS  not-implemented
            DESCRIPTION
                    "tBgpPeerNgOperVpnIpv6ActivePfxs is not implemented."

        VARIATION   tBgpPeerNgOperVpnIpv6SuppPfxDamp
            ACCESS  not-implemented
            DESCRIPTION
                    "tBgpPeerNgOperVpnIpv6SuppPfxDamp is not implemented."

        VARIATION   tBgpPeerNgOperMvpnV4SuppPfxDamp
            ACCESS  not-implemented
            DESCRIPTION
                    "tBgpPeerNgOperMvpnV4SuppPfxDamp is not implemented."

        VARIATION   tBgpPeerNgOperMvpnV4RecvPfxs
            ACCESS  not-implemented
            DESCRIPTION
                    "tBgpPeerNgOperMvpnV4RecvPfxs is not implemented."

        VARIATION   tBgpPeerNgOperMvpnV4SentPfxs
            ACCESS  not-implemented
            DESCRIPTION
                    "tBgpPeerNgOperMvpnV4SentPfxs is not implemented."

        VARIATION   tBgpPeerNgOperMvpnV4ActivePfxs
            ACCESS  not-implemented
            DESCRIPTION
                    "tBgpPeerNgOperMvpnV4ActivePfxs is not implemented."


        VARIATION   tBgpConfederation4BytTblLstChngd
            ACCESS  not-implemented
            DESCRIPTION
                    "tBgpConfederation4BytTblLstChngd is not implemented."

        VARIATION   tBgpConfederationTableLastChanged
            ACCESS  not-implemented
            DESCRIPTION
                    "tBgpConfederationTableLastChanged is not implemented."

        VARIATION   tBgpConfederationTable
            ACCESS  not-implemented
            DESCRIPTION
                    "tBgpConfederationTable is not implemented."

        VARIATION   tBgpInstRteTargetTable
            ACCESS  not-implemented
            DESCRIPTION
                    "tBgpInstRteTargetTable is not implemented."

        VARIATION   tBgpConfederation4ByteTable
            ACCESS  not-implemented
            DESCRIPTION
                    "tBgpConfederation4ByteTable is not implemented."
                    
        VARIATION   tBgpPGTTLLogId
            ACCESS  not-implemented
            DESCRIPTION
                    "tBgpPGTTLLogId is not implemented."

        VARIATION tBgpInstanceGRPathSelectDefer
            ACCESS  read-only
            DESCRIPTION 
                    "tBgpInstanceGRPathSelectDefer is implemented as 
                     read only."
        
        VARIATION tBgpInstanceGRRestartTime
            ACCESS  read-only
            DESCRIPTION 
                    "tBgpInstanceGRRestartTime is implemented as 
                     read only."

        VARIATION  tBgpNgBackwardTransition 
            DESCRIPTION
                    "The tBgpNgBackwardTransition notification has vRtrID 
                     appended to the variable list." 

        VARIATION  tBgpNgEstablished 
            DESCRIPTION
                    "The tBgpNgEstablished notification has vRtrID 
                     appended to the variable list."
        
        VARIATION   tBgpInstanceGracefulRestart
            ACCESS  not-implemented
            DESCRIPTION
                    "Not supported."

        VARIATION   tBgpInstanceGRPathSelectDefer 
            ACCESS  not-implemented
            DESCRIPTION
                    "Not supported."

        VARIATION   tBgpInstanceGRRestartTime
            ACCESS  not-implemented
            DESCRIPTION
                    "Not supported."

        VARIATION   tBgpInstanceGRStaleRoute
            ACCESS  not-implemented
            DESCRIPTION
                    "Not supported."

        VARIATION   tBgpInstanceGRAdminState
            ACCESS  not-implemented
            DESCRIPTION
                    "Not supported."

        VARIATION   tBgpInstanceGROperState
            ACCESS  not-implemented
            DESCRIPTION
                    "Not supported."

       VARIATION   tBgpInstanceIgnoreNextHopMetric  
            ACCESS  not-implemented
            DESCRIPTION
                    "Not supported."

        VARIATION   tBgpInstanceMpBgpKeep 
            ACCESS  not-implemented
            DESCRIPTION
                    "Not supported."

        VARIATION  tBgpInstanceIgnoreRouterId   
            ACCESS  not-implemented
            DESCRIPTION
                    "Not supported."


        VARIATION  tBgpInstRemovePrivateSkipPeerAs  
            ACCESS  not-implemented
            DESCRIPTION
                    "Not supported."

       VARIATION   tBgpInstanceNHResUseBgpRoutes  
            ACCESS  not-implemented
            DESCRIPTION
                    "Not supported."

        VARIATION   tBgpPeerGroupGracefulRestart
            ACCESS  not-implemented
            DESCRIPTION
                    "Not supported."

        VARIATION   tBgpPeerGroupGRRestartTime
            ACCESS  not-implemented
            DESCRIPTION
                    "Not supported."

        VARIATION   tBgpPeerGroupGRStaleRoute
            ACCESS  not-implemented
            DESCRIPTION
                    "Not supported."

        VARIATION   tBgpPeerGroupGRAdminState
            ACCESS  not-implemented
            DESCRIPTION
                    "Not supported."

        VARIATION   tBgpPeerGroupGROperState
            ACCESS  not-implemented
            DESCRIPTION
                    "Not supported."

        VARIATION   tBgpPeerGracefulRestart
            ACCESS  not-implemented
            DESCRIPTION
                    "Not supported."

        VARIATION   tBgpPeerGRRestartTime
            ACCESS  not-implemented
            DESCRIPTION
                    "Not supported."

        VARIATION   tBgpPeerGRStaleRoute
            ACCESS  not-implemented
            DESCRIPTION
                    "Not supported."

        VARIATION   tBgpPeerGRAdminState
            ACCESS  not-implemented
            DESCRIPTION
                    "Not supported."

        VARIATION   tBgpPeerGROperState
            ACCESS  not-implemented
            DESCRIPTION
                    "Not supported."

        VARIATION   tBgpPeerOperGRSupport
            ACCESS  not-implemented
            DESCRIPTION
                    "Not supported."

        VARIATION   tBgpPeerOperGRFamilyRestart
            ACCESS  not-implemented
            DESCRIPTION
                    "Not supported."

        VARIATION   tBgpPeerOperGRFamilyFwding 
            ACCESS  not-implemented
            DESCRIPTION
                    "Not supported."

        VARIATION   tBgpPeerOperGRFamilyNegotiated        
            ACCESS  not-implemented
            DESCRIPTION
                    "Not supported."

        VARIATION   tBgpPeerOperGRRecvEOR
            ACCESS  not-implemented
            DESCRIPTION
                    "Not supported."

        VARIATION   tBgpPeerOperGRSendEOR                 
            ACCESS  not-implemented
            DESCRIPTION
                    "Not supported."

        VARIATION   tBgpPeerOperGRStaleRoutesTime         
            ACCESS  not-implemented
            DESCRIPTION
                    "Not supported."

        VARIATION   tBgpPeerOperGRRequestRestartTime      
            ACCESS  not-implemented
            DESCRIPTION
                    "Not supported."

        VARIATION   tBgpPeerOperGRStatus                  
            ACCESS  not-implemented
            DESCRIPTION
                    "Not supported."

        VARIATION   tBgpPeerNgGracefulRestart   
            ACCESS  not-implemented
            DESCRIPTION
                    "Not supported."

        VARIATION   tBgpPeerNgGRRestartTime     
            ACCESS  not-implemented
            DESCRIPTION
                    "Not supported."

        VARIATION   tBgpPeerNgGRStaleRoute           
            ACCESS  not-implemented
            DESCRIPTION
                    "Not supported."
                    
        VARIATION   tBgpPeerNgGRAdminState           
            ACCESS  not-implemented
            DESCRIPTION
                    "Not supported."
                    
        VARIATION   tBgpPeerNgGROperState            
            ACCESS  not-implemented
            DESCRIPTION
                    "Not supported."
                    
        VARIATION   tBgpPeerNgOperGRSupport                      
            ACCESS  not-implemented
            DESCRIPTION
                    "Not supported."
                    
        VARIATION   tBgpPeerNgOperGRFamilyRestart                
            ACCESS  not-implemented
            DESCRIPTION
                    "Not supported."
                    
        VARIATION   tBgpPeerNgOperGRFamilyFwding                 
            ACCESS  not-implemented
            DESCRIPTION
                    "Not supported."
                    
        VARIATION   tBgpPeerNgOperGRFamilyNegotiated             
            ACCESS  not-implemented
            DESCRIPTION
                    "Not supported."
                    
        VARIATION   tBgpPeerNgOperGRRecvEOR                      
            ACCESS  not-implemented
            DESCRIPTION
                    "Not supported."
                    
        VARIATION   tBgpPeerNgOperGRSendEOR                      
            ACCESS  not-implemented
            DESCRIPTION
                    "Not supported."

        VARIATION   tBgpPeerNgOperGRStaleRoutesTime                               
            ACCESS  not-implemented
            DESCRIPTION
                    "Not supported."

        VARIATION   tBgpPeerNgOperGRReqRestartTime                                
            ACCESS  not-implemented
            DESCRIPTION
                    "Not supported."

        VARIATION   tBgpPeerNgOperGRStatus                                        
            ACCESS  not-implemented
            DESCRIPTION
                    "Not supported."

        VARIATION  tBgpPeerNgOperRtTgtSuppPfxDamp                                 
            ACCESS  not-implemented
            DESCRIPTION
                    "Not supported."

        VARIATION  tBgpPeerNgOperRtTgtRecvPfxs                                  
            ACCESS  not-implemented
            DESCRIPTION
                    "Not supported."

        VARIATION  tBgpPeerNgOperRtTgtSentPfxs                                          
            ACCESS  not-implemented
            DESCRIPTION
                    "Not supported."

        VARIATION  tBgpPeerNgOperRtTgtActivePfxs                                  
            ACCESS  not-implemented
            DESCRIPTION
                    "Not supported."

        VARIATION  tBgpPeerNgOperVpnV4BackupPfxs                                  
            ACCESS  not-implemented
            DESCRIPTION
                    "Not supported."

        VARIATION   tBgpPeerNgOperVpnV6BackupPfxs                                         
            ACCESS  not-implemented
            DESCRIPTION
                    "Not supported."

        VARIATION  tBgpPeerNgOperMcastVpnV4RecvPfxs                                 
            ACCESS  not-implemented
            DESCRIPTION
                    "Not supported."

        VARIATION   tBgpPeerNgOperMcastVpnV4SentPfxs                                 
            ACCESS  not-implemented
            DESCRIPTION
                    "Not supported."

        VARIATION   tBgpPeerNgOperMcastVpnV4ActPfxs                                         
            ACCESS  not-implemented
            DESCRIPTION
                    "Not supported."

        VARIATION  tBgpPeerNgDefaultRouteTarget                        
            ACCESS  not-implemented
            DESCRIPTION
                    "Not supported."

        VARIATION  tBgpPeerNgAigp                                 
            ACCESS  not-implemented
            DESCRIPTION
                    "Not supported."

        VARIATION  tBgpPeerNgSplitHorizon                                  
            ACCESS  not-implemented
            DESCRIPTION
                    "Not supported."

        VARIATION  tBgpPeerNgRemPrivateSkipPeerAs                                          
            ACCESS  not-implemented
            DESCRIPTION
                    "Not supported."

        VARIATION    tBgpPeerNgMinTTLValue                   
            ACCESS  not-implemented
            DESCRIPTION
                    "Not supported."

            
        VARIATION   tBgpPGMinTTLValue            
            ACCESS  not-implemented
            DESCRIPTION
                    "Not supported."



            VARIATION tBgpInstanceAllowInterAsVpn                                      
            ACCESS  not-implemented
            DESCRIPTION
                    "Not supported."

                    
       
                    
                   
    ::= { tmnxSASM7210V6v0 55 }

--
-- TWAMP CAPABILITIES
--

tmnxTwampCapsSASM7210V6v0    AGENT-CAPABILITIES
    PRODUCT-RELEASE "Alcatel SAS-M 7210"
    STATUS          current
    DESCRIPTION     "Implementation of twamp capabilities
                     for Alcatel SAS-M 7210 release R6.0."

    SUPPORTS        TIMETRA-TWAMP-MIB
        INCLUDES    {
            tmnxTwampSrvV9v0Group,
            tmnxTwampSrvNotifyV9v0Group,
            tmnxTwampSrvNotifyObjsV9v0Group
        }
        
 VARIATION   tmnxTwampSrvMaxConnections
            DESCRIPTION
                    "tmnxTwampSrvMaxConnections has a range of 0 to 16
                    with default as 8"

 VARIATION   tmnxTwampSrvMaxSessions
            DESCRIPTION
                    "tmnxTwampSrvMaxSessions has a range of 0 to 16
                    with default as 8"        

 VARIATION   tmnxTwampSrvPrefixMaxConnections
            DESCRIPTION
                    "tmnxTwampSrvPrefixMaxConnections has a range of 0 to 16
                    with default as 8"

 VARIATION   tmnxTwampSrvPrefixMaxSessions
            DESCRIPTION
                    "tmnxTwampSrvPrefixMaxSessions has a range of 0 to 16
                    with default as 8"      
                    
    ::= { tmnxSASM7210V6v0 56 }


tmnxPimCapsV7v0    AGENT-CAPABILITIES
    PRODUCT-RELEASE "Alcatel SAS-M 7210"
    STATUS          current
    DESCRIPTION     "Implementation of PIM protocol capabilities
                     for Alcatel-Lucent SAS-M release R7.0"

    SUPPORTS        TIMETRA-PIM-NG-MIB
        INCLUDES    {
            tmnxPimNgGlobalGrpSrcV9v0Group,
            tmnxPimNgIfGroup,
            tmnxPimIfSecNbrV6v0Group,
            tmnxPimNgIfStatsV7v0Group,
            tmnxPimNgNotificationGroup,
            tmnxPimNgNotificationV7v0Group,
            tmnxPimNgNotifyObjsV7v0Group,
            tmnxPimNgEmbeddedRPV7v0Group,
            tmnxPimNgV7v0Group,
            tmnxPimNgEchoGroup,
            tmnxPimNgMvpnV8v0Group,
            tmnxPimNgIfV8v0Group,
            tmnxPimNgGlobalSSMV6v1Group,
            tmnxPimNgGlobalGroupV8v0,
            tmnxPimNgIfIpv6BfdV9v0Group,
            tmnxPimNgNotifyObjsV8v0Group,
            tmnxPimNgNotifyObjsV9v0Group,
            tmnxPimNgMvpnV9v0Group,
            tmnxPimNgIfStatsV9v0Group,
            tmnxPimNgIfIPMSIV9v0Group,
            tmnxPimNgMvpnV9v0R4Group,
            tmnxPimNgGlobalGroupV10v0,
            tmnxPimNgLdpEntryV10v0Group,
            tmnxPimNgIfV10v0Group,
            tmnxPimNgIfStatsV10v0Group,
            tmnxPimNgMvpnExtranetGroupV10v0,
            tmnxPimNgGlobalGrpSrcV10v0Group
        }

      VARIATION vRtrPimNgGenLagUsageOptimize
            ACCESS  not-implemented
            DESCRIPTION
                "Not supported."


      VARIATION vRtrPimNgGenEnableMdtSpt
            ACCESS  not-implemented
            DESCRIPTION
                "Not supported."

       VARIATION vRtrPimNgIfBSMCheckRouterAlert
            ACCESS  not-implemented
            DESCRIPTION
                "Not supported."          

        
       VARIATION vRtrPimNgIfP2mpLdpTreeJoin
            ACCESS  not-implemented
            DESCRIPTION
                "Not supported."          

        VARIATION vRtrPimNgAfGenAutoRPDiscovery
            ACCESS  not-implemented
            DESCRIPTION
                "Not supported."          
   
         VARIATION vRtrPimNgImportBootstrapPolicy1
            ACCESS  not-implemented
            DESCRIPTION
                "Not supported."          
   
         VARIATION vRtrPimNgImportBootstrapPolicy2
            ACCESS  not-implemented
            DESCRIPTION
                "Not supported."          

     
         VARIATION vRtrPimNgImportBootstrapPolicy3
            ACCESS  not-implemented
            DESCRIPTION
                "Not supported."          

          
         VARIATION vRtrPimNgImportBootstrapPolicy4
            ACCESS  not-implemented
            DESCRIPTION
                "Not supported."

        
         VARIATION vRtrPimNgImportBootstrapPolicy5
            ACCESS  not-implemented
            DESCRIPTION
                "Not supported."


         VARIATION vRtrPimNgExportBootstrapPolicy1 
            ACCESS  not-implemented
            DESCRIPTION
                "Not supported."

     
         VARIATION vRtrPimNgExportBootstrapPolicy2
            ACCESS  not-implemented
            DESCRIPTION
                "Not supported."

     
         VARIATION vRtrPimNgExportBootstrapPolicy3
            ACCESS  not-implemented
            DESCRIPTION
                "Not supported."

      VARIATION vRtrPimNgExportBootstrapPolicy4
            ACCESS  not-implemented
            DESCRIPTION
                "Not supported."
 
        VARIATION vRtrPimNgExportBootstrapPolicy5
            ACCESS  not-implemented
            DESCRIPTION
                "Not supported."


        VARIATION   vRtrPimNgRsvpIfSenderAddrType
            SYNTAX  INTEGER {
                        -- unknown  (0),
                        ipv4        (1)
                        -- ipv6      (2)
                        -- ipv4z    (3),
                        -- ipv6z    (4),
                        -- dns      (16)
                    }
            DESCRIPTION
                    "vRtrPimNgRsvpIfSenderAddrType supports only InetAddressType
                     'ipv4'."

        VARIATION   vRtrPimNgRsvpIfSenderAddr
            SYNTAX  InetAddress (SIZE (4))
            DESCRIPTION
                    "vRtrPimNgRsvpIfSenderAddr supports only InetAddressType
                    'ipv4'."

        VARIATION   vRtrPimNgMvpnUMHPEStandbyAdrTyp
            SYNTAX  INTEGER {
                        -- unknown  (0),
                        ipv4        (1)
                        -- ipv6      (2)
                        -- ipv4z    (3),
                        -- ipv6z    (4),
                        -- dns      (16)
                    }
            DESCRIPTION
                    "vRtrPimNgMvpnUMHPEStandbyAdrTyp supports only
                     InetAddressType 'ipv4'."

        VARIATION   vRtrPimNgMvpnUMHPEStandbyAddr
            SYNTAX  InetAddress (SIZE (4))
            DESCRIPTION
                    "vRtrPimNgMvpnUMHPEStandbyAddr supports only
                     InetAddressType 'ipv4'."

        VARIATION   vRtrPimNgAFGenMvpnUMHSelection
            SYNTAX  INTEGER {
                        highestip    (0),
                        hashbased    (1)
                        -- tunnelstatus (2)
                    }
            DESCRIPTION
                    "vRtrPimNgAFGenMvpnUMHSelection does not support the value
                     'tunnelStatus (2)' for version 7.0R1 on  Alcatel-Lucent
                     SROS series systems."

    ::= {tmnxSASM7210V6v0 57 }  -- PIM


--
--  IGMP CAPABILITIES
-- 
tmnxIgmpCapsV7v0    AGENT-CAPABILITIES
    PRODUCT-RELEASE "Alcatel-Lucent SAS-M"
    STATUS          current
    DESCRIPTION     "Implementation of IGMP protocol capabilities for
                     Alcatel-Lucent SASM release R7.0"

 
    SUPPORTS        TIMETRA-IGMP-MIB
        INCLUDES    {
            tmnxIgmpGlobalGroup,
            tmnxIgmpIfV5v0Group,
            tmnxIgmpNotificationV10v0Group,
            tmnxIgmpIfV6v1Group,
            tmnxIgmpIfV7v0Group,
            tmnxIgmpIfV8v0Group,
            tmnxIgmpIfV9v0Group,
            tmnxIgmpIfV10v0Group
        }

    VARIATION   vRtrIgmpGrpIfRowStatus 
            ACCESS  not-implemented
            DESCRIPTION
                "Not supported."
                
       VARIATION  vRtrIgmpIfMcacPolicyName 
           ACCESS  not-implemented
           DESCRIPTION
                "Not supported."
                
       VARIATION vRtrIgmpIfMcacUnconstrainedBW 
           ACCESS  not-implemented
           DESCRIPTION
                "Not supported."

      VARIATION vRtrIgmpIfMcacConstAdminState 
            ACCESS  not-implemented
            DESCRIPTION
                "Not supported."
                
       VARIATION  vRtrIgmpIfMcacPreRsvdMandBW 
            ACCESS  not-implemented
            DESCRIPTION
                "Not supported."
                
        VARIATION  vRtrIgmpIfMcacinUseMandBw  
            ACCESS  not-implemented
            DESCRIPTION
                "Not supported."

        VARIATION  vRtrIgmpIfMcacinUseOpnlBw  
            ACCESS  not-implemented
            DESCRIPTION
                "Not supported."
                
        VARIATION  vRtrIgmpIfMcacAvailMandBw  
             ACCESS  not-implemented
             DESCRIPTION
                "Not supported."
                
        VARIATION  vRtrIgmpIfMcacAvailOpnlBw  
            ACCESS  not-implemented
            DESCRIPTION
                "Not supported."

         VARIATION  vRtrIgmpIfMcacValuesInTransit  
             ACCESS  not-implemented
             DESCRIPTION
                "Not supported."     

    ::= { tmnxSASM7210V6v0 58 }  -- IGMP

    
    
END
