--       TIMETRA MOBILE PROFILE 
--       Management Information Base

TIMETRA-MOBILE-PROFILE-MIB DEFINITIONS ::= BEGIN

IMPORTS
   MODULE-IDENTITY, OBJECT-TYPE, Unsigned32, Counter32
       FROM SNMPv2-SMI

   MODULE-COMPLIANCE, OBJECT-GROUP
       FROM SNMPv2-CONF

   TEXTUAL-CONVENTION, RowStatus, TimeStamp, TruthValue, DisplayString
       FROM SNMPv2-TC

   InterfaceIndexOrZero
       FROM IF-MIB

   InetAddress, InetAddressType, InetAddressPrefixLength, InetPortNumber
       FROM INET-ADDRESS-MIB

   timetraSRMIBModules, tmnxSRObjs, tmnxSRConfs
       FROM TIMETRA-GLOBAL-MIB

   TIpProtocol, TmnxEnabledDisabled, TTcpUdpPort, TTcpUdpPortOperator,
   TDSCPValue, TmnxMobProfName, TmnxMobProfIpTtl, TmnxVRtrID,
   TmnxAdminState, TmnxMobDiaTransTimer, TmnxTimeInSec, TItemDescription,
   TmnxMobDiaPeerHost, TmnxMobQciValue, TmnxMobArpValue, TmnxMobChargingProfile,
   TFCName, TDSCPName, TmnxMobBufferLimit, TmnxMobQueueLimit,
   TmnxMobProfGbrRate, TmnxMobProfMbrRate, TmnxMobProfNameOrEmpty,
   TmnxMobProfPolReportingLevel, TmnxMobProfPolChargingMethod, 
   TmnxMobProfPolMeteringMethod, TmnxMobArpValueOrZero, TmnxMobQciValueOrZero,
   TmnxMobStaticPolPrecedenceOrZero, TNamedItemOrEmpty, TmnxMobMcc, TmnxMobMnc,
   TmnxMobMccOrEmpty, TmnxMobMncOrEmpty
       FROM TIMETRA-TC-MIB

   ;

timetraMobProfileMIBModule    MODULE-IDENTITY
    LAST-UPDATED    "0912230000Z"
    ORGANIZATION    "Alcatel-Lucent"
    CONTACT-INFO
    "Alcatel-Lucent 7xxx Support
    Web: http://www.alcatel.com/comps/pages/carrier_support.jhtml"
    DESCRIPTION
    "This document is the SNMP MIB module to manage and provision
    the profile and the policy for the mobile gateways.

    Copyright 2008-2012 Alcatel-Lucent. All rights reserved.
    Reproduction of this document is authorized on the condition that
    the foregoing copyright notice is included.

    This SNMP MIB module (Specification) embodies Alcatel-Lucent's
    proprietary intellectual property. Alcatel-Lucent retains all title and
    ownership in the Specification, including any revisions.

    Alcatel-Lucent grants all interested parties a non-exclusive
    license to use and distribute an unmodified copy of this
    Specification in connection with management of Alcatel-Lucent products,
    and without fee, provided this copyright notice and license appear
    on all copies.

    This Specification is supplied 'as is', and Alcatel-Lucent
    makes no warranty, either express or implied, as to the use,
    operation, condition, or performance of the Specification."

--
--  Revision History
--

    REVISION        "0912230000Z"
    DESCRIPTION     "Rev MG-1.0             23 Dec 2009 00:00
                     MG-1.0 release of the TIMETRA-MOBILE-PROFILE-MIB."

    ::= { timetraSRMIBModules 67 }

-- ----------------------------------------------------------------------------
--  Alcatel-Lucent 7xxx series MOBILE-PROFILE MIB structure
-- ----------------------------------------------------------------------------
tmnxMobProfile                   OBJECT IDENTIFIER ::= { tmnxSRObjs 67 }
    tmnxMobProfileObjs           OBJECT IDENTIFIER ::= { tmnxMobProfile 1 }
    tmnxMobProfileGlobalObjs     OBJECT IDENTIFIER ::= { tmnxMobProfile 2 }

tmnxMobProfileConformance       OBJECT IDENTIFIER ::= { tmnxSRConfs 67 }
    tmnxMobProfileCompliances   OBJECT IDENTIFIER ::=
                                            { tmnxMobProfileConformance 1 }
    tmnxMobProfileGroups        OBJECT IDENTIFIER ::=
                                            { tmnxMobProfileConformance 2 }

-- --------------------------
-- Textual Conventions
-- --------------------------
TmnxMobProfThreshold  ::=  TEXTUAL-CONVENTION
    STATUS       current
    DESCRIPTION
        "The data type TmnxMobProfThreshold describes the threshold
         percentage."
    SYNTAX       Unsigned32 (1..100)

TmnxMobProfMsgReTxTimeout  ::=  TEXTUAL-CONVENTION
    STATUS       current
    DESCRIPTION
        "The data type TmnxMobProfMsgReTxTimeout describes the message
         retransmit timeout value in seconds."
    SYNTAX       Unsigned32 (1..30)

TmnxMobProfMsgReTxRetryCount  ::=  TEXTUAL-CONVENTION
    STATUS       current
    DESCRIPTION
        "The data type TmnxMobProfMsgReTxRetryCount describes the message
         retransmit retry count value."
    SYNTAX       Unsigned32 (1..8)

TmnxMobProfKeepAliveTimeout  ::=  TEXTUAL-CONVENTION
    STATUS       current
    DESCRIPTION
        "The data type TmnxMobProfKeepAliveTimeout describes the keep-alive
         timeout value in seconds."
    SYNTAX       Unsigned32 (0|60..180)

TmnxMobProfKeepAliveRetryCount  ::=  TEXTUAL-CONVENTION
    STATUS       current
    DESCRIPTION
        "The data type TmnxMobProfKeepAliveRetryCount describes the keep-alive
         retry count value."
    SYNTAX       Unsigned32 (1..15)

TmnxMobProfKeepAliveResponse  ::=  TEXTUAL-CONVENTION
    STATUS       current
    DESCRIPTION
        "The data type TmnxMobProfKeepAliveResponse describes the keep-alive
         T3 response value in seconds."
    SYNTAX       Unsigned32 (1..20)

TmnxMobProfKeepAliveInterval  ::=   TEXTUAL-CONVENTION
    STATUS        current
    DESCRIPTION
        "The data type TmnxMobProfKeepAliveInterval describes the intervals
         between heartbeat messages"
    SYNTAX        Unsigned32 (0|60..180)
        
TmnxMobProfAllowDiscard ::= TEXTUAL-CONVENTION
    STATUS        current
    DESCRIPTION
        "The TmnxMobProfAllowDiscard is an enumerated integer that describes 
         the traffic handling option for each Diameter Credit Control 
         Application (DCCA) profile."
    SYNTAX        INTEGER {
                          allow      (1),
                          discard    (2)
                          }

-- --------------------------
--  Mib objects
-- --------------------------

--
--  System limit profile table
--

tmnxMobProfSysTblLstChgd  OBJECT-TYPE
    SYNTAX      TimeStamp
    MAX-ACCESS  read-only
    STATUS      current
    DESCRIPTION
        "The value of tmnxMobProfSysTblLstChgd indicates the sysUpTime at
         the time of the last modification to tmnxMobProfSysTable by adding,
         deleting an entry or change to a writable object in the table.

         If no changes were made to the table since the last re-initialization
         of the local network management subsystem, then this object contains
         a zero value."
    ::= { tmnxMobProfileGlobalObjs 1 }

tmnxMobProfSysTable  OBJECT-TYPE
    SYNTAX      SEQUENCE OF TmnxMobProfSysEntry
    MAX-ACCESS  not-accessible
    STATUS      current
    DESCRIPTION
        "The tmnxMobProfSysTable has an entry for each system limit profile
         configured on the system.

         A system limit profile is configured to limit the resource utilization
         and can be applied in system configuration mode at the global
         level (applicable for all MSMs) by setting the value of
         TIMETRA-MOBILE-GATEWAY-MIB::tmnxMobGwSysLimitName or at the mobile 
         system group level by setting the value of the corresponding 
         TIMETRA-MOBILE-GATEWAY-MIB::tmnxMobGwSysGroupSysLimitName."
    ::= { tmnxMobProfileObjs 1 }

tmnxMobProfSysEntry  OBJECT-TYPE
    SYNTAX      TmnxMobProfSysEntry
    MAX-ACCESS  not-accessible
    STATUS      current
    DESCRIPTION
        "Each row entry represents a system limit profile defined in the system.
         Entries can be created and deleted by the user.
         
         System limit profile 'default' is created by the agent itself at system 
         initialization. It cannot be modified or deleted."
    INDEX { IMPLIED tmnxMobProfSysName }
    ::= { tmnxMobProfSysTable 1 }

TmnxMobProfSysEntry ::= SEQUENCE {
        tmnxMobProfSysName                  TmnxMobProfName,
        tmnxMobProfSysRowStatus             RowStatus,
        tmnxMobProfSysLastChanged           TimeStamp,
        tmnxMobProfSysDescription           TItemDescription,
        tmnxMobProfSysBCLimit               Unsigned32,
        tmnxMobProfSysBCActivtyRate         Unsigned32,
        tmnxMobProfSysBCPdnLimit            Unsigned32,
        tmnxMobProfSysBCUeLimit             Unsigned32,
        tmnxMobProfSysSDFIpv4Limit          Unsigned32,
        tmnxMobProfSysSDFIpv6Limit          Unsigned32,
        tmnxMobProfSysCpuThreshldCriticl    TmnxMobProfThreshold,
        tmnxMobProfSysCpuThreshldMajor      TmnxMobProfThreshold,
        tmnxMobProfSysCpuThreshldMinor      TmnxMobProfThreshold,
        tmnxMobProfSysMemThreshldCriticl    TmnxMobProfThreshold,
        tmnxMobProfSysMemThreshldMajor      TmnxMobProfThreshold,
        tmnxMobProfSysMemThreshldMinor      TmnxMobProfThreshold,
        tmnxMobProfSysSgnlFailThrshldS5     TmnxMobProfThreshold,
        tmnxMobProfSysSgnlFailThrshldS8     TmnxMobProfThreshold,
        tmnxMobProfSysSgnlFailThrshldS11    TmnxMobProfThreshold,
        tmnxMobProfSysSgnlFailThrshldGxc    TmnxMobProfThreshold,
        tmnxMobProfSysTrfcDropThrshldS1u    TmnxMobProfThreshold,
        tmnxMobProfSysTrfcDropThrshldS5     TmnxMobProfThreshold,
        tmnxMobProfSysTrfcDropThrshldS8     TmnxMobProfThreshold,
        tmnxMobProfSysPagingBufferLimit     TmnxMobBufferLimit,
        tmnxMobProfSysPagingBufferSize      TmnxMobQueueLimit,
        tmnxMobProfSysPagingTimeout         Unsigned32,
        tmnxMobProfSysS1BufferLimit         TmnxMobBufferLimit,
        tmnxMobProfSysS1BufferSize          TmnxMobQueueLimit
    }

tmnxMobProfSysName  OBJECT-TYPE
    SYNTAX      TmnxMobProfName
    MAX-ACCESS  not-accessible
    STATUS      current
    DESCRIPTION
        "The value of tmnxMobProfSysName specifies the unique name of this
         system limit profile."
    ::= { tmnxMobProfSysEntry 1 }

tmnxMobProfSysRowStatus  OBJECT-TYPE
    SYNTAX      RowStatus
    MAX-ACCESS  read-create
    STATUS      current
    DESCRIPTION
        "The value of tmnxMobProfSysRowStatus specifies the row status of this
         entry. It is used for creation and deletion of this system limit
         profile."
    ::= { tmnxMobProfSysEntry 2 }

tmnxMobProfSysLastChanged  OBJECT-TYPE
    SYNTAX      TimeStamp
    MAX-ACCESS  read-only
    STATUS      current
    DESCRIPTION
        "The value of tmnxMobProfSysLastChanged indicates the timestamp of 
         the last change to this row in tmnxMobProfSysTable."
    ::= { tmnxMobProfSysEntry 3 }

tmnxMobProfSysDescription  OBJECT-TYPE
    SYNTAX      TItemDescription
    MAX-ACCESS  read-create
    STATUS      current
    DESCRIPTION
        "The value of tmnxMobProfSysDescription specifies the description
         string for this system limit profile. It can consist of any printable,
         seven-bit ASCII characters up to 80 characters in length."
    DEFVAL { ''H }
    ::= { tmnxMobProfSysEntry 4 }

tmnxMobProfSysBCLimit  OBJECT-TYPE
    SYNTAX      Unsigned32 (10000..250000)
    MAX-ACCESS  read-create
    STATUS      current
    DESCRIPTION
        "The value of tmnxMobProfSysBCLimit specifies the maximum number of
         bearer-contexts allowed on a Mobility Service Module (MSM).

         The bearer-context can be a default bearer type or a dedicated
         bearer type."
    DEFVAL { 250000 }
    ::= { tmnxMobProfSysEntry 5 }

tmnxMobProfSysBCActivtyRate  OBJECT-TYPE
    SYNTAX      Unsigned32 (100..1000)
    MAX-ACCESS  read-create
    STATUS      current
    DESCRIPTION
        "The value of tmnxMobProfSysBCActivtyRate specifies the maximum number
         of bearer-contexts creation or deletion activities per second per
         Mobility Service Module (MSM).

         The bearer-context activity can be related to a default bearer or a
         dedicated bearer. Activities above the specified limit will not be
         serviced by the MSM."
    DEFVAL { 500 }
    ::= { tmnxMobProfSysEntry 6 }

tmnxMobProfSysBCPdnLimit  OBJECT-TYPE
    SYNTAX      Unsigned32 (1..11)
    MAX-ACCESS  read-create
    STATUS      current
    DESCRIPTION
        "The value of tmnxMobProfSysBCPdnLimit specifies the maximum number of
         bearers allowed to be established per User Equipment (UE) and Access
         Point Name (APN) or Packet Data Network Gateway (PGW) connection.

         The gateway will reject the bearer creations once this is reached and
         allow the bearer creations only when the bearer number reaches below
         the limit."
    DEFVAL { 5 }
    ::= { tmnxMobProfSysEntry 7 }

tmnxMobProfSysBCUeLimit  OBJECT-TYPE
    SYNTAX      Unsigned32 (1..11)
    MAX-ACCESS  read-create
    STATUS      current
    DESCRIPTION
        "The value of tmnxMobProfSysBCUeLimit specifies the maximum number
         of bearers allowed to be established per User Equipment (UE).

         Gateway will reject the bearer creations once this is reached and
         allow the bearer creations only when the bearer number reaches below
         the limit."
    DEFVAL { 5 }
    ::= { tmnxMobProfSysEntry 8 }

tmnxMobProfSysSDFIpv4Limit  OBJECT-TYPE
    SYNTAX      Unsigned32 (1..1500000)
    MAX-ACCESS  read-create
    STATUS      current
    DESCRIPTION
        "The value of tmnxMobProfSysSDFIpv4Limit specifies the maximum number
         of IPv4 service data flows on a gateway."
    DEFVAL { 390000 }
    ::= { tmnxMobProfSysEntry 9 }

tmnxMobProfSysSDFIpv6Limit  OBJECT-TYPE
    SYNTAX      Unsigned32 (1..512000)
    MAX-ACCESS  read-create
    STATUS      current
    DESCRIPTION
        "The value of tmnxMobProfSysSDFIpv6Limit specifies the maximum number
         of IPv6 service data flows on a gateway."
    DEFVAL { 190000 }
    ::= { tmnxMobProfSysEntry 10 }

tmnxMobProfSysCpuThreshldCriticl  OBJECT-TYPE
    SYNTAX      TmnxMobProfThreshold
    UNITS       "percentage"
    MAX-ACCESS  read-create
    STATUS      current
    DESCRIPTION
        "The value of tmnxMobProfSysCpuThreshldCriticl specifies the critical
         CPU threshold for overload control per Mobility Service Module (MSM)."
    DEFVAL { 50 }
    ::= { tmnxMobProfSysEntry 11 }

tmnxMobProfSysCpuThreshldMajor  OBJECT-TYPE
    SYNTAX      TmnxMobProfThreshold
    UNITS       "percentage"
    MAX-ACCESS  read-create
    STATUS      current
    DESCRIPTION
        "The value of tmnxMobProfSysCpuThreshldMajor specifies the major
         CPU threshold for overload control per Mobility Service Module (MSM)."
    DEFVAL { 50 }
    ::= { tmnxMobProfSysEntry 12 }

tmnxMobProfSysCpuThreshldMinor  OBJECT-TYPE
    SYNTAX      TmnxMobProfThreshold
    UNITS       "percentage"
    MAX-ACCESS  read-create
    STATUS      current
    DESCRIPTION
        "The value of tmnxMobProfSysCpuThreshldMinor specifies the minor
         CPU threshold for overload control per Mobility Service Module (MSM)."
    DEFVAL { 50 }
    ::= { tmnxMobProfSysEntry 13 }

tmnxMobProfSysMemThreshldCriticl  OBJECT-TYPE
    SYNTAX      TmnxMobProfThreshold
    UNITS       "percentage"
    MAX-ACCESS  read-create
    STATUS      current
    DESCRIPTION
        "The value of tmnxMobProfSysMemThreshldCriticl specifies the critical
         memory threshold for overload control per Mobility Service
         Module (MSM)."
    DEFVAL { 50 }
    ::= { tmnxMobProfSysEntry 14 }

tmnxMobProfSysMemThreshldMajor  OBJECT-TYPE
    SYNTAX      TmnxMobProfThreshold
    UNITS       "percentage"
    MAX-ACCESS  read-create
    STATUS      current
    DESCRIPTION
        "The value of tmnxMobProfSysMemThreshldMajor specifies the major
         memory threshold for overload control per Mobility Service
         Module (MSM)."
    DEFVAL { 50 }
    ::= { tmnxMobProfSysEntry 15 }

tmnxMobProfSysMemThreshldMinor  OBJECT-TYPE
    SYNTAX      TmnxMobProfThreshold
    UNITS       "percentage"
    MAX-ACCESS  read-create
    STATUS      current
    DESCRIPTION
        "The value of tmnxMobProfSysMemThreshldMinor specifies the minor
         memory threshold for overload control per Mobility Service
         Module (MSM)."
    DEFVAL { 50 }
    ::= { tmnxMobProfSysEntry 16 }

tmnxMobProfSysSgnlFailThrshldS5  OBJECT-TYPE
    SYNTAX      TmnxMobProfThreshold
    UNITS       "percentage"
    MAX-ACCESS  read-create
    STATUS      current
    DESCRIPTION
        "The value of tmnxMobProfSysSgnlFailThrshldS5 specifies the S5
         reference point signaling failure threshold."
    DEFVAL { 50 }
    ::= { tmnxMobProfSysEntry 17 }

tmnxMobProfSysSgnlFailThrshldS8  OBJECT-TYPE
    SYNTAX      TmnxMobProfThreshold
    UNITS       "percentage"
    MAX-ACCESS  read-create
    STATUS      current
    DESCRIPTION
        "The value of tmnxMobProfSysSgnlFailThrshldS8 specifies the S8
         reference point signaling failure threshold."
    DEFVAL { 50 }
    ::= { tmnxMobProfSysEntry 18 }

tmnxMobProfSysSgnlFailThrshldS11  OBJECT-TYPE
    SYNTAX      TmnxMobProfThreshold
    UNITS       "percentage"
    MAX-ACCESS  read-create
    STATUS      current
    DESCRIPTION
        "The value of tmnxMobProfSysSgnlFailThrshldS11 specifies the S11
         reference point signaling failure threshold."
    DEFVAL { 50 }
    ::= { tmnxMobProfSysEntry 19 }

tmnxMobProfSysSgnlFailThrshldGxc  OBJECT-TYPE
    SYNTAX      TmnxMobProfThreshold
    UNITS       "percentage"
    MAX-ACCESS  read-create
    STATUS      current
    DESCRIPTION
        "The value of tmnxMobProfSysSgnlFailThrshldGxc specifies the Gxc
         reference point signaling failure threshold."
    DEFVAL { 50 }
    ::= { tmnxMobProfSysEntry 20 }

tmnxMobProfSysTrfcDropThrshldS1u  OBJECT-TYPE
    SYNTAX      TmnxMobProfThreshold
    UNITS       "percentage"
    MAX-ACCESS  read-create
    STATUS      current
    DESCRIPTION
        "The value of tmnxMobProfSysTrfcDropThrshldS1u specifies the S1u
         reference point traffic drop threshold."
    DEFVAL { 50 }
    ::= { tmnxMobProfSysEntry 21 }

tmnxMobProfSysTrfcDropThrshldS5  OBJECT-TYPE
    SYNTAX      TmnxMobProfThreshold
    UNITS       "percentage"
    MAX-ACCESS  read-create
    STATUS      current
    DESCRIPTION
        "The value of tmnxMobProfSysTrfcDropThrshldS5 specifies the S5
         reference point traffic drop threshold."
    DEFVAL { 50 }
    ::= { tmnxMobProfSysEntry 22 }

tmnxMobProfSysTrfcDropThrshldS8  OBJECT-TYPE
    SYNTAX      TmnxMobProfThreshold
    UNITS       "percentage"
    MAX-ACCESS  read-create
    STATUS      current
    DESCRIPTION
        "The value of tmnxMobProfSysTrfcDropThrshldS8 specifies the S8
         reference point traffic drop threshold."
    DEFVAL { 50 }
    ::= { tmnxMobProfSysEntry 23 }

tmnxMobProfSysPagingBufferLimit  OBJECT-TYPE
    SYNTAX      TmnxMobBufferLimit   
    MAX-ACCESS  read-create     
    STATUS      current     
    DESCRIPTION     
        "The value of tmnxMobProfSysPagingBufferLimit specifies the down-link   
         buffer limit for the idle-user in the Serving Gateway (SGW). The SGW
         buffers down-link packets from the Packet Data Network Gateway(PGW) and
         indicates the Mobility Management Entity (MME) to page or wakeup   
         the User Equipment (UE). The buffer is common for all the UE flows."   
    DEFVAL { 8000 }
    ::= { tmnxMobProfSysEntry 24 }

tmnxMobProfSysPagingBufferSize  OBJECT-TYPE
    SYNTAX      TmnxMobQueueLimit    
    UNITS       "bytes"     
    MAX-ACCESS  read-create     
    STATUS      current     
    DESCRIPTION     
        "The value of tmnxMobProfSysPagingBufferSize specifies the paging    
         buffer-size set aside in fast-path for idle-user down-link buffering."
         DEFVAL { 8000 }
    ::= { tmnxMobProfSysEntry 25 }

tmnxMobProfSysPagingTimeout  OBJECT-TYPE 
    SYNTAX      Unsigned32 (1..60)      
    UNITS       "seconds"   
    MAX-ACCESS  read-create     
    STATUS      current     
    DESCRIPTION     
        "The value of tmnxMobProfSysPagingTimeout specifies the paging 
         time-out value for the Serving Gateway (SGW) paging request. The SGW   
         waits till the tmnxMobProfSysPagingTimeout time for the paging    
         response, then the idle-user paging timer is canceled and the buffered
         down-link packets are discarded."
    DEFVAL { 30 }
    ::= { tmnxMobProfSysEntry 26 }

tmnxMobProfSysS1BufferLimit  OBJECT-TYPE
    SYNTAX      TmnxMobBufferLimit   
    MAX-ACCESS  read-create     
    STATUS      current     
    DESCRIPTION     
        "The value of tmnxMobProfSysS1BufferLimit specifies the down-link
         buffer limit for the S1 based mobility handover scenario in the Serving
         Gateway (SGW). If the buffer limit has been reached, then the incoming
         packets from the Packet Data Network Gateway (PGW) are dropped."   
    DEFVAL { 8000 }
    ::= { tmnxMobProfSysEntry 27 }

tmnxMobProfSysS1BufferSize  OBJECT-TYPE
    SYNTAX      TmnxMobQueueLimit    
    UNITS       "bytes"     
    MAX-ACCESS  read-create     
    STATUS      current     
    DESCRIPTION     
        "The value of tmnxMobProfSysS1BufferSize specifies the
         buffer-size set aside in fast-path for S1 based mobility down-link
         buffering."    
    DEFVAL { 8000 }
    ::= { tmnxMobProfSysEntry 28 }

--
--  Diameter profile table
--

tmnxMobProfDiaTblLstChgd  OBJECT-TYPE
    SYNTAX      TimeStamp
    MAX-ACCESS  read-only
    STATUS      current
    DESCRIPTION
        "The value of tmnxMobProfDiaTblLstChgd indicates the sysUpTime at
         the time of the last modification to tmnxMobProfDiaTable by adding,
         deleting an entry or change to a writable object in the table.

         If no changes were made to the table since the last re-initialization
         of the local network management subsystem, then this object contains
         a zero value."
    ::= { tmnxMobProfileGlobalObjs 2 }

tmnxMobProfDiaTable  OBJECT-TYPE
    SYNTAX      SEQUENCE OF TmnxMobProfDiaEntry
    MAX-ACCESS  not-accessible
    STATUS      current
    DESCRIPTION
        "The tmnxMobProfDiaTable has an entry for each diameter profile
         configured on the system. Diameter profile defines diameter connection
         related parameters.

         A maximum of 100 diameter profiles can be configured in the system."
    ::= { tmnxMobProfileObjs 2 }

tmnxMobProfDiaEntry  OBJECT-TYPE
    SYNTAX      TmnxMobProfDiaEntry
    MAX-ACCESS  not-accessible
    STATUS      current
    DESCRIPTION
        "Each row entry represents a diameter profile defined in the system.
         Entries can be created and deleted by the user.

         Diameter profile 'default' is created by the agent itself at system 
         initialization. It cannot be modified or deleted."
    INDEX { IMPLIED tmnxMobProfDiaName }
    ::= { tmnxMobProfDiaTable 1 }

TmnxMobProfDiaEntry ::= SEQUENCE {
        tmnxMobProfDiaName               TmnxMobProfName,
        tmnxMobProfDiaRowStatus          RowStatus,
        tmnxMobProfDiaLastChanged        TimeStamp,
        tmnxMobProfDiaDescription        TItemDescription,
        tmnxMobProfDiaWatchdgTimer       Unsigned32,
        tmnxMobProfDiaConnTimer          Unsigned32,
        tmnxMobProfDiaTransTimer         TmnxMobDiaTransTimer,
        tmnxMobProfDiaIpTtl              TmnxMobProfIpTtl,
        tmnxMobProfDiaIpDscp             TDSCPValue,
        tmnxMobProfDiaDprTimeout         Unsigned32,
        tmnxMobProfDiaPermFailRetryTime  Unsigned32,
        tmnxMobProfDiaDnsRefreshInt      Unsigned32
    }

tmnxMobProfDiaName  OBJECT-TYPE
    SYNTAX      TmnxMobProfName
    MAX-ACCESS  not-accessible
    STATUS      current
    DESCRIPTION
        "The value of tmnxMobProfDiaName specifies the unique name of this
         diameter profile."
    ::= { tmnxMobProfDiaEntry 1 }

tmnxMobProfDiaRowStatus  OBJECT-TYPE
    SYNTAX      RowStatus
    MAX-ACCESS  read-create
    STATUS      current
    DESCRIPTION
        "The value of tmnxMobProfDiaRowStatus specifies the row status of this
         entry. It is used for creation and deletion of this diameter profile."
    ::= { tmnxMobProfDiaEntry 2 }

tmnxMobProfDiaLastChanged  OBJECT-TYPE
    SYNTAX      TimeStamp
    MAX-ACCESS  read-only
    STATUS      current
    DESCRIPTION
        "The value of tmnxMobProfDiaLastChanged indicates the timestamp of 
         the last change to this row in tmnxMobProfDiaTable."
    ::= { tmnxMobProfDiaEntry 3 }

tmnxMobProfDiaDescription  OBJECT-TYPE
    SYNTAX      TItemDescription
    MAX-ACCESS  read-create
    STATUS      current
    DESCRIPTION
        "The value of tmnxMobProfDiaDescription specifies the description
         string for this diameter profile. It can consist of any printable,
         seven-bit ASCII characters up to 80 characters in length."
    DEFVAL { ''H }
    ::= { tmnxMobProfDiaEntry 4 }

tmnxMobProfDiaWatchdgTimer  OBJECT-TYPE
    SYNTAX      Unsigned32 (1..180)
    UNITS       "seconds"
    MAX-ACCESS  read-create
    STATUS      current
    DESCRIPTION
        "The value of tmnxMobProfDiaWatchdgTimer specifies the maximum amount
         of time the node waits for a diameter peer to respond to watchdog
         packet. When the watchdog timer expires, a Device-Watchdog-Request
         (DWR) is sent to the diameter peer and the watchdog timer
         is reset. If a Device-Watchdog-Answer (DWA) is not received before
         the next expiration of the watchdog timer, transport failure to the
         Diameter peer has occurred."
    DEFVAL { 30 }
    ::= { tmnxMobProfDiaEntry 5 }

tmnxMobProfDiaConnTimer  OBJECT-TYPE
    SYNTAX      Unsigned32 (0..180)
    UNITS       "seconds"
    MAX-ACCESS  read-create
    STATUS      current
    DESCRIPTION
        "The value of tmnxMobProfDiaConnTimer specifies the maximum amount of
         time the node attempts to reconnect to a diameter peer after a
         connection to the peer has been brought down due to a transport
         failure.

         There are certain exceptions to this rule, such as peer which
         terminated the transport connection indicating that it does not wish
         to communicate. The configuration at peer level overrules the value
         configured at diameter-base level for the given peer.

         A value of 0 means that no attempt will be made to re-establish the
         connection."
    DEFVAL { 30 }
    ::= { tmnxMobProfDiaEntry 6 }

tmnxMobProfDiaTransTimer  OBJECT-TYPE
    SYNTAX      TmnxMobDiaTransTimer
    UNITS       "seconds"
    MAX-ACCESS  read-create
    STATUS      current
    DESCRIPTION
        "The value of tmnxMobProfDiaTransTimer specifies the maximum amount of
         time the node waits for a diameter peer to respond before trying
         another peer."
    DEFVAL { 5 }
    ::= { tmnxMobProfDiaEntry 7 }

tmnxMobProfDiaIpTtl  OBJECT-TYPE
    SYNTAX      TmnxMobProfIpTtl
    MAX-ACCESS  read-create
    STATUS      current
    DESCRIPTION
        "The value of tmnxMobProfDiaIpTtl specifies the IP Time-To-Live (TTL)
         value to be used for diameter signaling messages."
    DEFVAL { 255 }
    ::= { tmnxMobProfDiaEntry 8 }

tmnxMobProfDiaIpDscp  OBJECT-TYPE
    SYNTAX      TDSCPValue
    MAX-ACCESS  read-create
    STATUS      current
    DESCRIPTION
        "The value of tmnxMobProfDiaIpDscp specifies the Differentiated
         Services Code Point (DSCP) value in the IP header for diameter
         signaling messages sent. This value can be configured to treat a
         packet as Network Control (NC) packet ahead of Expedited Forwarding
         (EF) packets."
    DEFVAL { 56 }
    ::= { tmnxMobProfDiaEntry 9 }

tmnxMobProfDiaDprTimeout  OBJECT-TYPE
    SYNTAX      Unsigned32 (1..3600)
    UNITS       "seconds"
    MAX-ACCESS  read-create
    STATUS      current
    DESCRIPTION
        "The value of tmnxMobProfDiaDprTimeout specifies the amount of time
         the node waits before re-starting diameter connection setup when
         remote peer intentionally disconnected by sending
         Disconnect-Peer-Request (DPR)."
    DEFVAL { 1800 }
    ::= { tmnxMobProfDiaEntry 10 }

tmnxMobProfDiaPermFailRetryTime  OBJECT-TYPE
    SYNTAX      Unsigned32 (0..1440)
    UNITS       "minutes"
    MAX-ACCESS  read-create
    STATUS      current
    DESCRIPTION
        "The value of tmnxMobProfDiaPermFailRetryTime specifies the amount of 
         time the node waits before retrying diameter connection setup to start
         the connection dynamically without operator's intervention incase of
         permanent failures from the remote peer.

         A value of 0 means that no attempt will be made to re-establish the
         connection."
    DEFVAL { 30 }
    ::= { tmnxMobProfDiaEntry 11 }

tmnxMobProfDiaDnsRefreshInt  OBJECT-TYPE
    SYNTAX      Unsigned32 (0..86400)
    UNITS       "seconds"
    MAX-ACCESS  read-create
    STATUS      current
    DESCRIPTION
        "The value of tmnxMobProfDiaDnsRefreshInt specifies the amount of time 
         the node waits before sending a Domain Name Server (DNS) query to
         refresh the Fully Qualified Domain Name (FQDN) resolution to a list of
         IP addresses. TTL received in a DNS Response is not used at the 
         Gateway.

         A value of 0 means that the DNS refresh timer is disabled."
    DEFVAL { 21600 }
    ::= { tmnxMobProfDiaEntry 12 }       

--
--  Diameter peer profile table
--

tmnxMobProfDiaPeerTblLstChgd  OBJECT-TYPE
    SYNTAX      TimeStamp
    MAX-ACCESS  read-only
    STATUS      current
    DESCRIPTION
        "The value of tmnxMobProfDiaPeerTblLstChgd indicates the sysUpTime
         at the time of the last modification to tmnxMobProfDiaPeerTable by
         adding, deleting an entry or change to a writable object in the table.

         If no changes were made to the table since the last re-initialization
         of the local network management subsystem, then this object contains
         a zero value."
    ::= { tmnxMobProfileGlobalObjs 3 }

tmnxMobProfDiaPeerTable  OBJECT-TYPE
    SYNTAX      SEQUENCE OF TmnxMobProfDiaPeerEntry
    MAX-ACCESS  not-accessible
    STATUS      current
    DESCRIPTION
        "The tmnxMobProfDiaPeerTable has an entry for each diameter peer profile
         configured on the system. Diameter peer profile defines peer related
         information needed for diameter applications.

         A maximum of 75 diameter peer profiles can be configured in 
         the system."
    ::= { tmnxMobProfileObjs 3 }

tmnxMobProfDiaPeerEntry  OBJECT-TYPE
    SYNTAX      TmnxMobProfDiaPeerEntry
    MAX-ACCESS  not-accessible
    STATUS      current
    DESCRIPTION
        "Each row entry represents a diameter peer profile defined in the
         system. Entries can be created and deleted by the user."
    INDEX { tmnxMobProfDiaPeerName }
    ::= { tmnxMobProfDiaPeerTable 1 }

TmnxMobProfDiaPeerEntry ::= SEQUENCE {
        tmnxMobProfDiaPeerName           TmnxMobProfName,
        tmnxMobProfDiaPeerRowStatus      RowStatus,
        tmnxMobProfDiaPeerLastChanged    TimeStamp,
        tmnxMobProfDiaPeerDescription    TItemDescription,
        tmnxMobProfDiaPeerDiaProfName    TmnxMobProfNameOrEmpty,
        tmnxMobProfDiaPeerDestRealm      TmnxMobDiaPeerHost,
        tmnxMobProfDiaPeerTransport      INTEGER,
        tmnxMobProfDiaPeerLoadBalance    TmnxEnabledDisabled,
        tmnxMobProfDiaPeerIfVRtrId       TmnxVRtrID,
        tmnxMobProfDiaPeerIfIndex        InterfaceIndexOrZero,
        tmnxMobProfDiaPeerApplication    INTEGER
    }

tmnxMobProfDiaPeerName  OBJECT-TYPE
    SYNTAX      TmnxMobProfName
    MAX-ACCESS  not-accessible
    STATUS      current
    DESCRIPTION
        "The value of tmnxMobProfDiaPeerName specifies the unique name of this
         diameter peer profile."
    ::= { tmnxMobProfDiaPeerEntry 1 }

tmnxMobProfDiaPeerRowStatus  OBJECT-TYPE
    SYNTAX      RowStatus
    MAX-ACCESS  read-create
    STATUS      current
    DESCRIPTION
        "The value of tmnxMobProfDiaPeerRowStatus specifies the row status of
         this entry. It is used for creation and deletion of this diameter
         peer profile."
    ::= { tmnxMobProfDiaPeerEntry 2 }

tmnxMobProfDiaPeerLastChanged  OBJECT-TYPE
    SYNTAX      TimeStamp
    MAX-ACCESS  read-only
    STATUS      current
    DESCRIPTION
        "The value of tmnxMobProfDiaPeerLastChanged indicates the timestamp of
         the last change to this row in tmnxMobProfDiaPeerTable."
    ::= { tmnxMobProfDiaPeerEntry 3 }

tmnxMobProfDiaPeerDescription  OBJECT-TYPE
    SYNTAX      TItemDescription
    MAX-ACCESS  read-create
    STATUS      current
    DESCRIPTION
        "The value of tmnxMobProfDiaPeerDescription specifies the description
         string for this diameter peer profile. It can consist of any printable,
         seven-bit ASCII characters up to 80 characters in length."
    DEFVAL { ''H }
    ::= { tmnxMobProfDiaPeerEntry 4 }

tmnxMobProfDiaPeerDiaProfName  OBJECT-TYPE
    SYNTAX      TmnxMobProfNameOrEmpty
    MAX-ACCESS  read-create
    STATUS      current
    DESCRIPTION
        "The value of tmnxMobProfDiaPeerDiaProfName specifies the name of the
         diameter profile to be associated with this diameter peer profile.
         Multiple diameter peer profiles can reference the same diameter
         profile."
    DEFVAL { ''H }
    ::= { tmnxMobProfDiaPeerEntry 5 }

tmnxMobProfDiaPeerDestRealm  OBJECT-TYPE
    SYNTAX      TmnxMobDiaPeerHost
    MAX-ACCESS  read-create
    STATUS      current
    DESCRIPTION
        "The value of tmnxMobProfDiaPeerDestRealm specifies the
         destination realm of the diameter peer."
    DEFVAL { ''H }
    ::= { tmnxMobProfDiaPeerEntry 6 }

tmnxMobProfDiaPeerTransport  OBJECT-TYPE
    SYNTAX      INTEGER {
                         tcp  (1),
                         sctp (2)
                        }
    MAX-ACCESS  read-create
    STATUS      current
    DESCRIPTION
        "The value of tmnxMobProfDiaPeerTransport specifies the type of
         diameter signaling to be used."
    DEFVAL { tcp }
    ::= { tmnxMobProfDiaPeerEntry 7 }

tmnxMobProfDiaPeerLoadBalance  OBJECT-TYPE
    SYNTAX      TmnxEnabledDisabled
    MAX-ACCESS  read-create
    STATUS      current
    DESCRIPTION
        "The value of tmnxMobProfDiaPeerLoadBalance specifies if load
         balanacing is enabled or not. If load balancing is enabled then all
         the peers will be used in round-robin fashion, otherwise only the
         first peer will be used for diameter sessions."
    DEFVAL { disabled }
    ::= { tmnxMobProfDiaPeerEntry 8 }

tmnxMobProfDiaPeerIfVRtrId  OBJECT-TYPE
    SYNTAX      TmnxVRtrID
    MAX-ACCESS  read-create
    STATUS      current
    DESCRIPTION
        "The value of tmnxMobProfDiaPeerIfVRtrId specifies the virtual
         router to which the interface specified by tmnxMobProfDiaPeerIfIndex
         belongs."
    DEFVAL { 1 }
    ::= { tmnxMobProfDiaPeerEntry 9 }

tmnxMobProfDiaPeerIfIndex  OBJECT-TYPE
    SYNTAX      InterfaceIndexOrZero
    MAX-ACCESS  read-create
    STATUS      current
    DESCRIPTION
        "The value of tmnxMobProfDiaPeerIfIndex specifies the interface index of
         the local interface used by diameter applications."
    DEFVAL { 0 }
    ::= { tmnxMobProfDiaPeerEntry 10 }
    
tmnxMobProfDiaPeerApplication  OBJECT-TYPE
    SYNTAX      INTEGER {
                         none (0),
                         gx   (1),
                         gxc  (2),
                         rf   (3),
                         gy   (4),
                         s6b  (5)
                        }
    MAX-ACCESS  read-create
    STATUS      current
    DESCRIPTION
        "The value of tmnxMobProfDiaPeerApplication specifies the type of
         application where this profile will be used. The names refer to the
         interfaces between different nodes in the LTE network."
    REFERENCE "3GPP TS 32.251 v 8.8.0"
    DEFVAL { none }
    ::= { tmnxMobProfDiaPeerEntry 11 }

--
--  Diameter peer profile peer address list table
--

tmnxMobProfDiaPeerListTblLstChgd  OBJECT-TYPE
    SYNTAX      TimeStamp
    MAX-ACCESS  read-only
    STATUS      current
    DESCRIPTION
        "The value of tmnxMobProfDiaPeerListTblLstChgd indicates the sysUpTime
         at the time of the last modification to tmnxMobProfDiaPeerListTable by
         adding, deleting an entry or change to a writable object in the table.

         If no changes were made to the table since the last re-initialization
         of the local network management subsystem, then this object contains
         a zero value."
    ::= { tmnxMobProfileGlobalObjs 4 }

tmnxMobProfDiaPeerListTable  OBJECT-TYPE
    SYNTAX      SEQUENCE OF TmnxMobProfDiaPeerListEntry
    MAX-ACCESS  not-accessible
    STATUS      current
    DESCRIPTION
        "The tmnxMobProfDiaPeerListTable has an entry for each IP address
         configured in a diameter peer profile. The diameter peer profiles for
         Gxc and Gx reference points will have exactly one peer address
         provisioned.

         A maximum of 20 peers can be configured for each diameter peer profile
         defined in the system."
    ::= { tmnxMobProfileObjs 4 }

tmnxMobProfDiaPeerListEntry  OBJECT-TYPE
    SYNTAX      TmnxMobProfDiaPeerListEntry
    MAX-ACCESS  not-accessible
    STATUS      current
    DESCRIPTION
        "Each row entry represents a IP address configured in a diameter peer
         profile. Entries can be created and deleted by the user."
    INDEX { tmnxMobProfDiaPeerName,
            tmnxMobProfDiaPeerListIndex
          }
    ::= { tmnxMobProfDiaPeerListTable 1 }

TmnxMobProfDiaPeerListEntry ::= SEQUENCE {
        tmnxMobProfDiaPeerListIndex        Unsigned32,
        tmnxMobProfDiaPeerListRowStatus    RowStatus,
        tmnxMobProfDiaPeerListLastChngd    TimeStamp,
        tmnxMobProfDiaPeerListAddrType     InetAddressType,
        tmnxMobProfDiaPeerListAddr         InetAddress,
        tmnxMobProfDiaPeerListPort         InetPortNumber,
        tmnxMobProfDiaPeerAdminState       TmnxAdminState
    }

tmnxMobProfDiaPeerListIndex  OBJECT-TYPE
    SYNTAX      Unsigned32 (0..19)
    MAX-ACCESS  not-accessible
    STATUS      current
    DESCRIPTION
        "The value of tmnxMobProfDiaPeerListIndex specifies the unique value
         which identifies this IP address entry."
    ::= { tmnxMobProfDiaPeerListEntry 1 }

tmnxMobProfDiaPeerListRowStatus  OBJECT-TYPE
    SYNTAX      RowStatus
    MAX-ACCESS  read-create
    STATUS      current
    DESCRIPTION
        "The value of tmnxMobProfDiaPeerListRowStatus specifies the row status
         of this entry. It is used for creation and deletion of this peer
         entry.

         In order for the row creation to succeed, values for 
         tmnxMobProfDiaPeerListAddrType, tmnxMobProfDiaPeerListAddr and 
         tmnxMobProfDiaPeerListPort must be included in the same SNMP SET PDU 
         as tmnxMobProfDiaPeerListRowStatus. Otherwise,
         the SET request will fail with an 'inconsistentValue' error."
    ::= { tmnxMobProfDiaPeerListEntry 2 }

tmnxMobProfDiaPeerListLastChngd  OBJECT-TYPE
    SYNTAX      TimeStamp
    MAX-ACCESS  read-only
    STATUS      current
    DESCRIPTION
        "The value of tmnxMobProfDiaPeerListLastChngd indicates the timestamp of
         the last change to this row in tmnxMobProfDiaPeerListTable."
    ::= { tmnxMobProfDiaPeerListEntry 3 }

tmnxMobProfDiaPeerListAddrType  OBJECT-TYPE
    SYNTAX      InetAddressType
    MAX-ACCESS  read-create
    STATUS      current
    DESCRIPTION
        "The value of tmnxMobProfDiaPeerListAddrType specifies the type of
         address represented by tmnxMobProfDiaPeerListAddr.

         The value of this object cannot be modified once the row has been 
         created."
    ::= { tmnxMobProfDiaPeerListEntry 4 }

tmnxMobProfDiaPeerListAddr  OBJECT-TYPE
    SYNTAX      InetAddress (SIZE (1..255))
    MAX-ACCESS  read-create
    STATUS      current
    DESCRIPTION
        "The value of tmnxMobProfDiaPeerListAddr specifies the IP address of
         the peer for which this entry contains information. If the value of
         the corresponsding tmnxMobProfDiaPeerListAddrType is 'dns', then the
         IP address for this Peer will be obtained via DNS A-Record query.

         The value of this object cannot be modified once the row has been 
         created."
    ::= { tmnxMobProfDiaPeerListEntry 5 }

tmnxMobProfDiaPeerListPort  OBJECT-TYPE
    SYNTAX      InetPortNumber (3868..3888)
    MAX-ACCESS  read-create
    STATUS      current
    DESCRIPTION
        "The value of tmnxMobProfDiaPeerListPort specifies the port number for
         this peer.

         The value of this object cannot be modified once the row has been 
         created."
    DEFVAL { 3868 }
    ::= { tmnxMobProfDiaPeerListEntry 6 }
    
tmnxMobProfDiaPeerAdminState  OBJECT-TYPE
    SYNTAX      TmnxAdminState
    MAX-ACCESS  read-create
    STATUS      current
    DESCRIPTION
        "The value of tmnxMobProfDiaPeerAdminState specifies the desired 
         administrative state of this peer."
    DEFVAL { outOfService }
    ::= { tmnxMobProfDiaPeerListEntry 7 }

--
--  Pmipv6 profile table
--

tmnxMobProfPmipv6TblLstChgd  OBJECT-TYPE
    SYNTAX      TimeStamp
    MAX-ACCESS  read-only
    STATUS      current
    DESCRIPTION
        "The value of tmnxMobProfPmipv6TblLstChgd indicates the sysUpTime at
         the time of the last modification to tmnxMobProfPmipv6Table by adding,
         deleting an entry or change to a writable object in the table.

         If no changes were made to the table since the last re-initialization
         of the local network management subsystem, then this object contains
         a zero value."
    ::= { tmnxMobProfileGlobalObjs 5 }

tmnxMobProfPmipv6Table  OBJECT-TYPE
    SYNTAX      SEQUENCE OF TmnxMobProfPmipv6Entry
    MAX-ACCESS  not-accessible
    STATUS      current
    DESCRIPTION
        "The tmnxMobProfPmipv6Table has an entry for each Proxy Mobile IPv6
         (PMIPv6) profile configured on the system. PMIPv6 profile defines
         protocol related information applicable to PMIPv6 peers."
    ::= { tmnxMobProfileObjs 5 }

tmnxMobProfPmipv6Entry  OBJECT-TYPE
    SYNTAX      TmnxMobProfPmipv6Entry
    MAX-ACCESS  not-accessible
    STATUS      current
    DESCRIPTION
        "Each row entry represents a Proxy Mobile IPv6 (PMIPv6) profile defined
         in the system. Entries can be created and deleted by the user."
    INDEX { IMPLIED tmnxMobProfPmipv6Name }
    ::= { tmnxMobProfPmipv6Table 1 }

TmnxMobProfPmipv6Entry ::= SEQUENCE {
        tmnxMobProfPmipv6Name               TmnxMobProfName,
        tmnxMobProfPmipv6RowStatus          RowStatus,
        tmnxMobProfPmipv6LastChanged        TimeStamp,
        tmnxMobProfPmipv6Description        TItemDescription,
        tmnxMobProfPmipv6MsgReTxTimeout     TmnxMobProfMsgReTxTimeout,
        tmnxMobProfPmipv6MsgReTxRetryCnt    TmnxMobProfMsgReTxRetryCount,
        tmnxMobProfPmipv6KeepAlvTimeout     TmnxMobProfKeepAliveResponse,
        tmnxMobProfPmipv6KeepAlvRetryCnt    TmnxMobProfKeepAliveRetryCount,
        tmnxMobProfPmipv6KeepAlvIntvl       TmnxMobProfKeepAliveInterval,
        tmnxMobProfPmipv6IpTtl              TmnxMobProfIpTtl,
        tmnxMobProfPmipv6IpDscp             TDSCPValue
    }

tmnxMobProfPmipv6Name  OBJECT-TYPE
    SYNTAX      TmnxMobProfName
    MAX-ACCESS  not-accessible
    STATUS      current
    DESCRIPTION
        "The value of tmnxMobProfPmipv6Name specifies the unique name of this
         Proxy Mobile IPv6 (PMIPv6) profile."
    ::= { tmnxMobProfPmipv6Entry 1 }

tmnxMobProfPmipv6RowStatus  OBJECT-TYPE
    SYNTAX      RowStatus
    MAX-ACCESS  read-create
    STATUS      current
    DESCRIPTION
        "The value of tmnxMobProfPmipv6RowStatus specifies the row status of
         this entry. It is used for creation and deletion of this Proxy Mobile
         IPv6 (PMIPv6) profile."
    ::= { tmnxMobProfPmipv6Entry 2 }

tmnxMobProfPmipv6LastChanged  OBJECT-TYPE
    SYNTAX      TimeStamp
    MAX-ACCESS  read-only
    STATUS      current
    DESCRIPTION
        "The value of tmnxMobProfPmipv6LastChanged indicates the timestamp of
         the last change to this row in tmnxMobProfPmipv6Table."
    ::= { tmnxMobProfPmipv6Entry 3 }

tmnxMobProfPmipv6Description  OBJECT-TYPE
    SYNTAX      TItemDescription
    MAX-ACCESS  read-create
    STATUS      current
    DESCRIPTION
        "The value of tmnxMobProfPmipv6Description specifies the description
         string for this profile. It can consist of any printable,
         seven-bit ASCII characters up to 80 characters in length."
    DEFVAL { ''H }
    ::= { tmnxMobProfPmipv6Entry 4 }

tmnxMobProfPmipv6MsgReTxTimeout  OBJECT-TYPE
    SYNTAX      TmnxMobProfMsgReTxTimeout
    UNITS       "seconds"
    MAX-ACCESS  read-create
    STATUS      current
    DESCRIPTION
        "The value of tmnxMobProfPmipv6MsgReTxTimeout specifies the time, in
         seconds, that the Proxy Mobile IPv6 (PMIPv6) signaling component
         waits for a response from the remote peer before making another
         transmit request."
    DEFVAL { 5 }
    ::= { tmnxMobProfPmipv6Entry 5 }

tmnxMobProfPmipv6MsgReTxRetryCnt  OBJECT-TYPE
    SYNTAX      TmnxMobProfMsgReTxRetryCount
    MAX-ACCESS  read-create
    STATUS      current
    DESCRIPTION
        "The value of tmnxMobProfPmipv6MsgReTxRetryCnt specifies the number of
         times the same message is retried before declaring a failed attempt."
    DEFVAL { 3 }
    ::= { tmnxMobProfPmipv6Entry 6 }

tmnxMobProfPmipv6KeepAlvTimeout  OBJECT-TYPE
    SYNTAX      TmnxMobProfKeepAliveResponse
    UNITS       "seconds"
    MAX-ACCESS  read-create
    STATUS      current
    DESCRIPTION
        "The value of tmnxMobProfPmipv6KeepAlvTimeout specifies the time, in
         seconds, that the Proxy Mobile IPv6 (PMIPv6) signaling component waits
         for a response from a Mobile Management Entity (MME), and after
         receiving a response, the number of seconds it waits before sending
         the next echo-request message."
    DEFVAL { 5 }
    ::= { tmnxMobProfPmipv6Entry 7 }

tmnxMobProfPmipv6KeepAlvRetryCnt  OBJECT-TYPE
    SYNTAX      TmnxMobProfKeepAliveRetryCount
    MAX-ACCESS  read-create
    STATUS      current
    DESCRIPTION
        "The value of tmnxMobProfPmipv6KeepAlvRetryCnt specifies the maximum
         number of times that the Proxy Mobile IPv6 (PMIPv6) signaling
         component attempts to send a echo-request message for which there is
         no reply from the remote peer. Once the retry count reaches the
         specified value, remote peer will be declared as unreachable."
    DEFVAL { 4 }
    ::= { tmnxMobProfPmipv6Entry 8 }

tmnxMobProfPmipv6KeepAlvIntvl  OBJECT-TYPE
    SYNTAX      TmnxMobProfKeepAliveInterval
    MAX-ACCESS  read-create
    STATUS      current
    DESCRIPTION
        "The value of tmnxMobProfPmipv6KeepAlvIntvl specifies the interval
         between the heartbeat messages"
    DEFVAL { 60 }
    ::=  { tmnxMobProfPmipv6Entry 9 }

tmnxMobProfPmipv6IpTtl  OBJECT-TYPE
    SYNTAX      TmnxMobProfIpTtl
    MAX-ACCESS  read-create
    STATUS      current
    DESCRIPTION
        "The value of tmnxMobProfPmipv6IpTtl specifies the IP Time-To-Live (TTL)
         value to be used for Proxy Mobile IPv6 (PMIPv6) messages."
    DEFVAL { 255 }
    ::= { tmnxMobProfPmipv6Entry 10 }

tmnxMobProfPmipv6IpDscp  OBJECT-TYPE
    SYNTAX      TDSCPValue
    MAX-ACCESS  read-create
    STATUS      current
    DESCRIPTION
        "The value of tmnxMobProfPmipv6IpDscp specifies the Differentiated
         Services Code Point (DSCP) value in the IP header for Proxy Mobile
         IPv6 (PMIPv6) messages sent. This value can be configured to treat a
         packet as Network Control (NC) packet ahead of Expedited Forwarding
         (EF) packets."
    DEFVAL { 56 }
    ::= { tmnxMobProfPmipv6Entry 11 }

--
--  GTP profile table
--

tmnxMobProfGtpTblLstChgd  OBJECT-TYPE
    SYNTAX      TimeStamp
    MAX-ACCESS  read-only
    STATUS      current
    DESCRIPTION
        "The value of tmnxMobProfGtpTblLstChgd indicates the sysUpTime at
         the time of the last modification to tmnxMobProfGtpTable by adding,
         deleting an entry or change to a writable object in the table.

         If no changes were made to the table since the last re-initialization
         of the local network management subsystem, then this object contains
         a zero value."
    ::= { tmnxMobProfileGlobalObjs 6 }

tmnxMobProfGtpTable  OBJECT-TYPE
    SYNTAX      SEQUENCE OF TmnxMobProfGtpEntry
    MAX-ACCESS  not-accessible
    STATUS      current
    DESCRIPTION
        "The tmnxMobProfGtpTable has an entry for each General Packet Radio
         Services Tunneling Protocol (GTP) profile configured on the system. 
         GTP profile defines GTP signaling related configuration."
    ::= { tmnxMobProfileObjs 6 }

tmnxMobProfGtpEntry  OBJECT-TYPE
    SYNTAX      TmnxMobProfGtpEntry
    MAX-ACCESS  not-accessible
    STATUS      current
    DESCRIPTION
        "Each row entry represents a General Packet Radio Services Tunneling
         Protocol (GTP) profile defined in the system.
         Entries can be created and deleted by the user.
      
         GTP profile 'default' is created by the agent itself at system 
         initialization. It cannot be modified or deleted."
    INDEX { IMPLIED tmnxMobProfGtpName }
    ::= { tmnxMobProfGtpTable 1 }

TmnxMobProfGtpEntry ::= SEQUENCE {
        tmnxMobProfGtpName                 TmnxMobProfName,
        tmnxMobProfGtpRowStatus            RowStatus,
        tmnxMobProfGtpLastChanged          TimeStamp,
        tmnxMobProfGtpDescription          TItemDescription,
        tmnxMobProfGtpMsgReTxTimeout       TmnxMobProfMsgReTxTimeout,
        tmnxMobProfGtpMsgReTxRetryCnt      TmnxMobProfMsgReTxRetryCount,
        tmnxMobProfGtpKeepAlvTimeout       TmnxMobProfKeepAliveTimeout,
        tmnxMobProfGtpKeepAlvRetryCnt      TmnxMobProfKeepAliveRetryCount,
        tmnxMobProfGtpKeepAlvResp          TmnxMobProfKeepAliveResponse,
        tmnxMobProfGtpIpTtl                TmnxMobProfIpTtl,
        tmnxMobProfGtpIpDscp               TDSCPValue
    }

tmnxMobProfGtpName  OBJECT-TYPE
    SYNTAX      TmnxMobProfName
    MAX-ACCESS  not-accessible
    STATUS      current
    DESCRIPTION
        "The value of tmnxMobProfGtpName specifies the unique name of this
         General Packet Radio Services Tunneling Protocol (GTP) profile."
    ::= { tmnxMobProfGtpEntry 1 }

tmnxMobProfGtpRowStatus  OBJECT-TYPE
    SYNTAX      RowStatus
    MAX-ACCESS  read-create
    STATUS      current
    DESCRIPTION
        "The value of tmnxMobProfGtpRowStatus specifies the  row status of
         this entry. It is used for creation and deletion of this General Packet
         Radio Services Tunneling Protocol (GTP) profile."
    ::= { tmnxMobProfGtpEntry 2 }

tmnxMobProfGtpLastChanged  OBJECT-TYPE
    SYNTAX      TimeStamp
    MAX-ACCESS  read-only
    STATUS      current
    DESCRIPTION
        "The value of tmnxMobProfGtpLastChanged indicates the timestamp of
         the last change to this row in tmnxMobProfGtpTable."
    ::= { tmnxMobProfGtpEntry 3 }

tmnxMobProfGtpDescription  OBJECT-TYPE
    SYNTAX      TItemDescription
    MAX-ACCESS  read-create
    STATUS      current
    DESCRIPTION
        "The value of tmnxMobProfGtpDescription specifies the description
         string for this profile. It can consist of any printable,
         seven-bit ASCII characters up to 80 characters in length."
    DEFVAL { ''H }
    ::= { tmnxMobProfGtpEntry 4 }

tmnxMobProfGtpMsgReTxTimeout  OBJECT-TYPE
    SYNTAX      TmnxMobProfMsgReTxTimeout
    UNITS       "seconds"
    MAX-ACCESS  read-create
    STATUS      current
    DESCRIPTION
        "The value of tmnxMobProfGtpMsgReTxTimeout specifies the time, in
         seconds, that the General Packet Radio Services Tunneling Protocol
         (GTP) signaling component waits for a response
         from the remote peer before making another transmit request. This
         applies to all control messages other than keep-alive messages.

         The value of this object is applicable for GTP-C messaging only."
    DEFVAL { 5 }
    ::= { tmnxMobProfGtpEntry 5 }

tmnxMobProfGtpMsgReTxRetryCnt  OBJECT-TYPE
    SYNTAX      TmnxMobProfMsgReTxRetryCount
    MAX-ACCESS  read-create
    STATUS      current
    DESCRIPTION
        "The value of tmnxMobProfGtpMsgReTxRetryCnt specifies the number of
         times the same message is retried before declaring a failed attempt.

         The value of this object is applicable for GTP-C messaging only."
    DEFVAL { 3 }
    ::= { tmnxMobProfGtpEntry 6 }

tmnxMobProfGtpKeepAlvTimeout  OBJECT-TYPE
    SYNTAX      TmnxMobProfKeepAliveTimeout
    UNITS       "seconds"
    MAX-ACCESS  read-create
    STATUS      current
    DESCRIPTION
        "The value of tmnxMobProfGtpKeepAlvTimeout specifies the time, in
         seconds, that the General Packet Radio Services Tunneling Protocol 
         (GTP) signaling component waits for a response from a
         Mobile Management Entity (MME), and after receiving a response, the
         number of seconds it waits before sending the next echo-request
         message."
    DEFVAL { 60 }
    ::= { tmnxMobProfGtpEntry 7 }

tmnxMobProfGtpKeepAlvRetryCnt  OBJECT-TYPE
    SYNTAX      TmnxMobProfKeepAliveRetryCount
    MAX-ACCESS  read-create
    STATUS      current
    DESCRIPTION
        "The value of tmnxMobProfGtpKeepAlvRetryCnt specifies the maximum
         number of times that the General Packet Radio Services Tunneling
         Protocol (GTP) signaling component attempts to
         send a echo-request message for which there is no reply from the
         remote peer. Once the retry count reaches the specified value, remote
         peer will be declared as unreachable."
    DEFVAL { 4 }
    ::= { tmnxMobProfGtpEntry 8 }

tmnxMobProfGtpKeepAlvResp  OBJECT-TYPE
    SYNTAX      TmnxMobProfKeepAliveResponse
    UNITS       "seconds"
    MAX-ACCESS  read-create
    STATUS      current
    DESCRIPTION
        "The value of tmnxMobProfGtpKeepAlvResp specifies the time, in
         seconds, that the Serving gateway (SGW) waits before resending a
         General Packet Radio Services Tunneling Protocol (GTP) signaling 
         request message when a response to a request has not
         been received. This time is doubled for every retry."
    DEFVAL { 5 }
    ::= { tmnxMobProfGtpEntry 9 }

tmnxMobProfGtpIpTtl  OBJECT-TYPE
    SYNTAX      TmnxMobProfIpTtl
    MAX-ACCESS  read-create
    STATUS      current
    DESCRIPTION
        "The value of tmnxMobProfGtpIpTtl specifies the IP Time-To-Live (TTL)
         value to be used for General Packet Radio Services Tunneling Protocol
         (GTP) signaling messages."
    DEFVAL { 255 }
    ::= { tmnxMobProfGtpEntry 10 }

tmnxMobProfGtpIpDscp  OBJECT-TYPE
    SYNTAX      TDSCPValue
    MAX-ACCESS  read-create
    STATUS      current
    DESCRIPTION
        "The value of tmnxMobProfGtpIpDscp specifies the Differentiated
         Services Code Point (DSCP) value in the IP header for General Packet
         Radio Services Tunneling Protocol (GTP) signaling
         messages sent. This value can be configured to treat a packet as
         Network Control (NC) packet ahead of Expedited Forwarding (EF)
         packets."
    DEFVAL { 56 }
    ::= { tmnxMobProfGtpEntry 11 }
    
--
--  PLMN list table
--

tmnxMobProfPlmnListTblLstChgd  OBJECT-TYPE
    SYNTAX      TimeStamp
    MAX-ACCESS  read-only
    STATUS      current
    DESCRIPTION
        "The value of tmnxMobProfPlmnListTblLstChgd indicates the sysUpTime
         at the time of the last modification to tmnxMobProfPlmnListTable
         by adding, deleting an entry or change to a writable object in the
         table.

         If no changes were made to the table since the last re-initialization
         of the local network management subsystem, then this object contains
         a zero value."
    ::= { tmnxMobProfileGlobalObjs 7 }

tmnxMobProfPlmnListTable  OBJECT-TYPE
    SYNTAX      SEQUENCE OF TmnxMobProfPlmnListEntry
    MAX-ACCESS  not-accessible
    STATUS      current
    DESCRIPTION
        "The tmnxMobProfPlmnListTable has entries for Public Land Mobile
         Network (PLMN) lists configured on the system. A PLMN list consists of
         a list of Mobile Country Code (MCC) and Mobile Network Code (MNC) ids."
    ::= { tmnxMobProfileObjs 7 }

tmnxMobProfPlmnListEntry  OBJECT-TYPE
    SYNTAX      TmnxMobProfPlmnListEntry
    MAX-ACCESS  not-accessible
    STATUS      current
    DESCRIPTION
        "Each row entry represents a Public Land Mobile Network (PLMN) defined
         in the system. Entries can be created and deleted by the user."
    INDEX { tmnxMobProfPlmnListName,
            tmnxMobProfPlmnListMcc,
            tmnxMobProfPlmnListMnc
          }
    ::= { tmnxMobProfPlmnListTable 1 }

TmnxMobProfPlmnListEntry ::= SEQUENCE {
        tmnxMobProfPlmnListName         TmnxMobProfName,
        tmnxMobProfPlmnListMcc          TmnxMobMcc,
        tmnxMobProfPlmnListMnc          TmnxMobMnc,
        tmnxMobProfPlmnListRowStatus    RowStatus
    }

tmnxMobProfPlmnListName  OBJECT-TYPE
    SYNTAX      TmnxMobProfName
    MAX-ACCESS  not-accessible
    STATUS      current
    DESCRIPTION
        "The value of tmnxMobProfPlmnListName specifies the name of this
         Public Land Mobile Network (PLMN) list."
    ::= { tmnxMobProfPlmnListEntry 1 }

tmnxMobProfPlmnListMcc  OBJECT-TYPE
    SYNTAX      TmnxMobMcc
    MAX-ACCESS  not-accessible
    STATUS      current
    DESCRIPTION
        "The value of tmnxMobProfPlmnListMcc specifies the Mobile Country Code
         (MCC) of this Public Land Mobile Network (PLMN)."
    ::= { tmnxMobProfPlmnListEntry 2 }

tmnxMobProfPlmnListMnc  OBJECT-TYPE
    SYNTAX      TmnxMobMnc
    MAX-ACCESS  not-accessible
    STATUS      current
    DESCRIPTION
        "The value of tmnxMobProfPlmnListMnc specifies the Mobile Network Code
         (MNC) of this Public Land Mobile Network (PLMN)."
    ::= { tmnxMobProfPlmnListEntry 3 }

tmnxMobProfPlmnListRowStatus  OBJECT-TYPE
    SYNTAX      RowStatus
    MAX-ACCESS  read-create
    STATUS      current
    DESCRIPTION
        "The value of tmnxMobProfPlmnListRowStatus specifies the row status
         of this entry. It is used for creation and deletion of this policy
         profile."
    ::= { tmnxMobProfPlmnListEntry 4 }

--
--  Policy rule table
--

tmnxMobProfPolTblLstChgd  OBJECT-TYPE
    SYNTAX      TimeStamp
    MAX-ACCESS  read-only
    STATUS      current
    DESCRIPTION
        "The value of tmnxMobProfPolTblLstChgd indicates the sysUpTime at
         the time of the last modification to tmnxMobProfPolTable by adding,
         deleting an entry or change to a writable object in the table.

         If no changes were made to the table since the last re-initialization
         of the local network management subsystem, then this object contains
         a zero value."
    ::= { tmnxMobProfileGlobalObjs 8 }

tmnxMobProfPolTable  OBJECT-TYPE
    SYNTAX      SEQUENCE OF TmnxMobProfPolEntry
    MAX-ACCESS  not-accessible
    STATUS      current
    DESCRIPTION
        "The tmnxMobProfPolTable has an entry for each policy profile
         configured on the system. Policy profile defines QoS parameters for
         policy control."
    ::= { tmnxMobProfileObjs 8 }

tmnxMobProfPolEntry  OBJECT-TYPE
    SYNTAX      TmnxMobProfPolEntry
    MAX-ACCESS  not-accessible
    STATUS      current
    DESCRIPTION
        "Each row entry represents a policy profile defined in the system.
         Entries can be created and deleted by the user.

         A maximum of 1024 policy profiles can be configured in the system."
    INDEX { tmnxMobProfPolName }
    ::= { tmnxMobProfPolTable 1 }

TmnxMobProfPolEntry ::= SEQUENCE {
        tmnxMobProfPolName               TmnxMobProfName,
        tmnxMobProfPolRowStatus          RowStatus,
        tmnxMobProfPolLastChanged        TimeStamp,
        tmnxMobProfPolRuleUnitName       TNamedItemOrEmpty,
        tmnxMobProfChgRuleUnitName       TNamedItemOrEmpty,
        tmnxMobProfPolQciValue           TmnxMobQciValueOrZero,
        tmnxMobProfPolArpValue           TmnxMobArpValueOrZero,
        tmnxMobProfPolPrecedence         TmnxMobStaticPolPrecedenceOrZero,
        tmnxMobProfPolInUse              TruthValue,
        tmnxMobProfPolRefCount           Counter32,
        tmnxMobProfPolConfRefCount       Counter32
    }

tmnxMobProfPolName  OBJECT-TYPE
    SYNTAX      TmnxMobProfName
    MAX-ACCESS  not-accessible
    STATUS      current
    DESCRIPTION
        "The value of tmnxMobProfPolName specifies the unique name of this
         policy profile."
    ::= { tmnxMobProfPolEntry 1 }

tmnxMobProfPolRowStatus  OBJECT-TYPE
    SYNTAX      RowStatus
    MAX-ACCESS  read-create
    STATUS      current
    DESCRIPTION
        "The value of tmnxMobProfPolRowStatus specifies the row status of
         this entry. It is used for creation and deletion of this policy
         profile."
    ::= { tmnxMobProfPolEntry 2 }

tmnxMobProfPolLastChanged  OBJECT-TYPE
    SYNTAX      TimeStamp
    MAX-ACCESS  read-only
    STATUS      current
    DESCRIPTION
        "The value of tmnxMobProfPolLastChanged indicates the timestamp of
         the last change to this row in tmnxMobProfPolTable."
    ::= { tmnxMobProfPolEntry 3 }

tmnxMobProfPolRuleUnitName  OBJECT-TYPE
    SYNTAX      TNamedItemOrEmpty
    MAX-ACCESS  read-create
    STATUS      current
    DESCRIPTION
        "The value of tmnxMobProfPolRuleUnitName specifies the policy rule unit  
         profile."
    DEFVAL { ''H }
    ::= { tmnxMobProfPolEntry 4 }

tmnxMobProfChgRuleUnitName  OBJECT-TYPE
    SYNTAX      TNamedItemOrEmpty
    MAX-ACCESS  read-create
    STATUS      current
    DESCRIPTION
        "The value of tmnxMobProfChgRuleUnitName specifies the charging rule
         unit profile."
    DEFVAL { ''H }
    ::= { tmnxMobProfPolEntry 5 }

tmnxMobProfPolQciValue  OBJECT-TYPE
    SYNTAX      TmnxMobQciValueOrZero
    MAX-ACCESS  read-create
    STATUS      current
    DESCRIPTION
        "The value of tmnxMobProfPolQciValue is used as a reference to access
         a set of node-specific parameters that control bearer level QoS packet
         forwarding treatment. Internally, this value is mapped to Forwarding
         Class (FC) within the mobile gateway system."
    DEFVAL { 0 }
    ::= { tmnxMobProfPolEntry 6 }

tmnxMobProfPolArpValue  OBJECT-TYPE
    SYNTAX      TmnxMobArpValueOrZero
    MAX-ACCESS  read-create
    STATUS      current
    DESCRIPTION
        "The value of tmnxMobProfPolArpValue specifies the admission control
         to prioritize allocation and retention for bearer establishment and
         modification."
    DEFVAL { 0 }
    ::= { tmnxMobProfPolEntry 7 }

tmnxMobProfPolPrecedence  OBJECT-TYPE
    SYNTAX      TmnxMobStaticPolPrecedenceOrZero
    MAX-ACCESS  read-create
    STATUS      current
    DESCRIPTION
        "The value of tmnxMobProfPolPrecedence specifies the precedence
         value of this policy profile."
    DEFVAL { 0 }
    ::= { tmnxMobProfPolEntry 8 }

tmnxMobProfPolInUse  OBJECT-TYPE
    SYNTAX      TruthValue
    MAX-ACCESS  read-only
    STATUS      current
    DESCRIPTION
        "The value of tmnxMobProfPolInUse specifies if this policy profile
         is being used by one of the sessions."
    DEFVAL { false }
    ::= { tmnxMobProfPolEntry 9 }

tmnxMobProfPolRefCount  OBJECT-TYPE
    SYNTAX Counter32
    MAX-ACCESS  read-only
    STATUS      current
    DESCRIPTION
        "The value of tmnxMobProfPolRefCount specifies the number of sessions
         referencing this policy profile."
    ::= { tmnxMobProfPolEntry 10 }

tmnxMobProfPolConfRefCount  OBJECT-TYPE
    SYNTAX      Counter32
    MAX-ACCESS  read-only
    STATUS      current
    DESCRIPTION
        "The value of tmnxMobProfPolConfRefCount specifies the number of policy 
         rule base entries referencing this policy profile."
    ::= { tmnxMobProfPolEntry 11 }

--
--  Policy rule flow entry table
--

tmnxMobProfPolUntFlowTblLstChgd  OBJECT-TYPE
    SYNTAX      TimeStamp
    MAX-ACCESS  read-only
    STATUS      current
    DESCRIPTION
        "The value of tmnxMobProfPolUntFlowTblLstChgd indicates the sysUpTime
         at the time of the last modification to tmnxMobProfPolUntFlwTable by
         adding, deleting an entry or change to a writable object in the table.

         If no changes were made to the table since the last re-initialization
         of the local network management subsystem, then this object contains
         a zero value."
    ::= { tmnxMobProfileGlobalObjs 9 }

tmnxMobProfPolUntFlwTable  OBJECT-TYPE
    SYNTAX      SEQUENCE OF TmnxMobProfPolUntFlwEntry
    MAX-ACCESS  not-accessible
    STATUS      current
    DESCRIPTION
        "The tmnxMobProfPolUntFlwTable has an entry for each policy unit flow 
          profile configured for a policy profile on the system. Policy unit flow 
         profile defines a set of filters identifying a Service Data Flow (SDF)."
    ::= { tmnxMobProfileObjs 9 }

tmnxMobProfPolUntFlwEntry  OBJECT-TYPE
    SYNTAX      TmnxMobProfPolUntFlwEntry
    MAX-ACCESS  not-accessible
    STATUS      current
    DESCRIPTION
        "Each row entry represents a policy unit flow profile defined in the system.
         Entries can be created and deleted by the user.

         A maximum of 15 flow profiles can be configured for each policy base 
         profile."
    INDEX { tmnxMobProfPolUnitName,
            tmnxMobProfPolUntFlwId
          }
    ::= { tmnxMobProfPolUntFlwTable 1 }

TmnxMobProfPolUntFlwEntry ::= SEQUENCE {
        tmnxMobProfPolUntFlwId                Unsigned32,
        tmnxMobProfPolUntFlwRowStatus         RowStatus,
        tmnxMobProfPolUntFlwLastChanged       TimeStamp,
        tmnxMobProfPolUntFlwDirection         INTEGER,
        tmnxMobProfPolUntFlwMatchPrtcl        TIpProtocol,
        tmnxMobProfPolUntFlwLclAddrType       InetAddressType,
        tmnxMobProfPolUntFlwLclAddr           InetAddress,
        tmnxMobProfPolUntFlwLclPrefixLen      InetAddressPrefixLength,
        tmnxMobProfPolUntFlwRmtAddrType       InetAddressType,
        tmnxMobProfPolUntFlwRmtAddr           InetAddress,
        tmnxMobProfPolUntFlwRmtPrefixLen      InetAddressPrefixLength,
        tmnxMobProfPolUntFlwLclPortVal1       TTcpUdpPort,
        tmnxMobProfPolUntFlwLclPortVal2       TTcpUdpPort,
        tmnxMobProfPolUntFlwLclPortOper       TTcpUdpPortOperator,
        tmnxMobProfPolUntFlwRmtPortVal1       TTcpUdpPort,
        tmnxMobProfPolUntFlwRmtPortVal2       TTcpUdpPort,
        tmnxMobProfPolUntFlwRmtPortOper       TTcpUdpPortOperator,
        tmnxMobProfPolUntFlwAaApp             TNamedItemOrEmpty
    }

tmnxMobProfPolUntFlwId  OBJECT-TYPE
    SYNTAX      Unsigned32 (1..255)
    MAX-ACCESS  not-accessible
    STATUS      current
    DESCRIPTION
        "The value of tmnxMobProfPolUntFlwId specifies the unique id of this
         policy unit flow profile."
    ::= { tmnxMobProfPolUntFlwEntry 1 }

tmnxMobProfPolUntFlwRowStatus  OBJECT-TYPE
    SYNTAX      RowStatus
    MAX-ACCESS  read-create
    STATUS      current
    DESCRIPTION
        "The value of tmnxMobProfPolUntFlwRowStatus specifies the row status of
         this entry. It is used for creation and deletion of this policy unit
         flow profile."
    ::= { tmnxMobProfPolUntFlwEntry 2 }

tmnxMobProfPolUntFlwLastChanged  OBJECT-TYPE
    SYNTAX      TimeStamp
    MAX-ACCESS  read-only
    STATUS      current
    DESCRIPTION
        "The value of tmnxMobProfPolUntFlwLastChanged indicates the timestamp of
         the last change to this row in tmnxMobProfPolUntFlwTable."
    ::= { tmnxMobProfPolUntFlwEntry 3 }

tmnxMobProfPolUntFlwDirection  OBJECT-TYPE
    SYNTAX      INTEGER {
                          downLink (1),
                          upLink (2),
                          both (3)
                        }
    MAX-ACCESS  read-create
    STATUS      current
    DESCRIPTION
        "The value of tmnxMobProfPolUntFlwDirection specifies the direction of
         this Service Data Flow (SDF) filter."
    DEFVAL { both }
    ::= { tmnxMobProfPolUntFlwEntry 4 }

tmnxMobProfPolUntFlwMatchPrtcl  OBJECT-TYPE
    SYNTAX      TIpProtocol
    MAX-ACCESS  read-create
    STATUS      current
    DESCRIPTION
        "The value of tmnxMobProfPolUntFlwMatchPrtcl specifies the IP protocol
         to match. If the protocol is changed, the protocol specific
         parameters are reset.
         
         The value of tmnxMobProfPolUntFlwMatchPrtcl can not be set to '-1'."
    DEFVAL { -2 }
    ::= { tmnxMobProfPolUntFlwEntry 5 }

tmnxMobProfPolUntFlwLclAddrType  OBJECT-TYPE
    SYNTAX      InetAddressType
    MAX-ACCESS  read-create
    STATUS      current
    DESCRIPTION
        "The value of tmnxMobProfPolUntFlwLclAddrType specifies the type of
         address represented by tmnxMobProfPolUntFlwLclAddr."
    DEFVAL { unknown }
    ::= { tmnxMobProfPolUntFlwEntry 6 }

tmnxMobProfPolUntFlwLclAddr  OBJECT-TYPE
    SYNTAX      InetAddress (SIZE(0|4|16))
    MAX-ACCESS  read-create
    STATUS      current
    DESCRIPTION
        "The value of tmnxMobProfPolUntFlwLclAddr specifies the IP address to
         match the local-ip of the packet."
    DEFVAL { ''H }
    ::= { tmnxMobProfPolUntFlwEntry 7 }

tmnxMobProfPolUntFlwLclPrefixLen  OBJECT-TYPE
    SYNTAX      InetAddressPrefixLength
    MAX-ACCESS  read-create
    STATUS      current
    DESCRIPTION
        "The value of tmnxMobProfPolUntFlwLclPrefixLen specifies the mask which is
         combined with received Local IP address to match address represented
         by tmnxMobProfPolUntFlwLclAddr."
    DEFVAL { 0 }
    ::= { tmnxMobProfPolUntFlwEntry 8 }

tmnxMobProfPolUntFlwRmtAddrType  OBJECT-TYPE
    SYNTAX      InetAddressType
    MAX-ACCESS  read-create
    STATUS      current
    DESCRIPTION
        "The value of tmnxMobProfPolUntFlwRmtAddrType specifies the type of
         address represented by tmnxMobProfPolUntFlwRmtAddr."
    DEFVAL { unknown }
    ::= { tmnxMobProfPolUntFlwEntry 9 }

tmnxMobProfPolUntFlwRmtAddr  OBJECT-TYPE
    SYNTAX      InetAddress (SIZE(0|4|16))
    MAX-ACCESS  read-create
    STATUS      current
    DESCRIPTION
        "The value of tmnxMobProfPolUntFlwRmtAddr specifies the IP address to
         match the remote-ip of the packet."
    DEFVAL { ''H }
    ::= { tmnxMobProfPolUntFlwEntry 10 }

tmnxMobProfPolUntFlwRmtPrefixLen  OBJECT-TYPE
    SYNTAX      InetAddressPrefixLength
    MAX-ACCESS  read-create
    STATUS      current
    DESCRIPTION
        "The value of tmnxMobProfPolUntFlwRmtPrefixLen specifies the mask which
         is combined with received remote IP address to match address
         represented by tmnxMobProfPolUntFlwRmtAddr."
    DEFVAL { 0 }
    ::= { tmnxMobProfPolUntFlwEntry 11 }

tmnxMobProfPolUntFlwLclPortVal1  OBJECT-TYPE
    SYNTAX      TTcpUdpPort
    MAX-ACCESS  read-create
    STATUS      current
    DESCRIPTION
        "The value of tmnxMobProfPolUntFlwLclPortVal1 specifies the TCP or UDP
         starting local port. The value of this object is used as per the
         description for tmnxMobProfPolUntFlwLclPortOper."
    DEFVAL { 0 }
    ::= { tmnxMobProfPolUntFlwEntry 12 }

tmnxMobProfPolUntFlwLclPortVal2  OBJECT-TYPE
    SYNTAX      TTcpUdpPort
    MAX-ACCESS  read-create
    STATUS      current
    DESCRIPTION
        "The value of tmnxMobProfPolUntFlwLclPortVal2 specifies the TCP or UDP
         ending local port. The value of this object is used as per the
         description for tmnxMobProfPolUntFlwLclPortOper."
    DEFVAL { 0 }
    ::= { tmnxMobProfPolUntFlwEntry 13 }

tmnxMobProfPolUntFlwLclPortOper  OBJECT-TYPE
    SYNTAX      TTcpUdpPortOperator
    MAX-ACCESS  read-create
    STATUS      current
    DESCRIPTION
        "The value of tmnxMobProfPolUntFlwLclPortOper specifies the manner in
         which tmnxMobProfPolUntFlwLclPortVal1 and
         tmnxMobProfPolUntFlwLclPortVal2 are to be used. The values of these
         three objects are used as described in TTcpUdpPortOperator."
    DEFVAL { none }
    ::= { tmnxMobProfPolUntFlwEntry 14 }

tmnxMobProfPolUntFlwRmtPortVal1  OBJECT-TYPE
    SYNTAX      TTcpUdpPort
    MAX-ACCESS  read-create
    STATUS      current
    DESCRIPTION
        "The value of tmnxMobProfPolUntFlwRmtPortVal1 specifies the TCP or UDP
         starting remote port. The value of this object is used as per the
         description for tmnxMobProfPolUntFlwRmtPortOper."
    DEFVAL { 0 }
    ::= { tmnxMobProfPolUntFlwEntry 15 }

tmnxMobProfPolUntFlwRmtPortVal2  OBJECT-TYPE
    SYNTAX      TTcpUdpPort
    MAX-ACCESS  read-create
    STATUS      current
    DESCRIPTION
        "The value of tmnxMobProfPolUntFlwRmtPortVal2 specifies the TCP or UDP
         ending remote port. The value of this object is used as per the
         description for tmnxMobProfPolUntFlwRmtPortOper."
    DEFVAL { 0 }
    ::= { tmnxMobProfPolUntFlwEntry 16 }

tmnxMobProfPolUntFlwRmtPortOper  OBJECT-TYPE
    SYNTAX      TTcpUdpPortOperator
    MAX-ACCESS  read-create
    STATUS      current
    DESCRIPTION
        "The value of tmnxMobProfPolUntFlwRmtPortOper specifies the manner in
         which tmnxMobProfPolUntFlwRmtPortVal1 and
         tmnxMobProfPolUntFlwRmtPortVal2 are to be used. The values of these
         three objects are used as described in TTcpUdpPortOperator."
    DEFVAL { none }
    ::= { tmnxMobProfPolUntFlwEntry 17 }

tmnxMobProfPolUntFlwAaApp  OBJECT-TYPE
    SYNTAX      TNamedItemOrEmpty
    MAX-ACCESS  read-create
    STATUS      current 
    DESCRIPTION
        "The value of tmnxMobProfPolUntFlwAaApp specifies the AA application that is 
         associated this policy.

         If the corresponding AA application is not specified in 
         TIMETRA-BSX-NG-MIB::tmnxBsxAppName, an 'inconsistentValue' 
         error will be returned." 
    DEFVAL  { ''H }
    ::= { tmnxMobProfPolUntFlwEntry 18 }

--
--  Policy base rule table
--

tmnxMobProfPolBaseTblLstChgd  OBJECT-TYPE
    SYNTAX      TimeStamp
    MAX-ACCESS  read-only
    STATUS      current
    DESCRIPTION
        "The value of tmnxMobProfPolBaseTblLstChgd indicates the sysUpTime
         at the time of the last modification to tmnxMobProfPolBaseTable by
         adding, deleting an entry or change to a writable object in the table.

         If no changes were made to the table since the last re-initialization
         of the local network management subsystem, then this object contains
         a zero value."
    ::= { tmnxMobProfileGlobalObjs 10 }

tmnxMobProfPolBaseTable  OBJECT-TYPE
    SYNTAX      SEQUENCE OF TmnxMobProfPolBaseEntry
    MAX-ACCESS  not-accessible
    STATUS      current
    DESCRIPTION
        "The tmnxMobProfPolBaseTable has entries for policy base profiles
         configured on the system. Each Policy base profile includes multiple
         policy profiles associated with a precedence value which is used for
         matching the User Equipment (UE) IP packets to respective bearers
         identified by a unique policy profile."
    ::= { tmnxMobProfileObjs 10 }

tmnxMobProfPolBaseEntry  OBJECT-TYPE
    SYNTAX      TmnxMobProfPolBaseEntry
    MAX-ACCESS  not-accessible
    STATUS      current
    DESCRIPTION
        "Each row entry represents a policy base profile defined in the system.
         Entries can be created and deleted by the user.

         A maximum of 1024 policy base profiles can be configured in the 
         system. A maximum of 8 policy profiles can be configured in a policy
         base profile."
    INDEX { tmnxMobProfPolBaseName,
            tmnxMobProfPolName
          }
    ::= { tmnxMobProfPolBaseTable 1 }

TmnxMobProfPolBaseEntry ::= SEQUENCE {
        tmnxMobProfPolBaseName           TmnxMobProfName,
        tmnxMobProfPolBaseRowStatus      RowStatus,
        tmnxMobProfPolBaseLastChanged    TimeStamp,
        tmnxMobProfPolBasePrecedence     TmnxMobStaticPolPrecedenceOrZero,
        tmnxMobProfPolBasePreActivate    TruthValue,
        tmnxMobProfPolBaseInUse          TruthValue, 
        tmnxMobProfPolBaseRefCount       Counter32,
        tmnxMobProfPolBaseConfRefCount   Counter32
    }

tmnxMobProfPolBaseName  OBJECT-TYPE
    SYNTAX      TmnxMobProfName
    MAX-ACCESS  not-accessible
    STATUS      current
    DESCRIPTION
        "The value of tmnxMobProfPolBaseName specifies the name of this policy
         base profile."
    ::= { tmnxMobProfPolBaseEntry 1 }

tmnxMobProfPolBaseRowStatus  OBJECT-TYPE
    SYNTAX      RowStatus
    MAX-ACCESS  read-create
    STATUS      current
    DESCRIPTION
        "The value of tmnxMobProfPolBaseRowStatus specifies the row status of
         this entry. It is used for creation and deletion of this policy
         profile."
    ::= { tmnxMobProfPolBaseEntry 2 }

tmnxMobProfPolBaseLastChanged  OBJECT-TYPE
    SYNTAX      TimeStamp
    MAX-ACCESS  read-only
    STATUS      current
    DESCRIPTION
        "The value of tmnxMobProfPolBaseLastChanged indicates the timestamp of
         the last change to this row in tmnxMobProfPolBaseTable."
    ::= { tmnxMobProfPolBaseEntry 3 }

tmnxMobProfPolBasePrecedence  OBJECT-TYPE
    SYNTAX      TmnxMobStaticPolPrecedenceOrZero
    MAX-ACCESS  read-create
    STATUS      current
    DESCRIPTION
        "The value of tmnxMobProfPolBasePrecedence specifies the precedence
         value of this policy base profile."
    DEFVAL { 0 }
    ::= { tmnxMobProfPolBaseEntry 4 }

tmnxMobProfPolBasePreActivate  OBJECT-TYPE
    SYNTAX      TruthValue
    MAX-ACCESS  read-create
    STATUS      current
    DESCRIPTION
        "The value of tmnxMobProfPolBasePreActivate specifies if a dedicated 
         bearer can be pre-activated at the time of User Equipment (UE) attach.
         Pre-activation of a dedicated bearer is limited to just one additional 
         bearer at the time of UE attach.

         Only one policy rule within a base policy can have the value of this
         object set to 'true'."
    DEFVAL { false }
    ::= { tmnxMobProfPolBaseEntry 5 }

tmnxMobProfPolBaseInUse   OBJECT-TYPE 
    SYNTAX      TruthValue
    MAX-ACCESS  read-only
    STATUS      current
    DESCRIPTION
        "The value of tmnxMobProfPolBaseInUse specifies if this policy base 
         profile is being used by one of the sessions."
    DEFVAL { false }
    ::= { tmnxMobProfPolBaseEntry 6 }

tmnxMobProfPolBaseRefCount OBJECT-TYPE
    SYNTAX      Counter32
    MAX-ACCESS  read-only
    STATUS      current
    DESCRIPTION
        "The value of tmnxMobProfPolBaseRefCount specifies the number of 
         sessions referencing this policy base profile."
    ::= { tmnxMobProfPolBaseEntry 7 }

tmnxMobProfPolBaseConfRefCount OBJECT-TYPE
    SYNTAX      Counter32
    MAX-ACCESS  read-only
    STATUS      current
    DESCRIPTION
        "The value of tmnxMobProfPolBaseConfRefCount specifies the number of 
         Access Point Name (APN) entries referencing this policy base profile."
    ::= { tmnxMobProfPolBaseEntry 8 }

--
--  QCI Policy Table
--

tmnxMobProfQciPolTblLstChgd  OBJECT-TYPE
    SYNTAX      TimeStamp
    MAX-ACCESS  read-only
    STATUS      current
    DESCRIPTION
        "The value of tmnxMobProfQciPolTblLstChgd indicates the sysUpTime
         at the time of the last modification to tmnxMobProfQciPolTable
         by adding, deleting an entry or change to a writable object in the
         table.

         If no changes were made to the table since the last re-initialization
         of the local network management subsystem, then this object contains
         a zero value."
    ::= { tmnxMobProfileGlobalObjs 11 }

tmnxMobProfQciPolTable  OBJECT-TYPE
    SYNTAX      SEQUENCE OF TmnxMobProfQciPolEntry
    MAX-ACCESS  not-accessible
    STATUS      current
    DESCRIPTION
       "The tmnxMobProfQciPolTable has an entry for each QCI policy profile
        configured on the system. QoS Class Identifier (QCI) Policy profile 
        defines internal QoS Class Identifier - Differentiated Services Code 
        Point (QCI-DSCP) and QoS Class Identifier - Forwarding Class (QCI-FC)
        mapping."
    ::= { tmnxMobProfileObjs 11 }

tmnxMobProfQciPolEntry  OBJECT-TYPE
    SYNTAX      TmnxMobProfQciPolEntry
    MAX-ACCESS  not-accessible
    STATUS      current
    DESCRIPTION
        "Each row entry represents a QCI policy defined in the system.
         Entries can be created and deleted by the user.

         QCI policy profile 'default' is created by the agent itself at system 
         initialization. It cannot be modified or deleted."
    INDEX { tmnxMobProfQciPolName }
    ::= { tmnxMobProfQciPolTable 1 }

TmnxMobProfQciPolEntry ::= SEQUENCE {
        tmnxMobProfQciPolName               TmnxMobProfName,
        tmnxMobProfQciPolRowStatus          RowStatus,
        tmnxMobProfQciPolLastChanged        TimeStamp,
        tmnxMobProfQciPolDescription        TItemDescription
    }

tmnxMobProfQciPolName  OBJECT-TYPE
    SYNTAX      TmnxMobProfName
    MAX-ACCESS  not-accessible
    STATUS      current
    DESCRIPTION
        "The value of tmnxMobProfQciPolName specifies the unique name of this
         QCI policy."
    ::= { tmnxMobProfQciPolEntry 1 }

tmnxMobProfQciPolRowStatus  OBJECT-TYPE
    SYNTAX      RowStatus
    MAX-ACCESS  read-create
    STATUS      current
    DESCRIPTION
        "The value of tmnxMobProfQciPolRowStatus specifies the row status of
         this entry. It is used for creation and deletion of this policy
         profile.

        The creation or deletion of an entry in this table causes creation or
        deletion of corresponding entries in tmnxMobProfQciPolQciTable."
    ::= { tmnxMobProfQciPolEntry 2 }

tmnxMobProfQciPolLastChanged  OBJECT-TYPE
    SYNTAX      TimeStamp
    MAX-ACCESS  read-only
    STATUS      current
    DESCRIPTION
        "The value of tmnxMobProfQciPolLastChanged indicates the timestamp of
         the last change to this row in tmnxMobProfQciPolTable."
    ::= { tmnxMobProfQciPolEntry 3 }

tmnxMobProfQciPolDescription  OBJECT-TYPE
    SYNTAX      TItemDescription
    MAX-ACCESS  read-create
    STATUS      current
    DESCRIPTION
        "The value of tmnxMobProfQciPolDescription specifies the description
         string for this QCI policy. It can consist of any printable,
         seven-bit ASCII characters up to 80 characters in length."
    DEFVAL { ''H }
    ::= { tmnxMobProfQciPolEntry 4 }

--
--  QCI Policy QCI list table
--

tmnxMobProfQciPolQciTblLstChgd  OBJECT-TYPE
    SYNTAX      TimeStamp
    MAX-ACCESS  read-only
    STATUS      current
    DESCRIPTION
        "The value of tmnxMobProfQciPolQciTblLstChgd indicates the sysUpTime
         at the time of the last modification to tmnxMobProfQciPolQciTable
         by adding, deleting an entry or change to a writable object in the
         table.

         If no changes were made to the table since the last re-initialization
         of the local network management subsystem, then this object contains
         a zero value."
    ::= { tmnxMobProfileGlobalObjs 12 }

tmnxMobProfQciPolQciTable  OBJECT-TYPE
    SYNTAX      SEQUENCE OF TmnxMobProfQciPolQciEntry
    MAX-ACCESS  not-accessible
    STATUS      current
    DESCRIPTION
       "The tmnxMobProfQciPolQciTable has entries for QoS Class Identifier (QCI)
        and Allocation and Retention Priority (ARP) values for each QCI policy 
        profile configured on the system."
    ::= { tmnxMobProfileObjs 12 }

tmnxMobProfQciPolQciEntry  OBJECT-TYPE
    SYNTAX      TmnxMobProfQciPolQciEntry
    MAX-ACCESS  not-accessible
    STATUS      current
    DESCRIPTION
        "Each row entry represents a QCI and ARP value for QCI policy defined in
         the system.

         Entries in this table are created or deleted by the agent itself when 
         an entry is created or deleted in the tmnxMobProfQciPolTable."
    INDEX { tmnxMobProfQciPolName,
            tmnxMobProfQciPolQciValue,
            tmnxMobProfQciPolQciArpValue
          }
    ::= { tmnxMobProfQciPolQciTable 1 }

TmnxMobProfQciPolQciEntry ::= SEQUENCE {
        tmnxMobProfQciPolQciValue              TmnxMobQciValue,
        tmnxMobProfQciPolQciArpValue           TmnxMobArpValue,
        tmnxMobProfQciPolQciLastChanged        TimeStamp,
        tmnxMobProfQciPolQciDscpPreserve       TmnxEnabledDisabled, 
        tmnxMobProfQciPolQciDscp               TDSCPName,
        tmnxMobProfQciPolQciDscpOut            TDSCPName,
        tmnxMobProfQciPolQciFcName             TFCName,
        tmnxMobProfQciPolQciProfile            INTEGER
    }

tmnxMobProfQciPolQciValue  OBJECT-TYPE
    SYNTAX      TmnxMobQciValue
    MAX-ACCESS  not-accessible
    STATUS      current
    DESCRIPTION
        "The value of tmnxMobProfQciPolQciValue indicates the QCI value."
    ::= { tmnxMobProfQciPolQciEntry 1 }

tmnxMobProfQciPolQciArpValue  OBJECT-TYPE
    SYNTAX      TmnxMobArpValue
    MAX-ACCESS  not-accessible
    STATUS      current
    DESCRIPTION
        "The value of tmnxMobProfQciPolQciArpValue indicates the ARP value."
    ::= { tmnxMobProfQciPolQciEntry 2 }

tmnxMobProfQciPolQciLastChanged  OBJECT-TYPE
    SYNTAX      TimeStamp
    MAX-ACCESS  read-only
    STATUS      current
    DESCRIPTION
        "The value of tmnxMobProfQciPolQciLastChanged indicates the timestamp of
         the last change to this row in tmnxMobProfQciPolQciTable."
    ::= { tmnxMobProfQciPolQciEntry 3 }

tmnxMobProfQciPolQciDscpPreserve  OBJECT-TYPE
    SYNTAX      TmnxEnabledDisabled
    MAX-ACCESS  read-write
    STATUS      current
    DESCRIPTION
        "The value of tmnxMobProfQciPolQciDscpPreserve specifies if the value of
         the Differentiated Services Code Point (DSCP) is preserved or not. 

         If the value of this object is set to 'enabled', the DSCP bits are 
         preserved. If the value of this object is set to 'disabled', the DSCP
         value is specified to tmnxMobProfQciPolQciDscp and 
         tmnxMobProfQciPolQciDscpOut."
    DEFVAL { enabled }
    ::= { tmnxMobProfQciPolQciEntry 4 }

tmnxMobProfQciPolQciDscp  OBJECT-TYPE
    SYNTAX      TDSCPName
    MAX-ACCESS  read-write
    STATUS      current
    DESCRIPTION
        "The value of tmnxMobProfQciPolQciDscp specifies the Differentiated 
         Services Code Point (DSCP) to be used while marking the in-profile
         packets.

         Default value for this object is set as follows, depending on the 
         value of tmnxMobProfQciPolQciValue which indicates the QCI value.

         QCI Value      Default value
         ---------      ------------- 
             1              nc2
             2              ef
             3              af41
             4              nc1
             5              af21
             6              af11
             7              af11
             8              cs1
             9              be
        "
    ::= { tmnxMobProfQciPolQciEntry 5 }

tmnxMobProfQciPolQciDscpOut  OBJECT-TYPE
    SYNTAX      TDSCPName
    MAX-ACCESS  read-write
    STATUS      current
    DESCRIPTION
        "The value of tmnxMobProfQciPolQciDscpOut specifies the DSCP to be used
         while marking the out-profile packets.

         Default value for this object is set as follows, depending on the 
         value of tmnxMobProfQciPolQciValue which indicates the QCI value.
        
         QCI Value      Default value
         ---------      ------------- 
             1              nc2
             2              ef
             3              af42
             4              nc1
             5              af22
             6              af12
             7              af12
             8              cs1
             9              be
        "
    ::= { tmnxMobProfQciPolQciEntry 6 }

tmnxMobProfQciPolQciFcName  OBJECT-TYPE
    SYNTAX      TFCName
    MAX-ACCESS  read-write
    STATUS      current
    DESCRIPTION
        "The value of tmnxMobProfQciPolQciFcName specifies the Forwarding 
         Class (FC) name.

         Default value for this object is set as follows, depending on the 
         value of tmnxMobProfQciPolQciValue which indicates the QCI value.
        
         QCI Value      Default value
         ---------      ------------- 
             1              nc
             2              ef
             3              h2
             4              h1
             5              l1
             6              af
             7              af
             8              l2
             9              be
        "
    ::= { tmnxMobProfQciPolQciEntry 7 }

tmnxMobProfQciPolQciProfile  OBJECT-TYPE
    SYNTAX      INTEGER {
                         none     (0),
                         in       (1),
                         out      (2),
                         applyCir (3)
                        }  
    MAX-ACCESS  read-write
    STATUS      current
    DESCRIPTION
        "The value of tmnxMobProfQciPolQciProfile specifies the profile to be
         assigned to the packet.

         When the value of this object is set to 'applyCir', then policer 
         provided color marking will be used for for the packet."
    DEFVAL { none }
    ::= { tmnxMobProfQciPolQciEntry 8 }
    
--
--  Peer list table
--

tmnxMobProfPeerListTblLstChgd  OBJECT-TYPE
    SYNTAX      TimeStamp
    MAX-ACCESS  read-only
    STATUS      current
    DESCRIPTION
        "The value of tmnxMobProfPeerListTblLstChgd indicates the sysUpTime at
         the time of the last modification to tmnxMobProfPeerListTable by 
         adding, deleting an entry or change to a writable object in the table.

         If no changes were made to the table since the last re-initialization
         of the local network management subsystem, then this object contains
         a zero value."
    ::= { tmnxMobProfileGlobalObjs 13 }

tmnxMobProfPeerListTable  OBJECT-TYPE
    SYNTAX      SEQUENCE OF TmnxMobProfPeerListEntry
    MAX-ACCESS  not-accessible
    STATUS      current
    DESCRIPTION
        "The tmnxMobProfPeerListTable has an entry for each peer list
         configured in the system. Levels of communication for each peer in the
         list or unlisted peers can be configured by the user."
    ::= { tmnxMobProfileObjs 13 }

tmnxMobProfPeerListEntry  OBJECT-TYPE
    SYNTAX      TmnxMobProfPeerListEntry
    MAX-ACCESS  not-accessible
    STATUS      current
    DESCRIPTION
        "Each row entry represents a peer list defined in the system. 
         Entries can be created and deleted by the user."
    INDEX { tmnxMobProfPeerListName }
    ::= { tmnxMobProfPeerListTable 1 }

TmnxMobProfPeerListEntry ::= SEQUENCE {
        tmnxMobProfPeerListName            TmnxMobProfName,
        tmnxMobProfPeerListRowStatus       RowStatus,
        tmnxMobProfPeerListLastChanged     TimeStamp,
        tmnxMobProfPeerListDescription     TItemDescription
    }

tmnxMobProfPeerListName  OBJECT-TYPE
    SYNTAX      TmnxMobProfName
    MAX-ACCESS  not-accessible
    STATUS      current
    DESCRIPTION
        "The value of tmnxMobProfPeerListName specifies the unique name of this
         peer list."
    ::= { tmnxMobProfPeerListEntry 1 }

tmnxMobProfPeerListRowStatus  OBJECT-TYPE
    SYNTAX      RowStatus
    MAX-ACCESS  read-create
    STATUS      current
    DESCRIPTION
        "The value of tmnxMobProfPeerListRowStatus specifies the row status of 
         this entry. It is used for creation and deletion of this peer list."
    ::= { tmnxMobProfPeerListEntry 2 }

tmnxMobProfPeerListLastChanged  OBJECT-TYPE
    SYNTAX      TimeStamp
    MAX-ACCESS  read-only
    STATUS      current
    DESCRIPTION
        "The value of tmnxMobProfPeerListLastChanged indicates the timestamp of 
         the last change to this row in tmnxMobProfPeerListTable."
    ::= { tmnxMobProfPeerListEntry 3 }

tmnxMobProfPeerListDescription  OBJECT-TYPE
    SYNTAX      TItemDescription
    MAX-ACCESS  read-create
    STATUS      current
    DESCRIPTION
        "The value of tmnxMobProfPeerListDescription specifies the description
         string for this peer list. It can consist of any printable,
         seven-bit ASCII characters up to 80 characters in length."
    DEFVAL { ''H }
    ::= { tmnxMobProfPeerListEntry 4 }

--
--  Peer list Peers table
--

tmnxMobProfPeerListPeerTblLtCgd  OBJECT-TYPE
    SYNTAX      TimeStamp
    MAX-ACCESS  read-only
    STATUS      current
    DESCRIPTION
        "The value of tmnxMobProfPeerListPeerTblLtCgd indicates the sysUpTime
         at the time of the last modification to tmnxMobProfPeerListPeerTable
         by adding, deleting an entry or change to a writable object in the
         table.

         If no changes were made to the table since the last re-initialization
         of the local network management subsystem, then this object contains
         a zero value."
    ::= { tmnxMobProfileGlobalObjs 14 }

tmnxMobProfPeerListPeerTable  OBJECT-TYPE
    SYNTAX      SEQUENCE OF TmnxMobProfPeerListPeerEntry
    MAX-ACCESS  not-accessible
    STATUS      current
    DESCRIPTION
        "The tmnxMobProfPeerListPeerTable has entries for peers in a peer list
         configured on the system."
    ::= { tmnxMobProfileObjs 14 }

tmnxMobProfPeerListPeerEntry  OBJECT-TYPE
    SYNTAX      TmnxMobProfPeerListPeerEntry
    MAX-ACCESS  not-accessible
    STATUS      current
    DESCRIPTION
        "Each row entry represents a peer in the peer list defined in the 
         system. Entries can be created and deleted by the user."
    INDEX { tmnxMobProfPeerListName,
            tmnxMobProfPeerListPeerAddrType,
            tmnxMobProfPeerListPeerAddr,
            tmnxMobProfPeerListPeerPrefixLen
          }
    ::= { tmnxMobProfPeerListPeerTable 1 }

TmnxMobProfPeerListPeerEntry ::= SEQUENCE {
        tmnxMobProfPeerListPeerAddrType    InetAddressType,
        tmnxMobProfPeerListPeerAddr        InetAddress,
        tmnxMobProfPeerListPeerPrefixLen   InetAddressPrefixLength,
        tmnxMobProfPeerListPeerRowStatus   RowStatus,
        tmnxMobProfPeerListPeerLastChgd    TimeStamp,
        tmnxMobProfPeerListPeerDesc        TItemDescription,
        tmnxMobProfPeerListPeerKeepAlive   TruthValue,
        tmnxMobProfPeerListPeerAdmnState   TmnxAdminState,        
        tmnxMobProfPeerListPeerRatType     INTEGER,
        tmnxMobProfPeerListPeerForeign     INTEGER,
        tmnxMobProfPeerListPeerPlmnMcc     TmnxMobMccOrEmpty,
        tmnxMobProfPeerListPeerPlmnMnc     TmnxMobMncOrEmpty
    }

tmnxMobProfPeerListPeerAddrType  OBJECT-TYPE
    SYNTAX      InetAddressType
    MAX-ACCESS  not-accessible
    STATUS      current
    DESCRIPTION
        "The value of tmnxMobProfPeerListPeerAddrType specifies the type of
         address represented by tmnxMobProfPeerListPeerAddr."
    ::= { tmnxMobProfPeerListPeerEntry 1 }

tmnxMobProfPeerListPeerAddr  OBJECT-TYPE
    SYNTAX      InetAddress (SIZE(4|16))
    MAX-ACCESS  not-accessible
    STATUS      current
    DESCRIPTION
        "The value of tmnxMobProfPeerListPeerAddr specifies the IP address of
         the peer. Unlisted IPv4 peer has address value '0.0.0.0' and 
         Unlisted IPv6 peer has address value '0:0:0:0:0:0:0:0'."
    ::= { tmnxMobProfPeerListPeerEntry 2 }

tmnxMobProfPeerListPeerPrefixLen  OBJECT-TYPE
    SYNTAX      InetAddressPrefixLength
    MAX-ACCESS  not-accessible
    STATUS      current
    DESCRIPTION
        "The value of tmnxMobProfPeerListPeerPrefixLen specifies the length of
         the IP netmask for the IP address represented by 
         tmnxMobProfPeerListPeerAddr. Unlisted peer has prefix length
         value '0'."
    ::= { tmnxMobProfPeerListPeerEntry 3 }

tmnxMobProfPeerListPeerRowStatus  OBJECT-TYPE
    SYNTAX      RowStatus
    MAX-ACCESS  read-create
    STATUS      current
    DESCRIPTION
        "The value of tmnxMobProfPeerListPeerRowStatus specifies the row status
         of this entry. It is used for creation and deletion of this policy
         profile."
    ::= { tmnxMobProfPeerListPeerEntry 4 }

tmnxMobProfPeerListPeerLastChgd  OBJECT-TYPE
    SYNTAX      TimeStamp
    MAX-ACCESS  read-only
    STATUS      current
    DESCRIPTION
        "The value of tmnxMobProfPeerListPeerLastChgd indicates the timestamp 
         of the last change to this row in tmnxMobProfPeerListPeerTable."
    ::= { tmnxMobProfPeerListPeerEntry 5 }

tmnxMobProfPeerListPeerDesc  OBJECT-TYPE
    SYNTAX      TItemDescription
    MAX-ACCESS  read-create
    STATUS      current
    DESCRIPTION
        "The value of tmnxMobProfPeerListPeerDesc specifies the 
         description string for this peer. It can consist of any printable,
         seven-bit ASCII characters up to 80 characters in length."
    DEFVAL { ''H }
    ::= { tmnxMobProfPeerListPeerEntry 6 }
    
tmnxMobProfPeerListPeerKeepAlive  OBJECT-TYPE
    SYNTAX      TruthValue
    MAX-ACCESS  read-create
    STATUS      current
    DESCRIPTION
        "The value of tmnxMobProfPeerListPeerKeepAlive specifies whether the
         General Packet Radio Services Tunneling Protocol (GTP) echo is enabled
         for this peer.  

         When the value of this object is set to 'true', communication is 
         made with this peer."
    DEFVAL { true }
    ::= { tmnxMobProfPeerListPeerEntry 7 }

tmnxMobProfPeerListPeerAdmnState  OBJECT-TYPE
    SYNTAX      TmnxAdminState
    MAX-ACCESS  read-create
    STATUS      current
    DESCRIPTION
        "The value of tmnxMobProfPeerListPeerAdmnState specifies the desired 
         administrative state of this peer list."
    DEFVAL { inService }
    ::= { tmnxMobProfPeerListPeerEntry 8 }

tmnxMobProfPeerListPeerRatType  OBJECT-TYPE
    SYNTAX      INTEGER {
                         geran   (1),
                         utran   (2),
                         eutran  (3),
                         ehrpd   (4),
                         hrpd    (5),
                         oneXrtt (6),
                         umb     (7)
                        }
    MAX-ACCESS  read-create
    STATUS      current
    DESCRIPTION
        "The value of tmnxMobGtpPriServerMaxRequests specifies the Radio Access
         Technology (RAT) type being served by this peer. The RAT type should
         be used if the RAT type cannot be determined via the General
         Packet Radio Services Tunneling Protocol (GTP) message itself."
    DEFVAL { utran }
    ::= { tmnxMobProfPeerListPeerEntry 9 }

tmnxMobProfPeerListPeerForeign  OBJECT-TYPE
    SYNTAX      INTEGER {
                         home       (1),
                         foreign    (2),
                         none       (3) 
                        }
    MAX-ACCESS  read-create
    STATUS      current
    DESCRIPTION
        "The value of tmnxMobProfPeerListPeerForeign specifies the peer as a
         foreign or a home node. 

         The value 'none' will be set when tmnxMobProfPeerListPeerPlmnMcc and 
         tmnxMobProfPeerListPeerPlmnMnc are specified."
    DEFVAL { home }
    ::= { tmnxMobProfPeerListPeerEntry 10 }

tmnxMobProfPeerListPeerPlmnMcc  OBJECT-TYPE
    SYNTAX      TmnxMobMccOrEmpty
    MAX-ACCESS  read-create
    STATUS      current
    DESCRIPTION
        "The value of tmnxMobProfPeerListPeerPlmnMcc specifies the Mobile
         Country Code (MCC) portion of the Public Land Mobile Network (PLMN) for
         this peer. 

         The value of the tmnxMobProfPeerListPeerPlmnMcc will be set as an empty
         string when tmnxMobProfPeerListPeerForeign is specified."
    DEFVAL { ''H }    
    ::= { tmnxMobProfPeerListPeerEntry 11 }

tmnxMobProfPeerListPeerPlmnMnc  OBJECT-TYPE
    SYNTAX      TmnxMobMncOrEmpty
    MAX-ACCESS  read-create
    STATUS      current
    DESCRIPTION
        "The value of tmnxMobProfPeerListPeerPlmnMnc specifies the Mobile
         Network Code (MNC) portion of the Public Land Mobile Network (PLMN) for
         this peer. 

         The value of the tmnxMobProfPeerListPeerPlmnMnc will be set as an empty
         string when tmnxMobProfPeerListPeerForeign is specified."
    DEFVAL { ''H }
    ::= { tmnxMobProfPeerListPeerEntry 12 }

--
--  SGW Charging table
--

tmnxMobProfSgwChargingTblLstChgd  OBJECT-TYPE
    SYNTAX      TimeStamp
    MAX-ACCESS  read-only
    STATUS      current
    DESCRIPTION
        "The value of tmnxMobProfPolTblLstChgd indicates the sysUpTime at
         the time of the last modification to tmnxMobProfSgwChargingTable by 
         adding, deleting an entry or change to a writable object in the table.

         If no changes were made to the table since the last re-initialization
         of the local network management subsystem, then this object contains
         a zero value."
    ::= { tmnxMobProfileGlobalObjs 15 }

tmnxMobProfSgwChargingTable  OBJECT-TYPE
    SYNTAX      SEQUENCE OF TmnxMobProfSgwChargingEntry
    MAX-ACCESS  not-accessible
    STATUS      current
    DESCRIPTION
        "The tmnxMobProfPolTable has an entry for each SGW profile
         configured on the system. SGW charging profile 
         defines charging parameters for the Serving Gateway (SGW)."
    ::= { tmnxMobProfileObjs 15 }

tmnxMobProfSgwChargingEntry  OBJECT-TYPE
    SYNTAX      TmnxMobProfSgwChargingEntry
    MAX-ACCESS  not-accessible
    STATUS      current
    DESCRIPTION
        "Each row entry represents a Serving Gateway (SGW) charging profile 
         defined in the system. Entries can be created and deleted by the user.

         SGW charging profile 0 is created by the agent itself at system 
         initialization. It cannot be modified or deleted."
    INDEX { tmnxMobProfSgwChrgId }
    ::= { tmnxMobProfSgwChargingTable 1 }

TmnxMobProfSgwChargingEntry ::= SEQUENCE {
        tmnxMobProfSgwChrgId                TmnxMobChargingProfile,
        tmnxMobProfSgwChrgRowStatus         RowStatus,
        tmnxMobProfSgwChrgLastChanged       TimeStamp,
        tmnxMobProfSgwChrgDesc              TItemDescription,
        tmnxMobProfSgwChrgOffLineState      TmnxEnabledDisabled,
        tmnxMobProfSgwChrgPriCdfDiaPeer     TmnxMobProfNameOrEmpty,
        tmnxMobProfSgwChrgSecCdfDiaPeer     TmnxMobProfNameOrEmpty,
        tmnxMobProfSgwChrgCitQosChange      TmnxEnabledDisabled, 
        tmnxMobProfSgwChrgCitUsrLocChnge    TmnxEnabledDisabled,
        tmnxMobProfSgwChrgCitTrfTimeChng    TmnxEnabledDisabled,
        tmnxMobProfSgwChrgCitTrfTmStart     TmnxTimeInSec,
        tmnxMobProfSgwChrgCitTrfTmEnd       TmnxTimeInSec,
        tmnxMobProfSgwChrgPrctTimeLmt       Unsigned32,
        tmnxMobProfSgwChrgPrctVolumeLmt     Unsigned32,
        tmnxMobProfSgwChrgPrctMaxChCond     Unsigned32,
        tmnxMobProfSgwChrgPrctMsTmzChnge    TmnxEnabledDisabled,
        tmnxMobProfSgwChrgPrctPlmnChange    TmnxEnabledDisabled,
        tmnxMobProfSgwChrgPrctRatChange     TmnxEnabledDisabled,
        tmnxMobProfSgwChrgPrctMgmtInterv    TmnxEnabledDisabled,
        tmnxMobProfSgwChrgCitSgwChange      TmnxEnabledDisabled,
        tmnxMobProfSgwChrgPrctSrvNdChLmt    Unsigned32
    }

tmnxMobProfSgwChrgId  OBJECT-TYPE
    SYNTAX      TmnxMobChargingProfile
    MAX-ACCESS  not-accessible
    STATUS      current
    DESCRIPTION
        "The value of tmnxMobProfSgwChrgId uniquely identifies a charging 
         profile configured for the Serving Gateway (SGW)."
    ::= { tmnxMobProfSgwChargingEntry 1 }

tmnxMobProfSgwChrgRowStatus  OBJECT-TYPE
    SYNTAX      RowStatus
    MAX-ACCESS  read-create
    STATUS      current
    DESCRIPTION
        "The value of tmnxMobProfSgwChrgRowStatus specifies the row status of
         this entry. It is used for creation and deletion of this charging
         profile."
    ::= { tmnxMobProfSgwChargingEntry 2 }

tmnxMobProfSgwChrgLastChanged  OBJECT-TYPE
    SYNTAX      TimeStamp
    MAX-ACCESS  read-only
    STATUS      current
    DESCRIPTION
        "The value of tmnxMobProfSgwChrgLastChanged indicates the timestamp of
         the last change to this row in tmnxMobProfSgwChargingTable."
    ::= { tmnxMobProfSgwChargingEntry 3 }

tmnxMobProfSgwChrgDesc  OBJECT-TYPE
    SYNTAX      TItemDescription
    MAX-ACCESS  read-create
    STATUS      current
    DESCRIPTION
        "The value of tmnxMobProfSgwChrgDesc is a user provided description
         string for this charging profile for the Serving Gateway (SGW). It can
         consist of any printable, seven-bit ASCII characters up to 80 
         characters in length."
    DEFVAL { ''H }
    ::= { tmnxMobProfSgwChargingEntry 4 }

tmnxMobProfSgwChrgOffLineState  OBJECT-TYPE
    SYNTAX      TmnxEnabledDisabled
    MAX-ACCESS  read-create
    STATUS      current
    DESCRIPTION
        "The value of tmnxMobProfSgwChrgOffLineState specifies whether offline 
         charging is enabled for this charging profile for the Serving Gateway
         (SGW)."
    DEFVAL { disabled }
    ::= { tmnxMobProfSgwChargingEntry 5 }

tmnxMobProfSgwChrgPriCdfDiaPeer  OBJECT-TYPE
    SYNTAX      TmnxMobProfNameOrEmpty
    MAX-ACCESS  read-create
    STATUS      current
    DESCRIPTION
        "The value of tmnxMobProfSgwChrgPriCdfDiaPeer specifies the primary 
         Charging Data Function (CDF) diameter peer profile for this charging 
         profile.

         If a corresponding diameter peer profile does not exist in
         tmnxMobProfDiaPeerTable, an 'inconsistentValue' error will be 
         returned."
    DEFVAL { ''H }
    ::= { tmnxMobProfSgwChargingEntry 6 }

tmnxMobProfSgwChrgSecCdfDiaPeer  OBJECT-TYPE
    SYNTAX      TmnxMobProfNameOrEmpty
    MAX-ACCESS  read-create
    STATUS      current
    DESCRIPTION
        "The value of tmnxMobProfSgwChrgSecCdfDiaPeer specifies the secondary 
         Charging Data Function (CDF) diameter peer profile for this charging 
         profile.

         If a corresponding diameter peer profile does not exist in
         tmnxMobProfDiaPeerTable, an 'inconsistentValue' error will be 
         returned."
    DEFVAL { ''H }
    ::= { tmnxMobProfSgwChargingEntry 7 }

tmnxMobProfSgwChrgCitQosChange  OBJECT-TYPE
    SYNTAX      TmnxEnabledDisabled
    MAX-ACCESS  read-create
    STATUS      current
    DESCRIPTION
        "The value of tmnxMobProfSgwChrgCitQosChange specifies whether the 
         QoS-Change trigger is enabled, which results in List of Traffic
         Data Volumes container charging information added to the Charging Data
         Record (CDR) when there is a change in Qos."
    DEFVAL { disabled }
    ::= { tmnxMobProfSgwChargingEntry 8 }

tmnxMobProfSgwChrgCitUsrLocChnge  OBJECT-TYPE
    SYNTAX      TmnxEnabledDisabled
    MAX-ACCESS  read-create
    STATUS      current
    DESCRIPTION
        "The value of tmnxMobProfSgwChrgCitQosChange specifies whether the 
         User Location Change trigger is enabled, which results in List 
         of Traffic Data Volumes container charging information added to the 
         Charging Data Record (CDR) when there is a change in Qos."
    DEFVAL { disabled }
    ::= { tmnxMobProfSgwChargingEntry 9 }

tmnxMobProfSgwChrgCitTrfTimeChng  OBJECT-TYPE
    SYNTAX      TmnxEnabledDisabled
    MAX-ACCESS  read-create
    STATUS      current
    DESCRIPTION
        "The value of tmnxMobProfSgwChrgCitTrfTimeChng specifies whether the 
         Tarrif Time Change trigger is enabled, which results in List of
         Traffic Data Volumes container charging information added to the 
         Charging Data Record (CDR) when there is a change in tarrif time."
    DEFVAL { disabled }
    ::= { tmnxMobProfSgwChargingEntry 10 }

tmnxMobProfSgwChrgCitTrfTmStart  OBJECT-TYPE
    SYNTAX      TmnxTimeInSec
    MAX-ACCESS  read-create
    STATUS      current
    DESCRIPTION
        "The value of tmnxMobProfSgwChrgCitTrfTmStart specifies the start of 
         the Tarrif Time for the Charging Data Record (CDR)."
    DEFVAL { 0 }
    ::= { tmnxMobProfSgwChargingEntry 11 }

tmnxMobProfSgwChrgCitTrfTmEnd  OBJECT-TYPE
    SYNTAX      TmnxTimeInSec
    MAX-ACCESS  read-create
    STATUS      current
    DESCRIPTION
        "The value of tmnxMobProfSgwChrgCitTrfTmEnd specifies the end of the 
         Tarrif Time for the Charging Data Record (CDR)."
    DEFVAL { 0 }
    ::= { tmnxMobProfSgwChargingEntry 12 }

tmnxMobProfSgwChrgPrctTimeLmt  OBJECT-TYPE
    SYNTAX      Unsigned32 (0..86400)
    UNITS       "seconds"
    MAX-ACCESS  read-create
    STATUS      current
    DESCRIPTION
        "The value of tmnxMobProfSgwChrgPrctTimeLmt specifies a time limit 
         (in seconds) applicable per session or bearer depending on the 
         accounting level selected like PDN-level accounting or QCI/bearer-level 
         accounting. A partial record is created when the specified time limit 
         is satisfied."
    DEFVAL { 3600 }
    ::= { tmnxMobProfSgwChargingEntry 13 }

tmnxMobProfSgwChrgPrctVolumeLmt  OBJECT-TYPE
    SYNTAX      Unsigned32 (0..65535)
    UNITS       "kbytes"
    MAX-ACCESS  read-create
    STATUS      current
    DESCRIPTION
        "The value of tmnxMobProfSgwChrgPrctVolumeLmt specifies a data volume 
         limit applicable per session or bearer depending on the accounting 
         level selected like PDN-level accounting or QCI/bearer-level 
         accounting. A partial record is created when the specified volume limit
         is satisfied."
    DEFVAL { 4096 }
    ::= { tmnxMobProfSgwChargingEntry 14 }

tmnxMobProfSgwChrgPrctMaxChCond  OBJECT-TYPE
    SYNTAX      Unsigned32 (0..32)
    MAX-ACCESS  read-create
    STATUS      current
    DESCRIPTION
        "The value of tmnxMobProfSgwChrgPrctMaxChCond specifies the maximum 
         number of change conditions that can occur like tariff change, location
         change before a partial record is created."
    DEFVAL { 0 }
    ::= { tmnxMobProfSgwChargingEntry 15 }

tmnxMobProfSgwChrgPrctMsTmzChnge  OBJECT-TYPE
    SYNTAX      TmnxEnabledDisabled
    MAX-ACCESS  read-create
    STATUS      current
    DESCRIPTION
        "The value of tmnxMobProfSgwChrgPrctMsTmzChnge specifies whether the MS 
         Time Zone Change partial record trigger is enabled. Upon 
         encountering a MS Time Zone change, a partial record is created."
    DEFVAL { disabled }
    ::= { tmnxMobProfSgwChargingEntry 16 }

tmnxMobProfSgwChrgPrctPlmnChange  OBJECT-TYPE
    SYNTAX      TmnxEnabledDisabled
    MAX-ACCESS  read-create
    STATUS      current
    DESCRIPTION
        "The value of tmnxMobProfSgwChrgPrctPlmnChange specifies whether the 
         plmn-change partial record trigger is enabled. Upon encountering
         a plmn-change, a partial record is created."
    DEFVAL { disabled }
    ::= { tmnxMobProfSgwChargingEntry 17 }

tmnxMobProfSgwChrgPrctRatChange  OBJECT-TYPE
    SYNTAX      TmnxEnabledDisabled
    MAX-ACCESS  read-create
    STATUS      current
    DESCRIPTION 
       "The value of tmnxMobProfSgwChrgPrctRatChange specifies whether the 
         rat-change partial record trigger is enabled. Upon encountering
         a rat-change, a partial record is created."
    DEFVAL { disabled }
    ::= { tmnxMobProfSgwChargingEntry 18 }

tmnxMobProfSgwChrgPrctMgmtInterv  OBJECT-TYPE
    SYNTAX      TmnxEnabledDisabled
    MAX-ACCESS  read-create
    STATUS      current
    DESCRIPTION
        "The value of tmnxMobProfSgwChrgPrctMgmtInterv specifies whether the 
         management intervention partial record trigger is enabled. Upon 
         management intervention, a partial record is created."
    DEFVAL { disabled }
    ::= { tmnxMobProfSgwChargingEntry 19 }

tmnxMobProfSgwChrgCitSgwChange  OBJECT-TYPE
    SYNTAX      TmnxEnabledDisabled
    MAX-ACCESS  read-create
    STATUS      obsolete
    DESCRIPTION
        "The value of tmnxMobProfSgwChrgCitSgwChange specifies whether the 
         Serving-Node-Change trigger is enabled, which results in List of
         Traffic Data Volumes container charging information added to the
         Charging Data Record (CDR) when there is a change in Mobility 
         Management Entity (MME).
  
         This object was made obsolete in the 3.0 release.
         "
    DEFVAL { disabled }
    ::= { tmnxMobProfSgwChargingEntry 20 }

tmnxMobProfSgwChrgPrctSrvNdChLmt  OBJECT-TYPE
    SYNTAX      Unsigned32 (0..15)
    MAX-ACCESS  read-create
    STATUS      current
    DESCRIPTION
        "The value of tmnxMobProfSgwChrgPrctSrvNdChLmt specifies a maximum limit 
         for the change in Serving Node. A partial record is
         created when the specified change limit is satisfied for this 
         Partial Record Closure Trigger(PRCT)."
    DEFVAL { 15 }
    ::= { tmnxMobProfSgwChargingEntry 21 }

--
--  PGW Charging table
--

tmnxMobProfPgwChargingTblLstChgd  OBJECT-TYPE
    SYNTAX      TimeStamp
    MAX-ACCESS  read-only
    STATUS      current
    DESCRIPTION
        "The value of tmnxMobProfPgwChargingTblLstChgd indicates the sysUpTime
         at the time of the last modification to tmnxMobProfPgwChargingTable by 
         adding, deleting an entry or change to a writable object in the table.

         If no changes were made to the table since the last re-initialization
         of the local network management subsystem, then this object contains
         a zero value."
    ::= { tmnxMobProfileGlobalObjs 16 }

tmnxMobProfPgwChargingTable  OBJECT-TYPE
    SYNTAX      SEQUENCE OF TmnxMobProfPgwChargingEntry
    MAX-ACCESS  not-accessible
    STATUS      current
    DESCRIPTION
        "The tmnxMobProfPgwChargingTable has an entry for each PGW profile
         configured on the system. PGW charging profile 
         defines charging parameters for the Packet Data Network Gateway (PGW)."
    ::= { tmnxMobProfileObjs 16 }

tmnxMobProfPgwChargingEntry  OBJECT-TYPE
    SYNTAX      TmnxMobProfPgwChargingEntry
    MAX-ACCESS  not-accessible
    STATUS      current
    DESCRIPTION
        "Each row entry represents a Packet Data Network Gateway (PGW) charging 
         profile defined in the system. Entries can be created and deleted by 
         the user.

         PGW charging profile 0 is created by the agent itself at system 
         initialization. It cannot be modified or deleted."
    INDEX { tmnxMobProfPgwChrgId }
    ::= { tmnxMobProfPgwChargingTable 1 }

TmnxMobProfPgwChargingEntry ::= SEQUENCE {
        tmnxMobProfPgwChrgId                TmnxMobChargingProfile,
        tmnxMobProfPgwChrgRowStatus         RowStatus,
        tmnxMobProfPgwChrgLastChanged       TimeStamp,
        tmnxMobProfPgwChrgDesc              TItemDescription,
        tmnxMobProfPgwChrgOffLineState      TmnxEnabledDisabled,
        tmnxMobProfPgwChrgPriCdfDiaPeer     TmnxMobProfNameOrEmpty,
        tmnxMobProfPgwChrgSecCdfDiaPeer     TmnxMobProfNameOrEmpty,
        tmnxMobProfPgwChrgCitQosChange      TmnxEnabledDisabled, 
        tmnxMobProfPgwChrgCitUsrLocChnge    TmnxEnabledDisabled,
        tmnxMobProfPgwChrgCitTrfTimeChng    TmnxEnabledDisabled,
        tmnxMobProfPgwChrgCitTrfTmStart     TmnxTimeInSec,
        tmnxMobProfPgwChrgCitTrfTmEnd       TmnxTimeInSec,
        tmnxMobProfPgwChrgCitSgwChange      TmnxEnabledDisabled,
        tmnxMobProfPgwChrgCitTimeLmtRg      Unsigned32,
        tmnxMobProfPgwChrgCitVolumeLmtRg    Unsigned32,
        tmnxMobProfPgwChrgCitTermServDf     TmnxEnabledDisabled,
        tmnxMobProfPgwChrgPrctTimeLmt       Unsigned32,
        tmnxMobProfPgwChrgPrctVolumeLmt     Unsigned32,
        tmnxMobProfPgwChrgPrctMaxChCond     Unsigned32,
        tmnxMobProfPgwChrgPrctMsTmzChnge    TmnxEnabledDisabled,
        tmnxMobProfPgwChrgPrctPlmnChange    TmnxEnabledDisabled,
        tmnxMobProfPgwChrgPrctRatChange     TmnxEnabledDisabled,
        tmnxMobProfPgwChrgGyState           TmnxEnabledDisabled,
        tmnxMobProfPgwGyPriOcsDiaPeer       TmnxMobProfNameOrEmpty,
        tmnxMobProfPgwGySecOcsDiaPeer       TmnxMobProfNameOrEmpty,
        tmnxMobProfPgwGyDccaProf            TmnxMobProfNameOrEmpty,
        tmnxMobProfPgwChrgPrctSrvNdChLmt    Unsigned32
    }

tmnxMobProfPgwChrgId  OBJECT-TYPE
    SYNTAX      TmnxMobChargingProfile
    MAX-ACCESS  not-accessible
    STATUS      current
    DESCRIPTION
        "The value of tmnxMobProfPgwChrgId uniquely identifies a charging 
         profile configured for the Packet Data Network Gateway (PGW)."
    ::= { tmnxMobProfPgwChargingEntry 1 }

tmnxMobProfPgwChrgRowStatus  OBJECT-TYPE
    SYNTAX      RowStatus
    MAX-ACCESS  read-create
    STATUS      current
    DESCRIPTION
        "The value of tmnxMobProfPgwChrgRowStatus specifies the row status of
         this entry. It is used for creation and deletion of this charging
         profile."
    ::= { tmnxMobProfPgwChargingEntry 2 }

tmnxMobProfPgwChrgLastChanged  OBJECT-TYPE
    SYNTAX      TimeStamp
    MAX-ACCESS  read-only
    STATUS      current
    DESCRIPTION
        "The value of tmnxMobProfPgwChrgLastChanged indicates the timestamp of
         the last change to this row in tmnxMobProfPgwChargingTable."
    ::= { tmnxMobProfPgwChargingEntry 3 }

tmnxMobProfPgwChrgDesc  OBJECT-TYPE
    SYNTAX      TItemDescription
    MAX-ACCESS  read-create
    STATUS      current
    DESCRIPTION
        "The value of tmnxMobProfPgwChrgDesc is a user provided description
         string for this charging profile for the Packet Data Network Gateway 
         (PGW)." 
    DEFVAL { ''H }
    ::= { tmnxMobProfPgwChargingEntry 4 }

tmnxMobProfPgwChrgOffLineState  OBJECT-TYPE
    SYNTAX      TmnxEnabledDisabled
    MAX-ACCESS  read-create
    STATUS      current
    DESCRIPTION
        "The value of tmnxMobProfPgwChrgOffLineState specifies whether offline 
         charging is enabled for this charging profile for the Packet Data 
         Network Gateway (PGW)."
    DEFVAL { disabled }
    ::= { tmnxMobProfPgwChargingEntry 5 }

tmnxMobProfPgwChrgPriCdfDiaPeer  OBJECT-TYPE
    SYNTAX      TmnxMobProfNameOrEmpty
    MAX-ACCESS  read-create
    STATUS      current
    DESCRIPTION
        "The value of tmnxMobProfPgwChrgPriCdfDiaPeer specifies the primary 
         Charging Data Function (CDF) diameter peer profile for this charging 
         profile.

         If a corresponding diameter peer profile does not exist in
         tmnxMobProfDiaPeerTable, an 'inconsistentValue' error will be 
         returned."
    DEFVAL { ''H }
    ::= { tmnxMobProfPgwChargingEntry 6 }

tmnxMobProfPgwChrgSecCdfDiaPeer  OBJECT-TYPE
    SYNTAX      TmnxMobProfNameOrEmpty
    MAX-ACCESS  read-create
    STATUS      current
    DESCRIPTION
        "The value of tmnxMobProfPgwChrgSecCdfDiaPeer specifies the secondary 
         Charging Data Function (CDF) diameter peer profile for this charging 
         profile.

         If a corresponding diameter peer profile does not exist in
         tmnxMobProfDiaPeerTable, an 'inconsistentValue' error will be 
         returned."
    DEFVAL { ''H }
    ::= { tmnxMobProfPgwChargingEntry 7 }

tmnxMobProfPgwChrgCitQosChange  OBJECT-TYPE
    SYNTAX      TmnxEnabledDisabled
    MAX-ACCESS  read-create
    STATUS      current
    DESCRIPTION
        "The value of tmnxMobProfPgwChrgCitQosChange specifies whether the 
         QoS-Change trigger is enabled, which results in List of Traffic
         Data Volumes container charging information added to the Charging Data
         Record (CDR) when there is a change in Qos."
    DEFVAL { disabled }
    ::= { tmnxMobProfPgwChargingEntry 8 }

tmnxMobProfPgwChrgCitUsrLocChnge  OBJECT-TYPE
    SYNTAX      TmnxEnabledDisabled
    MAX-ACCESS  read-create
    STATUS      current
    DESCRIPTION
        "The value of tmnxMobProfPgwChrgCitQosChange specifies whether the 
         User Location Change trigger is enabled, which results in List 
         of Traffic Data Volumes container charging information added to the 
         Charging Data Record (CDR) when there is a change in Qos."
    DEFVAL { disabled }
    ::= { tmnxMobProfPgwChargingEntry 9 }

tmnxMobProfPgwChrgCitTrfTimeChng  OBJECT-TYPE
    SYNTAX      TmnxEnabledDisabled
    MAX-ACCESS  read-create
    STATUS      current
    DESCRIPTION
        "The value of tmnxMobProfPgwChrgCitTrfTimeChng specifies whether the 
         Tarrif Time Change trigger is enabled, which results in List of
         Traffic Data Volumes container charging information added to the 
         Charging Data Record (CDR) when there is a change in tarrif time."
    DEFVAL { disabled }
    ::= { tmnxMobProfPgwChargingEntry 10 }

tmnxMobProfPgwChrgCitTrfTmStart  OBJECT-TYPE
    SYNTAX      TmnxTimeInSec
    MAX-ACCESS  read-create
    STATUS      current
    DESCRIPTION
        "The value of tmnxMobProfPgwChrgCitTrfTmStart specifies the start of 
         the Tarrif Time for the Charging Data Record (CDR)."
    DEFVAL { 0 }
    ::= { tmnxMobProfPgwChargingEntry 11 }

tmnxMobProfPgwChrgCitTrfTmEnd  OBJECT-TYPE
    SYNTAX      TmnxTimeInSec
    MAX-ACCESS  read-create
    STATUS      current
    DESCRIPTION
        "The value of tmnxMobProfPgwChrgCitTrfTmEnd specifies the end of the 
         Tarrif Time for the Charging Data Record (CDR)."
    DEFVAL { 0 }
    ::= { tmnxMobProfPgwChargingEntry 12 }

tmnxMobProfPgwChrgCitSgwChange  OBJECT-TYPE
    SYNTAX      TmnxEnabledDisabled
    MAX-ACCESS  read-create
    STATUS      current
    DESCRIPTION
        "The value of tmnxMobProfPgwChrgCitSgwChange specifies whether the 
         Serving-Node-Change trigger is enabled, which results in List of
         Traffic Data Volumes container charging information added to the
         Charging Data Record (CDR) when there is a change in Serving
         Gateway (SGW)."
    DEFVAL { disabled }
    ::= { tmnxMobProfPgwChargingEntry 13 }

tmnxMobProfPgwChrgCitTimeLmtRg  OBJECT-TYPE
    SYNTAX      Unsigned32 (0..86400)
    UNITS       "seconds"
    MAX-ACCESS  read-create
    STATUS      current
    DESCRIPTION
        "The value of tmnxMobProfPgwChrgCitTimeLmtRg specifies a time limit 
         (in seconds) applicable per rating group, which results in List of 
         Traffic Data Volumes container charging information added to the 
         Charging Data Record (CDR) when the time limit is reached."
    DEFVAL { 1800 }
    ::= { tmnxMobProfPgwChargingEntry 16 }

tmnxMobProfPgwChrgCitVolumeLmtRg  OBJECT-TYPE
    SYNTAX      Unsigned32 (0..32768)
    UNITS       "kbytes"
    MAX-ACCESS  read-create
    STATUS      current
    DESCRIPTION
        "The value of tmnxMobProfPgwChrgCitVolumeLmtRg specifies a data volume 
         limit applicable per rating group, which results in List of 
         Traffic Data Volumes container charging information added to the 
         Charging Data Record (CDR) when the volume limit is reached."
    DEFVAL { 2048 }
    ::= { tmnxMobProfPgwChargingEntry 17 }

tmnxMobProfPgwChrgCitTermServDf  OBJECT-TYPE
    SYNTAX      TmnxEnabledDisabled
    MAX-ACCESS  read-create
    STATUS      current
    DESCRIPTION
        "The value of tmnxMobProfPgwChrgCitTermServDf specifies whether the 
         termination of service data flow trigger is enabled, which results in 
         List of Traffic Data Volumes container charging information added to 
         the Charging Data Record (CDR) when the service data flow is 
         terminated."
    DEFVAL { disabled }
    ::= { tmnxMobProfPgwChargingEntry 18 }

tmnxMobProfPgwChrgPrctTimeLmt  OBJECT-TYPE
    SYNTAX      Unsigned32 (0..86400)
    UNITS       "seconds"
    MAX-ACCESS  read-create
    STATUS      current
    DESCRIPTION
        "The value of tmnxMobProfPgwChrgPrctTimeLmt specifies a time limit 
         (in seconds) applicable per session or bearer depending on the 
         accounting level selected like PDN-level accounting or QCI/bearer-level 
         accounting. A partial record is created when the specified time limit 
         is satisfied."
    DEFVAL { 3600 }
    ::= { tmnxMobProfPgwChargingEntry 19 }

tmnxMobProfPgwChrgPrctVolumeLmt  OBJECT-TYPE
    SYNTAX      Unsigned32 (0..65535)
    UNITS       "kbytes"
    MAX-ACCESS  read-create
    STATUS      current
    DESCRIPTION
        "The value of tmnxMobProfPgwChrgPrctVolumeLmt specifies a data volume 
         limit applicable per session or bearer depending on the accounting 
         level selected like PDN-level accounting or QCI/bearer-level 
         accounting. A partial record is created when the specified volume limit
         is satisfied."
    DEFVAL { 4096 }
    ::= { tmnxMobProfPgwChargingEntry 20 }

tmnxMobProfPgwChrgPrctMaxChCond  OBJECT-TYPE
    SYNTAX      Unsigned32 (0..32)
    MAX-ACCESS  read-create
    STATUS      current
    DESCRIPTION
        "The value of tmnxMobProfPgwChrgPrctMaxChCond specifies the maximum 
         number of change conditions that can occur like tariff change, location
         change before a partial record is created."
    DEFVAL { 0 }
    ::= { tmnxMobProfPgwChargingEntry 21 }

tmnxMobProfPgwChrgPrctMsTmzChnge  OBJECT-TYPE
    SYNTAX      TmnxEnabledDisabled
    MAX-ACCESS  read-create
    STATUS      current
    DESCRIPTION
        "The value of tmnxMobProfPgwChrgPrctMsTmzChnge specifies whether the MS 
         Time Zone Change partial record trigger is enabled. Upon 
         encountering a MS Time Zone change, a partial record is created."
    DEFVAL { disabled }
    ::= { tmnxMobProfPgwChargingEntry 22 }

tmnxMobProfPgwChrgPrctPlmnChange  OBJECT-TYPE
    SYNTAX      TmnxEnabledDisabled
    MAX-ACCESS  read-create
    STATUS      current
    DESCRIPTION
        "The value of tmnxMobProfPgwChrgPrctPlmnChange specifies whether the 
         plmn-change partial record trigger is enabled. Upon encountering
         a plmn-change, a partial record is created."
    DEFVAL { disabled }
    ::= { tmnxMobProfPgwChargingEntry 23 }

tmnxMobProfPgwChrgPrctRatChange  OBJECT-TYPE
    SYNTAX      TmnxEnabledDisabled
    MAX-ACCESS  read-create
    STATUS      current
    DESCRIPTION 
       "The value of tmnxMobProfPgwChrgPrctRatChange specifies whether the 
         rat-change partial record trigger is enabled. Upon encountering
         a rat-change, a partial record is created."
    DEFVAL { disabled }
    ::= { tmnxMobProfPgwChargingEntry 24 }

tmnxMobProfPgwChrgGyState  OBJECT-TYPE
    SYNTAX      TmnxEnabledDisabled
    MAX-ACCESS  read-create
    STATUS      current
    DESCRIPTION
        "The value of tmnxMobProfPgwChrgGyState specifies whether online 
         charging (Gy) is enabled for this charging profile for the Packet Data 
         Network Gateway (PGW)."
    DEFVAL { disabled }
    ::= { tmnxMobProfPgwChargingEntry 25 }

tmnxMobProfPgwGyPriOcsDiaPeer  OBJECT-TYPE
    SYNTAX      TmnxMobProfNameOrEmpty
    MAX-ACCESS  read-create
    STATUS      current
    DESCRIPTION
        "The value of tmnxMobProfPgwGyPriOcsDiaPeer specifies the primary 
         Online Charging System (OCS) diameter peer profile for this online 
         charging (Gy) profile.

         If a corresponding diameter peer profile does not exist in
         tmnxMobProfDiaPeerTable, an 'inconsistentValue' error will be 
         returned."
    DEFVAL { ''H }
    ::= { tmnxMobProfPgwChargingEntry 26 }

tmnxMobProfPgwGySecOcsDiaPeer  OBJECT-TYPE
    SYNTAX      TmnxMobProfNameOrEmpty
    MAX-ACCESS  read-create
    STATUS      current
    DESCRIPTION
        "The value of tmnxMobProfPgwGySecOcsDiaPeer specifies the secondary 
         Online Charging System (OCS) diameter peer profile for this online 
         charging (Gy) profile.

         If a corresponding diameter peer profile does not exist in
         tmnxMobProfDiaPeerTable, an 'inconsistentValue' error will be 
         returned."
    DEFVAL { ''H }
    ::= { tmnxMobProfPgwChargingEntry 27 }

tmnxMobProfPgwGyDccaProf  OBJECT-TYPE
    SYNTAX      TmnxMobProfNameOrEmpty
    MAX-ACCESS  read-create
    STATUS      current
    DESCRIPTION
        "The value of tmnxMobProfPgwGyDccaProf specifies Diameter Credit Control
         Application (DCCA) profile used for the primary and secondary 
         Online Charging System (OCS) for this Online charging (Gy) profile.

         If a corresponding diameter peer profile does not exist in
         tmnxMobProfDiaPeerTable, an 'inconsistentValue' error will be 
         returned."
    DEFVAL { ''H }
    ::= { tmnxMobProfPgwChargingEntry 28 }

tmnxMobProfPgwChrgPrctSrvNdChLmt  OBJECT-TYPE
    SYNTAX      Unsigned32 (0..15)
    MAX-ACCESS  read-create
    STATUS      current
    DESCRIPTION
        "The value of tmnxMobProfPgwChrgPrctSrvNdChLmt specifies a maximum limit 
         for the change in Serving Node. A partial record is created when
         the specified change limit is satisfied  for this Partial Record
         Closure Trigger(PRCT)."
    DEFVAL { 15 }
    ::= { tmnxMobProfPgwChargingEntry 29 }

--
--  Charging Gateway Group Table
--

tmnxMobGtpPriGrpTblLstChgd  OBJECT-TYPE
    SYNTAX      TimeStamp
    MAX-ACCESS  read-only
    STATUS      current
    DESCRIPTION
        "The value of tmnxMobGtpPriGrpTblLstChgd indicates the sysUpTime at
         the time of the last modification to tmnxMobGtpPriGrpTable by adding,
         deleting an entry or change to a writable object in the table.

         If no changes were made to the table since the last re-initialization
         of the local network management subsystem, then this object contains
         a zero value."
    ::= { tmnxMobProfileGlobalObjs 17 }

tmnxMobGtpPriGrpTable  OBJECT-TYPE
    SYNTAX      SEQUENCE OF TmnxMobGtpPriGrpEntry
    MAX-ACCESS  not-accessible
    STATUS      current
    DESCRIPTION
        "The tmnxMobGtpPriGrpTable has an entry for each GPRS Tunneling Protocol
         (GTP) Prime Server Group configured on the system. It defines GTP prime
          server parameters."
    ::= { tmnxMobProfileObjs 17 }

tmnxMobGtpPriGrpEntry  OBJECT-TYPE
    SYNTAX      TmnxMobGtpPriGrpEntry
    MAX-ACCESS  not-accessible
    STATUS      current
    DESCRIPTION
        "Each row entry represents a GPRS Tunneling Protocol (GTP) Prime Server 
         Group defined in the system. Entries can be created and deleted by the
         user."
    INDEX { tmnxMobGtpPriGrpName }
    ::= { tmnxMobGtpPriGrpTable 1 }

TmnxMobGtpPriGrpEntry ::= SEQUENCE {
        tmnxMobGtpPriGrpName                TmnxMobProfName,
        tmnxMobGtpPriGrpRowStatus           RowStatus,
        tmnxMobGtpPriGrpLastChanged         TimeStamp,
        tmnxMobGtpPriGrpDescription         TItemDescription,
        tmnxMobGtpPriGrpMaxCdrsPerPdu       Unsigned32,
        tmnxMobGtpPriGrpDeadtime            Unsigned32,
        tmnxMobGtpPriGrpRedirection         TruthValue,
        tmnxMobGtpPriGrpIfVRtrId            TmnxVRtrID,
        tmnxMobGtpPriGrpIfIndex             InterfaceIndexOrZero,
        tmnxMobGtpPriGrpLocalCdrStorage     TmnxEnabledDisabled,
        tmnxMobGtpPriGrpFilePrivateInfo     TNamedItemOrEmpty,
        tmnxMobGtpPriGrpFileExtension       DisplayString,
        tmnxMobGtpPriGrpFileClosureSize     Unsigned32,
        tmnxMobGtpPriGrpFileClsLifeTime     Unsigned32,
        tmnxMobGtpPriGrpFileClsMaxRecs      Unsigned32,
        tmnxMobGtpPriGrpFileObsoleteTime    Unsigned32,
        tmnxMobGtpPriGrpPrimaryCf           INTEGER,
        tmnxMobGtpPriGrpCf1State            TruthValue,
        tmnxMobGtpPriGrpCf1Limit            Unsigned32,
        tmnxMobGtpPriGrpCf2State            TruthValue,
        tmnxMobGtpPriGrpCf2Limit            Unsigned32,
        tmnxMobGtpPriGrpCpmMemoryState      TruthValue,  
        tmnxMobGtpPriGrpQueueSize           Unsigned32,
        tmnxMobGtpPriGrpAdminState          TmnxAdminState,
        tmnxMobGtpPriGrpInactiveTimer       Unsigned32
    }

tmnxMobGtpPriGrpName  OBJECT-TYPE
    SYNTAX      TmnxMobProfName 
    MAX-ACCESS  not-accessible
    STATUS      current
    DESCRIPTION
        "The value of tmnxMobGtpPriGrpName specifies the unique name of this
         GPRS Tunneling Protocol (GTP) Prime Server Group."
    ::= { tmnxMobGtpPriGrpEntry 1 }

tmnxMobGtpPriGrpRowStatus  OBJECT-TYPE
    SYNTAX      RowStatus
    MAX-ACCESS  read-create
    STATUS      current
    DESCRIPTION
        "The value of tmnxMobGtpPriGrpRowStatus specifies the row status of
         this entry. It is used for creation and deletion of this GPRS Tunneling
         Protocol (GTP) Prime Server Group."
    ::= { tmnxMobGtpPriGrpEntry 2 }

tmnxMobGtpPriGrpLastChanged  OBJECT-TYPE
    SYNTAX      TimeStamp
    MAX-ACCESS  read-only
    STATUS      current
    DESCRIPTION
        "The value of tmnxMobGtpPriGrpLastChanged indicates the timestamp of
         the last change to this row in tmnxMobGtpPriGrpTable."
    ::= { tmnxMobGtpPriGrpEntry 3 }

tmnxMobGtpPriGrpDescription  OBJECT-TYPE
    SYNTAX      TItemDescription
    MAX-ACCESS  read-create
    STATUS      current
    DESCRIPTION
        "The value of tmnxMobGtpPriGrpDescription specifies the description
         string for this GPRS Tunneling Protocol (GTP) Prime Server Group. 
         It can consist of any printable, seven-bit ASCII characters up to 80
         characters in length."
    DEFVAL { ''H }
    ::= { tmnxMobGtpPriGrpEntry 4 }

tmnxMobGtpPriGrpMaxCdrsPerPdu  OBJECT-TYPE
    SYNTAX      Unsigned32 (0..100)
    MAX-ACCESS  read-create
    STATUS      current
    DESCRIPTION
        "The value of tmnxMobGtpPriGrpMaxCdrsPerPdu specifies the maximum 
         number of the Charging Data Records (CDR) that can be placed in a 
         single GTP Prime Server PDU. The number of CDRs will also be bound by
         the size of the GPRS Tunneling Protocol (GTP) Prime Server PDU."
    DEFVAL { 0 }
    ::= { tmnxMobGtpPriGrpEntry 5 }

tmnxMobGtpPriGrpDeadtime  OBJECT-TYPE
    SYNTAX      Unsigned32 (0..3600)
    UNITS       "seconds"
    MAX-ACCESS  read-create
    STATUS      current
    DESCRIPTION
        "The value of tmnxMobGtpPriGrpDeadtime specifies the time that a server 
         should be considered dead before it may be used again."
    DEFVAL { 0 }
    ::= { tmnxMobGtpPriGrpEntry 6 }

tmnxMobGtpPriGrpRedirection  OBJECT-TYPE
    SYNTAX      TruthValue
    MAX-ACCESS  read-create
    STATUS      current
    DESCRIPTION
        "The value of tmnxMobGtpPriGrpRedirection specifies whether the GPRS 
         Tunneling Protocol (GTP) Prime Server redirection function is enabled.
         Enabling the redirection function allows the Charging Gateway Function
         (CGF) to inform the system when it is about to go out of service and it
         should cause the system to select a different CGF."
    DEFVAL { false }
    ::= { tmnxMobGtpPriGrpEntry 7 }

tmnxMobGtpPriGrpIfVRtrId  OBJECT-TYPE
    SYNTAX      TmnxVRtrID
    MAX-ACCESS  read-create
    STATUS      current
    DESCRIPTION
        "The value of tmnxMobGtpPriGrpIfVRtrId specifies the virtual
         router to which the interface specified by tmnxMobGtpPriGrpIfIndex
         belongs."
    DEFVAL { 1 }
    ::= { tmnxMobGtpPriGrpEntry 8 }

tmnxMobGtpPriGrpIfIndex  OBJECT-TYPE
    SYNTAX      InterfaceIndexOrZero
    MAX-ACCESS  read-create
    STATUS      current
    DESCRIPTION
        "The value of tmnxMobGtpPriGrpIfIndex specifies the interface index of
         the local interface used by this GPRS Tunneling Protocol (GTP) Prime
         Server Group. 

         The interface index at the profile level overrides the interface index 
         at the gateway level."
    DEFVAL { 0 }
    ::= { tmnxMobGtpPriGrpEntry 9 }

tmnxMobGtpPriGrpLocalCdrStorage  OBJECT-TYPE
    SYNTAX      TmnxEnabledDisabled
    MAX-ACCESS  read-create
    STATUS      current
    DESCRIPTION
        "The value of tmnxMobGtpPriGrpLocalCdrStorage specifies whether local 
         Charging Data Records (CDR) is enabled. The local CDR storage should be
         be used only if the set of charging gateways are unreachable.  However,
         it is also possible to configure a gtp-prime-group that does not 
         contain any charging-gateways (gtp-prime-servers). In that case the 
         local storage target would be considered the primary option."
    DEFVAL { disabled }
    ::= { tmnxMobGtpPriGrpEntry 10 }

tmnxMobGtpPriGrpFilePrivateInfo  OBJECT-TYPE
    SYNTAX      TNamedItemOrEmpty
    MAX-ACCESS  read-create
    STATUS      current
    DESCRIPTION
        "The value of tmnxMobGtpPriGrpFilePrivateInfo specifies an operator 
         configurable file private information field that is used in the file 
         name."
    DEFVAL { ''H }
    ::= { tmnxMobGtpPriGrpEntry 11 }

tmnxMobGtpPriGrpFileExtension  OBJECT-TYPE
    SYNTAX      DisplayString (SIZE (0..8))
    MAX-ACCESS  read-create
    STATUS      current
    DESCRIPTION
        "The value of tmnxMobGtpPriGrpFileExtension specifies an operator 
         configurable file extension field that is used in the file name."
    DEFVAL { ''H }
    ::= { tmnxMobGtpPriGrpEntry 12 }

tmnxMobGtpPriGrpFileClosureSize  OBJECT-TYPE
    SYNTAX      Unsigned32 (1..100)
    UNITS       "megabytes"
    MAX-ACCESS  read-create
    STATUS      current
    DESCRIPTION
        "The value of tmnxMobGtpPriGrpFileClosureSize specifies an operator 
         configurable file closure size limit."
    DEFVAL { 50 }
    ::= { tmnxMobGtpPriGrpEntry 13 }

tmnxMobGtpPriGrpFileClsLifeTime  OBJECT-TYPE
    SYNTAX      Unsigned32 (1..24)
    UNITS       "hours"
    MAX-ACCESS  read-create
    STATUS      current
    DESCRIPTION
        "The value of tmnxMobGtpPriGrpFileClsLifeTime specifies an operator 
         configurable file closure lifetime. The file is closed after the 
         specified duration."
    DEFVAL { 1 }
    ::= { tmnxMobGtpPriGrpEntry 14 }

tmnxMobGtpPriGrpFileClsMaxRecs  OBJECT-TYPE
    SYNTAX      Unsigned32 (100..75000)
    MAX-ACCESS  read-create
    STATUS      current
    DESCRIPTION
        "The value of tmnxMobGtpPriGrpFileClsMaxRecs specifies an operator 
         configurable limit for the number of Charging Data Records (CDR) that 
         are stored in a file. The file is closed after the specified limit is
         reached."
    DEFVAL { 50000 }
    ::= { tmnxMobGtpPriGrpEntry 15 }

tmnxMobGtpPriGrpFileObsoleteTime  OBJECT-TYPE
    SYNTAX      Unsigned32 (1..31)
    UNITS       "days"
    MAX-ACCESS  read-create
    STATUS      current
    DESCRIPTION
        "The value of tmnxMobGtpPriGrpFileObsoleteTime specifies an operator 
         configurable file duration, after which the file is deleted."
    DEFVAL { 7 }
    ::= { tmnxMobGtpPriGrpEntry 16 }

tmnxMobGtpPriGrpPrimaryCf  OBJECT-TYPE
    SYNTAX      INTEGER {
                         cf1    (1),
                         cf2    (2)
                        }
    MAX-ACCESS  read-create
    STATUS      current
    DESCRIPTION
        "The value of tmnxMobGtpPriGrpPrimaryCf specifies which compact flash
         will be used as a primary storage for the Charging Data Records (CDR)
         storage. 
 
         If the user tries to set the 'cf1' and if the 'cf1' is not available 
         then 'cf2' will be set as primary storage. If the user tries to set 
         the 'cf2' and if 'cf2' is not available then cf1 will be set as 
         primary storage."
    DEFVAL { cf1 }
    ::= { tmnxMobGtpPriGrpEntry 17 }

tmnxMobGtpPriGrpCf1State  OBJECT-TYPE
    SYNTAX      TruthValue
    MAX-ACCESS  read-create
    STATUS      current
    DESCRIPTION
        "The value of tmnxMobGtpPriGrpCf1State specifies whether the first 
         compact flash is enabled to be used for the Charging Data Records (CDR)
         storage. 
 
         If the compact flash is not available then it will be disabled."
    DEFVAL { true }
    ::= { tmnxMobGtpPriGrpEntry 18 }

tmnxMobGtpPriGrpCf1Limit  OBJECT-TYPE
    SYNTAX      Unsigned32
    UNITS       "megabytes"
    MAX-ACCESS  read-create
    STATUS      current
    DESCRIPTION
        "The value of tmnxMobGtpPriGrpCf1Limit specifies the limit 
         (in megabytes) for an amount of memory on the first compact flash that
         can be used for the Charging Data Records (CDR) storage. Once the 
         threshold has been reached, the system can no longer support accurate
         charging.
 
         If the compact flash is not available then tmnxMobGtpPriGrpCf1Limit 
         will be set to 0.   
 
         If tmnxMobGtpPriGrpCf1State is enabled and the value of 
         tmnxMobGtpPriGrpCf1Limit is 0, then maximum available memory on the 
         second compact flash can be used for the CDR storage."
    DEFVAL { 0 }
    ::= { tmnxMobGtpPriGrpEntry 19 }

tmnxMobGtpPriGrpCf2State  OBJECT-TYPE
    SYNTAX      TruthValue
    MAX-ACCESS  read-create
    STATUS      current
    DESCRIPTION
        "The value of tmnxMobGtpPriGrpCf2State specifies whether 
         the second compact flash is enabled to be used for the Charging Data 
         Record (CDR) storage.

         If the compact flash is not available then it will be disabled."
    DEFVAL { true }
    ::= { tmnxMobGtpPriGrpEntry 20 }

tmnxMobGtpPriGrpCf2Limit  OBJECT-TYPE
    SYNTAX      Unsigned32
    UNITS       "megabytes"
    MAX-ACCESS  read-create
    STATUS      current
    DESCRIPTION
        "The value of tmnxMobGtpPriGrpCf2Limit specifies the limit 
         (in megabytes) for an amount of memory on the second compact flash that
         can be used for the Charging Data Records (CDR) storage. Once the 
         threshold has been reached, the system can no longer support accurate
         charging.
         
         If the compact flash is not available then tmnxMobGtpPriGrpCf2Limit 
         will be set to 0.   
         
         If tmnxMobGtpPriGrpCf2State is enabled and the value of 
         tmnxMobGtpPriGrpCf2Limit is 0, then maximum available memory on the 
         second compact flash can be used for the CDR storage."
    DEFVAL { 0 }
    ::= { tmnxMobGtpPriGrpEntry 21 }

tmnxMobGtpPriGrpCpmMemoryState  OBJECT-TYPE
    SYNTAX      TruthValue
    MAX-ACCESS  read-create
    STATUS      current
    DESCRIPTION
        "The value of tmnxMobGtpPriGrpCpmMemoryState specifies whether the first 
         compact flash is enabled to be used for the Charging Data Records (CDR)
         storage. 
 
         If the compact flash is not available then it will be disabled."
    DEFVAL { false }
    ::= { tmnxMobGtpPriGrpEntry 22 }

tmnxMobGtpPriGrpQueueSize  OBJECT-TYPE
    SYNTAX      Unsigned32 (10000..500000)
    MAX-ACCESS  read-create
    STATUS      current
    DESCRIPTION
        "The value of tmnxMobGtpPriGrpQueueSize specifies the maximum number of 
         unsent GPRS Tunneling Protocol (GTP) packets cached in the Mobile 
         Gateway, waiting for atleast one Charging Gateway Function (CGF) to 
         come up. 

         Once this threshold is reached, all the cached GTP packets are stored 
         in the flash."
    DEFVAL { 100000 }
    ::= { tmnxMobGtpPriGrpEntry 23 }

tmnxMobGtpPriGrpAdminState  OBJECT-TYPE
    SYNTAX      TmnxAdminState
    MAX-ACCESS  read-create
    STATUS      current
    DESCRIPTION
        "The value of tmnxMobGtpPriServerAdminState specifies the desired 
         administrative state of this GPRS Tunneling Protocol (GTP) Prime Server 
         Group."
    DEFVAL { outOfService }
    ::= { tmnxMobGtpPriGrpEntry 24 }

tmnxMobGtpPriGrpInactiveTimer  OBJECT-TYPE
    SYNTAX      Unsigned32 (1..60)
    UNITS       "minutes"
    MAX-ACCESS  read-create
    STATUS      current
    DESCRIPTION
        "The value of tmnxMobGtpPriGrpInactiveTimer specifies the amount of 
         time the peer must remain inactive to store all the cached GPRS 
         Tunneling Protocol (GTP) packets in the flash."
    DEFVAL { 10 }
    ::= { tmnxMobGtpPriGrpEntry 25 }

--
-- GPRS Tunneling Protocol (GTP)Prime Server Table
--

tmnxMobGtpPriServerTblLstChgd  OBJECT-TYPE
    SYNTAX      TimeStamp
    MAX-ACCESS  read-only
    STATUS      current
    DESCRIPTION
        "The value of tmnxMobGtpPriServerTblLstChgd indicates the sysUpTime
         at the time of the last modification to tmnxMobGtpPriServerTable by
         adding, deleting an entry or change to a writable object in the table.

         If no changes were made to the table since the last re-initialization
         of the local network management subsystem, then this object contains
         a zero value."
    ::= { tmnxMobProfileGlobalObjs 18 }

tmnxMobGtpPriServerTable  OBJECT-TYPE
    SYNTAX      SEQUENCE OF TmnxMobGtpPriServerEntry
    MAX-ACCESS  not-accessible
    STATUS      current
    DESCRIPTION
        "The tmnxMobGtpPriServerTable has an entry for each GPRS Tunneling 
         Protocol (GTP) Prime Server configured for each GTP Prime Server Group 
         configured on the system."
    ::= { tmnxMobProfileObjs 18 }

tmnxMobGtpPriServerEntry  OBJECT-TYPE
    SYNTAX      TmnxMobGtpPriServerEntry
    MAX-ACCESS  not-accessible
    STATUS      current
    DESCRIPTION
        "Each row entry represents a IP address configured for each GPRS 
         Tunneling Protocol (GTP) Prime Server. Entries can be created and 
         deleted by the user."
    INDEX { tmnxMobGtpPriGrpName,
            tmnxMobGtpPriServerIndex
          }
    ::= { tmnxMobGtpPriServerTable 1 }

TmnxMobGtpPriServerEntry ::= SEQUENCE {
        tmnxMobGtpPriServerIndex        Unsigned32,
        tmnxMobGtpPriServerRowStatus    RowStatus,
        tmnxMobGtpPriServerLastChngd    TimeStamp,
        tmnxMobGtpPriServerAdminState   TmnxAdminState,
        tmnxMobGtpPriServerAddrType     InetAddressType,
        tmnxMobGtpPriServerAddr         InetAddress,
        tmnxMobGtpPriServerPort         InetPortNumber,
        tmnxMobGtpPriServerRetries      Unsigned32,
        tmnxMobGtpPriServerTimeout      Unsigned32,
        tmnxMobGtpPriServerEchoInterval Unsigned32,
        tmnxMobGtpPriServerMaxRequests  Unsigned32,
        tmnxMobGtpPriServerNodeAlive    TruthValue,
        tmnxMobGtpPriServerPriority     Unsigned32,
        tmnxMobGtpPriServerPathProtocol INTEGER
    }

tmnxMobGtpPriServerIndex  OBJECT-TYPE
    SYNTAX      Unsigned32
    MAX-ACCESS  not-accessible
    STATUS      current
    DESCRIPTION
        "The value of tmnxMobGtpPriServerIndex specifies the unique value
         which identifies this IP address entry."
    ::= { tmnxMobGtpPriServerEntry 1 }

tmnxMobGtpPriServerRowStatus  OBJECT-TYPE
    SYNTAX      RowStatus
    MAX-ACCESS  read-create
    STATUS      current
    DESCRIPTION
        "The value of tmnxMobGtpPriServerRowStatus specifies the row status
         of this entry. It is used for creation and deletion of this GPRS 
         Tunneling Protocol (GTP) primary server entry.

         In order for the row creation to succeed, values for 
         tmnxMobGtpPriServerAddrType, tmnxMobGtpPriServerAddr and 
         tmnxMobProfDiaPeerListPort must be included in the same SNMP SET PDU 
         as tmnxMobGtpPriServerRowStatus. Otherwise,
         the SET request will fail with an 'inconsistentValue' error."
    ::= { tmnxMobGtpPriServerEntry 2 }

tmnxMobGtpPriServerLastChngd  OBJECT-TYPE
    SYNTAX      TimeStamp
    MAX-ACCESS  read-only
    STATUS      current
    DESCRIPTION
        "The value of tmnxMobGtpPriServerLastChngd indicates the timestamp of
         the last change to this row in tmnxMobGtpPriServerTable."
    ::= { tmnxMobGtpPriServerEntry 3 }

tmnxMobGtpPriServerAdminState  OBJECT-TYPE
    SYNTAX      TmnxAdminState
    MAX-ACCESS  read-create
    STATUS      current
    DESCRIPTION
        "The value of tmnxMobGtpPriServerAdminState specifies the desired 
         administrative state of this GPRS Tunneling Protocol (GTP) primary
         server."
    DEFVAL { outOfService }
    ::= { tmnxMobGtpPriServerEntry 4 }

tmnxMobGtpPriServerAddrType  OBJECT-TYPE
    SYNTAX      InetAddressType
    MAX-ACCESS  read-create
    STATUS      current
    DESCRIPTION
        "The value of tmnxMobGtpPriServerAddrType specifies the type of
         address represented by tmnxMobGtpPriServerAddr.

         The value of this object cannot be modified once the row has been 
         created."
    ::= { tmnxMobGtpPriServerEntry 5 }

tmnxMobGtpPriServerAddr  OBJECT-TYPE
    SYNTAX      InetAddress (SIZE (1..255))
    MAX-ACCESS  read-create
    STATUS      current
    DESCRIPTION
        "The value of tmnxMobGtpPriServerAddr specifies the IP address of
         the peer for which this entry contains information. If the value of
         the corresponsding tmnxMobGtpPriServerAddrType is 'dns', then the
         IP address for this Peer will be obtained via DNS A-Record query.

         The value of this object cannot be modified once the row has been 
         created."
    ::= { tmnxMobGtpPriServerEntry 6 }

tmnxMobGtpPriServerPort  OBJECT-TYPE
    SYNTAX      InetPortNumber
    MAX-ACCESS  read-create
    STATUS      current
    DESCRIPTION
        "The value of tmnxMobGtpPriServerPort specifies the destination TCP 
         or UDP port number for GTP Prime Server.

         The value of this object cannot be modified once the row has been 
         created."
    DEFVAL { 3386 }
    ::= { tmnxMobGtpPriServerEntry 7 }

tmnxMobGtpPriServerRetries  OBJECT-TYPE
    SYNTAX      Unsigned32 (1..8)
    MAX-ACCESS  read-create
    STATUS      current
    DESCRIPTION
        "The value of tmnxMobGtpPriServerRetries specifies the number of times 
         the system will attempt to send a GPRS Tunneling Protocol (GTP) Prime
         Server PDU to a Charging Gateway Function (CGF)."
    DEFVAL { 4 }
    ::= { tmnxMobGtpPriServerEntry 8 }

tmnxMobGtpPriServerTimeout  OBJECT-TYPE
    SYNTAX      Unsigned32 (1..180)
    UNITS       "seconds"
    MAX-ACCESS  read-create
    STATUS      current
    DESCRIPTION
        "The value of tmnxMobGtpPriServerTimeout specifies the interval between
         GPRS Tunneling Protocol (GTP) Prime Server PDU retries."
    DEFVAL { 20 }
    ::= { tmnxMobGtpPriServerEntry 9 }

tmnxMobGtpPriServerEchoInterval  OBJECT-TYPE
    SYNTAX      Unsigned32 (1..3600)
    UNITS       "seconds"
    MAX-ACCESS  read-create
    STATUS      current
    DESCRIPTION
        "The value of tmnxMobGtpPriServerEchoInterval specifies the interval at
         which the system should send echo-requests for the GPRS Tunneling 
         Protocol (GTP) Prime Server PDUs used to send the Charging Data Records
         (CDR)."
    DEFVAL { 60 }
    ::= { tmnxMobGtpPriServerEntry 10 }

tmnxMobGtpPriServerMaxRequests  OBJECT-TYPE
    SYNTAX      Unsigned32 (1..512)
    MAX-ACCESS  read-create
    STATUS      current
    DESCRIPTION
        "The value of tmnxMobGtpPriServerMaxRequests specifies the maximum 
         number of unacknowledged GPRS Tunneling Protocol (GTP) Prime Server 
         PDUs before the system stops sending the Charging Data Records (CDR)."
    DEFVAL { 256 }
    ::= { tmnxMobGtpPriServerEntry 11 }

tmnxMobGtpPriServerNodeAlive  OBJECT-TYPE
    SYNTAX      TruthValue
    MAX-ACCESS  read-create
    STATUS      current
    DESCRIPTION
        "The value of tmnxMobGtpPriServerNodeAlive specifies whethere the GPRS
         Tunneling Protocol (GTP) Prime Server node alive mechanism is enabled.
         This mechanism results in a quicker restart than the echo protocol. 
         This command will also enable the system to respond to Node Alive 
         Requests from the Charging Gateway Function (CGF)."
    DEFVAL { false }
    ::= { tmnxMobGtpPriServerEntry 12 }

tmnxMobGtpPriServerPriority  OBJECT-TYPE
    SYNTAX      Unsigned32 (0..100)
    MAX-ACCESS  read-create
    STATUS      current
    DESCRIPTION
        "The value of tmnxMobGtpPriServerPriority specifies the priority of the  
         this GPRS Tunneling Protocol (GTP) primary server."
    DEFVAL { 0 }
    ::= { tmnxMobGtpPriServerEntry 13 }

tmnxMobGtpPriServerPathProtocol  OBJECT-TYPE
    SYNTAX      INTEGER {
                         tcp  (1),
                         udp  (2)
                        }
    MAX-ACCESS  read-create
    STATUS      current
    DESCRIPTION
        "The value of tmnxMobGtpPriServerMaxRequests specifies the path protocol  
         used for the GPRS Tunneling Protocol (GTP) primary server."
    DEFVAL { udp }
    ::= { tmnxMobGtpPriServerEntry 14 }

--
--  UMTS Qos Policy Table
--

tmnxMobUmtsQosPolTblLstChgd  OBJECT-TYPE
    SYNTAX      TimeStamp
    MAX-ACCESS  read-only
    STATUS      current
    DESCRIPTION
        "The value of tmnxMobUmtsQosPolTblLstChgd indicates the sysUpTime at
         the time of the last modification to tmnxMobUmtsQosPolTable by adding,
         deleting an entry or change to a writable object in the table.

         If no changes were made to the table since the last re-initialization
         of the local network management subsystem, then this object contains
         a zero value."
    ::= { tmnxMobProfileGlobalObjs 19 }

tmnxMobUmtsQosPolTable  OBJECT-TYPE
    SYNTAX      SEQUENCE OF TmnxMobUmtsQosPolEntry
    MAX-ACCESS  not-accessible
    STATUS      current
    DESCRIPTION
        "The tmnxMobUmtsQosPolTable has an entry for each Universal Mobile 
         Telecommunications System (UMTS) Quality of Service (QoS) Policy 
         configured on the system. It defines the mapping between standardized 
         QoS Class Identifier (QCI) and pre-Rel-8 QoS parameter values."
    ::= { tmnxMobProfileObjs 19 }

tmnxMobUmtsQosPolEntry  OBJECT-TYPE
    SYNTAX      TmnxMobUmtsQosPolEntry
    MAX-ACCESS  not-accessible
    STATUS      current
    DESCRIPTION
        "Each row entry represents a Universal Mobile Telecommunications System
         (UMTS) Quality of Service (QoS) Policy defined in the system. Entries
         can be created and deleted by the user.
    
         For each entry the mapping between pre-Rel-8 QoS parameter value pairs
         and QoS Class Identifier (QCI) values must be 1-to-1, which means the 
         values for all the QCI objects in tmnxMobUmtsQosPolTable must be 
         non-overlapping. If the mapping is not 1-to-1, at the time of 
         association of this policy at gateway level an 'inconsistentValue' 
         error will be returned.

         A maximum of 1024 policies can be configured in the system."
    INDEX { tmnxMobUmtsQosPolName }
    ::= { tmnxMobUmtsQosPolTable 1 }

TmnxMobUmtsQosPolEntry ::= SEQUENCE {
        tmnxMobUmtsQosPolName               TmnxMobProfName,
        tmnxMobUmtsQosPolRowStatus          RowStatus,
        tmnxMobUmtsQosPolLastChanged        TimeStamp,
        tmnxMobUmtsQosPolConvSpeechQci      TmnxMobQciValue,            
        tmnxMobUmtsQosPolConvUnkTdg         TmnxMobQciValue,
        tmnxMobUmtsQosPolConvUnkTdl         TmnxMobQciValue,
        tmnxMobUmtsQosPolStreamQciValue     TmnxMobQciValue,
        tmnxMobUmtsQosPolInterSigP1Qci      TmnxMobQciValue,
        tmnxMobUmtsQosPolInterP1Qci         TmnxMobQciValue,
        tmnxMobUmtsQosPolInterP2Qci         TmnxMobQciValue,
        tmnxMobUmtsQosPolInterP3Qci         TmnxMobQciValue,
        tmnxMobUmtsQosPolBackground         TmnxMobQciValue
    }

tmnxMobUmtsQosPolName  OBJECT-TYPE
    SYNTAX      TmnxMobProfName 
    MAX-ACCESS  not-accessible
    STATUS      current
    DESCRIPTION
        "The value of tmnxMobUmtsQosPolName specifies the unique name of this
         Universal Mobile Telecommunications System (UMTS) Quality of Service
         (QoS) Policy."
    ::= { tmnxMobUmtsQosPolEntry 1 }

tmnxMobUmtsQosPolRowStatus  OBJECT-TYPE
    SYNTAX      RowStatus
    MAX-ACCESS  read-create
    STATUS      current
    DESCRIPTION
        "The value of tmnxMobUmtsQosPolRowStatus specifies the row status of
         this entry. It is used for creation and deletion of this Universal
         Mobile Telecommunications System (UMTS) Quality of Service (QoS)
         Policy."
    ::= { tmnxMobUmtsQosPolEntry 2 }

tmnxMobUmtsQosPolLastChanged  OBJECT-TYPE
    SYNTAX      TimeStamp
    MAX-ACCESS  read-only
    STATUS      current
    DESCRIPTION
        "The value of tmnxMobUmtsQosPolLastChanged indicates the timestamp of
         the last change to this row in tmnxMobUmtsQosPolTable."
    ::= { tmnxMobUmtsQosPolEntry 3 }

tmnxMobUmtsQosPolConvSpeechQci  OBJECT-TYPE
    SYNTAX      TmnxMobQciValue
    MAX-ACCESS  read-create
    STATUS      current
    DESCRIPTION
        "The value of tmnxMobUmtsQosPolStreamQciValue specifies the QoS Class 
         Identifier (QCI) value when the value for Source Statistics Descriptor 
         (SSD) is speech and traffic class is Conversational."
    DEFVAL { 1 }
    ::= { tmnxMobUmtsQosPolEntry 4 }

tmnxMobUmtsQosPolConvUnkTdg  OBJECT-TYPE
    SYNTAX      TmnxMobQciValue
    MAX-ACCESS  read-create
    STATUS      current
    DESCRIPTION
        "The value of tmnxMobUmtsQosPolStreamQciValue specifies the QoS Class 
         Identifier (QCI) value when the value for Source Statistics Descriptor 
         (SSD) is unknown, traffic class is Conversational and the Transfer
         Delay parameter is greater or equal to 150 ms."
    DEFVAL { 2 }
    ::= { tmnxMobUmtsQosPolEntry 5 }

tmnxMobUmtsQosPolConvUnkTdl  OBJECT-TYPE
    SYNTAX      TmnxMobQciValue
    MAX-ACCESS  read-create
    STATUS      current
    DESCRIPTION
        "The value of tmnxMobUmtsQosPolStreamQciValue specifies the QoS Class 
         Identifier (QCI) value when the value for Source Statistics Descriptor 
         (SSD) is unknown, traffic class is Conversational and the Transfer
         Delay parameter is lower than 150 ms."
    DEFVAL { 3 }
    ::= { tmnxMobUmtsQosPolEntry 6 }

tmnxMobUmtsQosPolStreamQciValue  OBJECT-TYPE
    SYNTAX      TmnxMobQciValue
    MAX-ACCESS  read-create
    STATUS      current
    DESCRIPTION
        "The value of tmnxMobUmtsQosPolStreamQciValue specifies the QoS Class 
         Identifier (QCI) value when the value for Source Statistics Descriptor 
         (SSD) is unknown or speech and traffic class is Streaming."
    DEFVAL { 4 }
    ::= { tmnxMobUmtsQosPolEntry 7 }

tmnxMobUmtsQosPolInterSigP1Qci  OBJECT-TYPE
    SYNTAX      TmnxMobQciValue
    MAX-ACCESS  read-create
    STATUS      current
    DESCRIPTION
        "The value of tmnxMobUmtsQosPolInterSigP1Qci specifies the QoS Class 
         Identifier (QCI) value when the value for Traffic Handling Priority is
         1, Signaling Indication is enabled and traffic class is Interactive."
    DEFVAL { 5 }
    ::= { tmnxMobUmtsQosPolEntry 8 }

tmnxMobUmtsQosPolInterP1Qci  OBJECT-TYPE
    SYNTAX      TmnxMobQciValue
    MAX-ACCESS  read-create
    STATUS      current
    DESCRIPTION
        "The value of tmnxMobUmtsQosPolInterP1Qci specifies the QoS Class 
         Identifier (QCI) value when the value for Traffic Handling Priority is
         1, Signaling Indication is not enabled and traffic class is 
         Interactive."
    DEFVAL { 6 }
    ::= { tmnxMobUmtsQosPolEntry 9 }

tmnxMobUmtsQosPolInterP2Qci  OBJECT-TYPE
    SYNTAX      TmnxMobQciValue
    MAX-ACCESS  read-create
    STATUS      current
    DESCRIPTION
        "The value of tmnxMobUmtsQosPolInterP2Qci specifies the QoS Class 
         Identifier (QCI) value when the value for Traffic Handling Priority is
         2, Signaling Indication is not enabled and traffic class is
         Interactive."
    DEFVAL { 7 }
    ::= { tmnxMobUmtsQosPolEntry 10 }

tmnxMobUmtsQosPolInterP3Qci  OBJECT-TYPE
    SYNTAX      TmnxMobQciValue
    MAX-ACCESS  read-create
    STATUS      current
    DESCRIPTION
        "The value of tmnxMobUmtsQosPolInterP3Qci specifies the QoS Class 
         Identifier (QCI) value when the value for Traffic Handling Priority is
         3, Signaling Indication is not enabled and traffic class is 
         Interactive."
    DEFVAL { 8 }
    ::= { tmnxMobUmtsQosPolEntry 11 }

tmnxMobUmtsQosPolBackground  OBJECT-TYPE
    SYNTAX      TmnxMobQciValue
    MAX-ACCESS  read-create
    STATUS      current
    DESCRIPTION
        "The value of tmnxMobUmtsQosPolBackground specifies the QoS Class 
         Identifier (QCI) value when the traffic class is Background."
    DEFVAL { 9 }
    ::= { tmnxMobUmtsQosPolEntry 12 }

--
--  Radius profile table
--

tmnxMobProfRadTblLstChgd  OBJECT-TYPE
    SYNTAX      TimeStamp
    MAX-ACCESS  read-only
    STATUS      current
    DESCRIPTION
        "The value of tmnxMobProfRadTblLstChgd indicates the sysUpTime at
         the time of the last modification to the tmnxMobProfRadTable by adding,
         deleting an entry or change to a writable object in the table.

         If no changes were made to the table since the last re-initialization
         of the local network management subsystem, then this object contains
         a zero value."
    ::= { tmnxMobProfileGlobalObjs 20 }

tmnxMobProfRadTable  OBJECT-TYPE
    SYNTAX      SEQUENCE OF TmnxMobProfRadEntry
    MAX-ACCESS  not-accessible
    STATUS      current
    DESCRIPTION
        "The tmnxMobProfRadTable has an entry for each radius profile
         configured in the system. Radius profile defines parameters applicable
         when RADIUS is used for authentication and accounting purposes."
    ::= { tmnxMobProfileObjs 20 }

tmnxMobProfRadEntry  OBJECT-TYPE
    SYNTAX      TmnxMobProfRadEntry
    MAX-ACCESS  not-accessible
    STATUS      current
    DESCRIPTION
        "Each row entry represents a radius profile defined in the system.
         Entries can be created and deleted by the user."
    INDEX { IMPLIED tmnxMobProfRadName }
    ::= { tmnxMobProfRadTable 1 }

TmnxMobProfRadEntry ::= SEQUENCE {
        tmnxMobProfRadName                  TmnxMobProfName,
        tmnxMobProfRadRowStatus             RowStatus,
        tmnxMobProfRadLastChanged           TimeStamp,
        tmnxMobProfRadDescription           TItemDescription,
        tmnxMobProfRadAuthProbeInt          Unsigned32,
        tmnxMobProfRadServerDeadTime        Unsigned32,
        tmnxMobProfRadRetryTimeout          Unsigned32,
        tmnxMobProfRadRetryCount            Unsigned32
    }

tmnxMobProfRadName  OBJECT-TYPE
    SYNTAX      TmnxMobProfName
    MAX-ACCESS  not-accessible
    STATUS      current
    DESCRIPTION
        "The value of tmnxMobProfRadName specifies the unique name of this
         radius profile."
    ::= { tmnxMobProfRadEntry 1 }

tmnxMobProfRadRowStatus  OBJECT-TYPE
    SYNTAX      RowStatus
    MAX-ACCESS  read-create
    STATUS      current
    DESCRIPTION
        "The value of tmnxMobProfRadRowStatus specifies the row status of this
         entry. It is used for creation and deletion of this radius
         profile."
    ::= { tmnxMobProfRadEntry 2 }

tmnxMobProfRadLastChanged  OBJECT-TYPE
    SYNTAX      TimeStamp
    MAX-ACCESS  read-only
    STATUS      current
    DESCRIPTION
        "The value of tmnxMobProfRadLastChanged indicates the timestamp of 
         the last change to this row in tmnxMobProfRadTable."
    ::= { tmnxMobProfRadEntry 3 }

tmnxMobProfRadDescription  OBJECT-TYPE
    SYNTAX      TItemDescription
    MAX-ACCESS  read-create
    STATUS      current
    DESCRIPTION
        "The value of tmnxMobProfRadDescription specifies the description
         string for this profile. It can consist of any printable,
         seven-bit ASCII characters up to 80 characters in length."
    DEFVAL { ''H }
    ::= { tmnxMobProfRadEntry 4 }

tmnxMobProfRadAuthProbeInt  OBJECT-TYPE
    SYNTAX      Unsigned32 (0|20..600)
    UNITS       "seconds"
    MAX-ACCESS  read-create
    STATUS      current
    DESCRIPTION
        "The value of tmnxMobProfRadAuthProbeInt specifies the interval at
         which the system sends authentication probe messages to an 
         authentication server.  An authentication probe is a 'fake' 
         Access-Request message for a certain username and password.  If the 
         server responds to the Access-Request (even with an Access-
         Reject), the server will be considered operational.

         Note that the authentication probe messages will not be sent to 
         the servers that are used for accounting only."
    DEFVAL { 0 }
    ::= { tmnxMobProfRadEntry 5 }

tmnxMobProfRadServerDeadTime  OBJECT-TYPE
    SYNTAX      Unsigned32 (0|60..3600)
    UNITS       "seconds"
    MAX-ACCESS  read-create
    STATUS      current
    DESCRIPTION
        "The value of tmnxMobProfRadServerDeadTime specifies the time, in 
         seconds, that the server continues to be considered dead before 
         the system will attempt to use it for normal authentication or 
         accounting requests. When the system fails to reach a particular 
         server after a configurable number of retries, the server is marked 
         dead and another server is selected.

         Note that for the authentication servers, the system will continuously 
         attempt to verify the operational state of the dead server if the 
         auth-probe-interval is set to be non-zero.  If the authentication 
         server responds to an auth-probe, the system considers the server to be 
         operational even if the dead timer has not yet expired.

         Once the dead-timer expires the system may once again send the server 
         authentication or accounting messages.  The server is subject to the 
         retry-timeout and retry-count mechanism to determine if the server 
         is still in the failed state.
        
         The server-dead-time is ignored if there are no other available servers 
         to use (either because they are not defined or if they are also down).  
         In this case the system will not mark the server as down.  Similarly 
         the server-dead-time can be set to 0 so that the server is never marked 
         dead."
    DEFVAL { 300 }
    ::= { tmnxMobProfRadEntry 6 }

tmnxMobProfRadRetryTimeout  OBJECT-TYPE
    SYNTAX      Unsigned32 (3..20)
    UNITS       "seconds"
    MAX-ACCESS  read-create
    STATUS      current
    DESCRIPTION
        "The value of tmnxMobProfRadRetryTimeout specifies the time, in 
         seconds, to wait before resending a request to which no response has 
         been received."
    DEFVAL { 4 }
    ::= { tmnxMobProfRadEntry 7 }

tmnxMobProfRadRetryCount  OBJECT-TYPE
    SYNTAX      Unsigned32 (1..8)
    MAX-ACCESS  read-create
    STATUS      current
    DESCRIPTION
        "The value of tmnxMobProfRadRetryCount specifies the maximum number
         of times the system sends a radius message to the server. When this count
         is reached the server is considered dead and another server is selected."
    DEFVAL { 4 }
    ::= { tmnxMobProfRadEntry 8 }

--
--  Radius group table
--

tmnxMobProfRadGrpTblLstChgd  OBJECT-TYPE
    SYNTAX      TimeStamp
    MAX-ACCESS  read-only
    STATUS      current
    DESCRIPTION
        "The value of tmnxMobProfRadGrpTblLstChgd indicates the sysUpTime at
         the time of the last modification to the tmnxMobProfRadGrpTable by 
         adding, deleting an entry or change to a writable object in the table.

         If no changes were made to the table since the last re-initialization
         of the local network management subsystem, then this object contains
         a zero value."
    ::= { tmnxMobProfileGlobalObjs 21 }

tmnxMobProfRadGrpTable  OBJECT-TYPE
    SYNTAX      SEQUENCE OF TmnxMobProfRadGrpEntry
    MAX-ACCESS  not-accessible
    STATUS      current
    DESCRIPTION
        "The tmnxMobProfRadGrpTable has an entry for each radius group
         configured in the system. Radius group defines parameters applicable
         to a peer when radius is used for authentication and accounting 
         purposes."
    ::= { tmnxMobProfileObjs 21 }

tmnxMobProfRadGrpEntry  OBJECT-TYPE
    SYNTAX      TmnxMobProfRadGrpEntry
    MAX-ACCESS  not-accessible
    STATUS      current
    DESCRIPTION
        "Each row entry represents a radius group defined in the system.
         Entries can be created and deleted by the user."
    INDEX { tmnxMobProfRadGrpName }
    ::= { tmnxMobProfRadGrpTable 1 }

TmnxMobProfRadGrpEntry ::= SEQUENCE {
        tmnxMobProfRadGrpName              TmnxMobProfName,
        tmnxMobProfRadGrpRowStatus         RowStatus,
        tmnxMobProfRadGrpLastChanged       TimeStamp,
        tmnxMobProfRadGrpDescription       TItemDescription,
        tmnxMobProfRadGrpIfVRtrId          TmnxVRtrID,
        tmnxMobProfRadGrpIfIndex           InterfaceIndexOrZero,
        tmnxMobProfRadGrpAuthServerPort    InetPortNumber,
        tmnxMobProfRadGrpAcctServerPort    InetPortNumber,
        tmnxMobProfRadGrpSecret            OCTET STRING,
        tmnxMobProfRadGrpIntUpdateIntvl    Unsigned32,
        tmnxMobProfRadGrpServerType        INTEGER,
        tmnxMobProfRadGrpRadiusProfile     TmnxMobProfNameOrEmpty,
        tmnxMobProfRadGrpIgnAcctResp       TruthValue     
    }

tmnxMobProfRadGrpName  OBJECT-TYPE
    SYNTAX      TmnxMobProfName
    MAX-ACCESS  not-accessible
    STATUS      current
    DESCRIPTION
        "The value of tmnxMobProfRadGrpName specifies the unique name of this
         radius group."
    ::= { tmnxMobProfRadGrpEntry 1 }

tmnxMobProfRadGrpRowStatus  OBJECT-TYPE
    SYNTAX      RowStatus
    MAX-ACCESS  read-create
    STATUS      current
    DESCRIPTION
        "The value of tmnxMobProfRadGrpRowStatus specifies the row status of 
         this entry. It is used for creation and deletion of this radius
         group."
    ::= { tmnxMobProfRadGrpEntry 2 }

tmnxMobProfRadGrpLastChanged  OBJECT-TYPE
    SYNTAX      TimeStamp
    MAX-ACCESS  read-only
    STATUS      current
    DESCRIPTION
        "The value of tmnxMobProfRadGrpLastChanged indicates the timestamp of 
         the last change to this row in tmnxMobProfRadGrpTable."
    ::= { tmnxMobProfRadGrpEntry 3 }

tmnxMobProfRadGrpDescription  OBJECT-TYPE
    SYNTAX      TItemDescription
    MAX-ACCESS  read-create
    STATUS      current
    DESCRIPTION
        "The value of tmnxMobProfRadGrpDescription specifies the description
         string for this profile. It can consist of any printable,
         seven-bit ASCII characters up to 80 characters in length."
    DEFVAL { ''H }
    ::= {  tmnxMobProfRadGrpEntry 4 }

tmnxMobProfRadGrpIfVRtrId  OBJECT-TYPE
    SYNTAX      TmnxVRtrID
    MAX-ACCESS  read-create
    STATUS      current
    DESCRIPTION
        "The value of tmnxMobProfRadGrpIfVRtrId specifies the virtual
         router to which the interface specified by tmnxMobProfRadGrpIfIndex
         belongs."
    DEFVAL { 1 }
    ::= { tmnxMobProfRadGrpEntry 5 }

tmnxMobProfRadGrpIfIndex  OBJECT-TYPE
    SYNTAX      InterfaceIndexOrZero
    MAX-ACCESS  read-create
    STATUS      current
    DESCRIPTION
        "The value of tmnxMobProfRadGrpIfIndex specifies the interface index of
         the local interface used for radius authentication and accounting."
    DEFVAL { 0 }
    ::= { tmnxMobProfRadGrpEntry 6 }

tmnxMobProfRadGrpAuthServerPort  OBJECT-TYPE
    SYNTAX      InetPortNumber
    MAX-ACCESS  read-create
    STATUS      current
    DESCRIPTION
        "The value of tmnxMobProfRadGrpAuthServerPort specifies the listening 
         port on the radius peer for authentication messages."
    DEFVAL { 1812 }
    ::= { tmnxMobProfRadGrpEntry 7 }

tmnxMobProfRadGrpAcctServerPort  OBJECT-TYPE
    SYNTAX      InetPortNumber
    MAX-ACCESS  read-create
    STATUS      current
    DESCRIPTION
        "The value of tmnxMobProfRadGrpAcctServerPort specifies the listening 
         port on the radius peer for accounting messages."
    DEFVAL { 1813 }
    ::= { tmnxMobProfRadGrpEntry 8 }

tmnxMobProfRadGrpSecret  OBJECT-TYPE
    SYNTAX      OCTET STRING (SIZE(0..20))
    MAX-ACCESS  read-create
    STATUS      current
    DESCRIPTION
        "The value of tmnxMobProfRadGrpSecret specifies the shared secret key 
         to be used with the server.

         The value returned by tmnxMobProfRadGrpSecret is always an empty 
         string."
    DEFVAL { ''H }
    ::= { tmnxMobProfRadGrpEntry 9 }

tmnxMobProfRadGrpIntUpdateIntvl  OBJECT-TYPE
    SYNTAX      Unsigned32 (0|15..1440)
    UNITS       "minutes"
    MAX-ACCESS  read-create
    STATUS      current
    DESCRIPTION
        "The value of tmnxMobProfRadGrpIntUpdateIntvl specifies the time 
         interval, in minutes, for sending interim-update messages to the 
         accounting server."
    DEFVAL { 0 }
    ::= { tmnxMobProfRadGrpEntry 10 }

tmnxMobProfRadGrpServerType  OBJECT-TYPE
    SYNTAX      INTEGER {
                         none (0),
                         auth (1),
                         acct (2),
                         both (3)
                        }
    MAX-ACCESS  read-create
    STATUS      current
    DESCRIPTION
        "The value of tmnxMobProfRadGrpServerType specifies the server type for
         this radius group."
    DEFVAL { none }
    ::= { tmnxMobProfRadGrpEntry 11 }

tmnxMobProfRadGrpRadiusProfile  OBJECT-TYPE
    SYNTAX      TmnxMobProfNameOrEmpty
    MAX-ACCESS  read-create
    STATUS      current
    DESCRIPTION
        "The value of tmnxMobProfRadGrpRadiusProfile specifies the radius 
         profile name.

         If a corresponding radius profile does not exist in the 
         tmnxMobProfRadTable, an 'inconsistentValue' error will be returned."
    DEFVAL { ''H }
    ::= { tmnxMobProfRadGrpEntry 12 }

tmnxMobProfRadGrpIgnAcctResp  OBJECT-TYPE
    SYNTAX      TruthValue
    MAX-ACCESS  read-create
    STATUS      current
    DESCRIPTION
        "The value of tmnxMobProfRadGrpIgnAcctResp specifies whether the mobile
         gateway will receive responses after sending account start request to 
         multiple radius servers."
    DEFVAL { false }
::= { tmnxMobProfRadGrpEntry 13 }


--
--  Radius group peer table
--

tmnxMobProfRadPeerTblLstChgd  OBJECT-TYPE
    SYNTAX      TimeStamp
    MAX-ACCESS  read-only
    STATUS      current
    DESCRIPTION
        "The value of tmnxMobProfRadPeerTblLstChgd indicates the sysUpTime at
         the time of the last modification to the tmnxMobProfRadPeerTable by 
         adding, deleting an entry or change to a writable object in the table.

         If no changes were made to the table since the last re-initialization
         of the local network management subsystem, then this object contains
         a zero value."
    ::= { tmnxMobProfileGlobalObjs 22 }

tmnxMobProfRadPeerTable  OBJECT-TYPE
    SYNTAX      SEQUENCE OF TmnxMobProfRadPeerEntry
    MAX-ACCESS  not-accessible
    STATUS      current
    DESCRIPTION
        "The tmnxMobProfRadPeerTable has an entry for each radius server 
         configured for each radius group configured on the system." 
    ::= { tmnxMobProfileObjs 22 }

tmnxMobProfRadPeerEntry  OBJECT-TYPE
    SYNTAX      TmnxMobProfRadPeerEntry
    MAX-ACCESS  not-accessible
    STATUS      current
    DESCRIPTION
        "Each row entry represents an IP address configured for each radius 
         server. Entries can be created and deleted by the user."
    INDEX { tmnxMobProfRadGrpName,
            tmnxMobProfRadPeerIndex
          }
    ::= { tmnxMobProfRadPeerTable 1 }

TmnxMobProfRadPeerEntry ::= SEQUENCE {
        tmnxMobProfRadPeerIndex           Unsigned32,
        tmnxMobProfRadPeerRowStatus       RowStatus,
        tmnxMobProfRadPeerLastChngd       TimeStamp,
        tmnxMobProfRadPeerAdminState      TmnxAdminState,
        tmnxMobProfRadPeerAddrType        InetAddressType,
        tmnxMobProfRadPeerAddr            InetAddress,
        tmnxMobProfRadPeerPriority        Unsigned32,
        tmnxMobProfRadPeerAuthSvrPort     InetPortNumber,
        tmnxMobProfRadPeerAcctSvrPort     InetPortNumber,
        tmnxMobProfRadPeerSecret          OCTET STRING,
        tmnxMobProfRadPeerRadProfile      TmnxMobProfNameOrEmpty
    }

tmnxMobProfRadPeerIndex  OBJECT-TYPE
    SYNTAX      Unsigned32
    MAX-ACCESS  not-accessible
    STATUS      current
    DESCRIPTION
        "The value of tmnxMobProfRadPeerIndex specifies the unique value
         which identifies this IP address entry."
    ::= { tmnxMobProfRadPeerEntry 1 }

tmnxMobProfRadPeerRowStatus  OBJECT-TYPE
    SYNTAX      RowStatus
    MAX-ACCESS  read-create
    STATUS      current
    DESCRIPTION
        "The value of tmnxMobProfRadPeerRowStatus specifies the row status
         of this entry. It is used for the creation and deletion of this
         radius server entry.

         In order for the row creation to succeed, values for 
         tmnxMobProfRadPeerAddrType, tmnxMobProfRadPeerAddr must be included
         in the same SNMP SET PDU as tmnxMobProfRadPeerRowStatus. Otherwise,
         the SET request will fail with an 'inconsistentValue' error."
    ::= { tmnxMobProfRadPeerEntry 2 }

tmnxMobProfRadPeerLastChngd  OBJECT-TYPE
    SYNTAX      TimeStamp
    MAX-ACCESS  read-only
    STATUS      current
    DESCRIPTION
        "The value of tmnxMobProfRadPeerLastChngd indicates the timestamp of
         the last change to this row in tmnxMobProfRadPeerTable."
    ::= { tmnxMobProfRadPeerEntry 3 }

tmnxMobProfRadPeerAdminState  OBJECT-TYPE
    SYNTAX      TmnxAdminState
    MAX-ACCESS  read-create
    STATUS      current
    DESCRIPTION
        "The value of tmnxMobProfRadPeerAdminState specifies the desired 
         administrative state of this radius server."
    DEFVAL { outOfService }
    ::= { tmnxMobProfRadPeerEntry 4 }

tmnxMobProfRadPeerAddrType  OBJECT-TYPE
    SYNTAX      InetAddressType
    MAX-ACCESS  read-create
    STATUS      current
    DESCRIPTION
        "The value of tmnxMobProfRadPeerAddrType specifies the type of
         address represented by tmnxMobProfRadPeerAddr.
         
         The value of this object cannot be modified once the row has been 
         created."
    DEFVAL { unknown }
    ::= { tmnxMobProfRadPeerEntry 5 }

tmnxMobProfRadPeerAddr  OBJECT-TYPE
    SYNTAX      InetAddress (SIZE (1..255))
    MAX-ACCESS  read-create
    STATUS      current
    DESCRIPTION
        "The value of tmnxMobProfRadPeerAddr specifies the IP address of
         the server for which this entry contains information. If the value of
         the corresponsding tmnxMobProfRadPeerAddrType is 'dns', then the
         IP address for this server will be obtained via DNS A-Record query.

         The value of this object cannot be modified once the row has been 
         created."
    DEFVAL { ''H }
    ::= { tmnxMobProfRadPeerEntry 6 }

tmnxMobProfRadPeerPriority  OBJECT-TYPE
    SYNTAX      Unsigned32 (1..3)
    MAX-ACCESS  read-create
    STATUS      current
    DESCRIPTION
        "The value of tmnxMobProfRadPeerPriority specifies the priority of 
         this server. The value of '3' is considered as the highest priority.
         The system will attempt to use the highest priority server available 
         at the time. 

         The system will automatically use round-robin load-balancing among 
         servers configured with the same priority."
    DEFVAL { 1 }
    ::= { tmnxMobProfRadPeerEntry 7 }

tmnxMobProfRadPeerAuthSvrPort  OBJECT-TYPE
    SYNTAX      InetPortNumber
    MAX-ACCESS  read-create
    STATUS      current
    DESCRIPTION
        "The value of tmnxMobProfRadPeerAuthSvrPort specifies the listening 
         port on the radius server for authentication messages."
    DEFVAL { 0 }
    ::= { tmnxMobProfRadPeerEntry 8 }

tmnxMobProfRadPeerAcctSvrPort  OBJECT-TYPE
    SYNTAX      InetPortNumber
    MAX-ACCESS  read-create
    STATUS      current
    DESCRIPTION
        "The value of tmnxMobProfRadPeerAcctSvrPort specifies the listening 
         port on the radius server for accounting messages."
    DEFVAL { 0 }
    ::= { tmnxMobProfRadPeerEntry 9 }

tmnxMobProfRadPeerSecret  OBJECT-TYPE
    SYNTAX      OCTET STRING (SIZE(0..20))
    MAX-ACCESS  read-create
    STATUS      current
    DESCRIPTION
        "The value of tmnxMobProfRadPeerSecret specifies the shared secret key 
         to be used with the server.

         The value returned by tmnxMobProfRadGrpSecret is always an empty 
         string."
    DEFVAL { ''H }
    ::= { tmnxMobProfRadPeerEntry 10 }

tmnxMobProfRadPeerRadProfile  OBJECT-TYPE
    SYNTAX      TmnxMobProfNameOrEmpty
    MAX-ACCESS  read-create
    STATUS      current
    DESCRIPTION
        "The value of tmnxMobProfRadPeerRadProfile specifies the radius 
         profile name.

         If a corresponding radius profile does not exist in the 
         tmnxMobProfRadTable, an 'inconsistentValue' error will be returned."
    DEFVAL { ''H }
    ::= { tmnxMobProfRadPeerEntry 11 }

--
--  DCCA profile table
--

tmnxMobProfDccaTblLstChgd  OBJECT-TYPE
    SYNTAX      TimeStamp
    MAX-ACCESS  read-only
    STATUS      current
    DESCRIPTION
        "The value of tmnxMobProfDccaTblLstChgd indicates the sysUpTime at
         the time of the last modification to tmnxMobProfDccaTable by adding,
         deleting an entry or change to a writable object in the table.

         If no changes were made to the table since the last re-initialization
         of the local network management subsystem, then this object contains
         a zero value."
    ::= { tmnxMobProfileGlobalObjs 23 }

tmnxMobProfDccaTable  OBJECT-TYPE
    SYNTAX      SEQUENCE OF TmnxMobProfDccaEntry  
    MAX-ACCESS  not-accessible
    STATUS      current
    DESCRIPTION
        "The tmnxMobProfDccaTable has an entry for each Diameter Credit Control
         Application (DCCA) profile configured on the system. DCCA profile 
         defines credit control related parameters for online charging.  

         A maximum of 100 DCCA profiles can be configured in the system."
    ::= { tmnxMobProfileObjs 23 }

tmnxMobProfDccaEntry  OBJECT-TYPE
    SYNTAX      TmnxMobProfDccaEntry
    MAX-ACCESS  not-accessible
    STATUS      current
    DESCRIPTION
        "Each row entry represents a Diameter Credit Control Application (DCCA)
         profile defined in the system. Entries can be created and deleted
         by the user.

         DCCA profile 'default' is created by the agent itself at system 
         initialization. It cannot be modified or deleted."
    INDEX { IMPLIED tmnxMobProfDccaName }
    ::= { tmnxMobProfDccaTable 1 }

TmnxMobProfDccaEntry ::= SEQUENCE {
        tmnxMobProfDccaName              TmnxMobProfName,
        tmnxMobProfDccaRowStatus         RowStatus,
        tmnxMobProfDccaLastChanged       TimeStamp,
        tmnxMobProfDccaDescription       TItemDescription,
        tmnxMobProfDccaApplTxTimer       Unsigned32,
        tmnxMobProfDccaRetryCnt          Unsigned32,
        tmnxMobProfDcca3GppQosNegProf    TmnxEnabledDisabled,
        tmnxMobProfDccaQosInformation    TmnxEnabledDisabled,
        tmnxMobProfDccaCalledStationId   INTEGER,
        tmnxMobProfDccaCcSessFailover    TmnxEnabledDisabled,
        tmnxMobProfDccaCcSessFlovrHndl   INTEGER,
        tmnxMobProfDccaForcedReAuth      TmnxMobProfAllowDiscard,
        tmnxMobProfDccaQuotaExNoThrsld   TmnxMobProfAllowDiscard,
        tmnxMobProfDccaQuotaExThrsldAct  TmnxMobProfAllowDiscard,
        tmnxMobProfDccaQuotaUnavail      TmnxMobProfAllowDiscard,
        tmnxMobProfDccaRatingCondtChng   TmnxMobProfAllowDiscard,
        tmnxMobProfDccaValidityTimeExp   TmnxMobProfAllowDiscard,
        tmnxMobProfDccaFhSessContTimer   Unsigned32,
        tmnxMobProfDccaDefaultQht        Unsigned32,
        tmnxMobProfDccaFirstPktBehavior  TmnxEnabledDisabled
    }

tmnxMobProfDccaName  OBJECT-TYPE
    SYNTAX      TmnxMobProfName
    MAX-ACCESS  not-accessible
    STATUS      current
    DESCRIPTION
        "The value of tmnxMobProfDccaName specifies the unique name of this
         Diameter Credit Control Application (DCCA) profile."
    ::= { tmnxMobProfDccaEntry 1 }

tmnxMobProfDccaRowStatus  OBJECT-TYPE
    SYNTAX      RowStatus
    MAX-ACCESS  read-create
    STATUS      current
    DESCRIPTION
        "The value of tmnxMobProfDccaRowStatus specifies the row status of this
         entry. It is used for creation and deletion of this Diameter Credit 
         Control Application (DCCA) profile."
    ::= { tmnxMobProfDccaEntry 2 }

tmnxMobProfDccaLastChanged  OBJECT-TYPE
    SYNTAX      TimeStamp
    MAX-ACCESS  read-only
    STATUS      current
    DESCRIPTION
        "The value of tmnxMobProfDccaLastChanged indicates the timestamp of 
         the last change to this row in tmnxMobProfDccaTable."
    ::= { tmnxMobProfDccaEntry 3 }

tmnxMobProfDccaDescription  OBJECT-TYPE
    SYNTAX      TItemDescription
    MAX-ACCESS  read-create
    STATUS      current
    DESCRIPTION
        "The value of tmnxMobProfDccaDescription specifies the description
         string for this Diameter Credit Control Application (DCCA) profile. 
         It can consist of any printable, seven-bit ASCII characters up to 80
         characters in length."
    DEFVAL { ''H }
    ::= { tmnxMobProfDccaEntry 4 }

tmnxMobProfDccaApplTxTimer  OBJECT-TYPE
    SYNTAX      Unsigned32 (1..30)
    UNITS       "seconds"
    MAX-ACCESS  read-create
    STATUS      current
    DESCRIPTION
        "The value of tmnxMobProfDccaApplTxTimer specifies the application 
         transaction timer for Credit Control Request (CCR) and 
         Credit Control Answer (CCA)."
    DEFVAL { 5 }
    ::= { tmnxMobProfDccaEntry 5 }

tmnxMobProfDccaRetryCnt  OBJECT-TYPE
    SYNTAX      Unsigned32 (0..3)
    MAX-ACCESS  read-create
    STATUS      current
    DESCRIPTION
        "The value of tmnxMobProfDccaRetryCnt specifies the number of
         times the Credit Control Request (CCR) message will be retransmitted, 
         when Credit Control Answer (CCA) is not received from the Online 
         Charging System (OCS) server."
    DEFVAL { 0 }
    ::= { tmnxMobProfDccaEntry 6 }

tmnxMobProfDcca3GppQosNegProf  OBJECT-TYPE
    SYNTAX      TmnxEnabledDisabled
    MAX-ACCESS  read-create
    STATUS      current
    DESCRIPTION
        "The value of tmnxMobProfDcca3GppQosNegProf specifies whether the 
         3GPP-QoS-Negotiated-Profile Attribute Value Pair (AVP) should be
         included in the Credit Control Request (CCR). Both 
         tmnxMobProfDcca3GppQosNegProf or tmnxMobProfDccaQosInformation can not
         be enabled at the same time."
    DEFVAL { disabled }
    ::= { tmnxMobProfDccaEntry 7 }

tmnxMobProfDccaQosInformation  OBJECT-TYPE
    SYNTAX      TmnxEnabledDisabled
    MAX-ACCESS  read-create
    STATUS      current
    DESCRIPTION
        "The value of tmnxMobProfDccaQosInformation specifies whether the
         Qos-Information Attribute Value Pair (AVP) should be
         included in the Credit Control Request (CCR). Both 
         tmnxMobProfDcca3GppQosNegProf or tmnxMobProfDccaQosInformation can not
         be enabled at the same time."
    DEFVAL { disabled }
    ::= { tmnxMobProfDccaEntry 8 }

tmnxMobProfDccaCalledStationId  OBJECT-TYPE
    SYNTAX      INTEGER {
                         real     (1),
                         virtual  (2)   
                        }
    MAX-ACCESS  read-create
    STATUS      current
    DESCRIPTION
        "The value of tmnxMobProfDccaCalledStationId specifies whether the
         real or virtual Access Point Name (APN) is included in the 
         called-station-id Attribute Value Pair (AVP)."
    DEFVAL { real }
    ::= { tmnxMobProfDccaEntry 9 }

tmnxMobProfDccaCcSessFailover OBJECT-TYPE
    SYNTAX      TmnxEnabledDisabled
    MAX-ACCESS  read-create
    STATUS      current
    DESCRIPTION
        "The value of tmnxMobProfDccaCcSessFailover specifies whether the 
         failover to secondary Online Charging System is supported if the 
         primary OCS is not available"
    DEFVAL { enabled }
    ::= { tmnxMobProfDccaEntry 10 }
        
tmnxMobProfDccaCcSessFlovrHndl OBJECT-TYPE
    SYNTAX      INTEGER {
                        terminate         (1),
                        continue          (2),
                        retryAndTerm      (3)
                        }
    MAX-ACCESS  read-create
    STATUS      current
    DESCRIPTION
        "The value of tmnxMobProfDccaCcSessFlovrHndl specifies the credit
         control failure handling on the gateway"
    DEFVAL { terminate }
    ::= { tmnxMobProfDccaEntry 11 }

tmnxMobProfDccaForcedReAuth  OBJECT-TYPE
    SYNTAX      TmnxMobProfAllowDiscard
    MAX-ACCESS  read-create
    STATUS      current
    DESCRIPTION 
        "The value of tmnxMobProfDccaForcedReAuth specifies the option to
         allow or discard the traffic for the service while waiting for a
         Credit Control Answer (CCA) response message from the Online Charging
         System (OCS) when a Credit Control Request (CCR) message is sent to the 
         OCS as a result of forced re-authorization by the OCS."
    DEFVAL    { allow }
    ::= { tmnxMobProfDccaEntry 12 }

tmnxMobProfDccaQuotaExNoThrsld  OBJECT-TYPE
    SYNTAX      TmnxMobProfAllowDiscard
    MAX-ACCESS  read-create
    STATUS      current
    DESCRIPTION 
        "The value of tmnxMobProfDccaQuotaExNoThrsld specifies the option to 
         allow or discard the traffic for the service while waiting for a 
         Credit Control Answer (CCA) response message from the Online Charging
         System (OCS) when no threshold is active and the quota gets exhausted."
    DEFVAL    { allow }
    ::= { tmnxMobProfDccaEntry 13 }

tmnxMobProfDccaQuotaExThrsldAct  OBJECT-TYPE
    SYNTAX      TmnxMobProfAllowDiscard
    MAX-ACCESS  read-create
    STATUS      current
    DESCRIPTION
        "The value of tmnxMobProfDccaQuotaExThrsldAct specifies the option to 
         allow or discard the traffic for the service while waiting for a 
         Credit Control Answer (CCA) response message from the Online Charging
         System (OCS) when the validity timer expires."
    DEFVAL  { allow }
    ::= { tmnxMobProfDccaEntry 14 }

tmnxMobProfDccaQuotaUnavail  OBJECT-TYPE
    SYNTAX      TmnxMobProfAllowDiscard
    MAX-ACCESS  read-create
    STATUS      current
    DESCRIPTION
        "The value of tmnxMobProfDccaQuotaUnavail specifies the option to 
         allow or discard the traffic for the service while waiting for a 
         Credit Control Answer (CCA) response message from the Online Charging
         System (OCS) when no quota is available for a Rating Group."
    DEFVAL { allow }
    ::= { tmnxMobProfDccaEntry 15 }
   
tmnxMobProfDccaRatingCondtChng  OBJECT-TYPE
    SYNTAX      TmnxMobProfAllowDiscard
    MAX-ACCESS  read-create
    STATUS      current
    DESCRIPTION
        "The value of tmnxMobProfDccaRatingCondtChng specifies the option to 
         allow or discard the traffic for the service while waiting for a 
         Credit Control Answer (CCA) response message from the Online Charging
         System (OCS) when a Credit Control Request (CCR) message is sent to the
         OCS due to the Rating-Condition change being detected and waiting for
         a Credit Control Answer (CCA) response message from the OCS."
    DEFVAL { allow }
    ::= { tmnxMobProfDccaEntry 16 }

tmnxMobProfDccaValidityTimeExp  OBJECT-TYPE
    SYNTAX      TmnxMobProfAllowDiscard
    MAX-ACCESS  read-create
    STATUS      current
    DESCRIPTION
        "The value of tmnxMobProfDccaValidityTimeExp specifies the option to 
         allow or discard the traffic for the service while waiting for a 
         Credit Control Answer (CCA) response message from the Online Charging
         System (OCS) when there is an active threshold, but the quota gets
         exhausted while waiting for a CCA upon hitting the threshold."
    DEFVAL { allow }
    ::= { tmnxMobProfDccaEntry 17 }

tmnxMobProfDccaFhSessContTimer  OBJECT-TYPE
    SYNTAX      Unsigned32 (0..1440)
    UNITS       "minutes"
    MAX-ACCESS  read-create
    STATUS      current
    DESCRIPTION
        "The value of tmnxMobProfDccaFhSessContTimer specifies the Failure
         Handling Session Continue timer. When the value of the object
         tmnxMobProfDccaCcSessFlovrHndl is 'continue', the credit control
         session is considered closed. However, the service is granted for the
         configured period of time."
    DEFVAL { 30 }
    ::= { tmnxMobProfDccaEntry 18 }

tmnxMobProfDccaDefaultQht  OBJECT-TYPE
    SYNTAX      Unsigned32 (0..5)
    UNITS       "minutes"
    MAX-ACCESS  read-create
    STATUS      current
    DESCRIPTION
        "The value of tmnxMobProfDccaDefaultQht specifies the default Quota
         Holding Timer (QHT) that would be applicable when the Online Charging
         System (OCS) does not specify a QHT. When OCS specifies a QHT,
         it overrides the default-QHT configured on the gateway."
    DEFVAL { 2 }
    ::= { tmnxMobProfDccaEntry 19 }

tmnxMobProfDccaFirstPktBehavior  OBJECT-TYPE
    SYNTAX      TmnxEnabledDisabled
    MAX-ACCESS  read-create
    STATUS      current
    DESCRIPTION
        "The value of tmnxMobProfDccaFirstPktBehavior specifies the option to
         enable the behavior to request quota upon detecting a first packet for
         the corresponding service data flow. Credit Control is on a per Rating
         Group basis. All Service Data Flow (SDFs) belong to a particular Rating
         Group consume from the quota allocated for that Rating Group."
    DEFVAL { enabled }
    ::= { tmnxMobProfDccaEntry 20 }

--
--  Policy rule unit table
--

tmnxMobProfPolUnitTblLstChgd  OBJECT-TYPE
    SYNTAX      TimeStamp
    MAX-ACCESS  read-only
    STATUS      current
    DESCRIPTION
        "The value of tmnxMobProfPolUnitTblLstChgd indicates the sysUpTime at
         the time of the last modification to tmnxMobProfPolUnitTable by adding,
         deleting an entry or change to a writable object in the table.

         If no changes were made to the table since the last re-initialization
         of the local network management subsystem, then this object contains
         a zero value."
    ::= { tmnxMobProfileGlobalObjs 24 }

tmnxMobProfPolUnitTable  OBJECT-TYPE
    SYNTAX      SEQUENCE OF TmnxMobProfPolUnitEntry
    MAX-ACCESS  not-accessible
    STATUS      current
    DESCRIPTION
        "The tmnxMobProfPolUnitTable has an entry for each policy rule unit 
         profile configured on the system. Policy rule unit profile defines QoS
         parameters for policy control."
    ::= { tmnxMobProfileObjs 24 }

tmnxMobProfPolUnitEntry  OBJECT-TYPE
    SYNTAX      TmnxMobProfPolUnitEntry
    MAX-ACCESS  not-accessible
    STATUS      current
    DESCRIPTION
        "Each row entry represents a policy rule unit profile defined in the
         system. Entries can be created and deleted by the user."
    INDEX { tmnxMobProfPolUnitName }
    ::= { tmnxMobProfPolUnitTable 1 }

TmnxMobProfPolUnitEntry ::= SEQUENCE {
        tmnxMobProfPolUnitName           TmnxMobProfName,
        tmnxMobProfPolUnitRowStatus      RowStatus,
        tmnxMobProfPolUnitLastChanged    TimeStamp,
        tmnxMobProfPolUnitUplinkGbrRate  TmnxMobProfGbrRate,
        tmnxMobProfPolUnitUplinkMbrRate  TmnxMobProfMbrRate,
        tmnxMobProfPolUnitDwnlinkGbrRate TmnxMobProfGbrRate,
        tmnxMobProfPolUnitDwnlinkMbrRate TmnxMobProfMbrRate,
        tmnxMobProfPolUntFlwGateStatus   INTEGER,
        tmnxMobProfPolUntRedirectAdrType InetAddressType,
        tmnxMobProfPolUntRedirectAddr    InetAddress,
        tmnxMobProfPolUntInUse           TruthValue,
        tmnxMobProfPolUntRefCount        Counter32
    }

tmnxMobProfPolUnitName  OBJECT-TYPE
    SYNTAX      TmnxMobProfName
    MAX-ACCESS  not-accessible
    STATUS      current
    DESCRIPTION
        "The value of tmnxMobProfPolUnitName specifies the unique name of this
         policy rule unit profile."
    ::= { tmnxMobProfPolUnitEntry 1 }

tmnxMobProfPolUnitRowStatus  OBJECT-TYPE
    SYNTAX      RowStatus
    MAX-ACCESS  read-create
    STATUS      current
    DESCRIPTION
        "The value of tmnxMobProfPolUnitRowStatus specifies the row status of
         this entry. It is used for creation and deletion of this policy
         rule unit profile."
    ::= { tmnxMobProfPolUnitEntry 2 }

tmnxMobProfPolUnitLastChanged  OBJECT-TYPE
    SYNTAX      TimeStamp
    MAX-ACCESS  read-only
    STATUS      current
    DESCRIPTION
        "The value of tmnxMobProfPolUnitLastChanged indicates the timestamp of
         the last change to this row in tmnxMobProfPolUnitTable."
    ::= { tmnxMobProfPolUnitEntry 3 }

tmnxMobProfPolUnitUplinkGbrRate  OBJECT-TYPE
    SYNTAX      TmnxMobProfGbrRate
    UNITS       "kbps"
    MAX-ACCESS  read-create
    STATUS      current
    DESCRIPTION
        "The value of tmnxMobProfPolUnitUplinkGbrRate specifies the expected
         uplink Guaranteed Bit Rate (GBR) provided by the GBR bearer."
    DEFVAL { 0 }
    ::= { tmnxMobProfPolUnitEntry 4 }

tmnxMobProfPolUnitUplinkMbrRate  OBJECT-TYPE
    SYNTAX      TmnxMobProfMbrRate
    UNITS       "kbps"
    MAX-ACCESS  read-create
    STATUS      current
    DESCRIPTION
        "The value of tmnxMobProfPolUnitUplinkMbrRate specifies the expected
         uplink Maximum Bit Rate (MBR) provided by the GBR bearer."
    DEFVAL { 0 }
    ::= { tmnxMobProfPolUnitEntry 5 }

tmnxMobProfPolUnitDwnlinkGbrRate  OBJECT-TYPE
    SYNTAX      TmnxMobProfGbrRate
    UNITS       "kbps"
    MAX-ACCESS  read-create
    STATUS      current
    DESCRIPTION
        "The value of tmnxMobProfPolUnitDwnlinkGbrRate specifies the expected
         downlink Guaranteed Bit Rate (GBR) provided by the GBR bearer."
    DEFVAL { 0 }
    ::= { tmnxMobProfPolUnitEntry 6 }

tmnxMobProfPolUnitDwnlinkMbrRate  OBJECT-TYPE
    SYNTAX      TmnxMobProfMbrRate
    UNITS       "kbps"
    MAX-ACCESS  read-create
    STATUS      current
    DESCRIPTION
        "The value of tmnxMobProfPolUnitDwnlinkMbrRate specifies the expected
         downlink Maximum Bit Rate (MBR) provided by the GBR bearer."
    DEFVAL { 0 }
    ::= { tmnxMobProfPolUnitEntry 7 }

tmnxMobProfPolUntFlwGateStatus  OBJECT-TYPE
    SYNTAX      INTEGER {
                         allowUL      (1),
                         allowDL      (2),
                         allow        (3),
                         drop         (4),
                         autoRedirect (5),
                         redirect     (6)
                        }
    MAX-ACCESS  read-create
    STATUS      current
    DESCRIPTION
        "The value of tmnxMobProfPolUntFlwGateStatus specifies gating behavior 
         associated with the policy rule unit.

         If the value of this object is set to 'allowUL', then IP packets that 
         match the flow-description entry will be allowed in the uplink 
         direction. If the value of this object is set to 'allowDL', then IP 
         packets that match the flow-description entry will be allowed in the 
         downlink direction. If the value of this object is set to 'allow', 
         then IP packets that match the flow-description entry will be allowed 
         in both the uplink and downlink directions. If the value of this object
         is set to 'drop', then IP packets that match the flow-description entry
         will be dropped in both the uplink and downlink directions. If the 
         value of this object is set to 'autoRedirect', then the subscriber's 
         requests will be redirected to a address specified by the online 
         charging server upon credit expiration. If the value of this object is
         set to 'redirect' then the subscriber's requests will be redirected to
         the address specified  by 'tmnxMobProfPolUntRedirectAddr' upon 
         credit expiration."
    DEFVAL { allow }
    ::= { tmnxMobProfPolUnitEntry 8 }

tmnxMobProfPolUntRedirectAdrType  OBJECT-TYPE
    SYNTAX      InetAddressType
    MAX-ACCESS  read-create
    STATUS      current
    DESCRIPTION
        "The value of tmnxMobProfPolUntRedirectAdrType specifies the type of
         address represented by tmnxMobProfPolUntRedirectAddr."
    DEFVAL { unknown }
    ::= { tmnxMobProfPolUnitEntry 9 }

tmnxMobProfPolUntRedirectAddr  OBJECT-TYPE
    SYNTAX      InetAddress (SIZE (0..255))
    MAX-ACCESS  read-create
    STATUS      current
    DESCRIPTION
        "The value of tmnxMobProfPolUntRedirectAddr specifies the IP address 
         to redirect the http requests to upon credit expiration, when the
         value of tmnxMobProfPolUntFlwGateStatus is set to 'redirect'. If
         the value of the corresponding tmnxMobProfPolUntRedirectAdrType is 
         'dns', then the IP address will be obtained via DNS A-Record query."
    DEFVAL { ''H }
    ::= { tmnxMobProfPolUnitEntry 10 }

tmnxMobProfPolUntInUse OBJECT-TYPE
    SYNTAX      TruthValue
    MAX-ACCESS  read-only
    STATUS      current 
    DESCRIPTION
        "The value of tmnxMobProfPolUntInUse specifies if this policy rule unit
         profile is being used by one of the policy profiles." 
    DEFVAL  { false }
    ::= { tmnxMobProfPolUnitEntry 11 }

tmnxMobProfPolUntRefCount OBJECT-TYPE
    SYNTAX      Counter32 
    MAX-ACCESS  read-only
    STATUS      current 
    DESCRIPTION
        "The value of tmnxMobProfPolUntRefCount specifies the number of policy
         profiles referencing this policy rule unit profile." 
    ::= {  tmnxMobProfPolUnitEntry 12 }

--
--  Charging Rule Unit Table
--

tmnxMobProfChgUnitTblLstChgd  OBJECT-TYPE
    SYNTAX      TimeStamp
    MAX-ACCESS  read-only
    STATUS      current
    DESCRIPTION
        "The value of tmnxMobProfChgUnitTblLstChgd indicates the sysUpTime at
         the time of the last modification to tmnxMobProfChgUnitTable by adding,
         deleting an entry or change to a writable object in the table.

         If no changes were made to the table since the last re-initialization
         of the local network management subsystem, then this object contains
         a zero value."
    ::= { tmnxMobProfileGlobalObjs 25 }

tmnxMobProfChgUnitTable  OBJECT-TYPE
    SYNTAX      SEQUENCE OF TmnxMobProfChgUnitEntry
    MAX-ACCESS  not-accessible
    STATUS      current
    DESCRIPTION
        "The tmnxMobProfChgUnitTable has an entry for each charging rule unit 
         profile configured on the system. Charging rule unit profile defines
         charging parameters for policy control."
    ::= { tmnxMobProfileObjs 25 }

tmnxMobProfChgUnitEntry  OBJECT-TYPE
    SYNTAX      TmnxMobProfChgUnitEntry
    MAX-ACCESS  not-accessible
    STATUS      current
    DESCRIPTION
        "Each row entry represents a charging rule unit profile defined in the
         system. Entries can be created and deleted by the user."
    INDEX { tmnxMobProfChgUnitName }
    ::= { tmnxMobProfChgUnitTable 1 }

TmnxMobProfChgUnitEntry ::= SEQUENCE {
        tmnxMobProfChgUnitName              TmnxMobProfName,
        tmnxMobProfChgUnitRowStatus         RowStatus,
        tmnxMobProfChgUnitLastChanged       TimeStamp,
        tmnxMobProfChgUnitRatingGroup       Unsigned32,
        tmnxMobProfChgUnitServIdentifier    Unsigned32,
        tmnxMobProfChgUnitReportingLevel    TmnxMobProfPolReportingLevel,
        tmnxMobProfChgUnitChargingMethod    TmnxMobProfPolChargingMethod, 
        tmnxMobProfChgUnitMeteringMethod    TmnxMobProfPolMeteringMethod,
        tmnxMobProfChgUnitInUse             TruthValue,
        tmnxMobProfChgUnitRefCount          Counter32
    }

tmnxMobProfChgUnitName  OBJECT-TYPE
    SYNTAX      TmnxMobProfName
    MAX-ACCESS  not-accessible
    STATUS      current
    DESCRIPTION
        "The value of tmnxMobProfChgUnitName specifies the unique name of this
         charging rule unit profile."
    ::= { tmnxMobProfChgUnitEntry 1 }

tmnxMobProfChgUnitRowStatus  OBJECT-TYPE
    SYNTAX      RowStatus
    MAX-ACCESS  read-create
    STATUS      current
    DESCRIPTION
        "The value of tmnxMobProfChgUnitRowStatus specifies the row status of
         this entry. It is used for creation and deletion of this charging
         rule unit profile."
    ::= { tmnxMobProfChgUnitEntry 2 }

tmnxMobProfChgUnitLastChanged  OBJECT-TYPE
    SYNTAX      TimeStamp
    MAX-ACCESS  read-only
    STATUS      current
    DESCRIPTION
        "The value of tmnxMobProfChgUnitLastChanged indicates the timestamp of
         the last change to this row in tmnxMobProfChgUnitTable."
    ::= { tmnxMobProfChgUnitEntry 3 }

tmnxMobProfChgUnitRatingGroup  OBJECT-TYPE
    SYNTAX      Unsigned32 (0..4294967295)
    MAX-ACCESS  read-create
    STATUS      current
    DESCRIPTION
        "The value of tmnxMobProfChgUnitRatingGroup specifies the rating group 
         (charging key) for the Policy and Charging Control (PCC) rule used 
         for rating."
    DEFVAL { 0 }
    ::= { tmnxMobProfChgUnitEntry 4 }

tmnxMobProfChgUnitServIdentifier  OBJECT-TYPE
    SYNTAX      Unsigned32 (0..4294967295)
    MAX-ACCESS  read-create
    STATUS      current
    DESCRIPTION
        "The value of tmnxMobProfChgUnitServIdentifier specifies the service 
         used for the Policy and Charging Control (PCC) rule."
    DEFVAL { 0 }
    ::= { tmnxMobProfChgUnitEntry 5 }

tmnxMobProfChgUnitReportingLevel  OBJECT-TYPE
    SYNTAX      TmnxMobProfPolReportingLevel
    MAX-ACCESS  read-create
    STATUS      current
    DESCRIPTION
        "The value of tmnxMobProfChgUnitReportingLevel specifies the level at
         which the usage reporting for the Policy and Charging Control (PCC)
         rule is applicable."
    DEFVAL { ratingGrp }
    ::= { tmnxMobProfChgUnitEntry 6 }

tmnxMobProfChgUnitChargingMethod  OBJECT-TYPE
    SYNTAX      TmnxMobProfPolChargingMethod
    MAX-ACCESS  read-create
    STATUS      current
    DESCRIPTION
        "The value of tmnxMobProfChgUnitChargingMethod specifies the applicable 
         charging method for the service data flow specified in the Policy and 
         Charging Control (PCC) rule."
    DEFVAL { profChargingMtd }
    ::= { tmnxMobProfChgUnitEntry 7 }

tmnxMobProfChgUnitMeteringMethod  OBJECT-TYPE
    SYNTAX      TmnxMobProfPolMeteringMethod
    MAX-ACCESS  read-create
    STATUS      current
    DESCRIPTION
        "The value of tmnxMobProfChgUnitMeteringMethod specifies the applicable 
         metering-method for the service data flow specified in the Policy and 
         Charging Control (PCC) rule."
    DEFVAL { volBased }
    ::= { tmnxMobProfChgUnitEntry 8 }

tmnxMobProfChgUnitInUse    OBJECT-TYPE
    SYNTAX      TruthValue
    MAX-ACCESS  read-only
    STATUS      current
    DESCRIPTION
        "The value of tmnxMobProfChgUnitInUse specifies if this charging rule unit
         profile is being used by one of the policy profiles."
    DEFVAL { false }
    ::= { tmnxMobProfChgUnitEntry 9 }

tmnxMobProfChgUnitRefCount OBJECT-TYPE          
    SYNTAX      Counter32
    MAX-ACCESS  read-only
    STATUS      current
    DESCRIPTION
        "The value of tmnxMobProfChgUnitRefCount specifies the number of policy
         profiles referencing this charging rule unit profile."
    ::= { tmnxMobProfChgUnitEntry 10 }

--
--  HTTP redirect table
--

tmnxMobProfHTTPRedirctTblLstChgd    OBJECT-TYPE
    SYNTAX      TimeStamp
    MAX-ACCESS  read-only
    STATUS      current
    DESCRIPTION
        "The value of tmnxMobProfHTTPRedirctTblLstChgd indicates the sysUpTime
         at the time of the last modification to tmnxMobProfHTTPRedirectTable by
         adding, deleting an entry or change to a writable object in the table.

         If no changes were made to the table since the last re-initialization
         of the local network management subsystem, then this object contains
         a zero value."
    ::= { tmnxMobProfileGlobalObjs 26 }

tmnxMobProfHTTPRedirectTable  OBJECT-TYPE
    SYNTAX      SEQUENCE OF TmnxMobProfHTTPRedirectEntry
    MAX-ACCESS  not-accessible
    STATUS      current
    DESCRIPTION
        "The tmnxMobProfHTTPRedirectTable has entries for HTTP redirect profiles
         configured on the system. Each HTTP redirect profile includes multiple
         policy rule unit profiles which determine the rules to be applied when
         in re-direct state."
    ::= { tmnxMobProfileObjs 26 }

tmnxMobProfHTTPRedirectEntry  OBJECT-TYPE
    SYNTAX      TmnxMobProfHTTPRedirectEntry
    MAX-ACCESS  not-accessible
    STATUS      current
    DESCRIPTION
        "Each row entry represents a HTTP redirect profile defined in the system.
         Entries can be created and deleted by the user."

    INDEX { tmnxMobProfHttpRedirectName,
            tmnxMobProfPolUnitName 
          }
    ::= { tmnxMobProfHTTPRedirectTable 1 }

TmnxMobProfHTTPRedirectEntry  ::=  SEQUENCE {
       tmnxMobProfHttpRedirectName           TmnxMobProfName,
       tmnxMobProfHttpRedirectRowStatus      RowStatus,
       tmnxMobProfHttpRedirectLstChgd        TimeStamp,
       tmnxMobProfHttpRedirctPrecedence      TmnxMobStaticPolPrecedenceOrZero
    }

tmnxMobProfHttpRedirectName  OBJECT-TYPE
    SYNTAX      TmnxMobProfName
    MAX-ACCESS  not-accessible
    STATUS      current
    DESCRIPTION
        "The value of tmnxMobProfHttpRedirectName specifies the name of this HTTP
         redirect policy."
    ::= { tmnxMobProfHTTPRedirectEntry 1 }

tmnxMobProfHttpRedirectRowStatus  OBJECT-TYPE
    SYNTAX      RowStatus
    MAX-ACCESS  read-create
    STATUS      current
    DESCRIPTION
        "The value of tmnxMobProfHttpRedirectRowStatus specifies the row status of
         this entry. It is used for creation and deletion of this policy
         profile."
    ::= { tmnxMobProfHTTPRedirectEntry 2 }

tmnxMobProfHttpRedirectLstChgd  OBJECT-TYPE
    SYNTAX      TimeStamp
    MAX-ACCESS  read-only
    STATUS      current
    DESCRIPTION
        "The value of tmnxMobProfHttpRedirectLstChgd indicates the timestamp of
         the last change to this row in tmnxMobProfHTTPRedirectTable."
    ::= { tmnxMobProfHTTPRedirectEntry 3 }

tmnxMobProfHttpRedirctPrecedence  OBJECT-TYPE
    SYNTAX      TmnxMobStaticPolPrecedenceOrZero
    MAX-ACCESS  read-create
    STATUS      current
    DESCRIPTION
        "The value of tmnxMobProfHttpRedirctPrecedence specifies the precedence
         value of this policy rule unit profile."
    DEFVAL { 0 }
    ::= { tmnxMobProfHTTPRedirectEntry 4 }
       
-- ----------------------------------------------
-- Compliance Statements
-- ----------------------------------------------

tmnxMobProfV1v0Compliance  MODULE-COMPLIANCE
    STATUS      obsolete
    DESCRIPTION
        "The compliance statement for management of profiles for the
         mobile gateways on the Alcatel-Lucent 7750 Mobile Gateway systems 
         R1.0."
    MODULE
        MANDATORY-GROUPS {
            tmnxMobProfGlobalGroup,
            tmnxMobProfGroup,
            tmnxMobProfQciPolicyGroup,
            tmnxMobProfDiameterGroup,
            tmnxMobProfChargingGroup,
            tmnxMobProfGtpPrimeServerGroup,
            tmnxMobProfUmtsQosPolGroup
            -- tmnxMobProfUnsupportedGroup Not supported
        }
    ::= { tmnxMobProfileCompliances 1 }

tmnxMobProfV3v0Compliance  MODULE-COMPLIANCE
    STATUS      obsolete
    DESCRIPTION
        "The compliance statement for management of profiles for the
         mobile gateways on the Alcatel-Lucent 7750 Mobile Gateway systems 
         R3.0.

         This compliance statement was made obsolete in the R3.1 release. "
    MODULE
        MANDATORY-GROUPS {
            tmnxMobProfGlobalGroup,
            tmnxMobProfGroup,
            tmnxMobProfQciPolicyGroup,
            tmnxMobProfDiameterGroup,
            tmnxMobProfChargingGroup,
            tmnxMobProfGtpPrimeServerGroup,
            tmnxMobProfUmtsQosPolGroup,
            tmnxMobProfRadiusGroup,
            tmnxMobProfChargingV3Group,
            tmnxMobProfDccaGroup,
            tmnxMobProfGlobalV3Group,
            tmnxMobProfV3Group,
            tmnxMobProfPolicyRulesV3Group,
            tmnxMobProfPmipv6V3Group
            -- tmnxMobProfUnsupportedGroup Not supported
        }
    ::= { tmnxMobProfileCompliances 2 }

tmnxMobProf7xxxV10v0Compl  MODULE-COMPLIANCE
    STATUS      current
    DESCRIPTION
        "The compliance statement for management of profiles for the
         mobile gateways on the Alcatel-Lucent 7750 SROS R10.0."
    MODULE
        MANDATORY-GROUPS {
            tmnxMobProfChargingGroup,
            tmnxMobProfChargingV3Group,
            tmnxMobProfDccaGroup,
            tmnxMobProfDiameterGroup,
            tmnxMobProfGlobalGroup,
            tmnxMobProfGlobalV3Group,
            tmnxMobProfGroup,
            tmnxMobProfGtpPrimeServerGroup,
            tmnxMobProfPmipv6V3Group,
            tmnxMobProfPolicyRulesV31Group,
            tmnxMobProfPolicyRulesV3Group,
            tmnxMobProfQciPolicyGroup,
            tmnxMobProfRadiusGroup,
            tmnxMobProfUmtsQosPolGroup,
            tmnxMobProfV3Group,
            tmnxMobProfUnsupportedGroup
        }
    ::= { tmnxMobProfileCompliances 3 }

tmnxMobProfV4v0Compliance  MODULE-COMPLIANCE
    STATUS      current
    DESCRIPTION
        "The compliance statement for management of profiles for the
         mobile gateways on the Alcatel-Lucent 7750 Mobile Gateway systems 
         4.0 release."
    MODULE
        MANDATORY-GROUPS {
            tmnxMobProfChargingGroup,
            tmnxMobProfChargingV3Group,
            tmnxMobProfDccaGroup,
            tmnxMobProfDiameterGroup,
            tmnxMobProfGlobalGroup,
            tmnxMobProfGlobalV3Group,
            tmnxMobProfGroup,
            tmnxMobProfGtpPrimeServerGroup,
            tmnxMobProfPmipv6V3Group,
            tmnxMobProfPolicyRulesV31Group,
            tmnxMobProfPolicyRulesV3Group,
            tmnxMobProfQciPolicyGroup,
            tmnxMobProfRadiusGroup,
            tmnxMobProfUmtsQosPolGroup,
            tmnxMobProfV3Group,
            tmnxMobProfUnsupportedGroup,
            tmnxMobProfDccaV4v0Group

        }
    ::= { tmnxMobProfileCompliances 4 }

-- ----------------------------------------------
-- Units of Conformance
-- ----------------------------------------------

tmnxMobProfGlobalGroup  OBJECT-GROUP
    OBJECTS {
                tmnxMobProfSysTblLstChgd,
                tmnxMobProfDiaTblLstChgd,
                tmnxMobProfDiaPeerTblLstChgd,
                tmnxMobProfDiaPeerListTblLstChgd,
                tmnxMobProfGtpTblLstChgd,
                tmnxMobProfQciPolTblLstChgd,
                tmnxMobProfQciPolQciTblLstChgd,
                tmnxMobProfPeerListTblLstChgd,
                tmnxMobProfPeerListPeerTblLtCgd,
                tmnxMobProfPolTblLstChgd,
                tmnxMobProfPolUntFlowTblLstChgd,
                tmnxMobProfPolBaseTblLstChgd,
                tmnxMobProfSgwChargingTblLstChgd,
                tmnxMobProfPgwChargingTblLstChgd,
                tmnxMobGtpPriGrpTblLstChgd,
                tmnxMobGtpPriServerTblLstChgd,
                tmnxMobUmtsQosPolTblLstChgd,
                tmnxMobProfPmipv6TblLstChgd
            }
    STATUS      current
    DESCRIPTION
        "The group of global objects supporting management of profiles for the
         mobile gateways on the Alcatel-Lucent 7750 Mobile Gateway systems."
    ::= { tmnxMobProfileGroups 1 }

tmnxMobProfGroup  OBJECT-GROUP
    OBJECTS {
                tmnxMobProfSysRowStatus,
                tmnxMobProfSysLastChanged,
                tmnxMobProfSysBCLimit,
                tmnxMobProfSysBCActivtyRate,
                tmnxMobProfSysBCPdnLimit,
                tmnxMobProfSysBCUeLimit,
                tmnxMobProfSysSDFIpv4Limit,
                tmnxMobProfSysSDFIpv6Limit,
                tmnxMobProfSysCpuThreshldCriticl,
                tmnxMobProfSysCpuThreshldMajor,
                tmnxMobProfSysCpuThreshldMinor,
                tmnxMobProfSysMemThreshldCriticl,
                tmnxMobProfSysMemThreshldMajor,
                tmnxMobProfSysMemThreshldMinor,
                tmnxMobProfSysSgnlFailThrshldS5,
                tmnxMobProfSysSgnlFailThrshldS8,
                tmnxMobProfSysSgnlFailThrshldS11,
                tmnxMobProfSysSgnlFailThrshldGxc,
                tmnxMobProfSysTrfcDropThrshldS1u,
                tmnxMobProfSysTrfcDropThrshldS5,
                tmnxMobProfSysTrfcDropThrshldS8,
                tmnxMobProfSysPagingBufferLimit,
                tmnxMobProfSysPagingBufferSize,
                tmnxMobProfSysPagingTimeout,
                tmnxMobProfSysS1BufferLimit,
                tmnxMobProfSysS1BufferSize,
                tmnxMobProfGtpRowStatus,
                tmnxMobProfGtpLastChanged,
                tmnxMobProfGtpMsgReTxTimeout,
                tmnxMobProfGtpMsgReTxRetryCnt,
                tmnxMobProfGtpKeepAlvTimeout,
                tmnxMobProfGtpKeepAlvRetryCnt,
                tmnxMobProfGtpKeepAlvResp,
                tmnxMobProfGtpIpTtl,
                tmnxMobProfGtpIpDscp
            }
    STATUS      current
    DESCRIPTION
        "The group of objects supporting management of profiles for the
         mobile gateways on the Alcatel-Lucent 7750 Mobile Gateway systems."
    ::= { tmnxMobProfileGroups 2 }

tmnxMobProfQciPolicyGroup  OBJECT-GROUP
    OBJECTS {
                tmnxMobProfQciPolRowStatus,
                tmnxMobProfQciPolLastChanged,
                tmnxMobProfQciPolQciLastChanged,
                tmnxMobProfQciPolQciDscpPreserve,
                tmnxMobProfQciPolQciDscp,
                tmnxMobProfQciPolQciDscpOut,
                tmnxMobProfQciPolQciFcName,
                tmnxMobProfQciPolQciProfile
            }
    STATUS      current
    DESCRIPTION
        "The group of objects supporting management of QCI policies for the
         mobile gateways on the Alcatel-Lucent 7750 Mobile Gateway systems."
    ::= { tmnxMobProfileGroups 3 }

tmnxMobProfDiameterGroup  OBJECT-GROUP
    OBJECTS {
                tmnxMobProfDiaRowStatus,
                tmnxMobProfDiaLastChanged,
                tmnxMobProfDiaWatchdgTimer,
                tmnxMobProfDiaConnTimer,
                tmnxMobProfDiaTransTimer,
                tmnxMobProfDiaIpTtl,
                tmnxMobProfDiaIpDscp,
                tmnxMobProfDiaDprTimeout,
                tmnxMobProfDiaPermFailRetryTime,
                tmnxMobProfDiaDnsRefreshInt,
                tmnxMobProfDiaPeerRowStatus,
                tmnxMobProfDiaPeerLastChanged,
                tmnxMobProfDiaPeerDiaProfName,
                tmnxMobProfDiaPeerDestRealm,
                tmnxMobProfDiaPeerTransport,
                tmnxMobProfDiaPeerLoadBalance,
                tmnxMobProfDiaPeerIfVRtrId,
                tmnxMobProfDiaPeerIfIndex,
                tmnxMobProfDiaPeerApplication,
                tmnxMobProfDiaPeerListRowStatus,
                tmnxMobProfDiaPeerListLastChngd, 
                tmnxMobProfDiaPeerListAddrType,
                tmnxMobProfDiaPeerListAddr,
                tmnxMobProfDiaPeerListPort,
                tmnxMobProfDiaPeerAdminState
            }
    STATUS      current
    DESCRIPTION
        "The group of objects supporting management of the diameter profiles for 
         the mobile gateways on the Alcatel-Lucent 7750 Mobile Gateway systems."
    ::= { tmnxMobProfileGroups 4 }

tmnxMobProfUnsupportedGroup  OBJECT-GROUP
    OBJECTS {
                tmnxMobProfPlmnListTblLstChgd,
                tmnxMobProfPlmnListRowStatus,
                tmnxMobProfSysDescription,
                tmnxMobProfDiaDescription,
                tmnxMobProfDiaPeerDescription,
                tmnxMobProfGtpDescription,
                tmnxMobProfQciPolDescription
            }
    STATUS      current
    DESCRIPTION
        "This group of objects is not supported on the Alcatel-Lucent 7750 
         Mobile Gateway systems."
    ::= { tmnxMobProfileGroups 5 }

tmnxMobProfChargingGroup  OBJECT-GROUP
    OBJECTS {
                tmnxMobProfSgwChrgRowStatus,
                tmnxMobProfSgwChrgLastChanged,
                tmnxMobProfSgwChrgDesc,
                tmnxMobProfSgwChrgOffLineState,
                tmnxMobProfSgwChrgPriCdfDiaPeer,
                tmnxMobProfSgwChrgSecCdfDiaPeer,
                tmnxMobProfSgwChrgCitQosChange, 
                tmnxMobProfSgwChrgCitUsrLocChnge,
                tmnxMobProfSgwChrgCitTrfTimeChng,
                tmnxMobProfSgwChrgCitTrfTmStart,
                tmnxMobProfSgwChrgCitTrfTmEnd,
                tmnxMobProfSgwChrgPrctTimeLmt,
                tmnxMobProfSgwChrgPrctVolumeLmt,
                tmnxMobProfSgwChrgPrctMaxChCond,
                tmnxMobProfSgwChrgPrctMsTmzChnge,
                tmnxMobProfSgwChrgPrctPlmnChange,
                tmnxMobProfSgwChrgPrctRatChange,
                tmnxMobProfSgwChrgPrctMgmtInterv,
                tmnxMobProfPgwChrgRowStatus,
                tmnxMobProfPgwChrgLastChanged,
                tmnxMobProfPgwChrgDesc,
                tmnxMobProfPgwChrgOffLineState,
                tmnxMobProfPgwChrgPriCdfDiaPeer,
                tmnxMobProfPgwChrgSecCdfDiaPeer,
                tmnxMobProfPgwChrgCitQosChange, 
                tmnxMobProfPgwChrgCitUsrLocChnge,
                tmnxMobProfPgwChrgCitTrfTimeChng,
                tmnxMobProfPgwChrgCitTrfTmStart,
                tmnxMobProfPgwChrgCitTrfTmEnd,
                tmnxMobProfPgwChrgCitSgwChange,
                tmnxMobProfPgwChrgCitTimeLmtRg,
                tmnxMobProfPgwChrgCitVolumeLmtRg,
                tmnxMobProfPgwChrgCitTermServDf,
                tmnxMobProfPgwChrgPrctTimeLmt,
                tmnxMobProfPgwChrgPrctVolumeLmt,
                tmnxMobProfPgwChrgPrctMaxChCond,
                tmnxMobProfPgwChrgPrctMsTmzChnge,
                tmnxMobProfPgwChrgPrctPlmnChange,
                tmnxMobProfPgwChrgPrctRatChange
            }
    STATUS      current
    DESCRIPTION
        "The group of objects supporting management of the charging profiles for 
         the mobile gateways on the Alcatel-Lucent 7750 Mobile Gateway systems."
    ::= { tmnxMobProfileGroups 6 }

tmnxMobProfGtpPrimeServerGroup  OBJECT-GROUP
    OBJECTS {
                tmnxMobGtpPriGrpRowStatus,
                tmnxMobGtpPriGrpLastChanged,
                tmnxMobGtpPriGrpDescription,
                tmnxMobGtpPriGrpMaxCdrsPerPdu,
                tmnxMobGtpPriGrpDeadtime,
                tmnxMobGtpPriGrpRedirection,
                tmnxMobGtpPriGrpIfVRtrId,
                tmnxMobGtpPriGrpIfIndex,
                tmnxMobGtpPriGrpLocalCdrStorage,
                tmnxMobGtpPriGrpFilePrivateInfo,
                tmnxMobGtpPriGrpFileExtension,
                tmnxMobGtpPriGrpFileClosureSize,
                tmnxMobGtpPriGrpFileClsLifeTime,
                tmnxMobGtpPriGrpFileClsMaxRecs,
                tmnxMobGtpPriGrpFileObsoleteTime,
                tmnxMobGtpPriGrpPrimaryCf,
                tmnxMobGtpPriGrpCf1State,
                tmnxMobGtpPriGrpCf1Limit,
                tmnxMobGtpPriGrpCf2State,
                tmnxMobGtpPriGrpCf2Limit,
                tmnxMobGtpPriGrpCpmMemoryState,
                tmnxMobGtpPriGrpQueueSize,
                tmnxMobGtpPriGrpAdminState,
                tmnxMobGtpPriGrpInactiveTimer,
                tmnxMobGtpPriServerRowStatus,
                tmnxMobGtpPriServerLastChngd,
                tmnxMobGtpPriServerAdminState,
                tmnxMobGtpPriServerAddrType,
                tmnxMobGtpPriServerAddr,
                tmnxMobGtpPriServerPort,
                tmnxMobGtpPriServerRetries,
                tmnxMobGtpPriServerTimeout,
                tmnxMobGtpPriServerEchoInterval,
                tmnxMobGtpPriServerMaxRequests,
                tmnxMobGtpPriServerNodeAlive,
                tmnxMobGtpPriServerPriority,
                tmnxMobGtpPriServerPathProtocol                
            }
    STATUS      current
    DESCRIPTION
        "The group of objects supporting management of the GPRS Tunneling 
         Protocol (GTP) Prime Server Groups for the mobile gateways on the 
         Alcatel-Lucent 7750 Mobile Gateway systems."
    ::= { tmnxMobProfileGroups 8 }

tmnxMobProfUmtsQosPolGroup  OBJECT-GROUP
    OBJECTS {
                tmnxMobUmtsQosPolRowStatus,
                tmnxMobUmtsQosPolLastChanged,
                tmnxMobUmtsQosPolConvSpeechQci,
                tmnxMobUmtsQosPolConvUnkTdg,
                tmnxMobUmtsQosPolConvUnkTdl,
                tmnxMobUmtsQosPolStreamQciValue,
                tmnxMobUmtsQosPolInterSigP1Qci,
                tmnxMobUmtsQosPolInterP1Qci,
                tmnxMobUmtsQosPolInterP2Qci,
                tmnxMobUmtsQosPolInterP3Qci,
                tmnxMobUmtsQosPolBackground
            }
    STATUS      current
    DESCRIPTION
        "The group of objects supporting management of the Universal Mobile 
         Telecommunications System (UMTS) Quality of Service (QoS) Policy 
         for the mobile gateways on the Alcatel-Lucent 7750 Mobile Gateway
         systems."
    ::= { tmnxMobProfileGroups 9 }

tmnxMobProfRadiusGroup  OBJECT-GROUP
    OBJECTS {
                tmnxMobProfRadRowStatus,
                tmnxMobProfRadLastChanged,
                tmnxMobProfRadDescription,
                tmnxMobProfRadAuthProbeInt,
                tmnxMobProfRadServerDeadTime,
                tmnxMobProfRadRetryTimeout,
                tmnxMobProfRadRetryCount,
                tmnxMobProfRadGrpRowStatus,
                tmnxMobProfRadGrpLastChanged,
                tmnxMobProfRadGrpDescription,
                tmnxMobProfRadGrpIfVRtrId,
                tmnxMobProfRadGrpIfIndex,
                tmnxMobProfRadGrpAuthServerPort,
                tmnxMobProfRadGrpAcctServerPort,
                tmnxMobProfRadGrpSecret,
                tmnxMobProfRadGrpIntUpdateIntvl,
                tmnxMobProfRadGrpServerType,
                tmnxMobProfRadGrpRadiusProfile,
                tmnxMobProfRadGrpIgnAcctResp,
                tmnxMobProfRadPeerRowStatus,
                tmnxMobProfRadPeerLastChngd,
                tmnxMobProfRadPeerAdminState,
                tmnxMobProfRadPeerAddrType,
                tmnxMobProfRadPeerAddr,
                tmnxMobProfRadPeerPriority,
                tmnxMobProfRadPeerAuthSvrPort,
                tmnxMobProfRadPeerAcctSvrPort,
                tmnxMobProfRadPeerSecret,
                tmnxMobProfRadPeerRadProfile
            }
    STATUS      current
    DESCRIPTION
        "The group of objects supporting management of the radius profiles for 
         the mobile gateways on the Alcatel 7750 series systems."
    ::= { tmnxMobProfileGroups 10 }

tmnxMobProfChargingV3Group  OBJECT-GROUP
    OBJECTS {
                tmnxMobProfPgwChrgGyState,
                tmnxMobProfPgwGyPriOcsDiaPeer,
                tmnxMobProfPgwGySecOcsDiaPeer,
                tmnxMobProfPgwGyDccaProf,
                tmnxMobProfPgwChrgPrctSrvNdChLmt,
                tmnxMobProfSgwChrgPrctSrvNdChLmt
            }
    STATUS      current
    DESCRIPTION
        "The group of objects supporting management of the charging profiles for 
         the mobile gateways on the Alcatel-Lucent 7750 Mobile Gateway systems 
         in 3.0 release."
    ::= { tmnxMobProfileGroups 11 }

tmnxMobProfDccaGroup  OBJECT-GROUP
    OBJECTS {
                tmnxMobProfDccaRowStatus,
                tmnxMobProfDccaLastChanged,
                tmnxMobProfDccaDescription,
                tmnxMobProfDccaApplTxTimer,
                tmnxMobProfDccaRetryCnt,
                tmnxMobProfDcca3GppQosNegProf,
                tmnxMobProfDccaQosInformation,
                tmnxMobProfDccaCalledStationId,
                tmnxMobProfDccaCcSessFailover,
                tmnxMobProfDccaCcSessFlovrHndl,
                tmnxMobProfDccaForcedReAuth,
                tmnxMobProfDccaQuotaExNoThrsld,
                tmnxMobProfDccaQuotaExThrsldAct,
                tmnxMobProfDccaQuotaUnavail,
                tmnxMobProfDccaRatingCondtChng,
                tmnxMobProfDccaValidityTimeExp       
            }
    STATUS      current
    DESCRIPTION
        "The group of objects supporting management of the Diameter Credit
         Control Application (DCCA) profiles for the mobile gateways on the
         Alcatel-Lucent 7750 Mobile Gateway systems."
    ::= { tmnxMobProfileGroups 12 }

tmnxMobProfGlobalV3Group  OBJECT-GROUP
    OBJECTS {
                tmnxMobProfDccaTblLstChgd,
                tmnxMobProfRadTblLstChgd,
                tmnxMobProfRadGrpTblLstChgd,
                tmnxMobProfRadPeerTblLstChgd,
                tmnxMobProfPolUnitTblLstChgd,
                tmnxMobProfChgUnitTblLstChgd,
                tmnxMobProfHTTPRedirctTblLstChgd
            }
    STATUS      current
    DESCRIPTION
        "The group of global objects supporting management of profiles for the
         mobile gateways on the Alcatel-Lucent 7750 Mobile Gateway systems 
         in 3.0 release."
    ::= { tmnxMobProfileGroups 13 }

tmnxMobProfV3Group  OBJECT-GROUP
    OBJECTS {
                tmnxMobProfPeerListRowStatus,
                tmnxMobProfPeerListLastChanged,
                tmnxMobProfPeerListDescription,
                tmnxMobProfPeerListPeerRowStatus,
                tmnxMobProfPeerListPeerLastChgd,
                tmnxMobProfPeerListPeerDesc,
                tmnxMobProfPeerListPeerKeepAlive,
                tmnxMobProfPeerListPeerAdmnState,        
                tmnxMobProfPeerListPeerRatType,
                tmnxMobProfPeerListPeerForeign,
                tmnxMobProfPeerListPeerPlmnMcc,
                tmnxMobProfPeerListPeerPlmnMnc
            }
    STATUS      current
    DESCRIPTION
        "The group of objects supporting management of profiles for the
         mobile gateways on the Alcatel-Lucent 7750 Mobile Gateway systems
         in 3.0 release."
    ::= { tmnxMobProfileGroups 14 }

tmnxMobProfPolicyRulesV3Group  OBJECT-GROUP
    OBJECTS {
                tmnxMobProfPolRowStatus,
                tmnxMobProfPolLastChanged,
                tmnxMobProfPolRuleUnitName,
                tmnxMobProfChgRuleUnitName,
                tmnxMobProfPolQciValue,
                tmnxMobProfPolArpValue,
                tmnxMobProfPolUntFlwRowStatus,
                tmnxMobProfPolUntFlwLastChanged,
                tmnxMobProfPolUntFlwDirection,
                tmnxMobProfPolUntFlwMatchPrtcl,
                tmnxMobProfPolUntFlwLclAddrType,
                tmnxMobProfPolUntFlwLclAddr,
                tmnxMobProfPolUntFlwLclPrefixLen,
                tmnxMobProfPolUntFlwRmtAddrType,
                tmnxMobProfPolUntFlwRmtAddr,
                tmnxMobProfPolUntFlwRmtPrefixLen,
                tmnxMobProfPolUntFlwLclPortVal1,
                tmnxMobProfPolUntFlwLclPortVal2,
                tmnxMobProfPolUntFlwLclPortOper,
                tmnxMobProfPolUntFlwRmtPortVal1,
                tmnxMobProfPolUntFlwRmtPortVal2,
                tmnxMobProfPolUntFlwRmtPortOper,
                tmnxMobProfPolBaseRowStatus,
                tmnxMobProfPolBaseLastChanged,
                tmnxMobProfPolBasePrecedence,
                tmnxMobProfPolBasePreActivate,
                tmnxMobProfPolUnitRowStatus,
                tmnxMobProfPolUnitLastChanged,
                tmnxMobProfPolUnitUplinkGbrRate,
                tmnxMobProfPolUnitUplinkMbrRate,
                tmnxMobProfPolUnitDwnlinkGbrRate,
                tmnxMobProfPolUnitDwnlinkMbrRate,
                tmnxMobProfPolUntFlwGateStatus,
                tmnxMobProfChgUnitRowStatus,
                tmnxMobProfChgUnitLastChanged,
                tmnxMobProfChgUnitRatingGroup,
                tmnxMobProfChgUnitServIdentifier,
                tmnxMobProfChgUnitReportingLevel,
                tmnxMobProfChgUnitChargingMethod, 
                tmnxMobProfChgUnitMeteringMethod,
                tmnxMobProfPolPrecedence,
                tmnxMobProfHttpRedirectRowStatus,
                tmnxMobProfHttpRedirectLstChgd,
                tmnxMobProfPolUntRedirectAdrType,
                tmnxMobProfPolUntRedirectAddr,
                tmnxMobProfPolUntFlwAaApp,
                tmnxMobProfHttpRedirctPrecedence,
                tmnxMobProfPolUntInUse,
                tmnxMobProfPolUntRefCount,
                tmnxMobProfPolInUse,
                tmnxMobProfPolRefCount,
                tmnxMobProfChgUnitInUse,
                tmnxMobProfChgUnitRefCount,
                tmnxMobProfPolBaseInUse, 
                tmnxMobProfPolBaseRefCount
            }
    STATUS      current
    DESCRIPTION
        "The group of objects supporting management of static policy rules for 
         the mobile gateways on the Alcatel-Lucent 7750 Mobile Gateway systems 
         in 3.0 release."
    ::= { tmnxMobProfileGroups 15 }

tmnxMobProfPmipv6V3Group  OBJECT-GROUP
    OBJECTS {
                tmnxMobProfPmipv6RowStatus,
                tmnxMobProfPmipv6LastChanged,
                tmnxMobProfPmipv6Description,
                tmnxMobProfPmipv6MsgReTxTimeout,
                tmnxMobProfPmipv6MsgReTxRetryCnt,
                tmnxMobProfPmipv6KeepAlvTimeout,
                tmnxMobProfPmipv6KeepAlvRetryCnt,
                tmnxMobProfPmipv6IpTtl,
                tmnxMobProfPmipv6IpDscp,
                tmnxMobProfPmipv6KeepAlvIntvl
            }
    STATUS      current
    DESCRIPTION
        "The group of objects supporting management of PMIPv6 profiles for 
         the mobile gateways on the Alcatel-Lucent 7750 Mobile Gateway systems 
         in 3.0 release."
    ::= { tmnxMobProfileGroups 16 }

tmnxMobProfileObsoletedGroup  OBJECT-GROUP
    OBJECTS {
                tmnxMobProfSgwChrgCitSgwChange
            }
    STATUS      current
    DESCRIPTION
        "The group of obsoleted objects which are no longer supported in the 3.0 
         release on the Alcatel-Lucent 7750 Mobile Gateway Systems."
    ::= { tmnxMobProfileGroups 17 }

tmnxMobProfPolicyRulesV31Group  OBJECT-GROUP
    OBJECTS {
                tmnxMobProfPolBaseConfRefCount,
                tmnxMobProfPolConfRefCount
            }
    STATUS      current
    DESCRIPTION
        "The group of objects supporting management of static policy rules for 
         the mobile gateways on the Alcatel-Lucent 7750 Mobile Gateway systems 
         in 3.1 release."
    ::= { tmnxMobProfileGroups 18 }

tmnxMobProfDccaV4v0Group  OBJECT-GROUP
    OBJECTS {
                tmnxMobProfDccaFhSessContTimer,
                tmnxMobProfDccaDefaultQht,
                tmnxMobProfDccaFirstPktBehavior      
            }
    STATUS      current
    DESCRIPTION
        "The group of objects supporting management of the Diameter Credit
         Control Application (DCCA) profiles for the mobile gateways on the
         Alcatel-Lucent 7750 Mobile Gateway systems in 4.0 release."
    ::= { tmnxMobProfileGroups 19 }

END
