--       TIMETRA ROUTE POLICY Management Information Base

TIMETRA-ROUTE-POLICY-MIB DEFINITIONS ::= BEGIN

IMPORTS
    IpAddress, MODULE-IDENTITY, OBJECT-TYPE, 
    Unsigned32
        FROM SNMPv2-SMI

    MODULE-COMPLIANCE, OBJECT-GROUP
        FROM SNMPv2-CONF

    DisplayString, RowStatus, TruthValue,
    TEXTUAL-CONVENTION, TimeInterval, TimeStamp
        FROM SNMPv2-TC

    InterfaceIndexOrZero
        FROM IF-MIB
        
    InetAddress, InetAddressType, InetAddressPrefixLength,
    InetAutonomousSystemNumber
        FROM INET-ADDRESS-MIB

    timetraSRMIBModules, tmnxSRObjs, tmnxSRNotifyPrefix,
    tmnxSRConfs
        FROM TIMETRA-GLOBAL-MIB

    IpAddressPrefixLength, TNamedItem, TNamedItemOrEmpty,
    TItemDescription, TmnxBgpAutonomousSystem, TmnxBgpLocalPreference,
    TmnxBgpPreference, TmnxBGPFamilyType, TmnxEnabledDisabled,
    TmnxServId, TFCNameOrEmpty, TPriority, TPriorityOrUndefined
        FROM TIMETRA-TC-MIB
    ;

timetraRoutePolicyMIBModule   MODULE-IDENTITY
        LAST-UPDATED "201202281200Z"
        ORGANIZATION "Alcatel-Lucent"
        CONTACT-INFO
            "Alcatel-Lucent SROS Support
             Web: http://support.alcatel-lucent.com"
        DESCRIPTION
        "This is the SNMP MIB module to manage and provision route policys 
         on Alcatel-Lucent SROS equipment.

         Copyright 2003-2012 Alcatel-Lucent. All rights reserved.
         Reproduction of this document is authorized on the condition that
         the foregoing copyright notice is included.

         This SNMP MIB module (Specification) embodies Alcatel-Lucent's
         proprietary intellectual property.  Alcatel-Lucent retains 
         all title and ownership in the Specification, including any 
         revisions.

         Alcatel-Lucent grants all interested parties a non-exclusive 
         license to use and distribute an unmodified copy of this 
         Specification in connection with management of Alcatel-Lucent
         products, and without fee, provided this copyright notice and 
         license appear on all copies.

         This Specification is supplied 'as is', and Alcatel-Lucent 
         makes no warranty, either express or implied, as to the use, 
         operation, condition, or performance of the Specification."

--
--  Revision History
--
        REVISION        "1202281200Z"
        DESCRIPTION     "Rev 10.0               28 Feb 2012 12:00
                         10.0 release of the TIMETRA-ROUTE-POLICY-MIB."

        REVISION        "1102010000Z"
        DESCRIPTION     "Rev 9.0                1 Feb 2011 00:00
                         9.0 release of the TIMETRA-ROUTE-POLICY-MIB."

        REVISION        "0902280000Z"
        DESCRIPTION     "Rev 7.0                28 Feb 2009 00:00
                         7.0 release of the TIMETRA-ROUTE-POLICY-MIB."

        REVISION        "0801010000Z"   
        DESCRIPTION     "Rev 6.0                01 Jan 2008 00:00
                         6.0 release of the TIMETRA-ROUTE-POLICY-MIB."

        REVISION        "0603230000Z"   
        DESCRIPTION     "Rev 4.0                23 Mar 2006 00:00
                         4.0 release of the TIMETRA-ROUTE-POLICY-MIB."

        REVISION        "0501240000Z"   
        DESCRIPTION     "Rev 2.1                24 Jan 2005 00:00
                         2.1 release of the TIMETRA-ROUTE-POLICY-MIB."

        REVISION        "0401150000Z"
        DESCRIPTION     "Rev 2.0                15 Jan 2004 00:00
                         2.0 release of the TIMETRA-ROUTE-POLICY-MIB."

        REVISION        "0308150000Z"
        DESCRIPTION     "Rev 1.2                15 Aug 2003 00:00
                         1.2 release of the TIMETRA-ROUTE-POLICY-MIB."

        REVISION        "200301200000Z"
        DESCRIPTION     "Rev 1.0                20 Jan 2003 00:00
                         1.0 Release of the TIMETRA-ROUTE-POLICY-MIB."

        REVISION        "200104300000Z"
        DESCRIPTION     "Rev 0.1                30 Apr 2001 00:00
                         Initial version of the TIMETRA-ROUTE-POLICY-MIB."

        ::= { timetraSRMIBModules 17 }

tRoutePolicyObjects         OBJECT IDENTIFIER ::= { tmnxSRObjs 17 }
tRoutePolicyNotifyPrefix   OBJECT IDENTIFIER ::= { tmnxSRNotifyPrefix 17 }
    tRoutePolicyNotifications   OBJECT IDENTIFIER ::= { tRoutePolicyNotifyPrefix 0 }
tmnxRoutePolicyConformance  OBJECT IDENTIFIER ::= { tmnxSRConfs 17 }

tRPOperObjects              OBJECT IDENTIFIER ::= { tRoutePolicyObjects 1 }
tRPAdminObjects             OBJECT IDENTIFIER ::= { tRoutePolicyObjects 2 }


--
-- textual conventions
--

TASPathName ::= TEXTUAL-CONVENTION
    STATUS       current
    DESCRIPTION 
        "The name of an AS path. An empty string indicates that no 
         AS Path has been specified and is invalid when used as an 
         index for a table."
    SYNTAX TNamedItemOrEmpty
        
TCommunityName ::= TEXTUAL-CONVENTION
    STATUS       current
    DESCRIPTION 
        "The name of a community. An empty string indicates that no 
         community has been specified and is invalid when used as an 
         index for a table."
    SYNTAX TNamedItemOrEmpty
        
TCommunityMember ::= TEXTUAL-CONVENTION
    STATUS       current
    DESCRIPTION 
        "The member of a community. Can be one of the following:
         1) [1..65535]:[0..65535]
         2) An extended community in one of the following formats
            - target:[0..65535]:[0..4294967295] 
            - origin:[0..65535]:[0..4294967295]
            - target:<ip-address>:[0..65535]
            - origin:<ip-address>:[0..65535]
            - target:[4-byte AS number]:[0..65535]
            - origin:[4-byte AS number]:[0..65535]
                4-byte AS number - [0..4294967295]
            - target:<regular-expression>&<regular-expression>
            - target:<ip-address>&<regular-expression>
         3) A regular expression 
         4) A well known community i.e. one of the following keywords
            - no-advertise
            - no-export
            - no-export-subconfed
            - null."
    SYNTAX DisplayString (SIZE(1..72))

TCommunityExpression ::= TEXTUAL-CONVENTION
    STATUS       current
    DESCRIPTION 
        "TCommunityExpression specifies a logical expression containing
         terms and operators. It can contain sub-expressions enclosed by
         round brackets. Terms, operators and brackets are separated by a
         space character.

         A term is a string of type TCommunityMember.

         An operator can be the string 'AND', 'OR', and 'NOT'."
    SYNTAX DisplayString

TDampingName ::= TEXTUAL-CONVENTION
    STATUS       current
    DESCRIPTION 
        "The name of a route damping policy. An empty string indicates
         that no damping policy has been specified and is invalid when
         used as an index for a table."
    SYNTAX TNamedItemOrEmpty
        
TPrefixListName ::= TEXTUAL-CONVENTION
    STATUS       current
    DESCRIPTION 
        "The name of a prefix list. An empty string indicates that no 
         prefix list has been specified and is invalid when used as an 
         index for a table."
    SYNTAX TNamedItemOrEmpty
        
TPolicyStatementName ::= TEXTUAL-CONVENTION
    STATUS       current
    DESCRIPTION 
        "The name of a policy statement when used as an index to a table."
    SYNTAX TNamedItem
      
TRegularExpression  ::= TEXTUAL-CONVENTION
    STATUS       current
    DESCRIPTION 
    "A regular expression string.
        
    The Regular expression string matches against
    1) an AS_PATH string e.g. '100 200 300', 
    2) a community string e.g. '100:200' where 100 is the as-number, 
       and 200 is the community-value.
       
    The regular expression is expressed in terms of a TERM, and an OPERATOR:

    A term is either:
    1) an AS Number 
    2) a community value e.g. in 100:200, we have three tokens: 
        (i)   100 is the as-number, 
        (ii)  ':' is the separator token, and 
        (iii) 200 is the community-value 
    3) '.' - DOT is a wild-card token which matches with either an AS Number
       or a Community.

    The list of operators are:
    1)  '|' - suggests an alternation.
    2)  '*' - multiple occurrences of the token.
    3)  '?' - 0 or 1 occurrence of token.
    4)  '+' - 1 or more occurrences of token.                     
    5)  '(' - is used to parenthesize so that a regular expression is 
              considered as one token.
    6)  ')' - closes the parenthesis.
    7)  '[' - used to demarcate range.
    8)  ']' - closes the box bracket.
    9)  '{m, [n]}' - suggest that the term can occur anywhere between m, and n
                     times.
    10) '^' - matches the beginning of the string - only allowed for 
              communities.
    11) '$' - matches the end of the string - only allowed for communities.
        
    Note, use only NVT ASCII displayable characters
    here, no control characters, no UTF-8, etc.

    The EBNF description for the regular expression string are:
    1) reg_ex ::= empty_string | non-empty_reg_ex
    2) non-empty_reg_ex ::= bounded_element | ( bounded_element '|' 
       non-empty_reg_ex )
    3) bounded_element ::= ['^'] element ['$']
    4) element ::= ( '(' list ')' | atomic ) ['*' | '?' | '+' | '{' integer 
       ',' [ integer ] '}' ] [element]
    5) list ::= element | (element '|' list)
    6) atomic ::=  '.' | ':' | '<' | '>' | atom_list
    7) atom_list ::= atom | ( '[' atom_list_boxed )
    8) atom_list_boxed ::= ( atom ']' ) | ( atom atom_list_boxed )
    9) (for as-path reg-ex)    atom ::= integer [ '-' integer ] 
       an atom is essentially EQUIVALENT to a TERM 
       (for community reg-ex)  atom ::= digit[ '-' digit ]
    NOTE -> atom_list_boxed is a list of integers ending in box bracket -
            BNF description is error-free."
    SYNTAX DisplayString

TPolicyStatementEntryID ::= TEXTUAL-CONVENTION
    STATUS       current
    DESCRIPTION 
        "Identification number for a policy statement entry. Entries are 
         sorted by ID number. Matching entries are evaluated in order from 
         lowest ID to highest ID.
        
         We suggest ordering policy statement entry IDs by 10s:  10, 20, 30, 
         etc., so entry insertions are easy."
    SYNTAX Unsigned32

TRoutePolicyProtocol ::= TEXTUAL-CONVENTION
    STATUS       current
    DESCRIPTION 
        "A list of routing protocols, for -to and -from policies."
    SYNTAX INTEGER { 
        none(1),
        direct(2),
        static(3),
        bgp(4),
        isis(5),
        ospf(6),
        rip(7),
        aggregate(8),
        bgpVpn(9),
        igmp(10),
        pim(11),
        ospf3(12),
        ldp(13),
        subscriber(14),
        mld(15),
        managed(16),
        msdp(17),
        vpnLeak(18),
        mobileHost(19),
        tms(20),
        nat(21),
        periodic(22),
        ipsec(23)
    }

TOspfRouteType  ::= TEXTUAL-CONVENTION
    STATUS       current
    DESCRIPTION 
        "The OSPF route type. Set to zero to disable."
    SYNTAX     INTEGER ( 0 | 1 | 2 )

TIsisLevel ::= TEXTUAL-CONVENTION
    STATUS       current
    DESCRIPTION
        "Indicates the ISIS Route Level match criterion. A value of 0 indicates
         no IS-IS route match criterion is configured. 

         There are two types of areas in IS-IS, namely Level 1 areas and Level 
         2 areas. Routers within a Level 1 area route to other routers in that 
         area. If the destination does not exist within the area, the Level 1 
         router will route toward a Level 2 router. Level 2 routers route 
         between areas and toward other ASs."
    SYNTAX       INTEGER ( 0 | 1 | 2 )

TPolicyEntryAction   ::= TEXTUAL-CONVENTION
    STATUS       current
    DESCRIPTION 
        "Action to take when route matches the entry's match criteria.

         accept(1) - perform the accept-action modifications, 
              advertise the route, do not evaluate any more policy entries.

         reject(2) - do not advertise the route, do not evaluate any more
              policy entries.

         continue(3) - perform the accept-action modifications, 
              evaluate the next policy entry in the policy statement.

         nextPolicy(4) - perform the accept-action modifications, 
              evaluate the next policy statement."
    SYNTAX       INTEGER { none(0), 
                           accept(1), 
                           reject(2), 
                           continue(3),
                           nextPolicy(4) }

TPolicyEntryEdit   ::= TEXTUAL-CONVENTION
    STATUS       current
    DESCRIPTION 
        "Editing action to take when route matches the entry's match criteria.

         none(1) - do not change the value in the route
        
         add(2) - add the corresponding objects to the route
        
         remove(3) - remove the corresponding objects to the route
        
         replace(4) - replace the value in the route with the 
                      corresponding object."
    SYNTAX       INTEGER { none(1), add(2), remove(3), replace(4) }

TPolicyEntryCriteriaOrigin   ::= TEXTUAL-CONVENTION
    STATUS       current
    DESCRIPTION 
        "Origin of the route.
        
         none(1) - ignore this criteria
        
         igp(2) - learned from an Interior Gateway Protocol (OSPF, ISIS, etc.)
        
         egp(3) - learned from an Exterior Gateway Protocol (BGP)
        
         incomplete(4) - Route origin is unknown (usually due to aggregation)
        
         any(5) - to or from either igp or egp

         aaa(6) - subscriber host address originated from aaa

         dhcp(7) - subscriber host address originated from dhcp

         ludb(8) - subscriber host address originated from local user database."
    SYNTAX       INTEGER { none(1),
                           igp(2),
                           egp(3),
                           incomplete(4),
                           any(5),
                           aaa(6),
                           dhcp(7),
                           ludb(8) }

TPolicyActionTag   ::= TEXTUAL-CONVENTION
    STATUS       current
    DESCRIPTION 
        "Tag value to set. Zero means disabled, no tag value will be set."
    SYNTAX       Unsigned32 (0..4294967295)

TPolicyEntryCriteriaState   ::= TEXTUAL-CONVENTION
    STATUS       current
    DESCRIPTION 
        "Generic criteria state.
        
         none(1) - ignore this criteria
        
         srrpMaster(2) - srrp-master
        
         srrpNonMaster(3) - srrp-non-master
         ipsecMaster (6), - Routes that are in ipsec-master with peer state
         ipsecMasterNoPeer (7), - Routes that are ipsec-master-without-peer
         ipsecNonMaster (8) - Routes that are in ipsec-non-master state."
    SYNTAX       INTEGER { none(1),
                           srrpMaster(2),
                           srrpNonMaster(3),
                           ipsecMaster (6),
                           ipsecMasterNoPeer (7),
                           ipsecNonMaster (8)
                         }

TPolicyActionMetricSource ::= TEXTUAL-CONVENTION
    STATUS       current
    DESCRIPTION  
        "The source of the Action Metric."
    SYNTAX       INTEGER { igpCost(1),
                           metricVal(2) }

TPolicyEntryAigpMetricEdit   ::= TEXTUAL-CONVENTION
    STATUS       current
    DESCRIPTION
        "Editing action to take when route matches the entry's match criteria.

         none(1)    - do not change the value in the route.
         add(2)     - add the corresponding object value to the aigp value
                      in the received route.
         replace(3) - replace the aigp value in the route with the 
                      corresponding object value.
         useIgp(4) - replace the aigp value in the route with the IGP cost."
    SYNTAX       INTEGER { none   (1), 
                           add    (2), 
                           replace(3), 
                           useIgp (4) }

--
-- mib objects
--

--
-- the requirements for this MIB are:
-- o allow user to add and remove route policies
-- o allow user to see the values used by route policies
-- o allow user to add, remove, and change any number of 
--   values used by route policies, at the same time.
--   
-- this MIB is split in to three sections:
-- o the route policy object operational objects
-- o the route policy object administrative objects
-- o the objects to control transactions (begin/commit/abort)
--   applying administrative add/remove/change objects to the
--   operational objects.
--   
-- for each route policy configuration area,
-- there are two MIB tables.  the operational tables
-- (tRPOperXXXXTable) can only be read, to show the 
-- running configuration of the route policies.
-- 
-- the administrative tables (tRPOperXXXXTable) can be 
-- read to show what the new object values will be at 
-- the next commit.  the administrative tables can 
-- be written to control add, change, and remove of 
-- operational table entries.
-- 
-- when new entries are created, the table entries will
-- exist in the administrative tables, but those table 
-- entries will not be created in 
-- the operational tables until committed.
-- 
-- 
-- the administrative tables are intended to support
-- changes from one user at a time.  Use tRPAdminSpinLock
-- to serialize access to the administrative tables
-- from separate users and management stations.
-- 
--
-- when a policy statement is created (tRPAdminPolicyStatementTable), 
-- a corresponding entry in tRPAdminPSDefaultActionParamsTable is 
-- also created.
-- 
-- when a policy statement entry is created (tRPAdminPSParamsTable),
-- corresponding entries in tRPAdminPSAcceptActionParamsTable,
-- tRPAdminPSToCriteriaTable, and tRPAdminPSFromCriteriaTable are 
-- also created.
-- 
-- similarly for deletion: when the policy statement entry is destroyed,
-- corresponding entries in tRPAdminPSAcceptActionParamsTable,
-- tRPAdminPSToCriteriaTable, and tRPAdminPSFromCriteriaTable are 
-- also destroyed.
-- 
-- when the policy statement is destroyed, corresponding entries
-- in tRPAdminPSDefaultActionTable, tRPAdminPSParamsTable 
-- and tRPAdminPSAcceptActionParamsTable,
-- tRPAdminPSToCriteriaTable, and tRPAdminPSFromCriteriaTable are 
-- also destroyed.
-- 
--


                                               

--
-- Operational value objects
--

tRPOperValueObjects OBJECT IDENTIFIER ::= { tRPOperObjects 1 }

--
-- route policy Operational value tables
--

--
-- AS Path 
--

tRPOperASPathTableLastChanged OBJECT-TYPE
    SYNTAX       TimeStamp
    MAX-ACCESS   read-only
    STATUS       obsolete
    DESCRIPTION
        "Timestamp of last change to tRPOperASPathTable.

         tRPOperASPathTableLastChanged is obsoleted in release 5.0.
         TIMETRA-SYSTEM-MIB::tmnxConfigModify notification is used instead."
    ::= { tRPOperValueObjects 1 }

tRPOperASPathTable OBJECT-TYPE
    SYNTAX       SEQUENCE OF TRPOperASPathEntry
    MAX-ACCESS   not-accessible
    STATUS       current
    DESCRIPTION
        "A list of AS Path names and corresponding regular-expressions."
    ::= { tRPOperValueObjects 2 }

tRPOperASPathEntry OBJECT-TYPE
    SYNTAX       TRPOperASPathEntry
    MAX-ACCESS   not-accessible
    STATUS       current
    DESCRIPTION 
        "Information about a particular AS Path Name.
         Entries are created by user, via tRPAdminASPathTable.
         Entries are deleted by user, via tRPAdminASPathTable.
        
         tRPAdminASPathTable entry must exist before referencing objects 
         {tRPOperPSDefaultActionASPathName, tRPOperPSAcceptActionASPathName,
         tRPOperPSToCriteriaASPathName, tRPOperPSFromCriteriaASPath}
         can be set to refer to the tRPOperASPathName."
    INDEX { tRPOperASPathName }
    ::= { tRPOperASPathTable 1 }

TRPOperASPathEntry ::= SEQUENCE
    {
        tRPOperASPathName      TASPathName,
        tRPOperASPathRowStatus RowStatus,
        tRPOperASPathRegEx     TRegularExpression,
        tRPOperASPathEntryLastChanged TimeStamp
    }

tRPOperASPathName  OBJECT-TYPE
    SYNTAX       TASPathName (SIZE(1..32))
    MAX-ACCESS   not-accessible
    STATUS       current
    DESCRIPTION 
        "The name of the AS Path entry used to uniquely identify an AS Path."
    ::= { tRPOperASPathEntry 1 }

tRPOperASPathRowStatus  OBJECT-TYPE
    SYNTAX       RowStatus
    MAX-ACCESS   read-only
    STATUS       current
    DESCRIPTION
        "RowStatus for this row. Values read will only be 
         active(1), notInService(2), notReady(3). To create
         or destroy entries in this table, use the 
         tRPAdminASPathTable."
    ::= { tRPOperASPathEntry 2 }

tRPOperASPathRegEx  OBJECT-TYPE
    SYNTAX       TRegularExpression
    MAX-ACCESS   read-only
    STATUS       current
    DESCRIPTION 
        "The regular expression for the AS Path entry."
    ::= { tRPOperASPathEntry 3 }
    
tRPOperASPathEntryLastChanged   OBJECT-TYPE
    SYNTAX       TimeStamp
    MAX-ACCESS   read-only
    STATUS       obsolete
    DESCRIPTION 
        "Timestamp of last change to this entry.

         tRPOperASPathEntryLastChanged is obsoleted in release 5.0.
         TIMETRA-SYSTEM-MIB::tmnxConfigModify notification is used instead."
    ::= { tRPOperASPathEntry 4 }
    
--
-- community members
--

tRPOperCommunityTableLastChanged OBJECT-TYPE
    SYNTAX       TimeStamp
    MAX-ACCESS   read-only
    STATUS       obsolete
    DESCRIPTION
        "Timestamp of last change to tRPOperCommunityTable.

         tRPOperCommunityTableLastChanged is obsoleted in release 5.0.
         TIMETRA-SYSTEM-MIB::tmnxConfigModify notification is used instead."
    ::= { tRPOperValueObjects 3 }

tRPOperCommunityTable OBJECT-TYPE
    SYNTAX       SEQUENCE OF TRPOperCommunityEntry
    MAX-ACCESS   not-accessible
    STATUS       current
    DESCRIPTION  
        "A table of community entries."
    ::= { tRPOperValueObjects 4 }

tRPOperCommunityEntry OBJECT-TYPE
    SYNTAX       TRPOperCommunityEntry
    MAX-ACCESS   not-accessible
    STATUS       current
    DESCRIPTION 
        "Information about a particular community member.
         Entries are created by user, via tRPAdminCommunityTable.
         Entries are deleted by user, via tRPAdminCommunityTable.
        
         There must be one entry for <community-name><member>, 
         or the <community-name> does not exist and can not be
         referenced {tRPAdminPSDefaultActionCommunityName, 
         tRPAdminPSAcceptActionCommunityName, tRPAdminPSToCriteriaCommunity
         tRPAdminPSFromCriteriaCommunity}."
    INDEX { tRPOperCommunityName, tRPOperCommunityMember }
    ::= { tRPOperCommunityTable 1 }

TRPOperCommunityEntry ::= SEQUENCE
    {
        tRPOperCommunityName               TCommunityName,
        tRPOperCommunityMember             TCommunityMember,
        tRPOperCommunityRowStatus          RowStatus,
        tRPOperCommunityEntryLastChanged   TimeStamp
    }

tRPOperCommunityName  OBJECT-TYPE
    SYNTAX       TCommunityName (SIZE(1..32))
    MAX-ACCESS   not-accessible
    STATUS       current
    DESCRIPTION 
        "The name of the community used as an index for this table."
    ::= { tRPOperCommunityEntry 1 }

tRPOperCommunityMember             OBJECT-TYPE
    SYNTAX       TCommunityMember
    MAX-ACCESS   not-accessible
    STATUS       current
    DESCRIPTION 
        "The AS Number or Community ID of the community member. The 
         community name and the member name uniquely identify a row 
         in this table."
    ::= { tRPOperCommunityEntry 2 }

tRPOperCommunityRowStatus  OBJECT-TYPE
    SYNTAX       RowStatus
    MAX-ACCESS   read-only
    STATUS       current
    DESCRIPTION
        "RowStatus for this row. Values read will only be 
         active(1), notInService(2), notReady(3). To create
         or destroy entries in this table, use the 
         tRPAdminCommunityTable."
    ::= { tRPOperCommunityEntry 3 }

tRPOperCommunityEntryLastChanged  OBJECT-TYPE
    SYNTAX       TimeStamp
    MAX-ACCESS   read-only
    STATUS       obsolete
    DESCRIPTION
        "Timestamp of last change to this entry.

         tRPOperCommunityEntryLastChanged is obsoleted in release 5.0.
         TIMETRA-SYSTEM-MIB::tmnxConfigModify notification is used instead."
    ::= { tRPOperCommunityEntry 4 }

--
-- damping 
--

tRPOperDampingTableLastChanged OBJECT-TYPE
    SYNTAX       TimeStamp
    MAX-ACCESS   read-only
    STATUS       obsolete
    DESCRIPTION
        "Timestamp of last change to tRPOperDampingTable.

         tRPOperDampingTableLastChanged is obsoleted in release 5.0.
         TIMETRA-SYSTEM-MIB::tmnxConfigModify notification is used instead."
    ::= { tRPOperValueObjects 5 }

tRPOperDampingTable OBJECT-TYPE
    SYNTAX       SEQUENCE OF TRPOperDampingEntry
    MAX-ACCESS   not-accessible
    STATUS       current
    DESCRIPTION  
        "A table of route damping control entries."
    ::= { tRPOperValueObjects 6 }

tRPOperDampingEntry OBJECT-TYPE
    SYNTAX       TRPOperDampingEntry
    MAX-ACCESS   not-accessible
    STATUS       current
    DESCRIPTION 
        "Information about a particular Damping entry.

         Entries are created by user, via tRPAdminDampingTable.
         Entries are deleted by user, via tRPAdminDampingTable.
        
         The entry for a damping name must exist before referring objects 
         (tRPAdminPSDefaultActionDamping, tRPAdminPSAcceptActionDamping)
         can be set to that name."
    INDEX { tRPOperDampingName }
    ::= { tRPOperDampingTable 1 }

TRPOperDampingEntry ::= SEQUENCE
    {
        tRPOperDampingName        TDampingName,
        tRPOperDampingRowStatus   RowStatus,
        tRPOperDampingHalfLife    Unsigned32,
        tRPOperDampingMaxSuppress Unsigned32,
        tRPOperDampingReuse       Unsigned32,
        tRPOperDampingSuppress    Unsigned32,
        tRPOperDampingEntryLastChanged TimeStamp
    }

tRPOperDampingName  OBJECT-TYPE
    SYNTAX       TDampingName (SIZE(1..32))
    MAX-ACCESS   not-accessible
    STATUS       current
    DESCRIPTION
        "The name of the damping entry used to uniquely identify a 
         row in this table."
    ::= { tRPOperDampingEntry 1 }

tRPOperDampingRowStatus  OBJECT-TYPE
    SYNTAX       RowStatus
    MAX-ACCESS   read-only
    STATUS       current
    DESCRIPTION
        "RowStatus for this row. Values read will only be 
         active(1), notInService(2), notReady(3). To create
         or destroy entries in this table, use the 
         tRPAdminDampingTable."
    ::= { tRPOperDampingEntry 2 }

tRPOperDampingHalfLife  OBJECT-TYPE
    SYNTAX       Unsigned32 (0..45)
    UNITS        "minutes"
    MAX-ACCESS   read-only
    STATUS       current
    DESCRIPTION 
        "Specifies the half-life, in minutes, for a routes figure-of-merit 
         after it has been dampened. If a route's half-life is set to 
         15 minutes and has a figure-of-merit of 1500, after 15 minutes, 
         the route's figure-of-merit will have decayed to 750. Set to 0 
         to disable."
    ::= { tRPOperDampingEntry 3 }

tRPOperDampingMaxSuppress  OBJECT-TYPE
    SYNTAX       Unsigned32 (0..720)
    UNITS        "minutes"
    MAX-ACCESS   read-only
    STATUS       current
    DESCRIPTION 
        "Specifies the maximum amount of time, in minutes, that a route 
         can be suppressed for. Set to 0 to disable."
    ::= { tRPOperDampingEntry 4 }

tRPOperDampingReuse  OBJECT-TYPE
    SYNTAX       Unsigned32 (0..20000)
    MAX-ACCESS   read-only
    STATUS       current
    DESCRIPTION 
        "Specifies the reuse threshold. If a route's figure-of-merit
         falls below the reuse threshold, the route can be reused.
         Set to 0 to disable."
    ::= { tRPOperDampingEntry 5 }

tRPOperDampingSuppress  OBJECT-TYPE
    SYNTAX       Unsigned32 (0..20000)
    MAX-ACCESS   read-only
    STATUS       current
    DESCRIPTION 
        "Specifies the suppress threshold. If a route's figure-of-merit
         goes above the suppress threshold, the route should be suppressed.
         Set to 0 to disable."
    ::= { tRPOperDampingEntry 6 }

tRPOperDampingEntryLastChanged   OBJECT-TYPE
    SYNTAX       TimeStamp
    MAX-ACCESS   read-only
    STATUS       obsolete
    DESCRIPTION 
        "Timestamp of last change to this entry.

         tRPOperDampingEntryLastChanged is obsoleted in release 5.0.
         TIMETRA-SYSTEM-MIB::tmnxConfigModify notification is used instead."
    ::= { tRPOperDampingEntry 7 }

--
-- prefix-list 
--

tRPOperPrefixListTableLastChanged OBJECT-TYPE
    SYNTAX       TimeStamp
    MAX-ACCESS   read-only
    STATUS       obsolete
    DESCRIPTION
        "Timestamp of last change to tRPOperPrefixListTable.

         tRPOperPrefixListTableLastChanged is obsoleted in release 5.0.
         TIMETRA-SYSTEM-MIB::tmnxConfigModify notification is used instead."
    ::= { tRPOperValueObjects 7 }

tRPOperPrefixListTable OBJECT-TYPE
    SYNTAX       SEQUENCE OF TRPOperPrefixListEntry
    MAX-ACCESS   not-accessible
    STATUS       current
    DESCRIPTION  
        "A table of prefix lists."
    ::= { tRPOperValueObjects 8 }

tRPOperPrefixListEntry OBJECT-TYPE
    SYNTAX       TRPOperPrefixListEntry
    MAX-ACCESS   not-accessible
    STATUS       current
    DESCRIPTION 
        "Information about a particular prefix list.

         Entries are created by user via tRPAdminPrefixListTable.
         Entries are deleted by user via tRPAdminPrefixListTable.
        
         A prefix list name entry must exist before referring objects
         (tRPAdminPSToCriteriaNeighborPrefixList, 
          tRPAdminPSFromCriteriaNeighborPrefixList,
          tRPAdminPSToCriteriaPrefixList1 - 5
          tRPAdminPSFromCriteriaPrefixList1 - 5)
         can be set to that name."
    INDEX { tRPOperPrefixListName, tRPOperPrefixListIpPrefix,
            tRPOperPrefixListMask, tRPOperPrefixListType }
    ::= { tRPOperPrefixListTable 1 }

TRPOperPrefixListEntry ::= SEQUENCE
    {
        tRPOperPrefixListName          TPrefixListName,
        tRPOperPrefixListIpPrefix      IpAddress,
        tRPOperPrefixListMask          IpAddressPrefixLength,
        tRPOperPrefixListRowStatus     RowStatus,
        tRPOperPrefixListType          INTEGER,
        tRPOperPrefixListThroughLength IpAddressPrefixLength,
        tRPOperPrefixListEntryLastChanged TimeStamp,
        tRPOperPrefixListBeginLength   IpAddressPrefixLength
    }

tRPOperPrefixListName  OBJECT-TYPE
    SYNTAX       TPrefixListName (SIZE(1..32))
    MAX-ACCESS   not-accessible
    STATUS       current
    DESCRIPTION
        "The name of the prefix list entry."
    ::= { tRPOperPrefixListEntry 1 }

tRPOperPrefixListIpPrefix  OBJECT-TYPE
    SYNTAX       IpAddress
    MAX-ACCESS   not-accessible
    STATUS       current
    DESCRIPTION
        "The IP prefix of the prefix list entry."
    ::= { tRPOperPrefixListEntry 2 }

tRPOperPrefixListMask  OBJECT-TYPE
    SYNTAX       IpAddressPrefixLength
    MAX-ACCESS   not-accessible
    STATUS       current
    DESCRIPTION
        "The IP mask length of the prefix list entry."
    ::= { tRPOperPrefixListEntry 3 }

tRPOperPrefixListRowStatus  OBJECT-TYPE
    SYNTAX       RowStatus
    MAX-ACCESS   read-only
    STATUS       current
    DESCRIPTION
        "RowStatus for this row. Values read will only be 
         active(1), notInService(2), notReady(3). To create
         or destroy entries in this table, use the 
         tRPAdminPrefixListTable."
    ::= { tRPOperPrefixListEntry 4 }

tRPOperPrefixListType  OBJECT-TYPE  
    SYNTAX       INTEGER { exact(1), longer(2), through(3), range(4) }
    MAX-ACCESS   not-accessible
    STATUS       current
    DESCRIPTION 
        "The type of the prefix length entry.
                                                              
         exact (1) - a route's prefix/length must match the 
         prefix-list entry exactly in order for an entry to 
         be considered a match.

         longer (2) - a route's prefix/length must match the 
         defined prefix AND have a length that is an exact match 
         or longer in order for an entry to be considered a match.

         through (3) - a route's prefix/length must match the 
         defined prefix AND have a length that is an exact match or 
         longer up to and including the defined maximum length in
         order for an entry to be considered a match.
        
         range (4) - a route's prefix/length must match the 
         defined prefix AND have a length that is greater than or 
         equal to the length defined by tRPOperPrefixListBeginLength 
         and less than or equal to the length defined by 
         tRPOperPrefixListThroughLength in order for an entry to 
         be considered a match."
    ::= { tRPOperPrefixListEntry 5 }

tRPOperPrefixListThroughLength  OBJECT-TYPE
    SYNTAX       IpAddressPrefixLength
    MAX-ACCESS   read-only
    STATUS       current
    DESCRIPTION
        "When tRPOperPrefixListType set to through(3), the mask length to use.
         Must be larger than tRPOperPrefixListMask."
    ::= { tRPOperPrefixListEntry 6 }

tRPOperPrefixListEntryLastChanged   OBJECT-TYPE
    SYNTAX       TimeStamp
    MAX-ACCESS   read-only
    STATUS       obsolete
    DESCRIPTION 
        "Timestamp of last change to this entry.

         tRPOperPrefixListEntryLastChanged is obsoleted in release 5.0.
         TIMETRA-SYSTEM-MIB::tmnxConfigModify notification is used instead."
    ::= { tRPOperPrefixListEntry 7 }

tRPOperPrefixListBeginLength  OBJECT-TYPE
    SYNTAX       IpAddressPrefixLength
    MAX-ACCESS   read-only
    STATUS       current
    DESCRIPTION
        "When tRPOperPrefixListType set to range(4), the mask length to use 
         as the lower limit for the mask range. Must be larger than
         tRPOperPrefixListMask and less than tRPOperPrefixListThroughLength."
    ::= { tRPOperPrefixListEntry 8 }

--
-- policy-statement 
--

tRPOperPolicyStatementTableLastChanged OBJECT-TYPE
    SYNTAX       TimeStamp
    MAX-ACCESS   read-only
    STATUS       obsolete
    DESCRIPTION
        "Timestamp of last change to tRPOperPolicyStatementTable.

         tRPOperPolicyStatementTableLastChanged is obsoleted in release 5.0.
         TIMETRA-SYSTEM-MIB::tmnxConfigModify notification is used instead."
    ::= { tRPOperValueObjects 9 }

tRPOperPolicyStatementTable OBJECT-TYPE
    SYNTAX       SEQUENCE OF TRPOperPolicyStatementEntry
    MAX-ACCESS   not-accessible
    STATUS       current
    DESCRIPTION 
        "Control table for policy-statements."
    ::= { tRPOperValueObjects 10 }

tRPOperPolicyStatementEntry OBJECT-TYPE
    SYNTAX       TRPOperPolicyStatementEntry
    MAX-ACCESS   not-accessible
    STATUS       current
    DESCRIPTION 
        "Information about a particular policy-statement.
        
         Entries are created by user via tRPAdminPolicyStatementTable.
         Entries are deleted by user via tRPAdminPolicyStatementTable."
    INDEX { tRPOperPolicyStatementName }
    ::= { tRPOperPolicyStatementTable 1 }

TRPOperPolicyStatementEntry ::= SEQUENCE
    {
        tRPOperPolicyStatementName          TPolicyStatementName,
        tRPOperPolicyStatementRowStatus     RowStatus,
        tRPOperPolicyStatementDescription   TItemDescription,
        tRPOperPolicyStatementDefaultAction TPolicyEntryAction,
        tRPOperPolicyStatementEntryLastChanged  TimeStamp
    }

tRPOperPolicyStatementName  OBJECT-TYPE
    SYNTAX       TPolicyStatementName
    MAX-ACCESS   not-accessible
    STATUS       current
    DESCRIPTION
        "The name of this policy statement that uniquely identifies an
         entry in this table."
    ::= { tRPOperPolicyStatementEntry 1 }

tRPOperPolicyStatementRowStatus  OBJECT-TYPE
    SYNTAX       RowStatus
    MAX-ACCESS   read-only
    STATUS       current
    DESCRIPTION
        "RowStatus for this row. Values read will only be 
         active(1), notInService(2), notReady(3). To create
         or destroy entries in this table, use the 
         tRPAdminPolicyStatementTable."
    ::= { tRPOperPolicyStatementEntry 2 }

tRPOperPolicyStatementDescription  OBJECT-TYPE
    SYNTAX       TItemDescription
    MAX-ACCESS   read-only
    STATUS       current
    DESCRIPTION 
        "Description for this policy statement."
    ::= { tRPOperPolicyStatementEntry 3 }

tRPOperPolicyStatementDefaultAction  OBJECT-TYPE
    SYNTAX       TPolicyEntryAction
    MAX-ACCESS   read-only
    STATUS       current
    DESCRIPTION 
        "The default-action for the policy statement indicates
         what happens to the route if none of the policy statement entries 
         match."
    ::= { tRPOperPolicyStatementEntry 4 }

tRPOperPolicyStatementEntryLastChanged   OBJECT-TYPE
    SYNTAX       TimeStamp
    MAX-ACCESS   read-only
    STATUS       obsolete
    DESCRIPTION 
        "Timestamp of last change to this entry.

         tRPOperPolicyStatementEntryLastChanged is obsoleted in release 5.0.
         TIMETRA-SYSTEM-MIB::tmnxConfigModify notification is used instead."
    ::= { tRPOperPolicyStatementEntry 5 }

--
-- policy-statement default action 
--

tRPOperPSDefaultActionParamsTableLastChanged OBJECT-TYPE
    SYNTAX       TimeStamp
    MAX-ACCESS   read-only
    STATUS       obsolete
    DESCRIPTION
        "Timestamp of last change to tRPOperPSDefaultActionParamsTable.

         tRPOperPSDefaultActionParamsTableLastChanged is obsoleted in release 5.0.
         TIMETRA-SYSTEM-MIB::tmnxConfigModify notification is used instead."
    ::= { tRPOperValueObjects 11 }

tRPOperPSDefaultActionParamsTable OBJECT-TYPE
    SYNTAX       SEQUENCE OF TRPOperPSDefaultActionParamsEntry
    MAX-ACCESS   not-accessible
    STATUS       current
    DESCRIPTION
        "Default action parameters for a policy-statement."
    ::= { tRPOperValueObjects 12 }

tRPOperPSDefaultActionParamsEntry OBJECT-TYPE
    SYNTAX       TRPOperPSDefaultActionParamsEntry
    MAX-ACCESS   not-accessible
    STATUS       current
    DESCRIPTION 
        "Default action information about a particular policy statement.
        
         These parameters are applied when the default action for the
         policy statement is 'accept' 
         (tRPOperPolicyStatementDefaultAction == accept(1)).
        
         These parameters are ignored when default action for the
         policy statement is 'reject'
         (tRPOperPolicyStatementDefaultAction == reject(2)).
        
         Entries are created when a policy statement is created.
         Entries are deleted when a policy statement is destroyed."
    INDEX { tRPOperPolicyStatementName }
    ::= { tRPOperPSDefaultActionParamsTable 1 }

TRPOperPSDefaultActionParamsEntry ::= SEQUENCE
    {
        tRPOperPSDefaultActionASPath              TPolicyEntryEdit,
        tRPOperPSDefaultActionASPathName          TASPathName,
        tRPOperPSDefaultActionASPathPrependAS     TmnxBgpAutonomousSystem,
        tRPOperPSDefaultActionASPathPrependCount  INTEGER,
        tRPOperPSDefaultActionCommunity1          TPolicyEntryEdit,
        tRPOperPSDefaultActionCommunityName1      TCommunityName,
        tRPOperPSDefaultActionCommunity2          TPolicyEntryEdit,
        tRPOperPSDefaultActionCommunityName2      TCommunityName,
        tRPOperPSDefaultActionOrigin              TPolicyEntryCriteriaOrigin,
        tRPOperPSDefaultActionLocalPreferenceSet  TruthValue,
        tRPOperPSDefaultActionLocalPreference     TmnxBgpLocalPreference,
        tRPOperPSDefaultActionMetric              TPolicyEntryEdit,
        tRPOperPSDefaultActionMetricValue         Unsigned32,
        tRPOperPSDefaultActionPreference          TmnxBgpPreference,
        tRPOperPSDefaultActionDamping             TDampingName,
        tRPOperPSDefaultActionNextHopSelf         TruthValue,
        tRPOperPSDefaultActionNextHop             IpAddress,
        tRPOperPSDefaultActionTag                 TPolicyActionTag,
        tRPOperPSDefaultActionOspfType            TOspfRouteType,
        tRPOperPSDefaultActionParamsEntryLastChanged  TimeStamp,
        tRPOperPSDefActInetNextHopType            InetAddressType,
        tRPOperPSDefActInetNextHop                InetAddress,
        tRPOperPSDefaultActionASPathPend          InetAutonomousSystemNumber,
        tRPOperPSDefActMcRedirSvcId               TmnxServId,
        tRPOperPSDefActMcRedirIfIndex             InterfaceIndexOrZero,
        tRPOperPSDefActionMetricSource            TPolicyActionMetricSource,
        tRPOperPSDefActionAigpMetric              TPolicyEntryAigpMetricEdit,
        tRPOperPSDefActnAigpMetricVal             Unsigned32
    }

tRPOperPSDefaultActionASPath  OBJECT-TYPE
    SYNTAX       TPolicyEntryEdit
    MAX-ACCESS   read-only
    STATUS       current
    DESCRIPTION 
        "The AS Path rewrite information for the route."
    ::= { tRPOperPSDefaultActionParamsEntry 1 }

tRPOperPSDefaultActionASPathName  OBJECT-TYPE
    SYNTAX       TASPathName
    MAX-ACCESS   read-only
    STATUS       current
    DESCRIPTION
        "The AS Path name to use for add, remove, or replace operation
         specified by tRPOperPSDefaultActionASPath.  Ignored when 
         tRPOperPSDefaultActionASPath is none(1)."
    ::= { tRPOperPSDefaultActionParamsEntry 2 }

tRPOperPSDefaultActionASPathPrependAS  OBJECT-TYPE
    SYNTAX       TmnxBgpAutonomousSystem
    MAX-ACCESS   read-only
    STATUS       obsolete
    DESCRIPTION 
        "AS Number to prepend to the AS-Path attribute of the route.
         Ignored when tRPOperPSDefaultActionASPathPrependCount is zero.

         This object was obsoleted in release 7.0.  It is replaced with the
         4-byte AS number defined by tRPOperPSDefaultActionASPathPend."
    ::= { tRPOperPSDefaultActionParamsEntry 3 }

tRPOperPSDefaultActionASPathPrependCount  OBJECT-TYPE
    SYNTAX       INTEGER (0..50)
    MAX-ACCESS   read-only
    STATUS       current
    DESCRIPTION 
        "Number of times tRPOperPSDefaultActionASPathPend is prepended
         to the AS-Path attribute of the route.
         
         Set to zero to disable."
    ::= { tRPOperPSDefaultActionParamsEntry 4 }

tRPOperPSDefaultActionCommunity1 OBJECT-TYPE
    SYNTAX       TPolicyEntryEdit
    MAX-ACCESS   read-only
    STATUS       current
    DESCRIPTION 
        "How to apply tRPOperPSDefaultActionCommunityName1
         to the communities for the route.
        
         Set to none(1) to disable this feature."
    ::= { tRPOperPSDefaultActionParamsEntry 5 }

tRPOperPSDefaultActionCommunityName1 OBJECT-TYPE
    SYNTAX       TCommunityName
    MAX-ACCESS   read-only
    STATUS       current
    DESCRIPTION 
        "Community name to add, remove, or replace, to any 
         existing community for the route.  Ignored when 
         tRPOperPSDefaultActionCommunity1 is none(1)"
    ::= { tRPOperPSDefaultActionParamsEntry 6 }

tRPOperPSDefaultActionCommunity2 OBJECT-TYPE
    SYNTAX       TPolicyEntryEdit
    MAX-ACCESS   read-only
    STATUS       current
    DESCRIPTION 
        "How to apply tRPOperPSDefaultActionCommunityName2
         to the communities for the route.
        
         Set to none(1) to disable this feature."
    ::= { tRPOperPSDefaultActionParamsEntry 7 }

tRPOperPSDefaultActionCommunityName2 OBJECT-TYPE
    SYNTAX       TCommunityName
    MAX-ACCESS   read-only
    STATUS       current
    DESCRIPTION 
        "Community name to add, remove, or replace, to any 
         existing community for the route.  Ignored when 
         tRPOperPSDefaultActionCommunity2 is none(1)"
    ::= { tRPOperPSDefaultActionParamsEntry 8 }

tRPOperPSDefaultActionOrigin  OBJECT-TYPE
    SYNTAX       TPolicyEntryCriteriaOrigin 
    MAX-ACCESS   read-only
    STATUS       current
    DESCRIPTION
        "The value of tRPOperPSDefaultActionOrigin indicates
         the origin of the route exported into BGP if it does not match an
         entry."
    ::= { tRPOperPSDefaultActionParamsEntry 9 }

tRPOperPSDefaultActionLocalPreferenceSet  OBJECT-TYPE
    SYNTAX       TruthValue
    MAX-ACCESS   read-only
    STATUS       current
    DESCRIPTION 
        "When set to true(1), use the value of 
         tRPOperPSDefaultActionLocalPreference for local preference."
    ::= { tRPOperPSDefaultActionParamsEntry 10 }

tRPOperPSDefaultActionLocalPreference  OBJECT-TYPE
    SYNTAX       TmnxBgpLocalPreference
    MAX-ACCESS   read-only
    STATUS       current
    DESCRIPTION 
        "Local preference to apply to the route.
         Set tRPOperPSDefaultActionLocalPreferenceSet to false(2) to disable."
    ::= { tRPOperPSDefaultActionParamsEntry 11 }

tRPOperPSDefaultActionMetric  OBJECT-TYPE
    SYNTAX       TPolicyEntryEdit
    MAX-ACCESS   read-only
    STATUS       current
    DESCRIPTION 
        "Action for tRPOperPSDefaultActionMetricValue."
    ::= { tRPOperPSDefaultActionParamsEntry 12 }

tRPOperPSDefaultActionMetricValue  OBJECT-TYPE
    SYNTAX       Unsigned32
    MAX-ACCESS   read-only
    STATUS       current
    DESCRIPTION 
        "Add, subtract, or set metric value.  Ignored when
         tRPOperPSDefaultActionMetric is none(1)."
    ::= { tRPOperPSDefaultActionParamsEntry 13 }

tRPOperPSDefaultActionPreference  OBJECT-TYPE
    SYNTAX       TmnxBgpPreference
    MAX-ACCESS   read-only
    STATUS       current
    DESCRIPTION 
        "Preference to apply to the route."
    ::= { tRPOperPSDefaultActionParamsEntry 15 }

tRPOperPSDefaultActionDamping  OBJECT-TYPE
    SYNTAX       TDampingName
    MAX-ACCESS   read-only
    STATUS       current
    DESCRIPTION 
        "Damping to apply to route.  Set to empty string to disable."
    ::= { tRPOperPSDefaultActionParamsEntry 16 }

tRPOperPSDefaultActionNextHopSelf  OBJECT-TYPE
    SYNTAX       TruthValue
    MAX-ACCESS   read-only
    STATUS       current
    DESCRIPTION 
        "The value of tRPOperPSDefaultActionNextHopSelf indicates
         the next-hop-self on the route. Next-hop-self cannot be 
         'true' when the next-hop object 'tRPOperPSDefActInetNextHop'
         has a valid IP address. If tRPOperPSDefaultActionNextHopSelf
         has a value of 'true' then tRPOperPSDefActInetNextHop 
         object is disabled."
    ::= { tRPOperPSDefaultActionParamsEntry 17 }

tRPOperPSDefaultActionNextHop  OBJECT-TYPE
    SYNTAX       IpAddress
    MAX-ACCESS   read-only
    STATUS       current
    DESCRIPTION 
        "Set next-hop address in route. Set to 255.255.255.255 to disable.
         Next-hop cannot be set to a valid IP address at the same time
         as setting next-hop-self to 'true'. Setting next-hop to a valid 
         IP address will reset next-hop-self to 'false'."
    ::= { tRPOperPSDefaultActionParamsEntry 18 }

tRPOperPSDefaultActionTag  OBJECT-TYPE
    SYNTAX       TPolicyActionTag
    MAX-ACCESS   read-only
    STATUS       current
    DESCRIPTION 
        "The value of tRPOperPSDefaultActionTag indicates the operational tag 
         for the route. 

         A value of 0 for tRPAdminPSDefaultActionTag indicates that tagging is
         disabled."
    ::= { tRPOperPSDefaultActionParamsEntry 19 }

tRPOperPSDefaultActionOspfType  OBJECT-TYPE
    SYNTAX       TOspfRouteType
    MAX-ACCESS   read-only
    STATUS       current
    DESCRIPTION 
        "OSPF route type for the route."
    ::= { tRPOperPSDefaultActionParamsEntry 20 }

tRPOperPSDefaultActionParamsEntryLastChanged OBJECT-TYPE
    SYNTAX       TimeStamp
    MAX-ACCESS   read-only
    STATUS       obsolete
    DESCRIPTION 
        "Timestamp of last change to this entry.

         tRPOperPSDefaultActionParamsEntryLastChanged is obsoleted in release 5.0.
         TIMETRA-SYSTEM-MIB::tmnxConfigModify notification is used instead."
    ::= { tRPOperPSDefaultActionParamsEntry 21 }

tRPOperPSDefActInetNextHopType  OBJECT-TYPE
    SYNTAX       InetAddressType
    MAX-ACCESS   read-only
    STATUS       current
    DESCRIPTION 
        "The value of tRPOperPSDefActInetNextHopType indicates
         the type of tRPOperPSDefActInetNextHop address, 
         as defined in the InetAddress MIB."
    ::= { tRPOperPSDefaultActionParamsEntry 22 }

tRPOperPSDefActInetNextHop  OBJECT-TYPE
    SYNTAX       InetAddress
    MAX-ACCESS   read-only
    STATUS       current
    DESCRIPTION 
        "The value of tRPOperPSDefActInetNextHop indicates the
         next-hop IP address in the route. The object 
         tRPOperPSDefActInetNextHop is disabled if it holds
         the value ffff:ffff:ffff:ffff:ffff:ffff:ffff:ffff.
       
         The type of this address is determined by the 
         value of tRPOperPSDefActInetNextHopType object.

         Next-hop cannot be a valid IP address when 
         next-hop-self object 'tRPOperPSDefaultActionNextHopSelf' 
         is set to 'true'. If next-hop is a valid IP address then  
         tRPOperPSDefaultActionNextHopSelf is set to 'false'.

         tRPOperPSDefActInetNextHop object replaces 
         tRPOperPSDefaultActionNextHop that supports only
         IPv4 address style next-hop."
    ::= { tRPOperPSDefaultActionParamsEntry 23 }

tRPOperPSDefaultActionASPathPend  OBJECT-TYPE
    SYNTAX       InetAutonomousSystemNumber
    MAX-ACCESS   read-only
    STATUS       current
    DESCRIPTION 
         "The value of tRPOperPSDefaultActionASPathPend indicates the AS Number
         to prepend to the AS-Path attribute of the route. Value of this
         object is ignored when tRPOperPSDefaultActionASPathPrependCount 
         is zero."
    ::= { tRPOperPSDefaultActionParamsEntry 24 }
    
tRPOperPSDefActMcRedirSvcId OBJECT-TYPE
     SYNTAX      TmnxServId
     MAX-ACCESS  read-only
     STATUS      current
     DESCRIPTION
         "The value of tRPOperPSDefActMcRedirSvcId indicates the service ID of
          the service where to redirect IGMP multicast traffic to.
          
          The value zero means that no multicast redirection is configured."
     ::= { tRPOperPSDefaultActionParamsEntry 30 }

tRPOperPSDefActMcRedirIfIndex OBJECT-TYPE
     SYNTAX      InterfaceIndexOrZero
     MAX-ACCESS  read-only
     STATUS      current
     DESCRIPTION
         "The value of tRPOperPSDefActMcRedirIfIndex indicates the interface 
          index of the interface where to redirect IGMP multicast traffic to.
          
          The value zero means that no multicast redirection is configured."
     ::= { tRPOperPSDefaultActionParamsEntry 31 }

tRPOperPSDefActionMetricSource OBJECT-TYPE
     SYNTAX      TPolicyActionMetricSource
     MAX-ACCESS  read-only
     STATUS      current
     DESCRIPTION
         "The value of tRPOperPSDefActionMetricSource indicates the source
          of the default action metric.
          
          The value 'igpCost(1)' means that the value of MED (Multi Exit 
          Discriminator) or the metric value is derived from the IGP 
          (Interior Gateway Protocol) cost of the route and the value of 
          the object tRPOperPSDefaultActionMetricValue is ignored.
          
          The value 'metricVal(2)' means the metric value is the value of 
          tRPOperPSDefaultActionMetricValue."
     ::= { tRPOperPSDefaultActionParamsEntry 32 }

tRPOperPSDefActionAigpMetric  OBJECT-TYPE
    SYNTAX       TPolicyEntryAigpMetricEdit
    MAX-ACCESS   read-only
    STATUS       current
    DESCRIPTION
        "The value of tRPOperPSDefActionAigpMetric indicates the editing
         action to be taken for the AIGP (Accumulated IGP) attribute when 
         the route satisfies the match criteria of the policy.
         
         When the value of tRPOperPSDefActionAigpMetric is set to 'none(1)'
         or 'useIgp(4)', the value of tRPOperPSDefActnAigpMetricVal is 
         ignored."
    ::= { tRPOperPSDefaultActionParamsEntry 33 }

tRPOperPSDefActnAigpMetricVal  OBJECT-TYPE
    SYNTAX       Unsigned32
    MAX-ACCESS   read-only
    STATUS       current
    DESCRIPTION
        "The value of tRPOperPSDefActnAigpMetricVal indicates the value to
         be added or set for the route AIGP(Accumulated IGP) metric.
         
         When the value of tRPOperPSDefActionAigpMetric is set to 'none(1)'
         or 'useIgp(4)', the value of tRPOperPSDefActnAigpMetricVal is 
         ignored."
    ::= { tRPOperPSDefaultActionParamsEntry 34 }

--
-- policy-statement entry params
--

tRPOperPSParamsTableLastChanged OBJECT-TYPE
    SYNTAX       TimeStamp
    MAX-ACCESS   read-only
    STATUS       obsolete
    DESCRIPTION
        "Timestamp of last change to tRPOperPSParamsTable.

         tRPOperPSParamsTableLastChanged is obsoleted in release 5.0.
         TIMETRA-SYSTEM-MIB::tmnxConfigModify notification is used instead."
    ::= { tRPOperValueObjects 13 }

tRPOperPSParamsTable OBJECT-TYPE
    SYNTAX       SEQUENCE OF TRPOperPSParamsEntry
    MAX-ACCESS   not-accessible
    STATUS       current
    DESCRIPTION 
        "A table of policy statement entries."
    ::= { tRPOperValueObjects 14 }

tRPOperPSParamsEntry OBJECT-TYPE
    SYNTAX       TRPOperPSParamsEntry
    MAX-ACCESS   not-accessible
    STATUS       current
    DESCRIPTION 
        "Information about a particular policy statement entry.
        
         Entries are created when a policy statement parameters entry
         is created.
         Entries are deleted when a policy statement parameters entry is
         destroyed."
    INDEX { tRPOperPolicyStatementName, tRPOperPSNameEntryIndex }
    ::= { tRPOperPSParamsTable 1 }

TRPOperPSParamsEntry ::= SEQUENCE
    {
        tRPOperPSNameEntryIndex    TPolicyStatementEntryID,
        tRPOperPSParamsRowStatus   RowStatus,
        tRPOperPSParamsDescription TItemDescription,
        tRPOperPSParamsAction      TPolicyEntryAction,
        tRPOperPSParamsEntryLastChanged  TimeStamp
    }

tRPOperPSNameEntryIndex  OBJECT-TYPE
    SYNTAX       TPolicyStatementEntryID
    MAX-ACCESS   not-accessible
    STATUS       current
    DESCRIPTION 
        "Identifier for this policy statement entry."
    ::= { tRPOperPSParamsEntry 1 }

tRPOperPSParamsRowStatus  OBJECT-TYPE
    SYNTAX       RowStatus
    MAX-ACCESS   read-only
    STATUS       current
    DESCRIPTION
        "RowStatus for this row. Values read will only be 
         active(1), notInService(2), notReady(3). To create
         or destroy entries in this table, use the 
         tRPAdminPSParamsTable."
    ::= { tRPOperPSParamsEntry 2 }

tRPOperPSParamsDescription  OBJECT-TYPE
    SYNTAX       TItemDescription
    MAX-ACCESS   read-only
    STATUS       current
    DESCRIPTION 
        "Description for this policy statement entry."
    ::= { tRPOperPSParamsEntry 3 }

tRPOperPSParamsAction  OBJECT-TYPE
    SYNTAX       TPolicyEntryAction
    MAX-ACCESS   read-only
    STATUS       current
    DESCRIPTION 
        "The action to take when a route matches this policy statement entry's
         to or from criteria."
    ::= { tRPOperPSParamsEntry 4 }

tRPOperPSParamsEntryLastChanged  OBJECT-TYPE
    SYNTAX       TimeStamp
    MAX-ACCESS   read-only
    STATUS       obsolete
    DESCRIPTION 
        "Timestamp of last change to this entry.

         tRPOperPSParamsEntryLastChanged is obsoleted in release 5.0.
         TIMETRA-SYSTEM-MIB::tmnxConfigModify notification is used instead."
    ::= { tRPOperPSParamsEntry 5 }

--
-- policy-statement default action 
--

tRPOperPSAcceptActionParamsTableLastChanged OBJECT-TYPE
    SYNTAX       TimeStamp
    MAX-ACCESS   read-only
    STATUS       obsolete
    DESCRIPTION
        "Timestamp of last change to tRPOperPSAcceptActionParamsTable.

         tRPOperPSAcceptActionParamsTableLastChanged is obsoleted in release 5.0.
         TIMETRA-SYSTEM-MIB::tmnxConfigModify notification is used instead."
    ::= { tRPOperValueObjects 15 }

tRPOperPSAcceptActionParamsTable OBJECT-TYPE
    SYNTAX       SEQUENCE OF TRPOperPSAcceptActionParamsEntry
    MAX-ACCESS   not-accessible
    STATUS       current
    DESCRIPTION  
        "Accept-action parameters for a policy-statement."
    ::= { tRPOperValueObjects 16 }

tRPOperPSAcceptActionParamsEntry OBJECT-TYPE
    SYNTAX       TRPOperPSAcceptActionParamsEntry
    MAX-ACCESS   not-accessible
    STATUS       current
    DESCRIPTION 
        "Accept-action information for a policy-statement entry.
         If the policy statement entry action is 'reject' then all of 
         these objects are ignored.
        
         Entries are created when a policy statement entry is created.
         Entries are deleted when a policy statement entry is destroyed.
         
         To Create or destroy entries in this table, use the 
         policy statement entry administrative table (tRPAdminPSParamsTable)."
    INDEX { tRPOperPolicyStatementName, tRPOperPSNameEntryIndex }
    ::= { tRPOperPSAcceptActionParamsTable 1 }

TRPOperPSAcceptActionParamsEntry ::= SEQUENCE
    {
        tRPOperPSAcceptActionASPath              TPolicyEntryEdit,
        tRPOperPSAcceptActionASPathName          TASPathName,
        tRPOperPSAcceptActionASPathPrependAS     TmnxBgpAutonomousSystem,
        tRPOperPSAcceptActionASPathPrependCount  INTEGER,
        tRPOperPSAcceptActionCommunity1          TPolicyEntryEdit,
        tRPOperPSAcceptActionCommunityName1      TCommunityName,
        tRPOperPSAcceptActionCommunity2          TPolicyEntryEdit,
        tRPOperPSAcceptActionCommunityName2      TCommunityName,
        tRPOperPSAcceptActionOrigin              TPolicyEntryCriteriaOrigin,
        tRPOperPSAcceptActionLocalPreferenceSet  TruthValue,
        tRPOperPSAcceptActionLocalPreference     TmnxBgpLocalPreference,
        tRPOperPSAcceptActionMetric              TPolicyEntryEdit,
        tRPOperPSAcceptActionMetricValue         Unsigned32,
        tRPOperPSAcceptActionPreference          TmnxBgpPreference,
        tRPOperPSAcceptActionDamping             TDampingName,
        tRPOperPSAcceptActionNextHopSelf         TruthValue,
        tRPOperPSAcceptActionNextHop             IpAddress,
        tRPOperPSAcceptActionTag                 TPolicyActionTag,
        tRPOperPSAcceptActionOspfType            TOspfRouteType,
        tRPOperPSAcceptActionParamsEntryLastChanged TimeStamp,
        tRPOperPSAcptActInetNextHopType          InetAddressType,
        tRPOperPSAcptActInetNextHop              InetAddress,
        tRPOperPSAcceptActionASPathPend          InetAutonomousSystemNumber,
        tRPOperPSAcptActMcRedirSvcId             TmnxServId,
        tRPOperPSAcptActMcRedirIfIndex           InterfaceIndexOrZero,
        tRPOperPSAcptActnMetricSource            TPolicyActionMetricSource,
        tRPOperPSAcptActionAigpMetric            TPolicyEntryAigpMetricEdit,
        tRPOperPSAcptActnAigpMetricVal           Unsigned32
    }

tRPOperPSAcceptActionASPath  OBJECT-TYPE
    SYNTAX       TPolicyEntryEdit
    MAX-ACCESS   read-only
    STATUS       current
    DESCRIPTION 
        "The AS Path rewrite information for the route."
    ::= { tRPOperPSAcceptActionParamsEntry 1 }

tRPOperPSAcceptActionASPathName  OBJECT-TYPE
    SYNTAX       TASPathName
    MAX-ACCESS   read-only
    STATUS       current
    DESCRIPTION 
        "AS Path Name to add, remove, or replace. Ignored when
         tRPOperPSAcceptActionASPath is none(1)"
    ::= { tRPOperPSAcceptActionParamsEntry 2 }

tRPOperPSAcceptActionASPathPrependAS  OBJECT-TYPE
    SYNTAX       TmnxBgpAutonomousSystem
    MAX-ACCESS   read-only
    STATUS       obsolete
    DESCRIPTION 
        "AS Number to prepend to the AS-Path attribute of the route.
         Ignored when tRPOperPSAcceptActionASPathPrependCount is zero.

         This object was obsoleted in release 7.0.  It is replaced with the
         4-byte AS number defined by tRPOperPSAcceptActionASPathPend."
    ::= { tRPOperPSAcceptActionParamsEntry 3 }

tRPOperPSAcceptActionASPathPrependCount  OBJECT-TYPE
    SYNTAX       INTEGER (0..50)
    MAX-ACCESS   read-only
    STATUS       current
    DESCRIPTION 
        "Number of times to prepend tRPOperPSAcceptActionASPathPend to 
         the route.  Set to zero to disable this feature."
    ::= { tRPOperPSAcceptActionParamsEntry 4 }

tRPOperPSAcceptActionCommunity1  OBJECT-TYPE
    SYNTAX       TPolicyEntryEdit
    MAX-ACCESS   read-only
    STATUS       current
    DESCRIPTION 
        "How to apply tRPOperPSAcceptActionCommunityName1 to the route."
    ::= { tRPOperPSAcceptActionParamsEntry 5 }

tRPOperPSAcceptActionCommunityName1  OBJECT-TYPE
    SYNTAX       TCommunityName
    MAX-ACCESS   read-only
    STATUS       current
    DESCRIPTION 
        "Community to apply to the route.  Ignored when 
         tRPOperPSAcceptActionCommunity1 is set to none(1)."
    ::= { tRPOperPSAcceptActionParamsEntry 6 }

tRPOperPSAcceptActionCommunity2  OBJECT-TYPE
    SYNTAX       TPolicyEntryEdit
    MAX-ACCESS   read-only
    STATUS       current
    DESCRIPTION 
        "How to apply tRPOperPSAcceptActionCommunityName2 to the route."
    ::= { tRPOperPSAcceptActionParamsEntry 7 }

tRPOperPSAcceptActionCommunityName2  OBJECT-TYPE
    SYNTAX       TCommunityName
    MAX-ACCESS   read-only
    STATUS       current
    DESCRIPTION 
        "Community to apply to the route.  Ignored when 
         tRPOperPSAcceptActionCommunity2 is set to none(1)."
    ::= { tRPOperPSAcceptActionParamsEntry 8 }

tRPOperPSAcceptActionOrigin  OBJECT-TYPE
    SYNTAX       TPolicyEntryCriteriaOrigin 
    MAX-ACCESS   read-only
    STATUS       current
    DESCRIPTION
        "The value of tRPOperPSAcceptActionOrigin indicates
         the origin of the route exported into BGP if it matches an entry."
    ::= { tRPOperPSAcceptActionParamsEntry 9 }

tRPOperPSAcceptActionLocalPreferenceSet  OBJECT-TYPE
    SYNTAX       TruthValue
    MAX-ACCESS   read-only
    STATUS       current
    DESCRIPTION 
        "When set to true(1), use tRPOperPSAcceptActionLocalPreference
         for the local preference for the route."
    ::= { tRPOperPSAcceptActionParamsEntry 10 }

tRPOperPSAcceptActionLocalPreference  OBJECT-TYPE
    SYNTAX       TmnxBgpLocalPreference
    MAX-ACCESS   read-only
    STATUS       current
    DESCRIPTION 
        "Local preference for the route.
         Ignored when tRPOperPSAcceptActionLocalPreferenceSet is false(2)."
    ::= { tRPOperPSAcceptActionParamsEntry 11 }

tRPOperPSAcceptActionMetric  OBJECT-TYPE
    SYNTAX       TPolicyEntryEdit
    MAX-ACCESS   read-only
    STATUS       current
    DESCRIPTION 
        "How to apply tRPOperPSAcceptActionMetricValue to the route."
    ::= { tRPOperPSAcceptActionParamsEntry 12 }

tRPOperPSAcceptActionMetricValue  OBJECT-TYPE
    SYNTAX       Unsigned32
    MAX-ACCESS   read-only
    STATUS       current
    DESCRIPTION 
        "Value to add, subtract, or set for the route metric.
         Ignored when tRPOperPSAcceptActionMetric is none(1)."
    ::= { tRPOperPSAcceptActionParamsEntry 13 }

tRPOperPSAcceptActionPreference  OBJECT-TYPE
    SYNTAX       TmnxBgpPreference
    MAX-ACCESS   read-only
    STATUS       current
    DESCRIPTION 
        "Preference to set in route."
    ::= { tRPOperPSAcceptActionParamsEntry 15 }

tRPOperPSAcceptActionDamping  OBJECT-TYPE
    SYNTAX       TDampingName
    MAX-ACCESS   read-only
    STATUS       current
    DESCRIPTION 
        "Damping to apply to route.  Set to empty string to disable."
    ::= { tRPOperPSAcceptActionParamsEntry 16 }

tRPOperPSAcceptActionNextHopSelf  OBJECT-TYPE
    SYNTAX       TruthValue
    MAX-ACCESS   read-only
    STATUS       current
    DESCRIPTION 
        "The value of tRPOperPSAcceptActionNextHopSelf indicates
         the next-hop-self on the route. Next-hop-self cannot be 
         'true' when the next-hop object 'tRPOperPSAcptActInetNextHop'
         has a valid IP address. If tRPOperPSAcceptActionNextHopSelf
         has a value of 'true' then tRPOperPSAcptActInetNextHop 
         object is disabled."
    ::= { tRPOperPSAcceptActionParamsEntry 17 }

tRPOperPSAcceptActionNextHop  OBJECT-TYPE
    SYNTAX       IpAddress
    MAX-ACCESS   read-only
    STATUS       current
    DESCRIPTION 
        "Set next-hop address in route.  Set to 255.255.255.255 to disable.
         Next-hop cannot be set to a valid IP address at the same time
         as setting next-hop-self to 'true'. Setting next-hop to a valid
         IP address will reset next-hop-self to 'false'."
    ::= { tRPOperPSAcceptActionParamsEntry 18 }

tRPOperPSAcceptActionTag  OBJECT-TYPE
    SYNTAX       TPolicyActionTag
    MAX-ACCESS   read-only
    STATUS       current
    DESCRIPTION 
        "The value of tRPOperPSAcceptActionTag indicates the operational tag 
         for the route. 
        
         A value of 0 for tRPAdminPSAcceptActionTag indicates that tagging is 
         disabled."
    ::= { tRPOperPSAcceptActionParamsEntry 19 }

tRPOperPSAcceptActionOspfType  OBJECT-TYPE
    SYNTAX       TOspfRouteType
    MAX-ACCESS   read-only
    STATUS       current
    DESCRIPTION 
        "OSPF route type to set in route."
    ::= { tRPOperPSAcceptActionParamsEntry 20 }

tRPOperPSAcceptActionParamsEntryLastChanged  OBJECT-TYPE
    SYNTAX       TimeStamp
    MAX-ACCESS   read-only
    STATUS       obsolete
    DESCRIPTION 
        "Timestamp of last change to this entry.

         tRPOperPSAcceptActionParamsEntryLastChanged is obsoleted in release 5.0.
         TIMETRA-SYSTEM-MIB::tmnxConfigModify notification is used instead."
    ::= { tRPOperPSAcceptActionParamsEntry 21 }

tRPOperPSAcptActInetNextHopType  OBJECT-TYPE
    SYNTAX       InetAddressType
    MAX-ACCESS   read-only
    STATUS       current
    DESCRIPTION 
        "The value of tRPOperPSAcptActInetNextHopType indicates
         the type of tRPOperPSAcptActInetNextHop address, 
         as defined in the InetAddress MIB."
    ::= { tRPOperPSAcceptActionParamsEntry 22 }

tRPOperPSAcptActInetNextHop  OBJECT-TYPE
    SYNTAX       InetAddress
    MAX-ACCESS   read-only
    STATUS       current
    DESCRIPTION 
        "The value of tRPOperPSAcptActInetNextHop indicates the
         next-hop IP address in the route. Next-hop is disabled
         if the value of tRPOperPSAcptActInetNextHopType is 
         'ipv6' and the value of tRPOperPSAcptActInetNextHop 
         is ffff:ffff:ffff:ffff:ffff:ffff:ffff:ffff.
       
         The type of this address is determined by the 
         value of tRPOperPSAcptActInetNextHopType object.

         Next-hop cannot be a valid IP address when 
         next-hop-self object 'tRPOperPSAcceptActionNextHopSelf' 
         is set to 'true'. If next-hop is a valid IP address then  
         tRPOperPSAcceptActionNextHopSelf is set to 'false'.
         
         tRPOperPSAcptActInetNextHop object replaces 
         tRPOperPSAcceptActionNextHop that supports only
         IPv4 address style next-hop."
    ::= { tRPOperPSAcceptActionParamsEntry 23 }

tRPOperPSAcceptActionASPathPend  OBJECT-TYPE
    SYNTAX       InetAutonomousSystemNumber
    MAX-ACCESS   read-only
    STATUS       current
    DESCRIPTION
        "The value of tRPOperPSAcceptActionASPathPend indicates the AS Number 
         to prepend to the AS-Path attribute of the route. Value of this object
         is ignored when tRPOperPSAcceptActionASPathPrependCount is zero."
    ::= { tRPOperPSAcceptActionParamsEntry 24 }
    
tRPOperPSAcptActMcRedirSvcId OBJECT-TYPE
    SYNTAX      TmnxServId
    MAX-ACCESS   read-only
    STATUS      current
    DESCRIPTION
        "The value of tRPOperPSAcptActMcRedirSvcId indicates the service ID of
         the service where to redirect IGMP multicast traffic to.
         
         The value zero means that no multicast redirection is configured."
    DEFVAL { 0 }
    ::= { tRPOperPSAcceptActionParamsEntry 30 }

tRPOperPSAcptActMcRedirIfIndex OBJECT-TYPE
    SYNTAX      InterfaceIndexOrZero
    MAX-ACCESS   read-only
    STATUS      current
    DESCRIPTION
        "The value of tRPOperPSAcptActMcRedirIfIndex indicates the interface 
         index of the interface where to redirect IGMP multicast traffic to.
         
         The value zero means that no multicast redirection is configured."
    DEFVAL { 0 }
    ::= { tRPOperPSAcceptActionParamsEntry 31 }

tRPOperPSAcptActnMetricSource OBJECT-TYPE
    SYNTAX      TPolicyActionMetricSource
    MAX-ACCESS  read-only
    STATUS      current
    DESCRIPTION
        "The value of tRPOperPSAcptActnMetricSource indicates the source
         of the accept action metric.
         
         The value 'igpCost(1)' means that the value of MED (Multi Exit 
         Discriminator) or the metric value is derived from the IGP 
         (Interior Gateway Protocol) cost of the route and the value of 
         the object tRPOperPSAcceptActionMetricValue is ignored.
         
         The value 'metricVal(2)' means the metric value is the value of 
         tRPOperPSAcceptActionMetricValue."
    DEFVAL { metricVal }
    ::= { tRPOperPSAcceptActionParamsEntry 32 }                 

tRPOperPSAcptActionAigpMetric  OBJECT-TYPE
    SYNTAX       TPolicyEntryAigpMetricEdit
    MAX-ACCESS   read-only
    STATUS       current
    DESCRIPTION
        "The value of tRPOperPSAcptActionAigpMetric indicates the editing
         action to be taken for the AIGP (Accumulated IGP) attribute when 
         the route satisfies the match criteria of the policy.
         
         When the value of tRPOperPSAcptActionAigpMetric is set to 'none(1)'
         or 'useIgp(4)', the value of tRPOperPSAcptActnAigpMetricVal is 
         ignored."
    ::= { tRPOperPSAcceptActionParamsEntry 33 }

tRPOperPSAcptActnAigpMetricVal  OBJECT-TYPE
    SYNTAX       Unsigned32
    MAX-ACCESS   read-only
    STATUS       current
    DESCRIPTION
        "The value of tRPOperPSAcptActnAigpMetricVal indicates the value to
         be added or set for the route AIGP(Accumulated IGP) metric.
         
         When the value of tRPOperPSAcptActionAigpMetric is set to 'none(1)'
         or 'useIgp(4)', the value of tRPOperPSAcptActnAigpMetricVal is 
         ignored."
    ::= { tRPOperPSAcceptActionParamsEntry 34 }

--
-- policy-statement entry to 
--

tRPOperPSToCriteriaTableLastChanged OBJECT-TYPE
    SYNTAX       TimeStamp
    MAX-ACCESS   read-only
    STATUS       obsolete
    DESCRIPTION
        "Timestamp of last change to tRPOperPSToCriteriaTable.

         tRPOperPSToCriteriaTableLastChanged is obsoleted in release 5.0.
         TIMETRA-SYSTEM-MIB::tmnxConfigModify notification is used instead."
    ::= { tRPOperValueObjects 17 }

tRPOperPSToCriteriaTable OBJECT-TYPE
    SYNTAX       SEQUENCE OF TRPOperPSToCriteriaEntry
    MAX-ACCESS   not-accessible
    STATUS       current
    DESCRIPTION 
        "A table of policy statement entry 'to' criteria"
    ::= { tRPOperValueObjects 18 }

tRPOperPSToCriteriaEntry OBJECT-TYPE
    SYNTAX       TRPOperPSToCriteriaEntry
    MAX-ACCESS   not-accessible
    STATUS       current
    DESCRIPTION 
        "Information about a policy statement entry's -to- criteria.
         Entries are created when a policy statement entry is created.
         Entries are deleted when a policy statement entry is destroyed."
    INDEX { tRPOperPolicyStatementName, tRPOperPSToCriteriaIndex }
    ::= { tRPOperPSToCriteriaTable 1 }

TRPOperPSToCriteriaEntry ::= SEQUENCE
    {
        tRPOperPSToCriteriaIndex              TPolicyStatementEntryID,
        tRPOperPSToCriteriaRowStatus          RowStatus,
        tRPOperPSToCriteriaProtocol           TRoutePolicyProtocol,
        tRPOperPSToCriteriaNeighborIpAddr     IpAddress,
        tRPOperPSToCriteriaNeighborPrefixList TPrefixListName,
        tRPOperPSToCriteriaEntryLastChanged   TimeStamp,
        tRPOperPSToCriteriaIsisLevel          TIsisLevel,
        tRPOperPSToCriteriaPrefixList1        TPrefixListName,
        tRPOperPSToCriteriaPrefixList2        TPrefixListName,
        tRPOperPSToCriteriaPrefixList3        TPrefixListName,
        tRPOperPSToCriteriaPrefixList4        TPrefixListName,
        tRPOperPSToCriteriaPrefixList5        TPrefixListName,
        tRPOperPSToCritNbrInetAddrType        InetAddressType,
        tRPOperPSToCritNbrInetAddr            InetAddress,
        tRPOperPSToCriteriaInstanceId         Unsigned32
    }

tRPOperPSToCriteriaIndex  OBJECT-TYPE
    SYNTAX       TPolicyStatementEntryID
    MAX-ACCESS   not-accessible
    STATUS       current
    DESCRIPTION 
        "The policy statement entry ID"
    ::= { tRPOperPSToCriteriaEntry 1 }

tRPOperPSToCriteriaRowStatus  OBJECT-TYPE
    SYNTAX       RowStatus
    MAX-ACCESS   read-only
    STATUS       current
    DESCRIPTION
        "RowStatus for this row. Values read will only be 
         active(1), notInService(2), notReady(3). To create
         or destroy entries in this table, use the 
         tRPAdminPSToCriteriaTable."
    ::= { tRPOperPSToCriteriaEntry 2 }

tRPOperPSToCriteriaProtocol  OBJECT-TYPE
    SYNTAX       TRoutePolicyProtocol
    MAX-ACCESS   read-only
    STATUS       current
    DESCRIPTION 
        "The protocol name to match on. 
         Set to none(1) to disable."
    ::= { tRPOperPSToCriteriaEntry 3 }

tRPOperPSToCriteriaNeighborIpAddr  OBJECT-TYPE
    SYNTAX       IpAddress
    MAX-ACCESS   read-only
    STATUS       current
    DESCRIPTION 
        "The IP address of neighbor to match on. 
         Set to 0.0.0.0 to disable."
    ::= { tRPOperPSToCriteriaEntry 4 }

tRPOperPSToCriteriaNeighborPrefixList  OBJECT-TYPE
    SYNTAX       TPrefixListName
    MAX-ACCESS   read-only
    STATUS       current
    DESCRIPTION 
        "The name of a neighbor prefix list to match on.
         Set to empty string to disable."
    ::= { tRPOperPSToCriteriaEntry 5 }

tRPOperPSToCriteriaEntryLastChanged   OBJECT-TYPE
    SYNTAX       TimeStamp
    MAX-ACCESS   read-only
    STATUS       obsolete
    DESCRIPTION 
        "Timestamp of last change to this entry.

         tRPOperPSToCriteriaEntryLastChanged is obsoleted in release 5.0.
         TIMETRA-SYSTEM-MIB::tmnxConfigModify notification is used instead."
    ::= { tRPOperPSToCriteriaEntry 6 }

tRPOperPSToCriteriaIsisLevel          OBJECT-TYPE
    SYNTAX       TIsisLevel
    MAX-ACCESS   read-only
    STATUS       current
    DESCRIPTION 
        "The value for tRPOperPSToCriteriaIsisLevel defines the IS-IS route 
         level match criterion. A value of 0 indicates that no IS-IS route 
         level match criterion has been configured."
    ::= { tRPOperPSToCriteriaEntry 7 }

tRPOperPSToCriteriaPrefixList1  OBJECT-TYPE
    SYNTAX       TPrefixListName
    MAX-ACCESS   read-only
    STATUS       current
    DESCRIPTION 
        "The value of tRPOperPSToCriteriaPrefixList1 specifies the name of  
         the first prefix list to match on. Setting this value to an empty
         string disables this prefix list as a match criteria."
    ::= { tRPOperPSToCriteriaEntry 8 }

tRPOperPSToCriteriaPrefixList2  OBJECT-TYPE
    SYNTAX       TPrefixListName
    MAX-ACCESS   read-only
    STATUS       current
    DESCRIPTION 
        "The value of tRPOperPSToCriteriaPrefixList2 specifies the name of  
         the second prefix list to match on. Setting this value to an empty
         string disables this prefix list as a match criteria."
    ::= { tRPOperPSToCriteriaEntry 9 }

tRPOperPSToCriteriaPrefixList3  OBJECT-TYPE
    SYNTAX       TPrefixListName
    MAX-ACCESS   read-only
    STATUS       current
    DESCRIPTION 
        "The value of tRPOperPSToCriteriaPrefixList3 specifies the name of  
         the third prefix list to match on. Setting this value to an empty
         string disables this prefix list as a match criteria."
    ::= { tRPOperPSToCriteriaEntry 10 }

tRPOperPSToCriteriaPrefixList4  OBJECT-TYPE
    SYNTAX       TPrefixListName
    MAX-ACCESS   read-only
    STATUS       current
    DESCRIPTION 
        "The value of tRPOperPSToCriteriaPrefixList4 specifies the name of  
         the fourth prefix list to match on. Setting this value to an empty
         string disables this prefix list as a match criteria."
    ::= { tRPOperPSToCriteriaEntry 11 }

tRPOperPSToCriteriaPrefixList5  OBJECT-TYPE
    SYNTAX       TPrefixListName
    MAX-ACCESS   read-only
    STATUS       current
    DESCRIPTION 
        "The value of tRPOperPSToCriteriaPrefixList5 specifies the name of  
         the fifth prefix list to match on. Setting this value to an empty
         string disables this prefix list as a match criteria."
    ::= { tRPOperPSToCriteriaEntry 12 }

tRPOperPSToCritNbrInetAddrType  OBJECT-TYPE
    SYNTAX       InetAddressType
    MAX-ACCESS   read-only
    STATUS       current
    DESCRIPTION 
        "The value of tRPOperPSToCritNbrInetAddrType indicates
         the type of tRPOperPSToCritNbrInetAddr address, 
         as defined in the InetAddress MIB."
    ::= { tRPOperPSToCriteriaEntry 13 }

tRPOperPSToCritNbrInetAddr  OBJECT-TYPE
    SYNTAX       InetAddress
    MAX-ACCESS   read-only
    STATUS       current
    DESCRIPTION 
        "The value of tRPOperPSToCritNbrInetAddr indicates 
         the IP address of neighbor to match on. 
         The object tRPOperPSToCritNbrInetAddr is disabled
         if it holds the value ffff:ffff:ffff:ffff:ffff:ffff:ffff:ffff.

         The type of this address is determined by the 
         value of tRPOperPSToCritNbrInetAddrType object.

         tRPOperPSToCritNbrInetAddr object replaces 
         tRPOperPSToCriteriaNeighborIpAddr that supports only
         IPv4 address style neighbor."
    ::= { tRPOperPSToCriteriaEntry 14 }

tRPOperPSToCriteriaInstanceId  OBJECT-TYPE
    SYNTAX       Unsigned32 (0..31| 4294967295)
    MAX-ACCESS   read-only
    STATUS       current
    DESCRIPTION 
        "The value of tRPOperPSToCriteriaInstanceId indicates instance 
         of a version of the OSPF protocol running in the router instance.

         If the value of tRPOperPSToCriteriaInstanceId is 4294967295,
         all instances of OSPF protocol are leaked into BGP."

    ::= { tRPOperPSToCriteriaEntry 15 }

--
-- policy-statement entry from
--

tRPOperPSFromCriteriaTableLastChanged OBJECT-TYPE
    SYNTAX       TimeStamp
    MAX-ACCESS   read-only
    STATUS       obsolete
    DESCRIPTION
        "Timestamp of last change to tRPOperPSFromCriteriaTable.

         tRPOperPSFromCriteriaTableLastChanged is obsoleted in release 5.0.
         TIMETRA-SYSTEM-MIB::tmnxConfigModify notification is used instead."
    ::= { tRPOperValueObjects 19 }

tRPOperPSFromCriteriaTable OBJECT-TYPE
    SYNTAX       SEQUENCE OF TRPOperPSFromCriteriaEntry
    MAX-ACCESS   not-accessible
    STATUS       current
    DESCRIPTION 
        "A table of from filter criteria for each policy-statement entry."
    ::= { tRPOperValueObjects 20 }

tRPOperPSFromCriteriaEntry OBJECT-TYPE
    SYNTAX       TRPOperPSFromCriteriaEntry
    MAX-ACCESS   not-accessible
    STATUS       current
    DESCRIPTION 
        "Information about policy statement entry -from- criteria.
        
         Entries are created when a policy statement entry is created.
         Entries are deleted when a policy statement entry is destroyed."
    INDEX { tRPOperPolicyStatementName, tRPOperPSFromCriteriaIndex }
    ::= { tRPOperPSFromCriteriaTable 1 }

TRPOperPSFromCriteriaEntry ::= SEQUENCE
    {
        tRPOperPSFromCriteriaIndex              TPolicyStatementEntryID,
        tRPOperPSFromCriteriaRowStatus          RowStatus,
        tRPOperPSFromCriteriaProtocol           TRoutePolicyProtocol,
        tRPOperPSFromCriteriaNeighborIpAddr     IpAddress,
        tRPOperPSFromCriteriaNeighborPrefixList TPrefixListName,
        tRPOperPSFromCriteriaPrefixList1        TPrefixListName,
        tRPOperPSFromCriteriaPrefixList2        TPrefixListName,
        tRPOperPSFromCriteriaPrefixList3        TPrefixListName,
        tRPOperPSFromCriteriaPrefixList4        TPrefixListName,
        tRPOperPSFromCriteriaPrefixList5        TPrefixListName,
        tRPOperPSFromCriteriaASPath             TASPathName,
        tRPOperPSFromCriteriaCommunity          TCommunityName,
        tRPOperPSFromCriteriaOrigin             TPolicyEntryCriteriaOrigin,
        tRPOperPSFromCriteriaOspfRouteType      TOspfRouteType,
        tRPOperPSFromCriteriaEntryLastChanged   TimeStamp,
        tRPOperPSFromCriteriaArea               IpAddress,
        tRPOperPSFromCriteriaAreaConfigured     TruthValue,
        tRPOperPSFromCriteriaIsisLevel          TIsisLevel,
        tRPOperPSFromCriteriaIsisExternal       TruthValue,
        tRPOperPSFromCriteriaIgmpHostPrefixList TPrefixListName,
        tRPOperPSFromCriteriaGrpAddrPrefixList  TPrefixListName,
        tRPOperPSFromCriteriaSrcAddr            IpAddress,
        tRPOperPSFromCriteriaInterface          TNamedItemOrEmpty,
        tRPOperPSFromCriteriaTag                TPolicyActionTag,
        tRPOperPSFromCritNbrInetAddrType        InetAddressType,
        tRPOperPSFromCritNbrInetAddr            InetAddress,
        tRPOperPSFromCritSrcInetAddrType        InetAddressType,
        tRPOperPSFromCritSrcInetAddr            InetAddress,
        tRPOperPSFromCriteriaFamily             TmnxBGPFamilyType,
        tRPOperPSFromCriteriaInstanceId         Unsigned32,
        tRPOperPSFromCriteriaMatchTag           TmnxEnabledDisabled,
        tRPOperPSFromCriteriaState              TPolicyEntryCriteriaState,
        tRPOperPSFromCritASPathGroup            TNamedItemOrEmpty
    }

tRPOperPSFromCriteriaIndex  OBJECT-TYPE
    SYNTAX       TPolicyStatementEntryID
    MAX-ACCESS   not-accessible
    STATUS       current
    DESCRIPTION 
        "The policy statement entry ID"
    ::= { tRPOperPSFromCriteriaEntry 1 }

tRPOperPSFromCriteriaRowStatus  OBJECT-TYPE
    SYNTAX       RowStatus
    MAX-ACCESS   read-only
    STATUS       current
    DESCRIPTION
        "RowStatus for this row. Values read will only be 
         active(1), notInService(2), notReady(3). To create
         or destroy entries in this table, use the 
         tRPAdminPSFromCriteriaTable."
    ::= { tRPOperPSFromCriteriaEntry 2 }

tRPOperPSFromCriteriaProtocol  OBJECT-TYPE
    SYNTAX       TRoutePolicyProtocol
    MAX-ACCESS   read-only
    STATUS       current
    DESCRIPTION 
        "The protocol name to match on. 
         Set to none(1) to disable."
    ::= { tRPOperPSFromCriteriaEntry 3 }

tRPOperPSFromCriteriaNeighborIpAddr  OBJECT-TYPE
    SYNTAX       IpAddress
    MAX-ACCESS   read-only
    STATUS       current
    DESCRIPTION 
        "The IP address of neighbor to match on. 
         Set to 0.0.0.0 to disable."
    ::= { tRPOperPSFromCriteriaEntry 4 }

tRPOperPSFromCriteriaNeighborPrefixList  OBJECT-TYPE
    SYNTAX       TPrefixListName
    MAX-ACCESS   read-only
    STATUS       current
    DESCRIPTION 
        "The name of a neighbor prefix list to match on.
         Set to empty string to disable."
    ::= { tRPOperPSFromCriteriaEntry 5 }

tRPOperPSFromCriteriaPrefixList1  OBJECT-TYPE
    SYNTAX       TPrefixListName
    MAX-ACCESS   read-only
    STATUS       current
    DESCRIPTION 
        "The name of the first prefix list to match on. 
         Set to empty string to disable."
    ::= { tRPOperPSFromCriteriaEntry 6 }

tRPOperPSFromCriteriaPrefixList2  OBJECT-TYPE
    SYNTAX       TPrefixListName
    MAX-ACCESS   read-only
    STATUS       current
    DESCRIPTION 
        "The name of the second prefix list to match on. 
         Set to empty string to disable."
    ::= { tRPOperPSFromCriteriaEntry 7 }

tRPOperPSFromCriteriaPrefixList3  OBJECT-TYPE
    SYNTAX       TPrefixListName
    MAX-ACCESS   read-only
    STATUS       current
    DESCRIPTION 
        "The name of the third prefix list to match on. 
         Set to empty string to disable."
    ::= { tRPOperPSFromCriteriaEntry 8 }

tRPOperPSFromCriteriaPrefixList4  OBJECT-TYPE
    SYNTAX       TPrefixListName
    MAX-ACCESS   read-only
    STATUS       current
    DESCRIPTION 
        "The name of the fourth prefix list to match on. 
         Set to empty string to disable."
    ::= { tRPOperPSFromCriteriaEntry 9 }

tRPOperPSFromCriteriaPrefixList5  OBJECT-TYPE
    SYNTAX       TPrefixListName
    MAX-ACCESS   read-only
    STATUS       current
    DESCRIPTION 
        "The name of the fifth prefix list to match on. 
         Set to empty string to disable."
    ::= { tRPOperPSFromCriteriaEntry 10 }

tRPOperPSFromCriteriaASPath  OBJECT-TYPE
    SYNTAX       TASPathName
    MAX-ACCESS   read-only
    STATUS       current
    DESCRIPTION 
        "The name of the AS Path to match on. 
         Set to empty string to disable."
    ::= { tRPOperPSFromCriteriaEntry 11 }

tRPOperPSFromCriteriaCommunity  OBJECT-TYPE
    SYNTAX       TCommunityName
    MAX-ACCESS   read-only
    STATUS       current
    DESCRIPTION 
        "The name of the community to match on.
         Set to empty string to disable."
    ::= { tRPOperPSFromCriteriaEntry 12 }

tRPOperPSFromCriteriaOrigin  OBJECT-TYPE
    SYNTAX       TPolicyEntryCriteriaOrigin 
    MAX-ACCESS   read-only
    STATUS       current
    DESCRIPTION
        "The value of tRPOperPSFromCriteriaOrigin indicates
         the route match criterion for an entry."
    ::= { tRPOperPSFromCriteriaEntry 13 }

tRPOperPSFromCriteriaOspfRouteType  OBJECT-TYPE
    SYNTAX       TOspfRouteType
    MAX-ACCESS   read-only
    STATUS       current
    DESCRIPTION 
        "The OSPF route type to match on. 
         Set to zero to disable."
    ::= { tRPOperPSFromCriteriaEntry 14 }
    
tRPOperPSFromCriteriaEntryLastChanged   OBJECT-TYPE
    SYNTAX       TimeStamp
    MAX-ACCESS   read-only
    STATUS       obsolete
    DESCRIPTION 
        "Timestamp of last change to this entry.

         tRPOperPSFromCriteriaEntryLastChanged is obsoleted in release 5.0.
         TIMETRA-SYSTEM-MIB::tmnxConfigModify notification is used instead."
    ::= { tRPOperPSFromCriteriaEntry 15 }

tRPOperPSFromCriteriaArea  OBJECT-TYPE
    SYNTAX       IpAddress
    MAX-ACCESS   read-only
    STATUS       current
    DESCRIPTION 
        "Used when redistributing OSPF routes into other protocols. Specifies
         the OSPF area that must be matched in filtered routes."
    ::= { tRPOperPSFromCriteriaEntry 16 }

tRPOperPSFromCriteriaAreaConfigured  OBJECT-TYPE
    SYNTAX       TruthValue
    MAX-ACCESS   read-only
    STATUS       current
    DESCRIPTION 
        "Specifies if the tRPOperPSFromCriteriaArea has been 
         configured"
    ::= { tRPOperPSFromCriteriaEntry 17 }

tRPOperPSFromCriteriaIsisLevel  OBJECT-TYPE
    SYNTAX       TIsisLevel
    MAX-ACCESS   read-only
    STATUS       current
    DESCRIPTION 
        "The value for tRPOperPSFromCriteriaIsisLevel defines the IS-IS route 
         level match criterion. A value of 0 indicates that no IS-IS route 
         level match criterion has been configured."
    ::= { tRPOperPSFromCriteriaEntry 18 }
   
tRPOperPSFromCriteriaIsisExternal  OBJECT-TYPE
    SYNTAX       TruthValue
    MAX-ACCESS   read-only
    STATUS       current
    DESCRIPTION 
        "When tRPOperPSFromCriteriaIsisExternal is 'true', match only 
         External IS-IS routes. If 'false', match all routes. 
         External IS-IS routes are those routes that have been learned from 
         outside the IS-IS domain."
    ::= { tRPOperPSFromCriteriaEntry 19 }

tRPOperPSFromCriteriaIgmpHostPrefixList  OBJECT-TYPE
    SYNTAX       TPrefixListName
    MAX-ACCESS   read-only
    STATUS       current
    DESCRIPTION 
        "tRPOperPSFromCriteriaIgmpHostPrefixList contains the name of the
         prefix list that is used to match the IGMP host IP address.
         The value of the object will be an empty string if it not set."
    ::= { tRPOperPSFromCriteriaEntry 20 }

tRPOperPSFromCriteriaGrpAddrPrefixList  OBJECT-TYPE
    SYNTAX       TPrefixListName
    MAX-ACCESS   read-only
    STATUS       current
    DESCRIPTION 
        "tRPOperPSFromCriteriaGrpAddrPrefixList contains the name of the
         prefix list that is used to match the multicast group address.
         The value of the object will be an empty string if it not set."
    ::= { tRPOperPSFromCriteriaEntry 21 }

tRPOperPSFromCriteriaSrcAddr  OBJECT-TYPE
    SYNTAX       IpAddress
    MAX-ACCESS   read-only
    STATUS       current
    DESCRIPTION 
        "tRPOperPSFromCriteriaSrcAddr contains the IP address of the 
         source to match on. This object will be used by multicast protocols
         like PIM and IGMP.
         The value of this object will be 0.0.0.0 if it is not set."
    ::= { tRPOperPSFromCriteriaEntry 22 }

tRPOperPSFromCriteriaInterface  OBJECT-TYPE
    SYNTAX       TNamedItemOrEmpty
    MAX-ACCESS   read-only
    STATUS       current
    DESCRIPTION 
        "tRPOperPSFromCriteriaInterface contains the name of the
         interface to match on. PIM Bootstrap route policy will use
         this object to accept/reject bootstrap messages coming on 
         the interface specified by this object.
         The value of the object will be an empty string if it not set."
    ::= { tRPOperPSFromCriteriaEntry 23 }

tRPOperPSFromCriteriaTag  OBJECT-TYPE
    SYNTAX       TPolicyActionTag
    MAX-ACCESS   read-only
    STATUS       current
    DESCRIPTION 
        "The value of tRPOperPSFromCriteriaTag indicates the operational tag 
         to match on. It will only be valid when tRPOperPSFromCriteriaMatchTag
         is enabled which indicates that route matching based on tags is 
         enabled.
        
         A value of 0 for tRPOperPSFromCriteriaTag when 
         tRPOperPSFromCriteriaMatchTag is enabled indicates untagged routes are
         matched."
    ::= { tRPOperPSFromCriteriaEntry 24 }

tRPOperPSFromCritNbrInetAddrType  OBJECT-TYPE
    SYNTAX       InetAddressType
    MAX-ACCESS   read-only
    STATUS       current
    DESCRIPTION 
        "The value of tRPOperPSFromCritNbrInetAddrType indicates
         the type of tRPOperPSFromCritNbrInetAddr address, 
         as defined in the InetAddress MIB."
    ::= { tRPOperPSFromCriteriaEntry 25 }

tRPOperPSFromCritNbrInetAddr  OBJECT-TYPE
    SYNTAX       InetAddress
    MAX-ACCESS   read-only
    STATUS       current
    DESCRIPTION 
        "The value of tRPOperPSFromCritNbrInetAddr indicates 
         the IP address of neighbor to match on. 
         The object tRPOperPSFromCritNbrInetAddr is disabled
         if it holds the value ffff:ffff:ffff:ffff:ffff:ffff:ffff:ffff.
      
         The type of this address is determined by the 
         value of the tRPOperPSFromCritNbrInetAddrType object.

         tRPOperPSFromCritNbrInetAddr object replaces 
         tRPOperPSFromCriteriaNeighborIpAddr that supports only
         IPv4 address style neighbor."
    
    ::= { tRPOperPSFromCriteriaEntry 26 }

tRPOperPSFromCritSrcInetAddrType  OBJECT-TYPE
    SYNTAX       InetAddressType
    MAX-ACCESS   read-only
    STATUS       current
    DESCRIPTION 
        "The value of tRPOperPSFromCritSrcInetAddrType indicates
         the type of tRPOperPSFromCritSrcInetAddr address, 
         as defined in the InetAddress MIB."
    ::= { tRPOperPSFromCriteriaEntry 27 }

tRPOperPSFromCritSrcInetAddr  OBJECT-TYPE
    SYNTAX       InetAddress
    MAX-ACCESS   read-only
    STATUS       current
    DESCRIPTION 
        "The value of tRPOperPSFromCritSrcInetAddr indicates 
         the IP address of the source to match on. 
         This object will be used by multicast protocols 
         like PIM and IGMP and is disabled if it holds the
         value ffff:ffff:ffff:ffff:ffff:ffff:ffff:ffff.

         The type of this address is determined by the 
         value of the tRPOperPSFromCritSrcInetAddrType object.

         tRPOperPSFromCritSrcInetAddr object replaces 
         tRPOperPSFromCriteriaSrcAddr that supports only
         IPv4 address style source."
    ::= { tRPOperPSFromCriteriaEntry 28 }

tRPOperPSFromCriteriaFamily  OBJECT-TYPE
    SYNTAX       TmnxBGPFamilyType
    MAX-ACCESS   read-only
    STATUS       current
    DESCRIPTION 
        "The  bits set in the value of tRPAdminPSFromCriteriaFamily indicate 
         the address families that this condition would match against."
    ::= { tRPOperPSFromCriteriaEntry 29 }

tRPOperPSFromCriteriaInstanceId OBJECT-TYPE
    SYNTAX       Unsigned32 (0..31| 4294967295)
    MAX-ACCESS   read-only
    STATUS       current
    DESCRIPTION 
        "The value of tRPOperPSFromCriteriaInstanceId indicates instance 
         of a version of the OSPF protocol running in the router instance.

         If the value of tRPOperPSFromCriteriaInstanceId is 4294967295,
         all instances of OSPF protocol are leaked into BGP."
    ::= { tRPOperPSFromCriteriaEntry 30 }

tRPOperPSFromCriteriaMatchTag  OBJECT-TYPE
    SYNTAX       TmnxEnabledDisabled
    MAX-ACCESS   read-only
    STATUS       current
    DESCRIPTION 
        "The value of tRPOperPSFromCriteriaMatchTag indicates if tag matching is
        enabled or disabled."
    ::= { tRPOperPSFromCriteriaEntry 31 }

tRPOperPSFromCriteriaState  OBJECT-TYPE
    SYNTAX       TPolicyEntryCriteriaState
    MAX-ACCESS   read-only
    STATUS       current
    DESCRIPTION
        "The value of tRPOperPSFromCriteriaState indicates
         the route state match criterion for this entry."
    ::= { tRPOperPSFromCriteriaEntry 32 }

tRPOperPSFromCritASPathGroup OBJECT-TYPE
    SYNTAX       TNamedItemOrEmpty
    MAX-ACCESS   read-only
    STATUS       current
    DESCRIPTION
        "The value of tRPOperPSFromCritASPathGroup indicates
         the AS-Path Group match criterion for this entry."
    ::= { tRPOperPSFromCriteriaEntry 33 }

--
-- Administrative value objects
--

tRPAdminControlObjects OBJECT IDENTIFIER ::= { tRPAdminObjects 1 }
tRPAdminValueObjects OBJECT IDENTIFIER ::= { tRPAdminObjects 2 }

--
-- AS Path
--

tRPAdminASPathTable OBJECT-TYPE
    SYNTAX       SEQUENCE OF TRPAdminASPathEntry
    MAX-ACCESS   not-accessible
    STATUS       current
    DESCRIPTION
        "A list of AS Path names and corresponding regular-expressions."
    ::= { tRPAdminValueObjects 1 }

tRPAdminASPathEntry OBJECT-TYPE
    SYNTAX       TRPAdminASPathEntry
    MAX-ACCESS   not-accessible
    STATUS       current
    DESCRIPTION 
        "Information about a particular AS Path Name.
         Entries are created by user.
         Entries are deleted by user.
        
         Entry must exist before referencing objects 
         can be set to refer to the tRPAdminASPathName."
    INDEX { tRPAdminASPathName }
    ::= { tRPAdminASPathTable 1 }

TRPAdminASPathEntry ::= SEQUENCE
    {
        tRPAdminASPathName      TASPathName,
        tRPAdminASPathRowStatus RowStatus,
        tRPAdminASPathRegEx     TRegularExpression
    }

tRPAdminASPathName  OBJECT-TYPE
    SYNTAX       TASPathName (SIZE(1..32))
    MAX-ACCESS   not-accessible
    STATUS       current
    DESCRIPTION 
        "The name of the AS Path entry used to uniquely identify an AS Path."
    ::= { tRPAdminASPathEntry 1 }

tRPAdminASPathRowStatus  OBJECT-TYPE
    SYNTAX       RowStatus
    MAX-ACCESS   read-create
    STATUS       current
    DESCRIPTION 
        "RowStatus for this row. Legal values to write are: 
         active(1), notInService(2), createAndGo(4) and destroy(6).
        
         To create a row, set this object to createAndGo(4). The value of
         tRPAdminASPathRegEx must also be set to a valid non-empty string for 
         the row creation to succeed. When tRPAdminControlApply is set to
         commit(3), the row will actually be created in the tRPOperASPathTable.
        
         To destroy a row, set this object to destroy(6). If there are no 
         objects that refer to the entry, when tRPAdminControlApply is 
         set to commit(3) the row will actually be removed from the 
         tRPOperASPathTable.
        
         If there are objects that refer to the entry, the destroy SET request
         will fail with an error."
    ::= { tRPAdminASPathEntry 2 }

tRPAdminASPathRegEx  OBJECT-TYPE
    SYNTAX       TRegularExpression
    MAX-ACCESS   read-create
    STATUS       current
    DESCRIPTION 
        "The regular expression for the AS Path entry. This object must be
         set to a valid non-empty string for the row creation to succeed."
    ::= { tRPAdminASPathEntry 3 }


--
-- community 
--

tRPAdminCommunityTable OBJECT-TYPE
    SYNTAX       SEQUENCE OF TRPAdminCommunityEntry
    MAX-ACCESS   not-accessible
    STATUS       current
    DESCRIPTION 
        "A table of community entries."
    ::= { tRPAdminValueObjects 2 }

tRPAdminCommunityEntry OBJECT-TYPE
    SYNTAX       TRPAdminCommunityEntry
    MAX-ACCESS   not-accessible
    STATUS       current
    DESCRIPTION 
        "Information about a particular community name member.
         Entries are created by user.
         Entries are deleted by user."
    INDEX { tRPAdminCommunityName, tRPAdminCommunityMember }
    ::= { tRPAdminCommunityTable 1 }

TRPAdminCommunityEntry ::= SEQUENCE
    {
        tRPAdminCommunityName      TCommunityName,
        tRPAdminCommunityMember    TCommunityMember,
        tRPAdminCommunityRowStatus RowStatus
    }

tRPAdminCommunityName  OBJECT-TYPE
    SYNTAX       TCommunityName (SIZE(1..32))
    MAX-ACCESS   not-accessible
    STATUS       current
    DESCRIPTION
        "The name of the community used as an index for this table."
    ::= { tRPAdminCommunityEntry 1 }

tRPAdminCommunityMember             OBJECT-TYPE
    SYNTAX       TCommunityMember
    MAX-ACCESS   not-accessible
    STATUS       current
    DESCRIPTION 
        "The AS Number or Community ID of the community member. The 
         community name and the member name uniquely identify a row 
         in this table."
    ::= { tRPAdminCommunityEntry 2 }

tRPAdminCommunityRowStatus  OBJECT-TYPE
    SYNTAX       RowStatus
    MAX-ACCESS   read-create
    STATUS       current
    DESCRIPTION 
        "RowStatus for this row. Legal values to write are: 
         active(1), createAndGo(4) and destroy(6).
        
         To create a row, set this object to createAndGo.
         When tRPAdminControlApply is set to commit(3), the row will actually 
         be created in the tRPOperCommunityTable.
        
         To destroy a row, set this object to destroy(6). If there are no 
         objects that refer to the entry, when tRPAdminControlApply is 
         set to commit(3) the row will actually be removed from the 
         tRPOperCommunityTable."
    ::= { tRPAdminCommunityEntry 3 }

--
-- damping 
--

tRPAdminDampingTable OBJECT-TYPE
    SYNTAX       SEQUENCE OF TRPAdminDampingEntry
    MAX-ACCESS   not-accessible
    STATUS       current
    DESCRIPTION  
        "A table of route damping control entries."
    ::= { tRPAdminValueObjects 3 }

tRPAdminDampingEntry OBJECT-TYPE
    SYNTAX       TRPAdminDampingEntry
    MAX-ACCESS   not-accessible
    STATUS       current
    DESCRIPTION 
        "Information about a particular Damping entry.
         Entries are created by user. 
         Entries are deleted by user."
    INDEX { tRPAdminDampingName }
    ::= { tRPAdminDampingTable 1 }

TRPAdminDampingEntry ::= SEQUENCE
    {
        tRPAdminDampingName        TDampingName,
        tRPAdminDampingRowStatus   RowStatus,
        tRPAdminDampingHalfLife    Unsigned32,
        tRPAdminDampingMaxSuppress Unsigned32,
        tRPAdminDampingReuse       Unsigned32,
        tRPAdminDampingSuppress    Unsigned32
    }

tRPAdminDampingName  OBJECT-TYPE
    SYNTAX       TDampingName (SIZE(1..32))
    MAX-ACCESS   not-accessible
    STATUS       current
    DESCRIPTION 
        "The name of the damping entry used to uniquely identify a 
         row in this table."
    ::= { tRPAdminDampingEntry 1 }

tRPAdminDampingRowStatus  OBJECT-TYPE
    SYNTAX       RowStatus
    MAX-ACCESS   read-create
    STATUS       current
    DESCRIPTION 
        "RowStatus for this row. Legal values to write are: 
         active(1), notInService(2), createAndGo(4), createAndWait(5), 
         destroy(6).
        
         To create a row, set this object to createAndGo or createAndWait.
         When tRPAdminControlApply is set to commit(3), the row will actually 
         be created in the tRPOperDampingTable.
        
         To destroy a row, set this object to destroy(6). If there are no 
         objects that refer to the entry, when tRPAdminControlApply is 
         set to commit(3) the row will actually be removed from the 
         tRPOperDampingTable.
         
        
        If there are objects that refer to the entry, the destroy SET request
        will fail with an error."
    ::= { tRPAdminDampingEntry 2 }

tRPAdminDampingHalfLife  OBJECT-TYPE
    SYNTAX       Unsigned32 (0..45)
    UNITS        "minutes"
    MAX-ACCESS   read-create
    STATUS       current
    DESCRIPTION 
        "Specifies the half-life, in minutes, for a routes figure-of-merit 
         after it has been dampened. If a route's half-life is set to 
         15 minutes and has a figure-of-merit of 1500, after 15 minutes, 
         the route's figure-of-merit will have decayed to 750. Set to 0 
         to disable."
    DEFVAL { 0 }
    ::= { tRPAdminDampingEntry 3 }

tRPAdminDampingMaxSuppress  OBJECT-TYPE
    SYNTAX       Unsigned32 (0..720)
    UNITS        "minutes"
    MAX-ACCESS   read-create
    STATUS       current
    DESCRIPTION 
        "Specifies the maximum amount of time, in minutes, that a route 
         can be suppressed for. Set to 0 to disable."
    DEFVAL { 0 }
    ::= { tRPAdminDampingEntry 4 }

tRPAdminDampingReuse  OBJECT-TYPE
    SYNTAX       Unsigned32 (0..20000)
    MAX-ACCESS   read-create
    STATUS       current
    DESCRIPTION 
        "Specifies the reuse threshold. If a route's figure-of-merit
         falls below the reuse threshold, the route can be reused.
         Set to 0 to disable."
    DEFVAL { 0 }
    ::= { tRPAdminDampingEntry 5 }

tRPAdminDampingSuppress  OBJECT-TYPE
    SYNTAX       Unsigned32 (0..20000)
    MAX-ACCESS   read-create
    STATUS       current
    DESCRIPTION 
        "Specifies the suppress threshold. If a route's figure-of-merit
         goes above the suppress threshold, the route should be suppressed.
         Set to 0 to disable."
    DEFVAL { 0 }
    ::= { tRPAdminDampingEntry 6 }


--
-- prefix-list 
--

tRPAdminPrefixListTable OBJECT-TYPE
    SYNTAX       SEQUENCE OF TRPAdminPrefixListEntry
    MAX-ACCESS   not-accessible
    STATUS       current
    DESCRIPTION  
        "A table of prefix lists."
    ::= { tRPAdminValueObjects 4 }

tRPAdminPrefixListEntry OBJECT-TYPE
    SYNTAX       TRPAdminPrefixListEntry
    MAX-ACCESS   not-accessible
    STATUS       current
    DESCRIPTION 
        "Information about a particular prefix list.
         Entries are created by user.
         Entries are deleted by user."
    INDEX { tRPAdminPrefixListName, tRPAdminPrefixListIpPrefix,
            tRPAdminPrefixListMask, tRPAdminPrefixListType}
    ::= { tRPAdminPrefixListTable 1 }

TRPAdminPrefixListEntry ::= SEQUENCE
    {
        tRPAdminPrefixListName          TPrefixListName,
        tRPAdminPrefixListIpPrefix      IpAddress,
        tRPAdminPrefixListMask          IpAddressPrefixLength,
        tRPAdminPrefixListRowStatus     RowStatus,
        tRPAdminPrefixListType          INTEGER,
        tRPAdminPrefixListThroughLength IpAddressPrefixLength,
        tRPAdminPrefixListBeginLength   IpAddressPrefixLength
    }

tRPAdminPrefixListName  OBJECT-TYPE
    SYNTAX       TPrefixListName (SIZE(1..32))
    MAX-ACCESS   not-accessible
    STATUS       current
    DESCRIPTION
        "The name of the prefix list entry."
    ::= { tRPAdminPrefixListEntry 1 }

tRPAdminPrefixListIpPrefix  OBJECT-TYPE
    SYNTAX       IpAddress
    MAX-ACCESS   not-accessible
    STATUS       current
    DESCRIPTION
        "The IP prefix of the prefix list entry."
    ::= { tRPAdminPrefixListEntry 2 }

tRPAdminPrefixListMask  OBJECT-TYPE
    SYNTAX       IpAddressPrefixLength
    MAX-ACCESS   not-accessible
    STATUS       current
    DESCRIPTION
        "The IP mask length of the prefix list entry."
    ::= { tRPAdminPrefixListEntry 3 }

tRPAdminPrefixListRowStatus  OBJECT-TYPE
    SYNTAX       RowStatus
    MAX-ACCESS   read-create
    STATUS       current
    DESCRIPTION 
        "RowStatus for this row. Legal values to write are: 
         active(1), notInService(2), createAndGo(4), createAndWait(5), 
         destroy(6).
        
         To create a row, set this object to createAndGo or createAndWait.
         When tRPAdminControlApply is set to commit(3), the row will actually 
         be created in the tRPOperPrefixListTable.
        
         To destroy a row, set this object to destroy(6). If there are no 
         objects that refer to the entry, when tRPAdminControlApply is 
         set to commit(3) the row will actually be removed from the 
         tRPOperPrefixListTable.
        
         If there are objects that refer to the entry, the destroy SET request
         will fail with an error."
    ::= { tRPAdminPrefixListEntry 4 }

tRPAdminPrefixListType  OBJECT-TYPE
    SYNTAX       INTEGER { exact(1), longer(2), through(3), range(4) }
    MAX-ACCESS   not-accessible
    STATUS       current
    DESCRIPTION 
        "The type of the prefix length entry.
        
         exact (1) - a route's prefix/length must match the 
         prefix-list entry exactly in order for an entry to 
         be considered a match.

         longer (2) - a route's prefix/length must match the 
         defined prefix AND have a length that is an exact match 
         or longer in order for an entry to be considered a match.

         through (3) - a route's prefix/length must match the 
         defined prefix AND have a length that is an exact match or 
         longer up to and including the defined maximum length in
         order for an entry to be considered a match.

         range (4) - a route's prefix/length must match the 
         defined prefix AND have a length that is greater than or 
         equal to the length defined by tRPAdminPrefixListBeginLength 
         and less than or equal to the length defined by 
         tRPAdminPrefixListThroughLength in order for an entry to 
         be considered a match."
    ::= { tRPAdminPrefixListEntry 5 }

tRPAdminPrefixListThroughLength  OBJECT-TYPE
    SYNTAX       IpAddressPrefixLength
    MAX-ACCESS   read-create
    STATUS       current
    DESCRIPTION
        "When tRPAdminPrefixListType set to through(3), the mask length to use.
         Must be larger than tRPAdminPrefixListMask."
    DEFVAL { 0 }
    ::= { tRPAdminPrefixListEntry 6 }

tRPAdminPrefixListBeginLength  OBJECT-TYPE
    SYNTAX       IpAddressPrefixLength
    MAX-ACCESS   read-create
    STATUS       current
    DESCRIPTION
        "When tRPAdminPrefixListType set to range(4), the mask length to use 
         as the lower limit for the mask range. Must be larger than
         tRPAdminPrefixListMask and less than tRPAdminPrefixListThroughLength."
    DEFVAL { 0 }
    ::= { tRPAdminPrefixListEntry 8 }


--
-- policy-statement 
--

tRPAdminPolicyStatementTable OBJECT-TYPE
    SYNTAX       SEQUENCE OF TRPAdminPolicyStatementEntry
    MAX-ACCESS   not-accessible
    STATUS       current
    DESCRIPTION  
        "Control table for policy-statements."
    ::= { tRPAdminValueObjects 5 }

tRPAdminPolicyStatementEntry OBJECT-TYPE
    SYNTAX       TRPAdminPolicyStatementEntry
    MAX-ACCESS   not-accessible
    STATUS       current
    DESCRIPTION 
        "Information about a particular policy-statement.
         Entries are created by user.
         Entries are deleted by user."
    INDEX { tRPAdminPolicyStatementName }
    ::= { tRPAdminPolicyStatementTable 1 }

TRPAdminPolicyStatementEntry ::= SEQUENCE
    {
        tRPAdminPolicyStatementName          TPolicyStatementName,
        tRPAdminPolicyStatementRowStatus     RowStatus,
        tRPAdminPolicyStatementDescription   TItemDescription,
        tRPAdminPolicyStatementDefaultAction TPolicyEntryAction
    }

tRPAdminPolicyStatementName  OBJECT-TYPE
    SYNTAX       TPolicyStatementName
    MAX-ACCESS   not-accessible
    STATUS       current
    DESCRIPTION
        "The name of this policy statement that uniquely identifies an
         entry in this table."
    ::= { tRPAdminPolicyStatementEntry 1 }

tRPAdminPolicyStatementRowStatus  OBJECT-TYPE
    SYNTAX       RowStatus
    MAX-ACCESS   read-create
    STATUS       current
    DESCRIPTION 
        "RowStatus for this row. Legal values to write are: 
         active(1), notInService(2), createAndGo(4), createAndWait(5), 
         destroy(6).
        
         To Create a row, set this object to createAndGo or createAndWait.
         When tRPAdminControlApply is set to commit(3), the row will actually 
         be created in the tRPOperPolicyStatementTable.
        
         To destroy a row, set this object to destroy(6). If there are no 
         objects that refer to the entry, when tRPAdminControlApply is 
         set to commit(3) the row will actually be removed from the 
         tRPOperPolicyStatementTable.
        
         If there are objects that refer to the entry, the destroy SET request
         will fail with an error."
    ::= { tRPAdminPolicyStatementEntry 2 }

tRPAdminPolicyStatementDescription  OBJECT-TYPE
    SYNTAX       TItemDescription
    MAX-ACCESS   read-create
    STATUS       current
    DESCRIPTION 
        "Description for this policy statement."
    DEFVAL { ''H }
    ::= { tRPAdminPolicyStatementEntry 3 }

tRPAdminPolicyStatementDefaultAction  OBJECT-TYPE
    SYNTAX       TPolicyEntryAction
    MAX-ACCESS   read-create
    STATUS       current
    DESCRIPTION 
        "The default-action for the policy statement indicates
         what happens to the route if none of the policy statement entries 
         match."
    DEFVAL { reject }
    ::= { tRPAdminPolicyStatementEntry 4 }


--
-- policy-statement default action 
--

tRPAdminPSDefaultActionParamsTable OBJECT-TYPE
    SYNTAX       SEQUENCE OF TRPAdminPSDefaultActionParamsEntry
    MAX-ACCESS   not-accessible
    STATUS       current
    DESCRIPTION  
        "Default action parameters for a policy-statement."
    ::= { tRPAdminValueObjects 6 }

tRPAdminPSDefaultActionParamsEntry OBJECT-TYPE
    SYNTAX       TRPAdminPSDefaultActionParamsEntry
    MAX-ACCESS   not-accessible
    STATUS       current
    DESCRIPTION 
        "Default action information about a particular policy statement.
         When tRPAdminPolicyStatementDefaultAction for the policy statement
         is accept(1), and no poliy statement entry matches the route, 
         the following default actions are applied to the route.
        
         When tRPAdminPolicyStatementDefaultAction is reject, these
         objects are ignored, and the route is dropped.
        
         Entries are created when a policy statement is created.
         Entries are deleted when a policy statement is destroyed."
    INDEX { tRPAdminPolicyStatementName }
    ::= { tRPAdminPSDefaultActionParamsTable 1 }

TRPAdminPSDefaultActionParamsEntry ::= SEQUENCE
    {
        tRPAdminPSDefaultActionASPath              TPolicyEntryEdit,
        tRPAdminPSDefaultActionASPathName          TASPathName,
        tRPAdminPSDefaultActionASPathPrependAS     TmnxBgpAutonomousSystem,
        tRPAdminPSDefaultActionASPathPrependCount  INTEGER,
        tRPAdminPSDefaultActionCommunity1          TPolicyEntryEdit,
        tRPAdminPSDefaultActionCommunityName1      TCommunityName,
        tRPAdminPSDefaultActionCommunity2          TPolicyEntryEdit,
        tRPAdminPSDefaultActionCommunityName2      TCommunityName,
        tRPAdminPSDefaultActionOrigin              TPolicyEntryCriteriaOrigin,
        tRPAdminPSDefaultActionLocalPreferenceSet  TruthValue,
        tRPAdminPSDefaultActionLocalPreference     TmnxBgpLocalPreference,
        tRPAdminPSDefaultActionMetric              TPolicyEntryEdit,
        tRPAdminPSDefaultActionMetricValue         Unsigned32,
        tRPAdminPSDefaultActionPreference          TmnxBgpPreference,
        tRPAdminPSDefaultActionDamping             TDampingName,
        tRPAdminPSDefaultActionNextHopSelf         TruthValue,
        tRPAdminPSDefaultActionNextHop             IpAddress,
        tRPAdminPSDefaultActionTag                 TPolicyActionTag,
        tRPAdminPSDefaultActionOspfType            TOspfRouteType,
        tRPAdminPSDefActInetNextHopType            InetAddressType,
        tRPAdminPSDefActInetNextHop                InetAddress,
        tRPAdminPSDefaultActionASPathPnd           InetAutonomousSystemNumber,
        tRPAdminPSDefActMcRedirSvcId               TmnxServId,
        tRPAdminPSDefActMcRedirIfIndex             InterfaceIndexOrZero,
        tRPAdminPSDefActionMetricSource            TPolicyActionMetricSource,
        tRPAdminPSDefActionAigpMetric              TPolicyEntryAigpMetricEdit,
        tRPAdminPSDefActnAigpMetricVal             Unsigned32
    }

tRPAdminPSDefaultActionASPath  OBJECT-TYPE
    SYNTAX       TPolicyEntryEdit
    MAX-ACCESS   read-create
    STATUS       current
    DESCRIPTION 
        "The AS Path rewrite information for the route."
    DEFVAL { none }
    ::= { tRPAdminPSDefaultActionParamsEntry 1 }

tRPAdminPSDefaultActionASPathName  OBJECT-TYPE
    SYNTAX       TASPathName
    MAX-ACCESS   read-create
    STATUS       current
    DESCRIPTION 
        "The AS Path name to use for add, remove, or replace operation
         specified by tRPAdminPSDefaultActionASPath.  Ignored when 
         tRPAdminPSDefaultActionASPath is none(1)."
    DEFVAL { ''H }
    ::= { tRPAdminPSDefaultActionParamsEntry 2 }

tRPAdminPSDefaultActionASPathPrependAS  OBJECT-TYPE
    SYNTAX       TmnxBgpAutonomousSystem
    MAX-ACCESS   read-create
    STATUS       obsolete
    DESCRIPTION 
        "AS Number to prepend to the AS-Path attribute of the route.
         Ignored when tRPAdminPSDefaultActionASPathPrependCount is zero.

         This object was obsoleted in release 7.0.  It is replaced with the
         4-byte AS number defined by tRPAdminPSDefaultActionASPathPnd."
    DEFVAL { 0 }
    ::= { tRPAdminPSDefaultActionParamsEntry 3 }

tRPAdminPSDefaultActionASPathPrependCount  OBJECT-TYPE
    SYNTAX       INTEGER (0..50)
    MAX-ACCESS   read-create
    STATUS       current
    DESCRIPTION 
        "Number of times tRPAdminPSDefaultActionASPathPnd is prepended
         to the AS-Path attribute of the route.
         
         Set to zero to disable."
    DEFVAL { 0 }
    ::= { tRPAdminPSDefaultActionParamsEntry 4 }

tRPAdminPSDefaultActionCommunity1  OBJECT-TYPE
    SYNTAX       TPolicyEntryEdit
    MAX-ACCESS   read-create
    STATUS       current
    DESCRIPTION 
        "How to apply tRPAdminPSDefaultActionCommunityName1
         to the communities for the route.
        
         Set to none(1) to disable this feature."
    DEFVAL { none }
    ::= { tRPAdminPSDefaultActionParamsEntry 5 }

tRPAdminPSDefaultActionCommunityName1  OBJECT-TYPE
    SYNTAX       TCommunityName
    MAX-ACCESS   read-create
    STATUS       current
    DESCRIPTION 
        "Community name to add, remove, or replace, to any 
         existing community for the route.  Ignored when 
         tRPAdminPSDefaultActionCommunity1 is none(1)"
    DEFVAL { ''H }
    ::= { tRPAdminPSDefaultActionParamsEntry 6 }

tRPAdminPSDefaultActionCommunity2  OBJECT-TYPE
    SYNTAX       TPolicyEntryEdit
    MAX-ACCESS   read-create
    STATUS       current
    DESCRIPTION 
        "How to apply tRPAdminPSDefaultActionCommunityName2
         to the communities for the route.
        
         Set to none(1) to disable this feature."
    DEFVAL { none }
    ::= { tRPAdminPSDefaultActionParamsEntry 7 }

tRPAdminPSDefaultActionCommunityName2  OBJECT-TYPE
    SYNTAX       TCommunityName
    MAX-ACCESS   read-create
    STATUS       current
    DESCRIPTION 
        "Community name to add, remove, or replace, to any 
         existing community for the route.  Ignored when 
         tRPAdminPSDefaultActionCommunity2 is none(1)"
    DEFVAL { ''H }
    ::= { tRPAdminPSDefaultActionParamsEntry 8 }

tRPAdminPSDefaultActionOrigin  OBJECT-TYPE
    SYNTAX       TPolicyEntryCriteriaOrigin
    MAX-ACCESS   read-create
    STATUS       current
    DESCRIPTION
        "The value of tRPAdminPSDefaultActionOrigin specifies
         the origin of the route exported into BGP if it does not match an
         entry."
    DEFVAL { none }
    ::= { tRPAdminPSDefaultActionParamsEntry 9 }

tRPAdminPSDefaultActionLocalPreferenceSet  OBJECT-TYPE
    SYNTAX       TruthValue
    MAX-ACCESS   read-create
    STATUS       current
    DESCRIPTION 
        "When set to true(1), use the value of 
         tRPAdminPSDefaultActionLocalPreference for local preference."
    DEFVAL { false }
    ::= { tRPAdminPSDefaultActionParamsEntry 10 }

tRPAdminPSDefaultActionLocalPreference  OBJECT-TYPE
    SYNTAX       TmnxBgpLocalPreference
    MAX-ACCESS   read-create
    STATUS       current
    DESCRIPTION 
        "Local preference to apply to the route.
         Set tRPAdminPSDefaultActionLocalPreferenceSet to false(2) to disable."
    DEFVAL { 0 }
    ::= { tRPAdminPSDefaultActionParamsEntry 11 }

tRPAdminPSDefaultActionMetric  OBJECT-TYPE
    SYNTAX       TPolicyEntryEdit
    MAX-ACCESS   read-create
    STATUS       current
    DESCRIPTION 
        "Action for tRPAdminPSDefaultActionMetricValue."
    DEFVAL { none }
    ::= { tRPAdminPSDefaultActionParamsEntry 12 }

tRPAdminPSDefaultActionMetricValue  OBJECT-TYPE
    SYNTAX       Unsigned32
    MAX-ACCESS   read-create
    STATUS       current
    DESCRIPTION 
        "Add, subtract, or set metric value.  Ignored when
         tRPAdminPSDefaultActionMetric is none(1)."
    DEFVAL { 0 }
    ::= { tRPAdminPSDefaultActionParamsEntry 13 }

tRPAdminPSDefaultActionPreference  OBJECT-TYPE
    SYNTAX       TmnxBgpPreference
    MAX-ACCESS   read-create
    STATUS       current
    DESCRIPTION 
        "Preference to apply to the route."
    DEFVAL { 0 }
    ::= { tRPAdminPSDefaultActionParamsEntry 15 }

tRPAdminPSDefaultActionDamping  OBJECT-TYPE
    SYNTAX       TDampingName
    MAX-ACCESS   read-create
    STATUS       current
    DESCRIPTION 
        "Damping to apply to route.  Set to empty string to disable."
    DEFVAL { ''H }
    ::= { tRPAdminPSDefaultActionParamsEntry 16 }

tRPAdminPSDefaultActionNextHopSelf  OBJECT-TYPE
    SYNTAX       TruthValue
    MAX-ACCESS   read-create
    STATUS       current
    DESCRIPTION 
        "The value of tRPAdminPSDefaultActionNextHopSelf specifies
         the next-hop-self on the route. Next-hop-self cannot be set 
         to 'true' at the same time as setting next-hop object
         tRPAdminPSDefActInetNextHop to a valid IP address. 
         Setting tRPAdminPSDefaultActionNextHopSelf to 'true' will  
         reset tRPAdminPSDefActInetNextHop object to disable."
    DEFVAL { false }
    ::= { tRPAdminPSDefaultActionParamsEntry 17 }

tRPAdminPSDefaultActionNextHop  OBJECT-TYPE
    SYNTAX       IpAddress
    MAX-ACCESS   read-create
    STATUS       current
    DESCRIPTION 
        "Set next-hop address in route.  Set to 255.255.255.255 to disable.
         Next-hop cannot be set to a valid IP address at the same time
         as setting next-hop-self to 'true'. Setting next-hop to a valid
         IP address will reset next-hop-self to 'false'."
    DEFVAL { 'FFFFFFFF'H }
    ::= { tRPAdminPSDefaultActionParamsEntry 18 }

tRPAdminPSDefaultActionTag  OBJECT-TYPE
    SYNTAX       TPolicyActionTag
    MAX-ACCESS   read-create
    STATUS       current
    DESCRIPTION 
        "The value of tRPAdminPSDefaultActionTag specifies the tag for the route.

         A value of 0 for tRPAdminPSDefaultActionTag specifies that tagging is
         disabled."
    DEFVAL { 0 }
    ::= { tRPAdminPSDefaultActionParamsEntry 19 }

tRPAdminPSDefaultActionOspfType  OBJECT-TYPE
    SYNTAX       TOspfRouteType
    MAX-ACCESS   read-create
    STATUS       current
    DESCRIPTION 
        "OSPF route type for the route."
    DEFVAL { 0 }
    ::= { tRPAdminPSDefaultActionParamsEntry 20 }

tRPAdminPSDefActInetNextHopType  OBJECT-TYPE
    SYNTAX       InetAddressType
    MAX-ACCESS   read-create
    STATUS       current
    DESCRIPTION 
        "The value of tRPAdminPSDefActInetNextHopType specifies 
         the type of tRPAdminPSDefActInetNextHop address, as 
         defined in the InetAddress MIB."
    ::= { tRPAdminPSDefaultActionParamsEntry 21 }

tRPAdminPSDefActInetNextHop  OBJECT-TYPE
    SYNTAX       InetAddress
    MAX-ACCESS   read-create
    STATUS       current
    DESCRIPTION  
        "The value of tRPAdminPSDefActInetNextHop specifies the  
         next-hop IP address in the route. To disable, 
         tRPAdminPSDefActInetNextHopType should be
         set to 'ipv6' and tRPAdminPSDefActInetNextHop should
         be set to ffff:ffff:ffff:ffff:ffff:ffff:fffff:ffff.
   
         The type of this address is determined by the 
         value of tRPAdminPSDefActInetNextHopType object.

         Next-hop cannot be set to a valid IP address at the 
         same time as setting next-hop-self object 
         'tRPAdminPSDefaultActionNextHopSelf' to 'true'. Setting 
         next-hop to a valid IP address will reset 
         tRPAdminPSDefaultActionNextHopSelf to 'false'.
         
         tRPAdminPSDefActInetNextHop object replaces 
         tRPAdminPSDefaultActionNextHop that supports only
         IPv4 address style next-hop."
    ::= { tRPAdminPSDefaultActionParamsEntry 22 }

tRPAdminPSDefaultActionASPathPnd  OBJECT-TYPE
    SYNTAX       InetAutonomousSystemNumber
    MAX-ACCESS   read-create
    STATUS       current
    DESCRIPTION 
        "The value of tRPAdminPSDefaultActionASPathPnd specifies the AS Number
         to prepend to the AS-Path attribute of the route. Value of this
         object is ignored when tRPAdminPSDefaultActionASPathPrependCount 
         is zero."
    DEFVAL { 0 }
    ::= { tRPAdminPSDefaultActionParamsEntry 23 }    
    
tRPAdminPSDefActMcRedirSvcId OBJECT-TYPE
    SYNTAX      TmnxServId
    MAX-ACCESS  read-create
    STATUS      current
    DESCRIPTION
        "The value of tRPAdminPSDefActMcRedirSvcId specifies the service ID of
         the service where to redirect IGMP multicast traffic to.
         
         The value zero means that no multicast redirection is configured."
    DEFVAL { 0 }
    ::= { tRPAdminPSDefaultActionParamsEntry 30 }

tRPAdminPSDefActMcRedirIfIndex OBJECT-TYPE
    SYNTAX      InterfaceIndexOrZero
    MAX-ACCESS  read-create
    STATUS      current
    DESCRIPTION
        "The value of tRPAdminPSDefActMcRedirIfIndex specifies the interface 
         index of the interface where to redirect IGMP multicast traffic to.
         
         The value zero means that no multicast redirection is configured."
    DEFVAL { 0 }
    ::= { tRPAdminPSDefaultActionParamsEntry 31 }

tRPAdminPSDefActionMetricSource OBJECT-TYPE
    SYNTAX      TPolicyActionMetricSource
    MAX-ACCESS  read-create
    STATUS      current
    DESCRIPTION
        "The value of tRPAdminPSDefActionMetricSource specifies the source
         of the default action metric.
         
         When the value of tRPAdminPSDefActionMetricSource is set to
         'igpCost(1)', the value of tRPAdminPSDefaultActionMetricValue is 
         ignored and the value of MED (Multi Exit Discriminator) or the metric
         value is derived from the IGP (Interior Gateway Protocol) cost of the
         route.
         
         The default value of tRPAdminPSDefActionMetricSource is 
         'metricVal(2)' which means the metric value is the value of 
         tRPAdminPSDefaultActionMetricValue."
    DEFVAL { metricVal }
    ::= { tRPAdminPSDefaultActionParamsEntry 32 }

tRPAdminPSDefActionAigpMetric  OBJECT-TYPE
    SYNTAX       TPolicyEntryAigpMetricEdit
    MAX-ACCESS   read-create
    STATUS       current
    DESCRIPTION 
        "The value of tRPAdminPSDefActionAigpMetric specifies the editing
         action to be taken for the AIGP (Accumulated IGP) attribute when 
         the route satisfies the match criteria of the policy.

         The value of tRPAdminPSDefActionAigpMetric decides how to apply 
         tRPAdminPSDefActnAigpMetricVal to the route. When the value of 
         tRPAdminPSDefActionAigpMetric is set to 'none(1)' or 'useIgp(4)', 
         the value of tRPAdminPSDefActnAigpMetricVal is ignored."
    DEFVAL { none }
    ::= { tRPAdminPSDefaultActionParamsEntry 33 }

tRPAdminPSDefActnAigpMetricVal  OBJECT-TYPE
    SYNTAX       Unsigned32
    MAX-ACCESS   read-create
    STATUS       current
    DESCRIPTION 
        "The value of tRPAdminPSDefActnAigpMetricVal specifies the value to
         add or set for the route AIGP(Accumulated IGP) metric.
         
         When the value of tRPAdminPSDefActionAigpMetric is set to 'none(1)'
         or 'useIgp(4)', the value of tRPAdminPSDefActnAigpMetricVal is 
         ignored."
    DEFVAL { 0 }
    ::= { tRPAdminPSDefaultActionParamsEntry 34 }

--
-- policy-statement entry params
--

tRPAdminPSParamsTable OBJECT-TYPE
    SYNTAX       SEQUENCE OF TRPAdminPSParamsEntry
    MAX-ACCESS   not-accessible
    STATUS       current
    DESCRIPTION 
        "A table of policy statement entries."
    ::= { tRPAdminValueObjects 7 }

tRPAdminPSParamsEntry OBJECT-TYPE
    SYNTAX       TRPAdminPSParamsEntry
    MAX-ACCESS   not-accessible
    STATUS       current
    DESCRIPTION 
        "Information about a particular policy statement entry.
        
         Entries are created by user.
         Entries are deleted by user."
    INDEX { tRPAdminPolicyStatementName, tRPAdminPSNameEntryIndex }
    ::= { tRPAdminPSParamsTable 1 }

TRPAdminPSParamsEntry ::= SEQUENCE
    {
        tRPAdminPSNameEntryIndex    TPolicyStatementEntryID,
        tRPAdminPSParamsRowStatus   RowStatus,
        tRPAdminPSParamsDescription TItemDescription,
        tRPAdminPSParamsAction      TPolicyEntryAction
    }

tRPAdminPSNameEntryIndex  OBJECT-TYPE
    SYNTAX       TPolicyStatementEntryID
    MAX-ACCESS   not-accessible
    STATUS       current
    DESCRIPTION 
        "The ID of this policy statement entry."
    ::= { tRPAdminPSParamsEntry 1 }

tRPAdminPSParamsRowStatus  OBJECT-TYPE
    SYNTAX       RowStatus
    MAX-ACCESS   read-create
    STATUS       current
    DESCRIPTION 
        "RowStatus for this row. Legal values to write are: 
         active(1), notInService(2), createAndGo(4), createAndWait(5), 
         destroy(6).
        
         To Create a row, set this object to createAndGo or createAndWait.
         When tRPAdminControlApply is set to commit(3), the row will actually 
         be created in the tRPOperPSParamsTable.
        
         To destroy a row, set this object to destroy(6). If there are no 
         objects that refer to the entry, when tRPAdminControlApply is 
         set to commit(3) the row will actually be removed from the
         tRPOperPSParamsTable.
        
         If there are objects that refer to the entry, the destroy SET request
         will fail with an error."
    ::= { tRPAdminPSParamsEntry 2 }

tRPAdminPSParamsDescription  OBJECT-TYPE
    SYNTAX       TItemDescription
    MAX-ACCESS   read-create
    STATUS       current
    DESCRIPTION 
        "Description for this policy statement entry."
    DEFVAL { ''H }
    ::= { tRPAdminPSParamsEntry 3 }

tRPAdminPSParamsAction  OBJECT-TYPE
    SYNTAX       TPolicyEntryAction
    MAX-ACCESS   read-create
    STATUS       current
    DESCRIPTION 
        "The action to take when a route matches this policy statement entry's
         to or from criteria."
    ::= { tRPAdminPSParamsEntry 4 }


--
-- policy-statement default action 
--

tRPAdminPSAcceptActionParamsTable OBJECT-TYPE
    SYNTAX       SEQUENCE OF TRPAdminPSAcceptActionParamsEntry
    MAX-ACCESS   not-accessible
    STATUS       current
    DESCRIPTION  
        "Accept-action parameters for a policy-statement."
    ::= { tRPAdminValueObjects 8 }

tRPAdminPSAcceptActionParamsEntry OBJECT-TYPE
    SYNTAX       TRPAdminPSAcceptActionParamsEntry
    MAX-ACCESS   not-accessible
    STATUS       current
    DESCRIPTION 
        "Accept-action information for a particular policy-statement entry.
        
         Entries are created when a policy statement entry is created.
         Entries are deleted when a policy statement entry is destroyed."
    INDEX { tRPAdminPolicyStatementName, tRPAdminPSNameEntryIndex }
    ::= { tRPAdminPSAcceptActionParamsTable 1 }

TRPAdminPSAcceptActionParamsEntry ::= SEQUENCE
    {
        tRPAdminPSAcceptActionASPath              TPolicyEntryEdit,
        tRPAdminPSAcceptActionASPathName          TASPathName,
        tRPAdminPSAcceptActionASPathPrependAS     TmnxBgpAutonomousSystem,
        tRPAdminPSAcceptActionASPathPrependCount  INTEGER,
        tRPAdminPSAcceptActionCommunity1          TPolicyEntryEdit,
        tRPAdminPSAcceptActionCommunityName1      TCommunityName,
        tRPAdminPSAcceptActionCommunity2          TPolicyEntryEdit,
        tRPAdminPSAcceptActionCommunityName2      TCommunityName,
        tRPAdminPSAcceptActionOrigin              TPolicyEntryCriteriaOrigin,
        tRPAdminPSAcceptActionLocalPreferenceSet  TruthValue,
        tRPAdminPSAcceptActionLocalPreference     TmnxBgpLocalPreference,
        tRPAdminPSAcceptActionMetric              TPolicyEntryEdit,
        tRPAdminPSAcceptActionMetricValue         Unsigned32,
        tRPAdminPSAcceptActionPreference          TmnxBgpPreference,
        tRPAdminPSAcceptActionDamping             TDampingName,
        tRPAdminPSAcceptActionNextHopSelf         TruthValue,
        tRPAdminPSAcceptActionNextHop             IpAddress,
        tRPAdminPSAcceptActionTag                 TPolicyActionTag,
        tRPAdminPSAcceptActionOspfType            TOspfRouteType,
        tRPAdminPSAcptActInetNextHopType          InetAddressType,
        tRPAdminPSAcptActInetNextHop              InetAddress,
        tRPAdminPSAcceptActionASPathPend          InetAutonomousSystemNumber,
        tRPAdminPSAcceptActionFC                  TNamedItemOrEmpty,
        tRPAdminPSAcceptActionFCPriority          TPriorityOrUndefined,
        tRPAdminPSAcptActMcRedirSvcId             TmnxServId,
        tRPAdminPSAcptActMcRedirIfIndex           InterfaceIndexOrZero,
        tRPAdminPSAcptActnMetricSource            TPolicyActionMetricSource,
        tRPAdminPSAcptActionAigpMetric            TPolicyEntryAigpMetricEdit,
        tRPAdminPSAcptActnAigpMetricVal           Unsigned32
    } 

tRPAdminPSAcceptActionASPath  OBJECT-TYPE
    SYNTAX       TPolicyEntryEdit
    MAX-ACCESS   read-create
    STATUS       current
    DESCRIPTION 
        "The AS Path rewrite information for the route."
    DEFVAL { none }
    ::= { tRPAdminPSAcceptActionParamsEntry 1 }

tRPAdminPSAcceptActionASPathName  OBJECT-TYPE
    SYNTAX       TASPathName
    MAX-ACCESS   read-create
    STATUS       current
    DESCRIPTION 
        "AS Path Name to add, remove, or replace. Ignored when
         tRPAdminPSAcceptActionASPath is none(1)"
    DEFVAL { ''H }
    ::= { tRPAdminPSAcceptActionParamsEntry 2 }

tRPAdminPSAcceptActionASPathPrependAS  OBJECT-TYPE
    SYNTAX       TmnxBgpAutonomousSystem
    MAX-ACCESS   read-create
    STATUS       obsolete
    DESCRIPTION 
        "AS Number to prepend to the AS-Path attribute of the route.
         Ignored when tRPAdminPSAcceptActionASPathPrependCount is zero.

         This object was obsoleted in release 7.0.  It is replaced with the
         4-byte AS number defined by tRPAdminPSAcceptActionASPathPend."
    DEFVAL { 0 }
    ::= { tRPAdminPSAcceptActionParamsEntry 3 }

tRPAdminPSAcceptActionASPathPrependCount  OBJECT-TYPE
    SYNTAX       INTEGER (0..50)
    MAX-ACCESS   read-create
    STATUS       current
    DESCRIPTION 
        "Number of times to prepend tRPAdminPSAcceptActionASPathPend to 
         the route.  Set to zero to disable this feature."
    DEFVAL { 0 }
    ::= { tRPAdminPSAcceptActionParamsEntry 4 }

tRPAdminPSAcceptActionCommunity1  OBJECT-TYPE
    SYNTAX       TPolicyEntryEdit
    MAX-ACCESS   read-create
    STATUS       current
    DESCRIPTION 
        "How to apply tRPAdminPSAcceptActionCommunityName1 to the route."
    DEFVAL { none }
    ::= { tRPAdminPSAcceptActionParamsEntry 5 }

tRPAdminPSAcceptActionCommunityName1  OBJECT-TYPE
    SYNTAX       TCommunityName
    MAX-ACCESS   read-create
    STATUS       current
    DESCRIPTION 
        "Community to apply to the route.  Ignored when 
         tRPAdminPSAcceptActionCommunity1 is set to none(1)."
    DEFVAL { ''H }
    ::= { tRPAdminPSAcceptActionParamsEntry 6 }

tRPAdminPSAcceptActionCommunity2  OBJECT-TYPE
    SYNTAX       TPolicyEntryEdit
    MAX-ACCESS   read-create
    STATUS       current
    DESCRIPTION 
        "How to apply tRPAdminPSAcceptActionCommunityName2 to the route."
    DEFVAL { none }
    ::= { tRPAdminPSAcceptActionParamsEntry 7 }

tRPAdminPSAcceptActionCommunityName2  OBJECT-TYPE
    SYNTAX       TCommunityName
    MAX-ACCESS   read-create
    STATUS       current
    DESCRIPTION 
        "Community to apply to the route.  Ignored when 
         tRPAdminPSAcceptActionCommunity2 is set to none(1)."
    DEFVAL { ''H }
    ::= { tRPAdminPSAcceptActionParamsEntry 8 }

tRPAdminPSAcceptActionOrigin  OBJECT-TYPE
    SYNTAX       TPolicyEntryCriteriaOrigin 
    MAX-ACCESS   read-create
    STATUS       current
    DESCRIPTION
        "The value of tRPAdminPSAcceptActionOrigin specifies
         the origin of the route exported into BGP if it matches an entry."
    DEFVAL { none }
    ::= { tRPAdminPSAcceptActionParamsEntry 9 }

tRPAdminPSAcceptActionLocalPreferenceSet  OBJECT-TYPE
    SYNTAX       TruthValue
    MAX-ACCESS   read-create
    STATUS       current
    DESCRIPTION 
        "When set to true(1), use tRPAdminPSAcceptActionLocalPreference
         for the local preference for the route."
    DEFVAL { false }
    ::= { tRPAdminPSAcceptActionParamsEntry 10 }

tRPAdminPSAcceptActionLocalPreference  OBJECT-TYPE
    SYNTAX       TmnxBgpLocalPreference
    MAX-ACCESS   read-create
    STATUS       current
    DESCRIPTION 
        "Local preference for the route.
         Ignored when tRPAdminPSAcceptActionLocalPreferenceSet is false(2)."
    DEFVAL { 0 }
    ::= { tRPAdminPSAcceptActionParamsEntry 11 }

tRPAdminPSAcceptActionMetric  OBJECT-TYPE
    SYNTAX       TPolicyEntryEdit
    MAX-ACCESS   read-create
    STATUS       current
    DESCRIPTION 
        "How to apply tRPAdminPSAcceptActionMetricValue to the route."
    DEFVAL { none }
    ::= { tRPAdminPSAcceptActionParamsEntry 12 }

tRPAdminPSAcceptActionMetricValue  OBJECT-TYPE
    SYNTAX       Unsigned32
    MAX-ACCESS   read-create
    STATUS       current
    DESCRIPTION 
        "Value to add, subtract, or set for the route metric.
         Ignored when tRPAdminPSAcceptActionMetric is none(1)."
    DEFVAL { 0 }
    ::= { tRPAdminPSAcceptActionParamsEntry 13 }

tRPAdminPSAcceptActionPreference  OBJECT-TYPE
    SYNTAX       TmnxBgpPreference
    MAX-ACCESS   read-create
    STATUS       current
    DESCRIPTION 
        "Preference to set in route."
    DEFVAL { 0 }
    ::= { tRPAdminPSAcceptActionParamsEntry 15 }

tRPAdminPSAcceptActionDamping  OBJECT-TYPE
    SYNTAX       TDampingName
    MAX-ACCESS   read-create
    STATUS       current
    DESCRIPTION 
        "Damping to apply to route.  Set to empty string to disable."
    DEFVAL { ''H }
    ::= { tRPAdminPSAcceptActionParamsEntry 16 }

tRPAdminPSAcceptActionNextHopSelf  OBJECT-TYPE
    SYNTAX       TruthValue
    MAX-ACCESS   read-create
    STATUS       current
    DESCRIPTION 
        "The value of tRPAdminPSAcceptActionNextHopSelf specifies
         the next-hop-self on the route. Next-hop-self cannot be set 
         to 'true' at the same time as setting next-hop object
         tRPAdminPSAcptActInetNextHop to a valid IP address. 
         Setting tRPAdminPSAcceptActionNextHopSelf to 'true' will  
         reset tRPAdminPSAcptActInetNextHop object to disable."
    DEFVAL { false }
    ::= { tRPAdminPSAcceptActionParamsEntry 17 }

tRPAdminPSAcceptActionNextHop  OBJECT-TYPE
    SYNTAX       IpAddress
    MAX-ACCESS   read-create
    STATUS       current
    DESCRIPTION 
        "Set next-hop address in route. Set to 255.255.255.255 to disable.
         Next-hop cannot be set to a valid IP address at the same time
         as setting next-hop-self to 'true'. Setting next-hop to a valid
         IP address will reset next-hop-self to 'false'."
    DEFVAL { 'FFFFFFFF'H }
    ::= { tRPAdminPSAcceptActionParamsEntry 18 }

tRPAdminPSAcceptActionTag  OBJECT-TYPE
    SYNTAX       TPolicyActionTag
    MAX-ACCESS   read-create
    STATUS       current
    DESCRIPTION 
        "The value of tRPAdminPSAcceptActionTag specifies the tag for the route.

         A value of 0 for tRPAdminPSAcceptActionTag when specifies that tagging
         is disabled."
    DEFVAL { 0 }
    ::= { tRPAdminPSAcceptActionParamsEntry 19 }

tRPAdminPSAcceptActionOspfType  OBJECT-TYPE
    SYNTAX       TOspfRouteType
    MAX-ACCESS   read-create
    STATUS       current
    DESCRIPTION 
        "OSPF route type to set in route."
    DEFVAL { 0 }
    ::= { tRPAdminPSAcceptActionParamsEntry 20 }

tRPAdminPSAcptActInetNextHopType  OBJECT-TYPE
    SYNTAX       InetAddressType
    MAX-ACCESS   read-create
    STATUS       current
    DESCRIPTION 
        "The value of tRPAdminPSAcptActInetNextHopType specifies 
         the type of tRPAdminPSAcptActInetNextHop address, as 
         defined in the InetAddress MIB."
    ::= { tRPAdminPSAcceptActionParamsEntry 21 }

tRPAdminPSAcptActInetNextHop  OBJECT-TYPE
    SYNTAX       InetAddress
    MAX-ACCESS   read-create
    STATUS       current
    DESCRIPTION 
        "The value of tRPAdminPSAcptActInetNextHop specifies
         the next-hop IP address in the route. To disable, 
         tRPAdminPSAcptActInetNextHopType should be
         set to 'ipv6' and tRPAdminPSAcptActInetNextHop should
         be set to ffff:ffff:ffff:ffff:ffff:ffff:fffff:ffff.

         The type of this address is determined by the 
         value of the tRPAdminPSAcptActInetNextHopType object.

         Next-hop cannot be set to a valid IP address at the 
         same time as setting next-hop-self object 
         'tRPAdminPSAcceptActionNextHopSelf' to 'true'. Setting 
         next-hop to a valid IP address will reset 
         tRPAdminPSAcceptActionNextHopSelf to 'false'.
           
         tRPAdminPSAcptActInetNextHop object replaces 
         tRPAdminPSAcceptActionNextHop that supports only
         IPv4 address style next-hop."
    ::= { tRPAdminPSAcceptActionParamsEntry 22 }

tRPAdminPSAcceptActionASPathPend  OBJECT-TYPE
    SYNTAX       InetAutonomousSystemNumber
    MAX-ACCESS   read-create
    STATUS       current
    DESCRIPTION 
        "The value of tRPAdminPSAcceptActionASPathPend specifies the AS Number 
         to prepend to the AS-Path attribute of the route. Value of this object
         is ignored when tRPAdminPSAcceptActionASPathPrependCount is zero."
    DEFVAL { 0 }
    ::= { tRPAdminPSAcceptActionParamsEntry 23 }

tRPAdminPSAcceptActionFC  OBJECT-TYPE
    SYNTAX       TNamedItemOrEmpty
    MAX-ACCESS   read-create
    STATUS       current
    DESCRIPTION 
        "The value of tRPAdminPSAcceptActionFC specifies the forwarding class
         associated with the routes matched by this route policy entry.

         An 'inconsistentValue' error is returned if an attempt is made to set
         this object to a non-default value when tRPAdminPSParamsAction is set 
         either to 'reject' or 'none'."
    DEFVAL { ''H }
    ::= { tRPAdminPSAcceptActionParamsEntry 24 }

tRPAdminPSAcceptActionFCPriority  OBJECT-TYPE
    SYNTAX       TPriorityOrUndefined
    MAX-ACCESS   read-create
    STATUS       current
    DESCRIPTION 
        "The value of tRPAdminPSAcceptActionFCPriority specifies the priority
         to be assigned to the routes matched by this route policy entry.

         An 'inconsistentValue' error is returned if an attempt is made to set
         this object to a non-default value when tRPAdminPSParamsAction is set 
         either to 'reject' or 'none'."
    DEFVAL { undefined }
    ::= { tRPAdminPSAcceptActionParamsEntry 25 }
    
tRPAdminPSAcptActMcRedirSvcId OBJECT-TYPE
    SYNTAX      TmnxServId
    MAX-ACCESS  read-create
    STATUS      current
    DESCRIPTION
        "The value of tRPAdminPSAcptActMcRedirSvcId specifies the service ID of
         the service where to redirect IGMP multicast traffic to.
         
         The value zero means that no multicast redirection is configured."
    DEFVAL { 0 }
    ::= { tRPAdminPSAcceptActionParamsEntry 30 }

tRPAdminPSAcptActMcRedirIfIndex OBJECT-TYPE
    SYNTAX      InterfaceIndexOrZero
    MAX-ACCESS  read-create
    STATUS      current
    DESCRIPTION
        "The value of tRPAdminPSAcptActMcRedirIfIndex specifies the interface 
         index of the interface where to redirect IGMP multicast traffic to.
         
         The value zero means that no multicast redirection is configured."
    DEFVAL { 0 }
    ::= { tRPAdminPSAcceptActionParamsEntry 31 }

tRPAdminPSAcptActnMetricSource OBJECT-TYPE
    SYNTAX      TPolicyActionMetricSource
    MAX-ACCESS  read-create
    STATUS      current
    DESCRIPTION
        "The value of tRPAdminPSAcptActnMetricSource specifies the source
         of the accept action metric.
         
         When the value of tRPAdminPSAcptActnMetricSource is set to 
         'igpCost(1)' the value of tRPAdminPSAcceptActionMetricValue is 
         ignored and the value of MED (Multi Exit Discriminator) or the 
         metric value is derived from the IGP (Interior Gateway Protocol) cost
         of the route.
         
         The default value of tRPAdminPSAcptActnMetricSource is 
         'metricVal(2)' which means the metric value is the value of 
         tRPAdminPSDefaultActionMetricValue."
    DEFVAL { metricVal }
    ::= { tRPAdminPSAcceptActionParamsEntry 32 }

tRPAdminPSAcptActionAigpMetric  OBJECT-TYPE
    SYNTAX       TPolicyEntryAigpMetricEdit
    MAX-ACCESS   read-create
    STATUS       current
    DESCRIPTION 
        "The value of tRPAdminPSAcptActionAigpMetric specifies the editing
         action to be taken for the AIGP (Accumulated IGP) attribute when 
         the route satisfies the match criteria of the policy.

         The value of tRPAdminPSAcptActionAigpMetric decides how to apply 
         tRPAdminPSAcptActnAigpMetricVal to the route. When the value of 
         tRPAdminPSAcptActionAigpMetric is set to 'none(1)' or 'useIgp(4)', 
         the value of tRPAdminPSAcptActnAigpMetricVal is ignored."
    DEFVAL { none }
    ::= { tRPAdminPSAcceptActionParamsEntry 33 }

tRPAdminPSAcptActnAigpMetricVal  OBJECT-TYPE
    SYNTAX       Unsigned32
    MAX-ACCESS   read-create
    STATUS       current
    DESCRIPTION 
        "The value of tRPAdminPSAcptActnAigpMetricVal specifies the value to
         add or set for the route AIGP(Accumulated IGP) metric.
         
         When the value of tRPAdminPSAcptActionAigpMetric is set to 'none(1)'
         or 'useIgp(4)', the value of tRPAdminPSAcptActnAigpMetricVal is 
         ignored."
    DEFVAL { 0 }
    ::= { tRPAdminPSAcceptActionParamsEntry 34 }

--
-- policy-statement entry to 
--

tRPAdminPSToCriteriaTable OBJECT-TYPE
    SYNTAX       SEQUENCE OF TRPAdminPSToCriteriaEntry
    MAX-ACCESS   not-accessible
    STATUS       current
    DESCRIPTION  
        "A table of policy statement entry 'to' criteria"
    ::= { tRPAdminValueObjects 9 }

tRPAdminPSToCriteriaEntry OBJECT-TYPE
    SYNTAX       TRPAdminPSToCriteriaEntry
    MAX-ACCESS   not-accessible
    STATUS       current
    DESCRIPTION 
        "Information about policy statement entry -to- criteria.

        Entries are created when a policy statement entry is created.
        Entries are deleted when a policy statement entry is destroyed."
    INDEX { tRPAdminPolicyStatementName, tRPAdminPSToCriteriaIndex }
    ::= { tRPAdminPSToCriteriaTable 1 }

TRPAdminPSToCriteriaEntry ::= SEQUENCE
    {
        tRPAdminPSToCriteriaIndex              TPolicyStatementEntryID,
        tRPAdminPSToCriteriaRowStatus          RowStatus,
        tRPAdminPSToCriteriaProtocol           TRoutePolicyProtocol,
        tRPAdminPSToCriteriaNeighborIpAddr     IpAddress,
        tRPAdminPSToCriteriaNeighborPrefixList TPrefixListName,
        tRPAdminPSToCriteriaIsisLevel          TIsisLevel,
        tRPAdminPSToCriteriaPrefixList1        TPrefixListName,
        tRPAdminPSToCriteriaPrefixList2        TPrefixListName,
        tRPAdminPSToCriteriaPrefixList3        TPrefixListName,
        tRPAdminPSToCriteriaPrefixList4        TPrefixListName,
        tRPAdminPSToCriteriaPrefixList5        TPrefixListName,
        tRPAdminPSToCritNbrInetAddrType        InetAddressType,
        tRPAdminPSToCritNbrInetAddr            InetAddress,
        tRPAdminPSToCriteriaInstanceId         Unsigned32
    }

tRPAdminPSToCriteriaIndex  OBJECT-TYPE
    SYNTAX       TPolicyStatementEntryID
    MAX-ACCESS   not-accessible
    STATUS       current
    DESCRIPTION 
        "The policy statement entry ID"
    ::= { tRPAdminPSToCriteriaEntry 1 }

tRPAdminPSToCriteriaRowStatus  OBJECT-TYPE
    SYNTAX       RowStatus
    MAX-ACCESS   read-create
    STATUS       current
    DESCRIPTION 
        "RowStatus for this row. Legal values to write are: 
         active(1), notInService(2), createAndGo(4), createAndWait(5), 
         destroy(6).
        
         To Create a row, set this object to createAndGo or createAndWait.
         When tRPAdminControlApply is set to commit(3), the row will actually 
         be created in the tRPOperPSToCriteriaTable.
        
         To destroy a row, set this object to destroy(6). If there are no 
         objects that refer to the entry, when tRPAdminControlApply is 
         set to commit(3) the row will actually be removed from the 
         tRPOperPSToCriteriaTable.
        
         If there are objects that refer to the entry, the destroy SET request
         will fail with an error."
    ::= { tRPAdminPSToCriteriaEntry 2 }

tRPAdminPSToCriteriaProtocol  OBJECT-TYPE
    SYNTAX       TRoutePolicyProtocol
    MAX-ACCESS   read-create
    STATUS       current
    DESCRIPTION 
        "The protocol name to match on. 
         Set to none(1) to disable."
    DEFVAL { none }
    ::= { tRPAdminPSToCriteriaEntry 3 }

tRPAdminPSToCriteriaNeighborIpAddr  OBJECT-TYPE
    SYNTAX       IpAddress
    MAX-ACCESS   read-create
    STATUS       current
    DESCRIPTION 
        "The IP address of neighbor to match on. 
         Set to 0.0.0.0 to disable."
    DEFVAL { '00000000'H }
    ::= { tRPAdminPSToCriteriaEntry 4 }

tRPAdminPSToCriteriaNeighborPrefixList  OBJECT-TYPE
    SYNTAX       TPrefixListName
    MAX-ACCESS   read-create
    STATUS       current
    DESCRIPTION 
        "The name of a neighbor prefix list to match on.
         Set to empty string to disable."
    DEFVAL { ''H }
    ::= { tRPAdminPSToCriteriaEntry 5 }

tRPAdminPSToCriteriaIsisLevel  OBJECT-TYPE
    SYNTAX       TIsisLevel 
    MAX-ACCESS   read-create
    STATUS       current
    DESCRIPTION 
        "The value for tRPAdminPSToCriteriaIsisLevel defines the IS-IS route 
         level match criterion. A value of 0 indicates that no IS-IS route 
         level match criterion has been configured."
    DEFVAL { 0 }
    ::= { tRPAdminPSToCriteriaEntry 7 }

tRPAdminPSToCriteriaPrefixList1  OBJECT-TYPE
    SYNTAX       TPrefixListName
    MAX-ACCESS   read-create
    STATUS       current
    DESCRIPTION 
        "The value of tRPAdminPSToCriteriaPrefixList1 specifies the name of  
         the first prefix list to match on. Setting this value to an empty
         string disables this prefix list as a match criteria."
    DEFVAL { ''H }
    ::= { tRPAdminPSToCriteriaEntry 8 }

tRPAdminPSToCriteriaPrefixList2  OBJECT-TYPE
    SYNTAX       TPrefixListName
    MAX-ACCESS   read-create
    STATUS       current
    DESCRIPTION 
        "The value of tRPAdminPSToCriteriaPrefixList2 specifies the name of  
         the second prefix list to match on. Setting this value to an empty
         string disables this prefix list as a match criteria."
    DEFVAL { ''H }
    ::= { tRPAdminPSToCriteriaEntry 9 }

tRPAdminPSToCriteriaPrefixList3  OBJECT-TYPE
    SYNTAX       TPrefixListName
    MAX-ACCESS   read-create
    STATUS       current
    DESCRIPTION 
        "The value of tRPAdminPSToCriteriaPrefixList3 specifies the name of  
         the third prefix list to match on. Setting this value to an empty
         string disables this prefix list as a match criteria."
    DEFVAL { ''H }
    ::= { tRPAdminPSToCriteriaEntry 10 }

tRPAdminPSToCriteriaPrefixList4  OBJECT-TYPE
    SYNTAX       TPrefixListName
    MAX-ACCESS   read-create
    STATUS       current
    DESCRIPTION 
        "The value of tRPAdminPSToCriteriaPrefixList4 specifies the name of  
         the fourth prefix list to match on. Setting this value to an empty
         string disables this prefix list as a match criteria."
    DEFVAL { ''H }
    ::= { tRPAdminPSToCriteriaEntry 11 }

tRPAdminPSToCriteriaPrefixList5  OBJECT-TYPE
    SYNTAX       TPrefixListName
    MAX-ACCESS   read-create
    STATUS       current
    DESCRIPTION 
        "The value of tRPAdminPSToCriteriaPrefixList5 specifies the name of  
         the fifth prefix list to match on. Setting this value to an empty
         string disables this prefix list as a match criteria."
    DEFVAL { ''H }
    ::= { tRPAdminPSToCriteriaEntry 12 }

tRPAdminPSToCritNbrInetAddrType  OBJECT-TYPE
    SYNTAX       InetAddressType
    MAX-ACCESS   read-create
    STATUS       current
    DESCRIPTION 
        "The value of tRPAdminPSToCritNbrInetAddrType specifies 
         the type of tRPAdminPSToCritNbrInetAddr address, as  
         defined in the InetAddress MIB."
    ::= { tRPAdminPSToCriteriaEntry 13 }

tRPAdminPSToCritNbrInetAddr  OBJECT-TYPE
    SYNTAX       InetAddress
    MAX-ACCESS   read-create
    STATUS       current
    DESCRIPTION 
        "The value of tRPAdminPSToCritNbrInetAddr specifies 
         the IP address of neighbor to match on. To disable, 
         tRPAdminPSToCritNbrInetAddrType should be
         set to 'ipv6' and tRPAdminPSToCritNbrInetAddr should
         be set to ffff:ffff:ffff:ffff:ffff:ffff:fffff:ffff.

         The type of this address is determined by the 
         value of the tRPAdminPSToCritNbrInetAddrType object.
         
         tRPAdminPSToCritNbrInetAddr object replaces 
         tRPAdminPSToCriteriaNeighborIpAddr that supports only
         IPv4 address style neighbor."
    ::= { tRPAdminPSToCriteriaEntry 14 }
    

tRPAdminPSToCriteriaInstanceId OBJECT-TYPE
    SYNTAX       Unsigned32 (0..31| 4294967295)
    MAX-ACCESS   read-create
    STATUS       current
    DESCRIPTION 
        "The value of tRPAdminPSToCriteriaInstanceId indicates instance 
         of a version of the OSPF protocol running in the router instance.
         
         If the value of tRPAdminPSToCriteriaInstanceId is set to 4294967295,
         all instances of OSPF protocol are leaked into BGP."
    DEFVAL { 0 }
    ::= { tRPAdminPSToCriteriaEntry 15 }

--
-- policy-statement entry from
--

tRPAdminPSFromCriteriaTable OBJECT-TYPE
    SYNTAX       SEQUENCE OF TRPAdminPSFromCriteriaEntry
    MAX-ACCESS   not-accessible
    STATUS       current
    DESCRIPTION 
        "A table of from filter criteria for each policy-statement entry."
    ::= { tRPAdminValueObjects 10 }

tRPAdminPSFromCriteriaEntry OBJECT-TYPE
    SYNTAX       TRPAdminPSFromCriteriaEntry
    MAX-ACCESS   not-accessible
    STATUS       current
    DESCRIPTION 
        "Information about policy statement entry -from- criteria.

        Entries are created when a policy statement entry is created.
        Entries are deleted when a policy statement entry is destroyed."
    INDEX { tRPAdminPolicyStatementName, tRPAdminPSFromCriteriaIndex }
    ::= { tRPAdminPSFromCriteriaTable 1 }

TRPAdminPSFromCriteriaEntry ::= SEQUENCE
    {
        tRPAdminPSFromCriteriaIndex              TPolicyStatementEntryID,
        tRPAdminPSFromCriteriaRowStatus          RowStatus,
        tRPAdminPSFromCriteriaProtocol           TRoutePolicyProtocol,
        tRPAdminPSFromCriteriaNeighborIpAddr     IpAddress,
        tRPAdminPSFromCriteriaNeighborPrefixList TPrefixListName,
        tRPAdminPSFromCriteriaPrefixList1        TPrefixListName,
        tRPAdminPSFromCriteriaPrefixList2        TPrefixListName,
        tRPAdminPSFromCriteriaPrefixList3        TPrefixListName,
        tRPAdminPSFromCriteriaPrefixList4        TPrefixListName,
        tRPAdminPSFromCriteriaPrefixList5        TPrefixListName,
        tRPAdminPSFromCriteriaASPath             TASPathName,
        tRPAdminPSFromCriteriaCommunity          TCommunityName,
        tRPAdminPSFromCriteriaOrigin             TPolicyEntryCriteriaOrigin,
        tRPAdminPSFromCriteriaOspfRouteType      TOspfRouteType,
        tRPAdminPSFromCriteriaArea               IpAddress,
        tRPAdminPSFromCriteriaAreaConfigured     TruthValue,
        tRPAdminPSFromCriteriaIsisLevel          TIsisLevel,
        tRPAdminPSFromCriteriaIsisExternal       TruthValue,
        tRPAdminPSFromCriteriaIgmpHostPrefixList TPrefixListName,
        tRPAdminPSFromCriteriaGrpAddrPrefixList  TPrefixListName,
        tRPAdminPSFromCriteriaSrcAddr            IpAddress,
        tRPAdminPSFromCriteriaInterface          TNamedItemOrEmpty,
        tRPAdminPSFromCriteriaTag                TPolicyActionTag,
        tRPAdminPSFromCritNbrInetAddrType        InetAddressType,
        tRPAdminPSFromCritNbrInetAddr            InetAddress,
        tRPAdminPSFromCritSrcInetAddrType        InetAddressType,
        tRPAdminPSFromCritSrcInetAddr            InetAddress,
        tRPAdminPSFromCriteriaFamily             TmnxBGPFamilyType,
        tRPAdminPSFromCriteriaInstanceId         Unsigned32,
        tRPAdminPSFromCriteriaMatchTag           TmnxEnabledDisabled,
        tRPAdminPSFromCriteriaState              TPolicyEntryCriteriaState,
        tRPAdminPSFromCritASPathGroup            TNamedItemOrEmpty
    }

tRPAdminPSFromCriteriaIndex  OBJECT-TYPE
    SYNTAX       TPolicyStatementEntryID
    MAX-ACCESS   not-accessible
    STATUS       current
    DESCRIPTION 
        "The policy statement entry ID"
    ::= { tRPAdminPSFromCriteriaEntry 1 }

tRPAdminPSFromCriteriaRowStatus  OBJECT-TYPE
    SYNTAX       RowStatus
    MAX-ACCESS   read-create
    STATUS       current
    DESCRIPTION 
        "RowStatus for this row. Legal values to write are: 
         active(1), notInService(2), createAndGo(4), createAndWait(5), 
         destroy(6).
        
         To Create a row, set this object to createAndGo or createAndWait.
         When tRPAdminControlApply is set to commit(3), the row will actually 
         be created in the tRPOperPSFromCriteriaTable.
        
         To destroy a row, set this object to destroy(6). If there are no 
         objects that refer to the entry, when tRPAdminControlApply is 
         set to commit(3) the row will actually be removed from the
         tRPOperPSFromCriteriaTable.
        
         If there are objects that refer to the entry, the destroy SET request
         will fail with an error."
    ::= { tRPAdminPSFromCriteriaEntry 2 }

tRPAdminPSFromCriteriaProtocol  OBJECT-TYPE
    SYNTAX       TRoutePolicyProtocol
    MAX-ACCESS   read-create
    STATUS       current
    DESCRIPTION 
        "The protocol name to match on. 
         Set to none(1) to disable."
    DEFVAL { none }
    ::= { tRPAdminPSFromCriteriaEntry 3 }

tRPAdminPSFromCriteriaNeighborIpAddr  OBJECT-TYPE
    SYNTAX       IpAddress
    MAX-ACCESS   read-create
    STATUS       current
    DESCRIPTION 
        "The IP address of neighbor to match on. 
         Set to 0.0.0.0 to disable."
    DEFVAL { '00000000'H }
    ::= { tRPAdminPSFromCriteriaEntry 4 }

tRPAdminPSFromCriteriaNeighborPrefixList  OBJECT-TYPE
    SYNTAX       TPrefixListName
    MAX-ACCESS   read-create
    STATUS       current
    DESCRIPTION 
        "The name of a neighbor prefix list to match on.
         Set to empty string to disable."
    DEFVAL { ''H }
    ::= { tRPAdminPSFromCriteriaEntry 5 }

tRPAdminPSFromCriteriaPrefixList1  OBJECT-TYPE
    SYNTAX       TPrefixListName
    MAX-ACCESS   read-create
    STATUS       current
    DESCRIPTION 
        "The name of the first prefix list to match on. 
         Set to empty string to disable."
    DEFVAL { ''H }
    ::= { tRPAdminPSFromCriteriaEntry 6 }

tRPAdminPSFromCriteriaPrefixList2  OBJECT-TYPE
    SYNTAX       TPrefixListName
    MAX-ACCESS   read-create
    STATUS       current
    DESCRIPTION 
        "The name of the second prefix list to match on. 
         Set to empty string to disable."
    DEFVAL { ''H }
    ::= { tRPAdminPSFromCriteriaEntry 7 }

tRPAdminPSFromCriteriaPrefixList3  OBJECT-TYPE
    SYNTAX       TPrefixListName
    MAX-ACCESS   read-create
    STATUS       current
    DESCRIPTION 
        "The name of the third prefix list to match on. 
         Set to empty string to disable."
    DEFVAL { ''H }
    ::= { tRPAdminPSFromCriteriaEntry 8 }

tRPAdminPSFromCriteriaPrefixList4  OBJECT-TYPE
    SYNTAX       TPrefixListName
    MAX-ACCESS   read-create
    STATUS       current
    DESCRIPTION 
        "The name of the fourth prefix list to match on. 
         Set to empty string to disable."
    DEFVAL { ''H }
    ::= { tRPAdminPSFromCriteriaEntry 9 }

tRPAdminPSFromCriteriaPrefixList5  OBJECT-TYPE
    SYNTAX       TPrefixListName
    MAX-ACCESS   read-create
    STATUS       current
    DESCRIPTION 
        "The name of the fifth prefix list to match on. 
         Set to empty string to disable."
    DEFVAL { ''H }
    ::= { tRPAdminPSFromCriteriaEntry 10 }

tRPAdminPSFromCriteriaASPath  OBJECT-TYPE
    SYNTAX       TASPathName
    MAX-ACCESS   read-create
    STATUS       current
    DESCRIPTION 
        "The name of the AS Path to match on. 
         Set to empty string to disable."
    DEFVAL { ''H }
    ::= { tRPAdminPSFromCriteriaEntry 11 }

tRPAdminPSFromCriteriaCommunity  OBJECT-TYPE
    SYNTAX       TCommunityName
    MAX-ACCESS   read-create
    STATUS       current
    DESCRIPTION 
        "The name of the community to match on.
         Set to empty string to disable."
    DEFVAL { ''H }
    ::= { tRPAdminPSFromCriteriaEntry 12 }

tRPAdminPSFromCriteriaOrigin  OBJECT-TYPE
    SYNTAX       TPolicyEntryCriteriaOrigin
    MAX-ACCESS   read-create
    STATUS       current
    DESCRIPTION
        "The value of tRPAdminPSFromCriteriaOrigin specifies
         the route match criterion for an entry."
    DEFVAL { none }
    ::= { tRPAdminPSFromCriteriaEntry 13 }

tRPAdminPSFromCriteriaOspfRouteType  OBJECT-TYPE
    SYNTAX       TOspfRouteType
    MAX-ACCESS   read-create
    STATUS       current
    DESCRIPTION 
        "The OSPF route type to match on. 
         Set to zero to disable."
    DEFVAL { 0 }
    ::= { tRPAdminPSFromCriteriaEntry 14 }

tRPAdminPSFromCriteriaArea  OBJECT-TYPE
    SYNTAX       IpAddress
    MAX-ACCESS   read-create
    STATUS       current
    DESCRIPTION 
        "Used when redistributing OSPF routes into other protocols. Specifies
         the OSPF area that must be matched in filtered routes."
    ::= { tRPAdminPSFromCriteriaEntry 16 }

tRPAdminPSFromCriteriaAreaConfigured  OBJECT-TYPE
    SYNTAX       TruthValue
    MAX-ACCESS   read-create
    STATUS       current
    DESCRIPTION 
        "Specifies if the tRPAdminPSFromCriteriaArea has been 
         configured"
    ::= { tRPAdminPSFromCriteriaEntry 17 }

tRPAdminPSFromCriteriaIsisLevel  OBJECT-TYPE
    SYNTAX       TIsisLevel
    MAX-ACCESS   read-create
    STATUS       current
    DESCRIPTION 
        "The value for tRPAdminPSFromCriteriaIsisLevel defines the IS-IS route 
         level match criterion. A value of 0 indicates that no IS-IS route 
         level match criterion has been configured."
    DEFVAL { 0 }
    ::= { tRPAdminPSFromCriteriaEntry 18 }

tRPAdminPSFromCriteriaIsisExternal  OBJECT-TYPE
    SYNTAX       TruthValue
    MAX-ACCESS   read-create
    STATUS       current
    DESCRIPTION 
        "When tRPAdminPSFromCriteriaIsisExternal is 'true', match only 
         External IS-IS routes. If 'false', match all routes. 
         External IS-IS routes are those routes that have been learned from 
         outside the IS-IS domain."
    DEFVAL { false }
    ::= { tRPAdminPSFromCriteriaEntry 19 }

tRPAdminPSFromCriteriaIgmpHostPrefixList  OBJECT-TYPE
    SYNTAX       TPrefixListName
    MAX-ACCESS   read-create
    STATUS       current
    DESCRIPTION 
        "tRPAdminPSFromCriteriaIgmpHostPrefixList contains the name of the
         prefix list that is used to match the IGMP host IP address.
         This object is set to empty string to disable."
    ::= { tRPAdminPSFromCriteriaEntry 20 }

tRPAdminPSFromCriteriaGrpAddrPrefixList  OBJECT-TYPE
    SYNTAX       TPrefixListName
    MAX-ACCESS   read-create
    STATUS       current
    DESCRIPTION 
        "tRPAdminPSFromCriteriaGrpAddrPrefixList contains the name of the
         prefix list that is used to match the multicast group address.
         This object is set to empty string to disable."
    ::= { tRPAdminPSFromCriteriaEntry 21 }

tRPAdminPSFromCriteriaSrcAddr  OBJECT-TYPE
    SYNTAX       IpAddress
    MAX-ACCESS   read-create
    STATUS       current
    DESCRIPTION 
        "tRPAdminPSFromCriteriaSrcAddr contains the IP address of the 
         source to match on. It is used by multicast protocols 
         like IGMP and PIM.
         This object is set to 0.0.0.0 to disable."
    ::= { tRPAdminPSFromCriteriaEntry 22 }

tRPAdminPSFromCriteriaInterface  OBJECT-TYPE
    SYNTAX       TNamedItemOrEmpty
    MAX-ACCESS   read-create
    STATUS       current
    DESCRIPTION 
        "tRPAdminPSFromCriteriaInterface contains the name of the
         interface to match on. PIM Bootstrap route policy will use
         this object to accept/reject bootstrap messages coming on 
         the interface specified by this object.
         This object is set to empty string to disable."
    ::= { tRPAdminPSFromCriteriaEntry 23 }

tRPAdminPSFromCriteriaTag  OBJECT-TYPE
    SYNTAX       TPolicyActionTag
    MAX-ACCESS   read-create
    STATUS       current
    DESCRIPTION 
        "The value of tRPAdminPSFromCriteriaTag specifies the route tag to match
         on. Routes will only be matched on this value when 
         tRPAdminPSFromCriteriaMatchTag is enabled.
        
         A value of 0 for tRPAdminPSFromCriteriaTag when 
         tRPAdminPSFromCriteriaMatchTag is enabled would match untagged routes."
    DEFVAL { 0 }
    ::= { tRPAdminPSFromCriteriaEntry 24 }

tRPAdminPSFromCritNbrInetAddrType  OBJECT-TYPE
    SYNTAX       InetAddressType
    MAX-ACCESS   read-create
    STATUS       current
    DESCRIPTION 
        "The value of tRPAdminPSFromCritNbrInetAddrType specifies
         the type of tRPAdminPSFromCritNbrInetAddr address, as  
         defined in the InetAddress MIB."
    ::= { tRPAdminPSFromCriteriaEntry 25 }

tRPAdminPSFromCritNbrInetAddr  OBJECT-TYPE
    SYNTAX       InetAddress
    MAX-ACCESS   read-create
    STATUS       current
    DESCRIPTION 
        "The value of tRPAdminPSFromCritNbrInetAddr specifies 
         the IP address of neighbor to match on. To disable, 
         tRPAdminPSFromCritNbrInetAddrType should be
         set to 'ipv6' and tRPAdminPSFromCritNbrInetAddr should
         be set to ffff:ffff:ffff:ffff:ffff:ffff:fffff:ffff.

         The type of this address is determined by the 
         value of the tRPAdminPSFromCritNbrInetAddrType object.
         
         tRPAdminPSFromCritNbrInetAddr object replaces 
         tRPAdminPSFromCriteriaNeighborIpAddr that supports only
         IPv4 address style neighbor."
    ::= { tRPAdminPSFromCriteriaEntry 26 }

tRPAdminPSFromCritSrcInetAddrType  OBJECT-TYPE
    SYNTAX       InetAddressType
    MAX-ACCESS   read-create
    STATUS       current
    DESCRIPTION 
        "The value of tRPAdminPSFromCritSrcInetAddrType specifies 
         the type of tRPAdminPSFromCritSrcInetAddr address, as 
         defined in the InetAddress MIB."
    ::= { tRPAdminPSFromCriteriaEntry 27 }

tRPAdminPSFromCritSrcInetAddr  OBJECT-TYPE
    SYNTAX       InetAddress (SIZE(4|16))
    MAX-ACCESS   read-create
    STATUS       current
    DESCRIPTION 
        "The value of tRPAdminPSFromCritSrcInetAddr specifies 
         the IP address of the source to match on. This 
         object will be used by multicast protocols 
         like PIM and IGMP. To disable,
         tRPAdminPSFromCritSrcInetAddrType should be
         set to 'ipv4' and tRPAdminPSFromCritSrcInetAddr should
         be set to 255.255.255.255.

         The type of this address is determined by the 
         value of the tRPAdminPSFromCritSrcInetAddrType object.
               
         tRPAdminPSFromCritSrcInetAddr object replaces 
         tRPAdminPSFromCriteriaSrcAddr that supports only
         IPv4 address style source."
    ::= { tRPAdminPSFromCriteriaEntry 28 }

tRPAdminPSFromCriteriaFamily  OBJECT-TYPE
    SYNTAX       TmnxBGPFamilyType
    MAX-ACCESS   read-create
    STATUS       current
    DESCRIPTION 
        "The  bits set in the value of tRPAdminPSFromCriteriaFamily specifies 
         the address families that this condition would match against."
    DEFVAL { {} }
    ::= { tRPAdminPSFromCriteriaEntry 29 }

tRPAdminPSFromCriteriaInstanceId OBJECT-TYPE
    SYNTAX       Unsigned32 (0..31| 4294967295)
    MAX-ACCESS   read-create
    STATUS       current
    DESCRIPTION 
        "The value of tRPAdminPSFromCriteriaInstanceId indicates instance 
         of a version of the OSPF protocol running in the router instance.

         If the value of tRPAdminPSToCriteriaInstanceId is set to 4294967295,
         all instances of OSPF protocol are leaked into BGP."
    DEFVAL { 0 }
    ::= { tRPAdminPSFromCriteriaEntry 30 }

tRPAdminPSFromCriteriaMatchTag  OBJECT-TYPE
    SYNTAX       TmnxEnabledDisabled
    MAX-ACCESS   read-create
    STATUS       current
    DESCRIPTION 
        "The value of tRPAdminPSFromCriteriaMatchTag specifies if tag matching
         is enabled or disabled. Disabling of this object will set 
         tRPAdminPSFromCriteriaTag to zero."
    DEFVAL { disabled }
    ::= { tRPAdminPSFromCriteriaEntry 31 }

tRPAdminPSFromCriteriaState  OBJECT-TYPE
    SYNTAX       TPolicyEntryCriteriaState
    MAX-ACCESS   read-create
    STATUS       current
    DESCRIPTION
        "The value of tRPAdminPSFromCriteriaState specifies 
         the route state match criterion for this entry."
    DEFVAL { none }
    ::= { tRPAdminPSFromCriteriaEntry 32 }

tRPAdminPSFromCritASPathGroup OBJECT-TYPE
    SYNTAX       TNamedItemOrEmpty
    MAX-ACCESS   read-create
    STATUS       current
    DESCRIPTION
        "The value of tRPAdminPSFromCritASPathGroup specifies
         the AS-Path Group match criterion for this entry."
    DEFVAL { "" }
    ::= { tRPAdminPSFromCriteriaEntry 33 }

--
-- Administrative value control objects
--

tRPAdminOwner  OBJECT-TYPE
    SYNTAX       DisplayString (SIZE (0..32))
    MAX-ACCESS   read-write
    STATUS       current
    DESCRIPTION
        "Who has last initialized the administrative tables, 
         who is making all the changes, and who is expected to 
         either commit or re-initialize (ABORT-TRANSACTION).
         
         tRPAdminOwner is advisory only.  Before beginning a transaction,
         read tRPAdminOwner. If it is empty then proceed with the configuration.
         Set tRPAdminOwner after setting tRPAdminControlApply so
         that other users will be advised to not make changes to the Admin 
         tables.
        
         Agent sets tRPAdminOwner to empty string after tRPAdminControlApply
         is set - either by user initializing or committing, 
         or by agent timing out the uncommitted transactions 
         (tRPAdminLastSetTimer)."
    ::= { tRPAdminControlObjects 1 }

tRPAdminControlApply  OBJECT-TYPE
    SYNTAX       INTEGER { none(1), initialize(2), commit(3) }
    MAX-ACCESS   read-write
    STATUS       current
    DESCRIPTION
        "This object controls the use of tRPAdminValueObjects tables.
        
         This object always reads none(1).
        
         When set to initialize(2), the objects in tRPAdminValueObjects tables
         are set to the current Operational values, from the 
         corresponding tRPOperValueObjects tables.  Any uncommitted changes are
         lost, so setting this value corresponds to both BEGIN-TRANSACTION
         and ABORT-TRANSACTION.
        
         When set to commit(3) (END-TRANSACTION), all of the objects from 
         tRPAdminValueObjects tables are copied to the corresponding
         tRPOperValueObjects table objects.  Then, all routes are re-evaluated
         with the new policies.  Later arriving routes are evaluated with the
         new policies.
        
         In this way, the (expensive) route re-evaluation can be performed
         at one time, with a coherent route policy configuration."
    ::= { tRPAdminControlObjects 2 }

tRPAdminLastSetTimer  OBJECT-TYPE
    SYNTAX       TimeInterval
    UNITS        "centiseconds"
    MAX-ACCESS   read-only
    STATUS       current
    DESCRIPTION
        "The time remaining until the agent re-initializes the 
         administrative tables.
       
         If tRPAdminControlApply is not set to commit(3) within 
         tRPAdminLastSetTimeout centiseconds, the agent will set it 
         to initialize(2) and all uncommitted changes will be lost.

         This way, uncommitted changes from failed (uncompleted) change sets 
         will eventually be removed, and another transaction can safely begin.
        
         This object is reset to tRPAdminLastSetTimeout after SNMP SET 
         operation to any of the tRPAdminValueObjects tables."
    ::= { tRPAdminControlObjects 3 }

tRPAdminLastSetTimeout  OBJECT-TYPE
    SYNTAX       TimeInterval
    UNITS        "centiseconds"
    MAX-ACCESS   read-write
    STATUS       current
    DESCRIPTION
        "Timeout for tRPAdminLastSetTimer.
         The value zero is not allowed."
    DEFVAL { 180000 } -- 30 minutes
    ::= { tRPAdminControlObjects 4 }

--
-- Oper prefix-list 
--

tRPOperInetPrefixListTblLastChg OBJECT-TYPE
    SYNTAX       TimeStamp
    MAX-ACCESS   read-only
    STATUS       obsolete
    DESCRIPTION
        "The value of tRPOperInetPrefixListTblLastChg indicates
         the timestamp of last change to tRPOperInetPrefixListTable.

         tRPOperInetPrefixListTblLastChg is obsoleted in release 5.0.
         TIMETRA-SYSTEM-MIB::tmnxConfigModify notification is used instead."
    ::= { tRPOperValueObjects 21 }

-- tRPOperInetPrefixListTable replaces the tRPOperPrefixListTable 
-- that lists only IPv4 address style prefix lists. 
-- The tRPOperInetPrefixListTable is IP version 
-- neutral and lists IPv4 and IPv6 InetAddress style
-- prefix lists.

tRPOperInetPrefixListTable OBJECT-TYPE
    SYNTAX       SEQUENCE OF TRPOperInetPrefixListEntry
    MAX-ACCESS   not-accessible
    STATUS       current
    DESCRIPTION  
        "The table of IPv4 and IPv6 operational prefix lists."
    ::= { tRPOperValueObjects 22 }

tRPOperInetPrefixListEntry OBJECT-TYPE
    SYNTAX       TRPOperInetPrefixListEntry
    MAX-ACCESS   not-accessible
    STATUS       current
    DESCRIPTION 
        "Each row entry in the tRPOperInetPrefixListTable represents
         information about a particular prefix list.

         Entries are created by user via tRPAdminInetPrefixListTable.
         Entries are deleted by user via tRPAdminInetPrefixListTable.
        
         A prefix list name entry must exist before referring objects
         (tRPAdminPSToCriteriaNeighborPrefixList, 
          tRPAdminPSFromCriteriaNeighborPrefixList,
          tRPAdminPSToCriteriaPrefixList1 - 5,
          tRPAdminPSFromCriteriaPrefixList1 - 5)
         can be set to that name."
    INDEX { tRPOperInetPrefixListName, 
            tRPOperInetPrefixListPrefixType,
            tRPOperInetPrefixListPrefix, 
            tRPOperInetPrefixListPrefixLen, 
            tRPOperInetPrefixListType }
    ::= { tRPOperInetPrefixListTable 1 }

TRPOperInetPrefixListEntry ::= SEQUENCE
    {
        tRPOperInetPrefixListName          TPrefixListName,
        tRPOperInetPrefixListPrefixType    InetAddressType,
        tRPOperInetPrefixListPrefix        InetAddress,
        tRPOperInetPrefixListPrefixLen     InetAddressPrefixLength,
        tRPOperInetPrefixListType          INTEGER,
        tRPOperInetPrefixListRowStatus     RowStatus,
        tRPOperInetPrefixListThroughLen    InetAddressPrefixLength,
        tRPOperInetPrefixListLastChg       TimeStamp,
        tRPOperInetPrefixListBeginLen      InetAddressPrefixLength
    }

tRPOperInetPrefixListName  OBJECT-TYPE
    SYNTAX       TPrefixListName (SIZE(1..32))
    MAX-ACCESS   not-accessible
    STATUS       current
    DESCRIPTION
        "The value of tRPOperInetPrefixListName indicates
         the name of the prefix list entry."
    ::= { tRPOperInetPrefixListEntry 1 }

tRPOperInetPrefixListPrefixType  OBJECT-TYPE
    SYNTAX       InetAddressType
    MAX-ACCESS   not-accessible
    STATUS       current
    DESCRIPTION
        "The value of tRPOperInetPrefixListPrefixType indicates
         the address type of tRPOperInetPrefixListPrefix."
    ::= { tRPOperInetPrefixListEntry 2 }

tRPOperInetPrefixListPrefix  OBJECT-TYPE
    SYNTAX       InetAddress
    MAX-ACCESS   not-accessible
    STATUS       current
    DESCRIPTION
        "The value of tRPOperInetPrefixListPrefix indicates
         the IP prefix of the prefix list entry."
    ::= { tRPOperInetPrefixListEntry 3 }

tRPOperInetPrefixListPrefixLen  OBJECT-TYPE
    SYNTAX       InetAddressPrefixLength
    MAX-ACCESS   not-accessible
    STATUS       current
    DESCRIPTION
        "The value of tRPOperInetPrefixListPrefixLen indicates
         the IP prefix length of the prefix list entry."
    ::= { tRPOperInetPrefixListEntry 4 }

tRPOperInetPrefixListType  OBJECT-TYPE  
    SYNTAX     INTEGER { 
                 exact(1), 
                 longer(2), 
                 through(3), 
                 range(4) 
               }
    MAX-ACCESS   not-accessible
    STATUS       current
    DESCRIPTION 
        "The value of tRPOperInetPrefixListType indicates
         the type of the prefix length entry.
                                                              
         exact (1) - a route's prefix/length must match the 
         prefix-list entry exactly in order for an entry to 
         be considered a match.

         longer (2) - a route's prefix/length must match the 
         defined prefix AND have a length that is an exact match 
         or longer in order for an entry to be considered a match.

         through (3) - a route's prefix/length must match the 
         defined prefix AND have a length that is an exact match or 
         longer up to and including the defined maximum length in
         order for an entry to be considered a match.
        
         range (4) - a route's prefix/length must match the 
         defined prefix AND have a length that is greater than or 
         equal to the length defined by tRPOperInetPrefixListBeginLen 
         and less than or equal to the length defined by 
         tRPOperInetPrefixListThroughLen in order for an entry to 
         be considered a match."
    ::= { tRPOperInetPrefixListEntry 5 }

tRPOperInetPrefixListRowStatus  OBJECT-TYPE
    SYNTAX       RowStatus
    MAX-ACCESS   read-only
    STATUS       current
    DESCRIPTION
        "RowStatus for this row. Values read will only be 
         active(1), notInService(2), notReady(3). To create
         or destroy entries in this table, use the 
         tRPAdminInetPrefixListTable."
    ::= { tRPOperInetPrefixListEntry 6 }   

tRPOperInetPrefixListThroughLen  OBJECT-TYPE
    SYNTAX       InetAddressPrefixLength
    MAX-ACCESS   read-only
    STATUS       current
    DESCRIPTION
        "The value of tRPOperInetPrefixListThroughLen indicates
         the prefix length to use when tRPOperInetPrefixListType
         set to through(3). The value must be larger than 
         tRPOperInetPrefixListPrefixLen."
    ::= { tRPOperInetPrefixListEntry 7 }

tRPOperInetPrefixListLastChg   OBJECT-TYPE
    SYNTAX       TimeStamp
    MAX-ACCESS   read-only
    STATUS       obsolete
    DESCRIPTION 
        "The value of tRPOperInetPrefixListLastChg indicates
         the timestamp of last change to this entry.

         tRPOperInetPrefixListLastChg is obsoleted in release 5.0.
         TIMETRA-SYSTEM-MIB::tmnxConfigModify notification is used instead."
    ::= { tRPOperInetPrefixListEntry 8 }

tRPOperInetPrefixListBeginLen  OBJECT-TYPE
    SYNTAX       InetAddressPrefixLength
    MAX-ACCESS   read-only
    STATUS       current
    DESCRIPTION
        "The value of tRPOperInetPrefixListBeginLen indicates
         the prefix length to use as the lower limit for
         the prefix range when tRPOperInetPrefixListType 
         set to range(4). The value must be larger than
         tRPOperInetPrefixListPrefixLen and less than 
         tRPOperInetPrefixListThroughLen."
    ::= { tRPOperInetPrefixListEntry 9 }

--
-- Admin prefix-list 
--

-- tRPAdminInetPrefixListTable replaces the tRPAdminPrefixListTable 
-- that allows configuration of only IPv4 address style prefix lists. 
-- The tRPOperInetPrefixListTable is IP version neutral and allows 
-- IPv4 and IPv6 InetAddress style prefix lists.

tRPAdminInetPrefixListTable OBJECT-TYPE
    SYNTAX       SEQUENCE OF TRPAdminInetPrefixListEntry
    MAX-ACCESS   not-accessible
    STATUS       current
    DESCRIPTION  
        "The table of IPv4 and IPv6 admin prefix lists."
    ::= { tRPAdminValueObjects 11 }

tRPAdminInetPrefixListEntry OBJECT-TYPE
    SYNTAX       TRPAdminInetPrefixListEntry
    MAX-ACCESS   not-accessible
    STATUS       current
    DESCRIPTION 
        "Each row entry in the tRPAdminInetPrefixListEntry represents
         information about a particular prefix list.

         Entries are created by user.
         Entries are deleted by user."
    INDEX { tRPAdminInetPrefixListName, 
            tRPAdminInetPrefixListPrefixType,
            tRPAdminInetPrefixListPrefix, 
            tRPAdminInetPrefixListPrefixLen,
            tRPAdminInetPrefixListType}
    ::= { tRPAdminInetPrefixListTable 1 }

TRPAdminInetPrefixListEntry ::= SEQUENCE
    {
        tRPAdminInetPrefixListName          TPrefixListName,
        tRPAdminInetPrefixListPrefixType    InetAddressType,
        tRPAdminInetPrefixListPrefix        InetAddress,
        tRPAdminInetPrefixListPrefixLen     InetAddressPrefixLength,         
        tRPAdminInetPrefixListType          INTEGER,
        tRPAdminInetPrefixListRowStatus     RowStatus,
        tRPAdminInetPrefixListThroughLen    InetAddressPrefixLength,
        tRPAdminInetPrefixListBeginLen      InetAddressPrefixLength
    }

tRPAdminInetPrefixListName  OBJECT-TYPE
    SYNTAX       TPrefixListName (SIZE(1..32))
    MAX-ACCESS   not-accessible
    STATUS       current
    DESCRIPTION
        "The value of tRPAdminInetPrefixListName indicates
         the name of the prefix list entry."
    ::= { tRPAdminInetPrefixListEntry 1 }

tRPAdminInetPrefixListPrefixType  OBJECT-TYPE
    SYNTAX       InetAddressType
    MAX-ACCESS   not-accessible
    STATUS       current
    DESCRIPTION
        "The value of tRPAdminInetPrefixListPrefixType indicates
         the address type of tRPAdminInetPrefixListPrefix."
    ::= { tRPAdminInetPrefixListEntry 2 }

tRPAdminInetPrefixListPrefix  OBJECT-TYPE
    SYNTAX       InetAddress
    MAX-ACCESS   not-accessible
    STATUS       current
    DESCRIPTION
        "The value of tRPAdminInetPrefixListPrefix indicates
         the IP prefix of the prefix list entry."
    ::= { tRPAdminInetPrefixListEntry 3 }

tRPAdminInetPrefixListPrefixLen  OBJECT-TYPE
    SYNTAX       InetAddressPrefixLength
    MAX-ACCESS   not-accessible
    STATUS       current
    DESCRIPTION
        "The value of tRPAdminInetPrefixListPrefixLen indicates
         the IP prefix length of the prefix list entry."
    ::= { tRPAdminInetPrefixListEntry 4 }
    
tRPAdminInetPrefixListType  OBJECT-TYPE
    SYNTAX     INTEGER { 
                 exact(1), 
                 longer(2), 
                 through(3), 
                 range(4) 
               }
    MAX-ACCESS   not-accessible
    STATUS       current
    DESCRIPTION 
        "The value of tRPAdminInetPrefixListType indicates
         the type of the prefix length entry.
        
         exact (1) - a route's prefix/length must match the 
         prefix-list entry exactly in order for an entry to 
         be considered a match.

         longer (2) - a route's prefix/length must match the 
         defined prefix AND have a length that is an exact match 
         or longer in order for an entry to be considered a match.

         through (3) - a route's prefix/length must match the 
         defined prefix AND have a length that is an exact match or 
         longer up to and including the defined maximum length in
         order for an entry to be considered a match.

         range (4) - a route's prefix/length must match the 
         defined prefix AND have a length that is greater than or 
         equal to the length defined by tRPAdminInetPrefixListBeginLen 
         and less than or equal to the length defined by 
         tRPAdminInetPrefixListThroughLen in order for an entry to 
         be considered a match."
    ::= { tRPAdminInetPrefixListEntry 5 }
    
tRPAdminInetPrefixListRowStatus  OBJECT-TYPE
    SYNTAX       RowStatus
    MAX-ACCESS   read-create
    STATUS       current
    DESCRIPTION 
        "RowStatus for this row. Legal values to write are: 
         active(1), notInService(2), createAndGo(4), createAndWait(5), 
         destroy(6).
        
         To create a row, set this object to createAndGo 
         or createAndWait. When tRPAdminControlApply is set 
         to commit(3), the row will actually be created in 
         the tRPOperInetPrefixListTable.
        
         To destroy a row, set this object to destroy(6). 
         If there are no objects that refer to the entry, 
         when tRPAdminControlApply is set to commit(3) 
         the row will actually be removed from the 
         tRPOperInetPrefixListTable.
        
         If there are objects that refer to the entry, the 
         destroy SET request will fail with an error."
    ::= { tRPAdminInetPrefixListEntry 6 }

tRPAdminInetPrefixListThroughLen  OBJECT-TYPE
    SYNTAX       InetAddressPrefixLength
    MAX-ACCESS   read-create
    STATUS       current
    DESCRIPTION
        "The value of tRPAdminInetPrefixListThroughLen specifies
         the prefix length to use when tRPAdminPrefixListType
         set to through(3). The value must be larger than 
         tRPAdminInetPrefixListPrefixLen."
    DEFVAL { 0 }
    ::= { tRPAdminInetPrefixListEntry 7 }

tRPAdminInetPrefixListBeginLen  OBJECT-TYPE
    SYNTAX       InetAddressPrefixLength
    MAX-ACCESS   read-create
    STATUS       current
    DESCRIPTION
        "The value of tRPAdminInetPrefixListBeginLen specifies
         the prefix length to use as the lower limit for
         the prefix range when tRPAdminInetPrefixListType 
         set to range(4). The value must be larger than
         tRPAdminInetPrefixListPrefixLen and less than 
         tRPAdminInetPrefixListThroughLen."
    DEFVAL { 0 }
    ::= { tRPAdminInetPrefixListEntry 8 }

--
-- Operational community expressions
--

tRPOperCommunityExprTable OBJECT-TYPE
    SYNTAX       SEQUENCE OF TRPOperCommunityExprEntry
    MAX-ACCESS   not-accessible
    STATUS       current
    DESCRIPTION
        "A table of community entries."
    ::= { tRPOperValueObjects 25 }

tRPOperCommunityExprEntry OBJECT-TYPE
    SYNTAX       TRPOperCommunityExprEntry
    MAX-ACCESS   not-accessible
    STATUS       current
    DESCRIPTION
        "Information about a particular community member.
         Entries are created by user, via tRPAdminCommunityExprTable.
         Entries are deleted by user, via tRPAdminCommunityExprTable."
    INDEX { tRPOperCommunityExprName }
    ::= { tRPOperCommunityExprTable 1 }

TRPOperCommunityExprEntry ::= SEQUENCE
    {
        tRPOperCommunityExprName         TCommunityName,
        tRPOperCommunityExprRowStatus    RowStatus,
        tRPOperCommunityExprString1      TCommunityExpression,
        tRPOperCommunityExprString2      TCommunityExpression,
        tRPOperCommunityExprString3      TCommunityExpression,
        tRPOperCommunityExprString4      TCommunityExpression
    }

tRPOperCommunityExprName OBJECT-TYPE
    SYNTAX       TCommunityName (SIZE(1..32))
    MAX-ACCESS   not-accessible
    STATUS       current
    DESCRIPTION
        "The value of object tRPOperCommunityExprName indicates
         the name of the community used as an index for this table."
    ::= { tRPOperCommunityExprEntry 1 }

tRPOperCommunityExprRowStatus OBJECT-TYPE
    SYNTAX       RowStatus
    MAX-ACCESS   read-only
    STATUS       current
    DESCRIPTION
        "The value of object tRPOperCommunityExprRowStatus indicates
         the RowStatus for this row.

         To create or destroy entries in this table, use the
         tRPAdminCommunityExprTable."
    ::= { tRPOperCommunityExprEntry 2 }

tRPOperCommunityExprString1 OBJECT-TYPE
    SYNTAX       TCommunityExpression
    MAX-ACCESS   read-only
    STATUS       current
    DESCRIPTION
        "The value of object tRPOperCommunityExprString1 indicates
         an expression that matches AS Numbers or Community ID's.

         The objects tRPOperCommunityExprString1, tRPOperCommunityExprString2,
         tRPOperCommunityExprString3 and tRPOperCommunityExprString4
         are substrings that form one string of type TCommunityExpression."
    ::= { tRPOperCommunityExprEntry 3 }

tRPOperCommunityExprString2 OBJECT-TYPE
    SYNTAX       TCommunityExpression
    MAX-ACCESS   read-only
    STATUS       current
    DESCRIPTION
        "The value of object tRPOperCommunityExprString2 indicates
         an expression that matches AS Numbers or Community ID's.

         The objects tRPOperCommunityExprString1, tRPOperCommunityExprString2,
         tRPOperCommunityExprString3 and tRPOperCommunityExprString4
         are substrings that form one string of type TCommunityExpression."
    ::= { tRPOperCommunityExprEntry 4 }

tRPOperCommunityExprString3 OBJECT-TYPE
    SYNTAX       TCommunityExpression
    MAX-ACCESS   read-only
    STATUS       current
    DESCRIPTION
        "The value of object tRPOperCommunityExprString3 indicates
         an expression that matches AS Numbers or Community ID's.

         The objects tRPOperCommunityExprString1, tRPOperCommunityExprString2,
         tRPOperCommunityExprString3 and tRPOperCommunityExprString4
         are substrings that form one string of type TCommunityExpression."
    ::= { tRPOperCommunityExprEntry 5 }

tRPOperCommunityExprString4 OBJECT-TYPE
    SYNTAX       TCommunityExpression
    MAX-ACCESS   read-only
    STATUS       current
    DESCRIPTION
        "The value of object tRPOperCommunityExprString4 indicates
         an expression that matches AS Numbers or Community ID's.

         The objects tRPOperCommunityExprString1, tRPOperCommunityExprString2,
         tRPOperCommunityExprString3 and tRPOperCommunityExprString4
         are substrings that form one string of type TCommunityExpression."
    ::= { tRPOperCommunityExprEntry 6 }

--
-- Admininstrative community expressions
--

tRPAdminCommunityExprTable OBJECT-TYPE
    SYNTAX       SEQUENCE OF TRPAdminCommunityExprEntry
    MAX-ACCESS   not-accessible
    STATUS       current
    DESCRIPTION
        "A table of community entries."
    ::= { tRPAdminValueObjects 12 }

tRPAdminCommunityExprEntry OBJECT-TYPE
    SYNTAX       TRPAdminCommunityExprEntry
    MAX-ACCESS   not-accessible
    STATUS       current
    DESCRIPTION
        "Information about a particular community name member.
         Entries are created by user.
         Entries are deleted by user."
    INDEX { tRPAdminCommunityExprName }
    ::= { tRPAdminCommunityExprTable 1 }

TRPAdminCommunityExprEntry ::= SEQUENCE
    {
        tRPAdminCommunityExprName        TCommunityName,
        tRPAdminCommunityExprRowStatus   RowStatus,
        tRPAdminCommunityExprString1     TCommunityExpression,
        tRPAdminCommunityExprString2     TCommunityExpression,
        tRPAdminCommunityExprString3     TCommunityExpression,
        tRPAdminCommunityExprString4     TCommunityExpression
    }

tRPAdminCommunityExprName OBJECT-TYPE
    SYNTAX       TCommunityName (SIZE(1..32))
    MAX-ACCESS   not-accessible
    STATUS       current
    DESCRIPTION
        "The value of tRPAdminCommunityExprName indicates
         the name of the community used as an index for this table."
    ::= { tRPAdminCommunityExprEntry 1 }

tRPAdminCommunityExprRowStatus  OBJECT-TYPE
    SYNTAX       RowStatus
    MAX-ACCESS   read-create
    STATUS       current
    DESCRIPTION
        "The value of tRPAdminCommunityExprRowStatus specifies
         the RowStatus for this row.

         To create a row, set this object to 'createAndGo(4)'.
         The value of tRPAdminCommunityExprString1 must be set to a non-empty
         string in the same SNMP SET PDU for the row creation to succeed.
         When tRPAdminControlApply is set to 'commit(3)', the row will actually
         be created in the tRPOperCommunityExprTable.

         When the value of this object is set to 'createAndWait(5)',
         a new entry is created with value of this object set to
         'notInService(2)' and the tRPAdminCommunityExprString1-4 strings
         can be configured separately. When the value of this object is set
         to 'active(1)', the values of objects tRPAdminCommunityExprString1-4,
         are concatenated to form one expression of at most 900 characters.
         When tRPAdminControlApply is set to 'commit(3)', the row will actually
         be created in the tRPOperCommunityExprTable.

         To destroy a row, set this object to 'destroy(6)'.
         When tRPAdminControlApply is set to 'commit(3)', the row will actually
         be removed from the tRPOperCommunityExprTable."
    ::= { tRPAdminCommunityExprEntry 2 }

tRPAdminCommunityExprString1 OBJECT-TYPE
    SYNTAX       TCommunityExpression
    MAX-ACCESS   read-create
    STATUS       current
    DESCRIPTION
        "The value of object tRPAdminCommunityExprString1 specifies
         an expression that matches AS Numbers or Community ID's.

         The objects tRPAdminCommunityExprString1, tRPAdminCommunityExprString2,
         tRPAdminCommunityExprString3 and tRPAdminCommunityExprString4
         are substrings that form one string of type TCommunityExpression.
         Substrings can only be set to a non-empty string
         if the previous substrings are non-empty."
    DEFVAL { "" }
    ::= { tRPAdminCommunityExprEntry 3 }

tRPAdminCommunityExprString2 OBJECT-TYPE
    SYNTAX       TCommunityExpression
    MAX-ACCESS   read-create
    STATUS       current
    DESCRIPTION
        "The value of object tRPAdminCommunityExprString1 specifies
         an expression that matches AS Numbers or Community ID's.

         The objects tRPAdminCommunityExprString1, tRPAdminCommunityExprString2,
         tRPAdminCommunityExprString3 and tRPAdminCommunityExprString4
         are substrings that form one string of type TCommunityExpression.
         Substrings can only be set to a non-empty string
         if the previous substrings are non-empty."
    DEFVAL { "" }
    ::= { tRPAdminCommunityExprEntry 4 }

tRPAdminCommunityExprString3 OBJECT-TYPE
    SYNTAX       TCommunityExpression
    MAX-ACCESS   read-create
    STATUS       current
    DESCRIPTION
        "The value of object tRPAdminCommunityExprString1 specifies
         an expression that matches AS Numbers or Community ID's.

         The objects tRPAdminCommunityExprString1, tRPAdminCommunityExprString2,
         tRPAdminCommunityExprString3 and tRPAdminCommunityExprString4
         are substrings that form one string of type TCommunityExpression.
         Substrings can only be set to a non-empty string
         if the previous substrings are non-empty."
    DEFVAL { "" }
    ::= { tRPAdminCommunityExprEntry 5 }

tRPAdminCommunityExprString4 OBJECT-TYPE
    SYNTAX       TCommunityExpression
    MAX-ACCESS   read-create
    STATUS       current
    DESCRIPTION
        "The value of object tRPAdminCommunityExprString1 specifies
         an expression that matches AS Numbers or Community ID's.

         The objects tRPAdminCommunityExprString1, tRPAdminCommunityExprString2,
         tRPAdminCommunityExprString3 and tRPAdminCommunityExprString4
         are substrings that form one string of type TCommunityExpression.
         Substrings can only be set to a non-empty string
         if the previous substrings are non-empty."
    DEFVAL { "" }
    ::= { tRPAdminCommunityExprEntry 6 }

--
-- Operational AS-Path Group Table
--

tRPOperASPathGroupTable OBJECT-TYPE
    SYNTAX       SEQUENCE OF TRPOperASPathGroupEntry
    MAX-ACCESS   not-accessible
    STATUS       current
    DESCRIPTION  
        "The table of AS-Path Groups."
    ::= { tRPOperValueObjects 26 }

tRPOperASPathGroupEntry OBJECT-TYPE
    SYNTAX       TRPOperASPathGroupEntry
    MAX-ACCESS   not-accessible
    STATUS       current
    DESCRIPTION 
        "Each row entry in the tRPOperASPathGroupTable represents
         information about a particular AS-Path Group.

         Entries are created by user via tRPAdminASPathGroupTable.
         Entries are deleted by user via tRPAdminASPathGroupTable."
    INDEX { tRPOperASPathGroupName,
            tRPOperASPathGroupEntryIndex }
    ::= { tRPOperASPathGroupTable 1 }

TRPOperASPathGroupEntry ::= SEQUENCE
    {
        tRPOperASPathGroupName             TNamedItem,
        tRPOperASPathGroupEntryIndex       Unsigned32,
        tRPOperASPathGroupRowStatus        RowStatus,
        tRPOperASPathGroupASPathName       TASPathName
    }

tRPOperASPathGroupName  OBJECT-TYPE
    SYNTAX       TNamedItem
    MAX-ACCESS   not-accessible
    STATUS       current
    DESCRIPTION
        "The value of tRPOperASPathGroupName indicates
         the name of the AS-Path Group."
    ::= { tRPOperASPathGroupEntry 1 }

tRPOperASPathGroupEntryIndex OBJECT-TYPE
    SYNTAX       Unsigned32 (1..4)
    MAX-ACCESS   not-accessible
    STATUS       current
    DESCRIPTION
        "The value of tRPOperASPathGroupEntryIndex indicates
         the index of the entry in the AS-Path Group."
    ::= { tRPOperASPathGroupEntry 2 }

tRPOperASPathGroupRowStatus OBJECT-TYPE
    SYNTAX       RowStatus
    MAX-ACCESS   read-only
    STATUS       current
    DESCRIPTION
        "The value of tRPOperASPathGroupRowStatus indicates
         the RowStatus for this entry. To create or destroy entries in this
         table, use the tRPAdminASPathGroupTable."
    ::= { tRPOperASPathGroupEntry 3 }

tRPOperASPathGroupASPathName OBJECT-TYPE
    SYNTAX       TASPathName (SIZE(1..32))
    MAX-ACCESS   read-only
    STATUS       current
    DESCRIPTION
        "The value of tRPOperASPathGroupASPathName indicates
         the name of the AS-Path from the tRPOperASPathTable."
    ::= { tRPOperASPathGroupEntry 4 }

--
-- Admininstrative AS-Path Group Table
--

tRPAdminASPathGroupTable OBJECT-TYPE
    SYNTAX       SEQUENCE OF TRPAdminASPathGroupEntry
    MAX-ACCESS   not-accessible
    STATUS       current
    DESCRIPTION  
        "The table of AS-Path Groups."
    ::= { tRPAdminValueObjects 13 }

tRPAdminASPathGroupEntry OBJECT-TYPE
    SYNTAX       TRPAdminASPathGroupEntry
    MAX-ACCESS   not-accessible
    STATUS       current
    DESCRIPTION 
        "Each row entry in the tRPAdminASPathGroupTable represents
         information about a particular AS-Path Group."
    INDEX { tRPAdminASPathGroupName,
            tRPAdminASPathGroupEntryIndex }
    ::= { tRPAdminASPathGroupTable 1 }

TRPAdminASPathGroupEntry ::= SEQUENCE
    {
        tRPAdminASPathGroupName             TNamedItem,
        tRPAdminASPathGroupEntryIndex       Unsigned32,
        tRPAdminASPathGroupRowStatus        RowStatus,
        tRPAdminASPathGroupASPathName       TASPathName
    }

tRPAdminASPathGroupName  OBJECT-TYPE
    SYNTAX       TNamedItem
    MAX-ACCESS   not-accessible
    STATUS       current
    DESCRIPTION
        "The value of tRPAdminASPathGroupName specifies
         the name of the AS-Path Group."
    ::= { tRPAdminASPathGroupEntry 1 }

tRPAdminASPathGroupEntryIndex OBJECT-TYPE
    SYNTAX       Unsigned32 (1..4)
    MAX-ACCESS   not-accessible
    STATUS       current
    DESCRIPTION
        "The value of tRPAdminASPathGroupEntryIndex specifies
         the index of the entry in the AS-Path Group."
    ::= { tRPAdminASPathGroupEntry 2 }

tRPAdminASPathGroupRowStatus OBJECT-TYPE
    SYNTAX       RowStatus
    MAX-ACCESS   read-create
    STATUS       current
    DESCRIPTION
        "The value of tRPAdminASPathGroupRowStatus specifies
         the RowStatus for this row.

         To create a row, set this object to 'createAndGo(4)'.
         When tRPAdminControlApply is set to 'commit(3)', the row will actually
         be created in the tRPOperASPathGroupTable.

         To destroy a row, set this object to 'destroy(6)'.
         When tRPAdminControlApply is set to 'commit(3)', the row will actually
         be removed from the tRPOperASPathGroupTable."
    ::= { tRPAdminASPathGroupEntry 3 }

tRPAdminASPathGroupASPathName OBJECT-TYPE
    SYNTAX       TASPathName (SIZE(1..32))
    MAX-ACCESS   read-create
    STATUS       current
    DESCRIPTION
        "The value of tRPAdminASPathGroupASPathName specifies
         the name of the AS-Path from the tRPAdminASPathTable."
    ::= { tRPAdminASPathGroupEntry 4 }

--
-- Conformance Information
--

tmnxRoutePolicyCompliances  
        OBJECT IDENTIFIER ::= { tmnxRoutePolicyConformance 1 }
tmnxRoutePolicyGroups      
        OBJECT IDENTIFIER ::= { tmnxRoutePolicyConformance 2 }


-- compliance statements

-- tmnxRoutePolicyCompliance MODULE-COMPLIANCE
--    ::= { tmnxRoutePolicyCompliances 1 }

-- tmnxRoutePolicyR2r1Compliance MODULE-COMPLIANCE
--    ::= { tmnxRoutePolicyCompliances 2 }

tmnxRoutePolicy7450V4v0Compliance MODULE-COMPLIANCE
    STATUS  obsolete
    DESCRIPTION
        "The compliance statement supporting management of Route Policies
         on Alcatel-Lucent 7450 ESS series systems 4.0 release."
    MODULE  -- this module
        MANDATORY-GROUPS { 
            tmnxRPAdminControlObjectsGroup,
            -- tmnxRPASPathObjectsGroup,
            -- tmnxRPCommunityObjectsGroup,
            -- tmnxRPDampingObjectsGroup,
            -- tmnxRPPrefixListObjectsGroup,
            tmnxRPPolicyObjectsV4v0Group,
            tmnxRPPolicyEntryObjectsV4v0Group
            -- tmnxRPInetPrefixListObjectsGroup
        }
    ::= { tmnxRoutePolicyCompliances 3 }

tmnxRoutePolicy7750V4v0Compliance MODULE-COMPLIANCE
    STATUS  obsolete 
    DESCRIPTION
        "The compliance statement supporting management of Route Policies
         on Alcatel-Lucent 7750 SR series systems 4.0 release."
    MODULE  -- this module
        MANDATORY-GROUPS { 
            tmnxRPAdminControlObjectsGroup,
            tmnxRPASPathObjectsGroup,
            tmnxRPCommunityObjectsGroup,
            tmnxRPDampingObjectsGroup,
            tmnxRPPrefixListObjectsGroup,
            tmnxRPPolicyObjectsV4v0Group,
            tmnxRPPolicyEntryObjectsV4v0Group,
            tmnxRPInetPrefixListObjectsGroup
        }
    ::= { tmnxRoutePolicyCompliances 4 }

tmnxRoutePolicy7450V5v0Compliance MODULE-COMPLIANCE
    STATUS  obsolete
    DESCRIPTION
        "The compliance statement supporting management of Route Policies
         on Alcatel-Lucent 7450 ESS series systems 5.0 release."
    MODULE  -- this module
        MANDATORY-GROUPS { 
            tmnxRPAdminControlObjectsGroup,
            -- tmnxRPASPathObjectsV5v0Group,
            -- tmnxRPCommunityObjectsV5v0Group,
            -- tmnxRPDampingObjectsV5v0Group,
            -- tmnxRPPrefixListObjectsV5v0Group,
            tmnxRPPolicyObjectsV5v0Group,
            tmnxRPPolicyEntryObjectsV5v0Group,
            -- tmnxRPInetPrefixListObjectsV5v0Group
            tmnxRPPolicyObsoleteV5v0Group
        }
    ::= { tmnxRoutePolicyCompliances 5 }

tmnxRoutePolicy7750V5v0Compliance MODULE-COMPLIANCE
    STATUS  obsolete
    DESCRIPTION
        "The compliance statement supporting management of Route Policies
         on Alcatel-Lucent 7750 SR series systems 5.0 release."
    MODULE  -- this module
        MANDATORY-GROUPS { 
            tmnxRPAdminControlObjectsGroup,
            tmnxRPASPathObjectsV5v0Group,
            tmnxRPCommunityObjectsV5v0Group,
            tmnxRPDampingObjectsV5v0Group,
            tmnxRPPrefixListObjectsV5v0Group,
            tmnxRPPolicyObjectsV5v0Group,
            tmnxRPPolicyEntryObjectsV5v0Group,
            tmnxRPInetPrefixListObjectsV5v0Group,
            tmnxRPPolicyObsoleteV5v0Group
        }
    ::= { tmnxRoutePolicyCompliances 6 }

tmnxRoutePolicy7450V7v0Compliance MODULE-COMPLIANCE
    STATUS  obsolete
    DESCRIPTION
        "The compliance statement supporting management of Route Policies
         on Alcatel-Lucent 7450 ESS series systems 5.0 release."
    MODULE  -- this module
        MANDATORY-GROUPS { 
            tmnxRPAdminControlObjectsGroup,
            -- tmnxRPASPathObjectsV5v0Group,
            -- tmnxRPCommunityObjectsV5v0Group,
            -- tmnxRPDampingObjectsV5v0Group,
            -- tmnxRPPrefixListObjectsV5v0Group,                        
            -- tmnxRPInetPrefixListObjectsV5v0Group
            tmnxRPPolicyObsoleteV5v0Group,
            tmnxRPPolicyObjectsV7v0Group,
            tmnxRPPolicyEntryObjectsV7v0Group,
            tmnxRPPolicyObsoleteV7v0Group
        }
    ::= { tmnxRoutePolicyCompliances 7 }

tmnxRoutePolicy7750V7v0Compliance MODULE-COMPLIANCE
    STATUS  obsolete
    DESCRIPTION
        "The compliance statement supporting management of Route Policies
         on Alcatel-Lucent 7750 SR series systems 5.0 release."
    MODULE  -- this module
        MANDATORY-GROUPS { 
            tmnxRPAdminControlObjectsGroup,
            tmnxRPASPathObjectsV5v0Group,
            tmnxRPCommunityObjectsV5v0Group,
            tmnxRPDampingObjectsV5v0Group,
            tmnxRPPrefixListObjectsV5v0Group,            
            tmnxRPInetPrefixListObjectsV5v0Group,
            tmnxRPPolicyObsoleteV5v0Group,
            tmnxRPPolicyObjectsV7v0Group,
            tmnxRPPolicyEntryObjectsV7v0Group,
            tmnxRPPolicyObsoleteV7v0Group
        }
    ::= { tmnxRoutePolicyCompliances 8 }    

tmnxRoutePolicy7450V8v0Compliance MODULE-COMPLIANCE
    STATUS  obsolete
    DESCRIPTION
        "The compliance statement supporting management of Route Policies
         on Alcatel-Lucent 7450 ESS series systems 5.0 release."
    MODULE  -- this module
        MANDATORY-GROUPS { 
            tmnxRPAdminControlObjectsGroup,
            -- tmnxRPASPathObjectsV5v0Group,
            -- tmnxRPCommunityObjectsV5v0Group,
            -- tmnxRPDampingObjectsV5v0Group,
            -- tmnxRPPrefixListObjectsV5v0Group,                        
            -- tmnxRPInetPrefixListObjectsV5v0Group
            tmnxRPPolicyObsoleteV5v0Group,
            tmnxRPPolicyObjectsV7v0Group,
            tmnxRPPolicyObjectsV8v0Group,
            tmnxRPPolicyEntryObjectsV7v0Group,
            tmnxRPPolicyObsoleteV7v0Group
        }
    ::= { tmnxRoutePolicyCompliances 9 }

tmnxRoutePolicy7750V8v0Compliance MODULE-COMPLIANCE
    STATUS  obsolete
    DESCRIPTION
        "The compliance statement supporting management of Route Policies
         on Alcatel-Lucent 7750 SR series systems 5.0 release."
    MODULE  -- this module
        MANDATORY-GROUPS { 
            tmnxRPAdminControlObjectsGroup,
            tmnxRPASPathObjectsV5v0Group,
            tmnxRPCommunityObjectsV5v0Group,
            tmnxRPDampingObjectsV5v0Group,
            tmnxRPPrefixListObjectsV5v0Group,            
            tmnxRPInetPrefixListObjectsV5v0Group,
            tmnxRPPolicyObsoleteV5v0Group,
            tmnxRPPolicyObjectsV7v0Group,
            tmnxRPPolicyObjectsV8v0Group,
            tmnxRPPolicyEntryObjectsV7v0Group,
            tmnxRPPolicyObsoleteV7v0Group
        }
    ::= { tmnxRoutePolicyCompliances 10 }    

tmnxRoutePolicy7450V9v0Compliance MODULE-COMPLIANCE
    STATUS  obsolete
    DESCRIPTION
        "The compliance statement supporting management of Route Policies
         on Alcatel-Lucent 7450 ESS series systems 9.0 release."
    MODULE  -- this module
        MANDATORY-GROUPS { 
            tmnxRPAdminControlObjectsGroup,
            -- tmnxRPASPathObjectsV5v0Group,
            -- tmnxRPCommunityObjectsV5v0Group,
            -- tmnxRPDampingObjectsV5v0Group,
            -- tmnxRPPrefixListObjectsV5v0Group,                        
            -- tmnxRPInetPrefixListObjectsV5v0Group
            tmnxRPPolicyObsoleteV5v0Group,
            tmnxRPPolicyObjectsV7v0Group,
            tmnxRPPolicyObjectsV8v0Group,
            tmnxRPPolicyObjectsV9v0Group,
            tmnxRPPolicyEntryObjectsV9v0Group,
            tmnxRPPolicyObsoleteV7v0Group,
            tmnxRPQPPBV9v0R4Group
        }
    ::= { tmnxRoutePolicyCompliances 11 }

tmnxRoutePolicy7750V9v0Compliance MODULE-COMPLIANCE
    STATUS  obsolete
    DESCRIPTION
        "The compliance statement supporting management of Route Policies
         on Alcatel-Lucent 7750 SR series systems 9.0 release."
    MODULE  -- this module
        MANDATORY-GROUPS { 
            tmnxRPAdminControlObjectsGroup,
            tmnxRPASPathObjectsV5v0Group,
            tmnxRPCommunityObjectsV5v0Group,
            tmnxRPDampingObjectsV5v0Group,
            tmnxRPPrefixListObjectsV5v0Group,            
            tmnxRPInetPrefixListObjectsV5v0Group,
            tmnxRPPolicyObsoleteV5v0Group,
            tmnxRPPolicyObjectsV7v0Group,
            tmnxRPPolicyObjectsV8v0Group,
            tmnxRPPolicyObjectsV9v0Group,
            tmnxRPPolicyEntryObjectsV9v0Group,
            tmnxRPPolicyObsoleteV7v0Group,
            tmnxRPQPPBV9v0R4Group
        }
    ::= { tmnxRoutePolicyCompliances 12 }    

tmnxRtPolicy7450V10v0Compliance MODULE-COMPLIANCE
    STATUS  current
    DESCRIPTION
        "The compliance statement supporting management of Route Policies
         on Alcatel-Lucent 7450 ESS series systems 10.0 release."
    MODULE  -- this module
        MANDATORY-GROUPS { 
            tmnxRPAdminControlObjectsGroup,
            tmnxRPPolicyObsoleteV5v0Group,
            tmnxRPPolicyObjectsV7v0Group,
            tmnxRPPolicyObjectsV8v0Group,
            tmnxRPPolicyObjectsV9v0Group,
            tmnxRPPolicyEntryObjectsV9v0Group,
            tmnxRPPolicyObsoleteV7v0Group,
            tmnxRPQPPBV9v0R4Group,
            tmnxRPPolicyObjectsV10v0Group,
            tmnxRPASPathGroupV10v0Group
        }
    ::= { tmnxRoutePolicyCompliances 13 }

tmnxRtPolicy7750V10v0Compliance MODULE-COMPLIANCE
    STATUS  current
    DESCRIPTION
        "The compliance statement supporting management of Route Policies
         on Alcatel-Lucent 7750 SR series systems 10.0 release."
    MODULE  -- this module
        MANDATORY-GROUPS { 
            tmnxRPAdminControlObjectsGroup,
            tmnxRPASPathObjectsV5v0Group,
            tmnxRPCommunityObjectsV5v0Group,
            tmnxRPDampingObjectsV5v0Group,
            tmnxRPPrefixListObjectsV5v0Group,            
            tmnxRPInetPrefixListObjectsV5v0Group,
            tmnxRPPolicyObsoleteV5v0Group,
            tmnxRPPolicyObjectsV7v0Group,
            tmnxRPPolicyObjectsV8v0Group,
            tmnxRPPolicyObjectsV9v0Group,
            tmnxRPPolicyEntryObjectsV9v0Group,
            tmnxRPPolicyObsoleteV7v0Group,
            tmnxRPQPPBV9v0R4Group,
            tmnxRPPolicyObjectsV10v0Group,
            tmnxRPASPathGroupV10v0Group
        }
    ::= { tmnxRoutePolicyCompliances 14 }    

-- units of conformance

tmnxRPAdminControlObjectsGroup OBJECT-GROUP
    OBJECTS {   tRPAdminOwner,
                tRPAdminControlApply,
                tRPAdminLastSetTimer,
                tRPAdminLastSetTimeout
            }
    STATUS      current
    DESCRIPTION
        "The group of objects supporting management of transactions
         applying changed Administrative values to the Operational
         Route Policy database on Alcatel-Lucent SROS series systems."
    ::= { tmnxRoutePolicyGroups 1 }

tmnxRPASPathObjectsGroup OBJECT-GROUP
    OBJECTS {   tRPOperASPathTableLastChanged,
                tRPOperASPathRowStatus,
                tRPOperASPathRegEx,
                tRPOperASPathEntryLastChanged,

                tRPAdminASPathRowStatus,
                tRPAdminASPathRegEx
            }
    STATUS      obsolete
    DESCRIPTION
        "The group of objects supporting management of AS Paths
         on Alcatel-Lucent SROS series systems."
    ::= { tmnxRoutePolicyGroups 2 }

tmnxRPCommunityObjectsGroup OBJECT-GROUP
    OBJECTS {   tRPOperCommunityTableLastChanged,
                tRPOperCommunityRowStatus,
                tRPOperCommunityEntryLastChanged,

                tRPAdminCommunityRowStatus
            }
    STATUS      obsolete
    DESCRIPTION
        "The group of objects supporting management of route policy 
         communities on Alcatel-Lucent SROS series systems."
    ::= { tmnxRoutePolicyGroups 3 }

tmnxRPDampingObjectsGroup OBJECT-GROUP
    OBJECTS {   tRPOperDampingTableLastChanged,
                tRPOperDampingRowStatus,
                tRPOperDampingHalfLife,
                tRPOperDampingMaxSuppress,
                tRPOperDampingReuse,
                tRPOperDampingSuppress,
                tRPOperDampingEntryLastChanged,
    
                tRPAdminDampingRowStatus,
                tRPAdminDampingHalfLife,
                tRPAdminDampingMaxSuppress,
                tRPAdminDampingReuse,
                tRPAdminDampingSuppress
            }
    STATUS      obsolete
    DESCRIPTION
        "The group of objects supporting management route policy damping
         on Alcatel-Lucent SROS series systems."
    ::= { tmnxRoutePolicyGroups 4 }

tmnxRPPrefixListObjectsGroup OBJECT-GROUP
    OBJECTS {   tRPOperPrefixListTableLastChanged,
                tRPOperPrefixListRowStatus,
                tRPOperPrefixListThroughLength,
                tRPOperPrefixListEntryLastChanged,
                tRPOperPrefixListBeginLength,

                tRPAdminPrefixListRowStatus,
                tRPAdminPrefixListThroughLength,
                tRPAdminPrefixListBeginLength
            }
    STATUS      obsolete
    DESCRIPTION
        "The group of objects supporting management of route policy
         prefix-lists on Alcatel-Lucent SROS series systems."
    ::= { tmnxRoutePolicyGroups 5 }

-- tmnxRPPolicyObjectsGroup OBJECT-GROUP
--    ::= { tmnxRoutePolicyGroups 6 }

-- tmnxRPPolicyEntryObjectsGroup OBJECT-GROUP
--    ::= { tmnxRoutePolicyGroups 7 }

-- tmnxRPPolicyEntryObjectsR2r1Group OBJECT-GROUP
--    ::= { tmnxRoutePolicyGroups 8 }

tmnxRPPolicyObjectsV4v0Group OBJECT-GROUP
    OBJECTS {   tRPOperPolicyStatementTableLastChanged,
                tRPOperPolicyStatementRowStatus,
                tRPOperPolicyStatementDescription,
                tRPOperPolicyStatementDefaultAction,
                tRPOperPolicyStatementEntryLastChanged,

                tRPOperPSDefaultActionParamsTableLastChanged,
                tRPOperPSDefaultActionASPath,
                tRPOperPSDefaultActionASPathName,
                tRPOperPSDefaultActionASPathPrependAS,
                tRPOperPSDefaultActionASPathPrependCount,
                tRPOperPSDefaultActionCommunity1,
                tRPOperPSDefaultActionCommunityName1,
                tRPOperPSDefaultActionCommunity2,
                tRPOperPSDefaultActionCommunityName2,
                tRPOperPSDefaultActionOrigin,
                tRPOperPSDefaultActionLocalPreferenceSet,
                tRPOperPSDefaultActionLocalPreference,
                tRPOperPSDefaultActionMetric,
                tRPOperPSDefaultActionMetricValue,
                tRPOperPSDefaultActionPreference,
                tRPOperPSDefaultActionDamping,
                tRPOperPSDefaultActionNextHopSelf,
                tRPOperPSDefaultActionNextHop,
                tRPOperPSDefaultActionTag,
                tRPOperPSDefaultActionOspfType,
                tRPOperPSDefaultActionParamsEntryLastChanged,
                tRPOperPSDefActInetNextHopType,
                tRPOperPSDefActInetNextHop,

                tRPAdminPolicyStatementRowStatus,
                tRPAdminPolicyStatementDescription,
                tRPAdminPolicyStatementDefaultAction,

                tRPAdminPSDefaultActionASPath,
                tRPAdminPSDefaultActionASPathName,
                tRPAdminPSDefaultActionASPathPrependAS,
                tRPAdminPSDefaultActionASPathPrependCount,
                tRPAdminPSDefaultActionCommunity1,
                tRPAdminPSDefaultActionCommunityName1,
                tRPAdminPSDefaultActionCommunity2,
                tRPAdminPSDefaultActionCommunityName2,
                tRPAdminPSDefaultActionOrigin,
                tRPAdminPSDefaultActionLocalPreferenceSet,
                tRPAdminPSDefaultActionLocalPreference,
                tRPAdminPSDefaultActionMetric,
                tRPAdminPSDefaultActionMetricValue,
                tRPAdminPSDefaultActionPreference,
                tRPAdminPSDefaultActionDamping,
                tRPAdminPSDefaultActionNextHopSelf,
                tRPAdminPSDefaultActionNextHop,
                tRPAdminPSDefaultActionTag,
                tRPAdminPSDefaultActionOspfType,
                tRPAdminPSDefActInetNextHopType,
                tRPAdminPSDefActInetNextHop
            }
    STATUS      obsolete
    DESCRIPTION
        "The group of objects supporting management of policy statements 
         and default action parameters on Alcatel-Lucent SROS series systems."
    ::= { tmnxRoutePolicyGroups 9 }    

tmnxRPPolicyEntryObjectsV4v0Group OBJECT-GROUP
    OBJECTS {   tRPOperPSParamsTableLastChanged,
                tRPOperPSParamsRowStatus,
                tRPOperPSParamsDescription,
                tRPOperPSParamsAction,
                tRPOperPSParamsEntryLastChanged,

                tRPOperPSAcceptActionParamsTableLastChanged,
                tRPOperPSAcceptActionASPath,
                tRPOperPSAcceptActionASPathName,
                tRPOperPSAcceptActionASPathPrependAS,
                tRPOperPSAcceptActionASPathPrependCount,
                tRPOperPSAcceptActionCommunity1,
                tRPOperPSAcceptActionCommunityName1,
                tRPOperPSAcceptActionCommunity2,
                tRPOperPSAcceptActionCommunityName2,
                tRPOperPSAcceptActionOrigin,
                tRPOperPSAcceptActionLocalPreferenceSet,
                tRPOperPSAcceptActionLocalPreference,
                tRPOperPSAcceptActionMetric,
                tRPOperPSAcceptActionMetricValue,
                tRPOperPSAcceptActionPreference,
                tRPOperPSAcceptActionDamping,
                tRPOperPSAcceptActionNextHopSelf,
                tRPOperPSAcceptActionNextHop,
                tRPOperPSAcceptActionTag,
                tRPOperPSAcceptActionOspfType,
                tRPOperPSAcceptActionParamsEntryLastChanged,
                tRPOperPSAcptActInetNextHopType,
                tRPOperPSAcptActInetNextHop,

                tRPOperPSToCriteriaTableLastChanged,
                tRPOperPSToCriteriaRowStatus,
                tRPOperPSToCriteriaProtocol,
                tRPOperPSToCriteriaNeighborIpAddr,
                tRPOperPSToCriteriaNeighborPrefixList,
                tRPOperPSToCriteriaEntryLastChanged,
                tRPOperPSToCriteriaIsisLevel,
                tRPOperPSToCriteriaPrefixList1,
                tRPOperPSToCriteriaPrefixList2,
                tRPOperPSToCriteriaPrefixList3,
                tRPOperPSToCriteriaPrefixList4,
                tRPOperPSToCriteriaPrefixList5,
                tRPOperPSToCritNbrInetAddrType,
                tRPOperPSToCritNbrInetAddr,
                
                tRPOperPSFromCriteriaTableLastChanged,
                tRPOperPSFromCriteriaRowStatus,
                tRPOperPSFromCriteriaProtocol,
                tRPOperPSFromCriteriaNeighborIpAddr,
                tRPOperPSFromCriteriaNeighborPrefixList,
                tRPOperPSFromCriteriaPrefixList1,
                tRPOperPSFromCriteriaPrefixList2,
                tRPOperPSFromCriteriaPrefixList3,
                tRPOperPSFromCriteriaPrefixList4,
                tRPOperPSFromCriteriaPrefixList5,
                tRPOperPSFromCriteriaASPath,
                tRPOperPSFromCriteriaCommunity,
                tRPOperPSFromCriteriaOrigin,
                tRPOperPSFromCriteriaOspfRouteType,
                tRPOperPSFromCriteriaEntryLastChanged,
                tRPOperPSFromCriteriaArea,
                tRPOperPSFromCriteriaAreaConfigured,
                tRPOperPSFromCriteriaIsisLevel,
                tRPOperPSFromCriteriaIsisExternal,
                tRPOperPSFromCriteriaIgmpHostPrefixList,
                tRPOperPSFromCriteriaGrpAddrPrefixList,
                tRPOperPSFromCriteriaSrcAddr,
                tRPOperPSFromCriteriaInterface,
                tRPOperPSFromCriteriaTag,
                tRPOperPSFromCritNbrInetAddrType,
                tRPOperPSFromCritNbrInetAddr,
                tRPOperPSFromCritSrcInetAddrType,
                tRPOperPSFromCritSrcInetAddr,
                tRPOperPSFromCriteriaFamily,

                tRPAdminPSParamsRowStatus,
                tRPAdminPSParamsDescription,
                tRPAdminPSParamsAction,

                tRPAdminPSAcceptActionASPath,
                tRPAdminPSAcceptActionASPathName,
                tRPAdminPSAcceptActionASPathPrependAS,
                tRPAdminPSAcceptActionASPathPrependCount,
                tRPAdminPSAcceptActionCommunity1,
                tRPAdminPSAcceptActionCommunityName1,
                tRPAdminPSAcceptActionCommunity2,
                tRPAdminPSAcceptActionCommunityName2,
                tRPAdminPSAcceptActionOrigin,
                tRPAdminPSAcceptActionLocalPreferenceSet,
                tRPAdminPSAcceptActionLocalPreference,
                tRPAdminPSAcceptActionMetric,
                tRPAdminPSAcceptActionMetricValue,
                tRPAdminPSAcceptActionPreference,
                tRPAdminPSAcceptActionDamping,
                tRPAdminPSAcceptActionNextHopSelf,
                tRPAdminPSAcceptActionNextHop,
                tRPAdminPSAcceptActionTag,
                tRPAdminPSAcceptActionOspfType,
                tRPAdminPSAcptActInetNextHopType,
                tRPAdminPSAcptActInetNextHop,

                tRPAdminPSToCriteriaRowStatus,
                tRPAdminPSToCriteriaProtocol,
                tRPAdminPSToCriteriaNeighborIpAddr,
                tRPAdminPSToCriteriaNeighborPrefixList,
                tRPAdminPSToCriteriaIsisLevel,
                tRPAdminPSToCriteriaPrefixList1,
                tRPAdminPSToCriteriaPrefixList2,
                tRPAdminPSToCriteriaPrefixList3,
                tRPAdminPSToCriteriaPrefixList4,
                tRPAdminPSToCriteriaPrefixList5,
                tRPAdminPSToCritNbrInetAddrType,
                tRPAdminPSToCritNbrInetAddr,
                
                tRPAdminPSFromCriteriaRowStatus,
                tRPAdminPSFromCriteriaProtocol,
                tRPAdminPSFromCriteriaNeighborIpAddr,
                tRPAdminPSFromCriteriaNeighborPrefixList,
                tRPAdminPSFromCriteriaPrefixList1,
                tRPAdminPSFromCriteriaPrefixList2,
                tRPAdminPSFromCriteriaPrefixList3,
                tRPAdminPSFromCriteriaPrefixList4,
                tRPAdminPSFromCriteriaPrefixList5,
                tRPAdminPSFromCriteriaASPath,
                tRPAdminPSFromCriteriaCommunity,
                tRPAdminPSFromCriteriaOrigin,
                tRPAdminPSFromCriteriaOspfRouteType,
                tRPAdminPSFromCriteriaArea,
                tRPAdminPSFromCriteriaAreaConfigured,
                tRPAdminPSFromCriteriaIsisLevel,
                tRPAdminPSFromCriteriaIsisExternal,
                tRPAdminPSFromCriteriaIgmpHostPrefixList,
                tRPAdminPSFromCriteriaGrpAddrPrefixList,
                tRPAdminPSFromCriteriaSrcAddr,
                tRPAdminPSFromCriteriaInterface,
                tRPAdminPSFromCriteriaTag,
                tRPAdminPSFromCritNbrInetAddrType,
                tRPAdminPSFromCritNbrInetAddr,
                tRPAdminPSFromCritSrcInetAddrType,
                tRPAdminPSFromCritSrcInetAddr,
                tRPAdminPSFromCriteriaFamily
            }
    STATUS      obsolete
    DESCRIPTION
        "The group of objects supporting management of route policy 
         statement entries, 'to' filter parameters, 'from' filter 
         parameters, and accept action parameters on Alcatel-Lucent
         SROS series systems 4.0 release."
    ::= { tmnxRoutePolicyGroups 10 }    

tmnxRPInetPrefixListObjectsGroup OBJECT-GROUP
    OBJECTS {   tRPOperInetPrefixListTblLastChg,
                tRPOperInetPrefixListRowStatus,
                tRPOperInetPrefixListThroughLen,
                tRPOperInetPrefixListLastChg,
                tRPOperInetPrefixListBeginLen,

                tRPAdminInetPrefixListRowStatus,
                tRPAdminInetPrefixListThroughLen,
                tRPAdminInetPrefixListBeginLen
            }
    STATUS      obsolete
    DESCRIPTION
        "The group of objects supporting management of route policy
         prefix-lists on Alcatel-Lucent SROS series systems."
    ::= { tmnxRoutePolicyGroups 11 }    

tmnxRPPolicyEntryObjectsV5v0Group OBJECT-GROUP
    OBJECTS {   tRPOperPSParamsRowStatus,
                tRPOperPSParamsDescription,
                tRPOperPSParamsAction,
                
                tRPOperPSAcceptActionASPath,
                tRPOperPSAcceptActionASPathName,
                tRPOperPSAcceptActionASPathPrependAS,
                tRPOperPSAcceptActionASPathPrependCount,
                tRPOperPSAcceptActionCommunity1,
                tRPOperPSAcceptActionCommunityName1,
                tRPOperPSAcceptActionCommunity2,
                tRPOperPSAcceptActionCommunityName2,
                tRPOperPSAcceptActionOrigin,
                tRPOperPSAcceptActionLocalPreferenceSet,
                tRPOperPSAcceptActionLocalPreference,
                tRPOperPSAcceptActionMetric,
                tRPOperPSAcceptActionMetricValue,
                tRPOperPSAcceptActionPreference,
                tRPOperPSAcceptActionDamping,
                tRPOperPSAcceptActionNextHopSelf,
                tRPOperPSAcceptActionNextHop,
                tRPOperPSAcceptActionTag,
                tRPOperPSAcceptActionOspfType,
                tRPOperPSAcptActInetNextHopType,
                tRPOperPSAcptActInetNextHop,

                tRPOperPSToCriteriaRowStatus,
                tRPOperPSToCriteriaProtocol,
                tRPOperPSToCriteriaNeighborIpAddr,
                tRPOperPSToCriteriaNeighborPrefixList,
                tRPOperPSToCriteriaIsisLevel,
                tRPOperPSToCriteriaPrefixList1,
                tRPOperPSToCriteriaPrefixList2,
                tRPOperPSToCriteriaPrefixList3,
                tRPOperPSToCriteriaPrefixList4,
                tRPOperPSToCriteriaPrefixList5,
                tRPOperPSToCritNbrInetAddrType,
                tRPOperPSToCritNbrInetAddr,
                tRPOperPSToCriteriaInstanceId,                      
                  
                tRPOperPSFromCriteriaRowStatus,
                tRPOperPSFromCriteriaProtocol,
                tRPOperPSFromCriteriaNeighborIpAddr,
                tRPOperPSFromCriteriaNeighborPrefixList,
                tRPOperPSFromCriteriaPrefixList1,
                tRPOperPSFromCriteriaPrefixList2,
                tRPOperPSFromCriteriaPrefixList3,
                tRPOperPSFromCriteriaPrefixList4,
                tRPOperPSFromCriteriaPrefixList5,
                tRPOperPSFromCriteriaASPath,
                tRPOperPSFromCriteriaCommunity,
                tRPOperPSFromCriteriaOrigin,
                tRPOperPSFromCriteriaOspfRouteType,
                tRPOperPSFromCriteriaArea,
                tRPOperPSFromCriteriaAreaConfigured,
                tRPOperPSFromCriteriaIsisLevel,
                tRPOperPSFromCriteriaIsisExternal,
                tRPOperPSFromCriteriaIgmpHostPrefixList,
                tRPOperPSFromCriteriaGrpAddrPrefixList,
                tRPOperPSFromCriteriaSrcAddr,
                tRPOperPSFromCriteriaInterface,
                tRPOperPSFromCriteriaTag,
                tRPOperPSFromCritNbrInetAddrType,
                tRPOperPSFromCritNbrInetAddr,
                tRPOperPSFromCritSrcInetAddrType,
                tRPOperPSFromCritSrcInetAddr,
                tRPOperPSFromCriteriaFamily,
                tRPOperPSFromCriteriaInstanceId,  

                tRPAdminPSParamsRowStatus,
                tRPAdminPSParamsDescription,
                tRPAdminPSParamsAction,

                tRPAdminPSAcceptActionASPath,
                tRPAdminPSAcceptActionASPathName,
                tRPAdminPSAcceptActionASPathPrependAS,
                tRPAdminPSAcceptActionASPathPrependCount,
                tRPAdminPSAcceptActionCommunity1,
                tRPAdminPSAcceptActionCommunityName1,
                tRPAdminPSAcceptActionCommunity2,
                tRPAdminPSAcceptActionCommunityName2,
                tRPAdminPSAcceptActionOrigin,
                tRPAdminPSAcceptActionLocalPreferenceSet,
                tRPAdminPSAcceptActionLocalPreference,
                tRPAdminPSAcceptActionMetric,
                tRPAdminPSAcceptActionMetricValue,
                tRPAdminPSAcceptActionPreference,
                tRPAdminPSAcceptActionDamping,
                tRPAdminPSAcceptActionNextHopSelf,
                tRPAdminPSAcceptActionNextHop,
                tRPAdminPSAcceptActionTag,
                tRPAdminPSAcceptActionOspfType,
                tRPAdminPSAcptActInetNextHopType,
                tRPAdminPSAcptActInetNextHop,

                tRPAdminPSToCriteriaRowStatus,
                tRPAdminPSToCriteriaProtocol,
                tRPAdminPSToCriteriaNeighborIpAddr,
                tRPAdminPSToCriteriaNeighborPrefixList,
                tRPAdminPSToCriteriaIsisLevel,
                tRPAdminPSToCriteriaPrefixList1,
                tRPAdminPSToCriteriaPrefixList2,
                tRPAdminPSToCriteriaPrefixList3,
                tRPAdminPSToCriteriaPrefixList4,
                tRPAdminPSToCriteriaPrefixList5,
                tRPAdminPSToCritNbrInetAddrType,
                tRPAdminPSToCritNbrInetAddr,
                tRPAdminPSToCriteriaInstanceId,

                
                tRPAdminPSFromCriteriaRowStatus,
                tRPAdminPSFromCriteriaProtocol,
                tRPAdminPSFromCriteriaNeighborIpAddr,
                tRPAdminPSFromCriteriaNeighborPrefixList,
                tRPAdminPSFromCriteriaPrefixList1,
                tRPAdminPSFromCriteriaPrefixList2,
                tRPAdminPSFromCriteriaPrefixList3,
                tRPAdminPSFromCriteriaPrefixList4,
                tRPAdminPSFromCriteriaPrefixList5,
                tRPAdminPSFromCriteriaASPath,
                tRPAdminPSFromCriteriaCommunity,
                tRPAdminPSFromCriteriaOrigin,
                tRPAdminPSFromCriteriaOspfRouteType,
                tRPAdminPSFromCriteriaArea,
                tRPAdminPSFromCriteriaAreaConfigured,
                tRPAdminPSFromCriteriaIsisLevel,
                tRPAdminPSFromCriteriaIsisExternal,
                tRPAdminPSFromCriteriaIgmpHostPrefixList,
                tRPAdminPSFromCriteriaGrpAddrPrefixList,
                tRPAdminPSFromCriteriaSrcAddr,
                tRPAdminPSFromCriteriaInterface,
                tRPAdminPSFromCriteriaTag,
                tRPAdminPSFromCritNbrInetAddrType,
                tRPAdminPSFromCritNbrInetAddr,
                tRPAdminPSFromCritSrcInetAddrType,
                tRPAdminPSFromCritSrcInetAddr,
                tRPAdminPSFromCriteriaFamily,
                tRPAdminPSFromCriteriaInstanceId

            }
    STATUS      obsolete
    DESCRIPTION
        "The group of objects supporting management of route policy 
         statement entries, 'to' filter parameters, 'from' filter 
         parameters, and accept action parameters on Alcatel-Lucent SROS
         SR series systems 5.0 release."
    ::= { tmnxRoutePolicyGroups 12 }

tmnxRPPolicyObsoleteV5v0Group OBJECT-GROUP
    OBJECTS {   tRPOperASPathTableLastChanged,
                tRPOperASPathEntryLastChanged,
                tRPOperCommunityTableLastChanged,
                tRPOperCommunityEntryLastChanged,
                tRPOperDampingTableLastChanged,
                tRPOperDampingEntryLastChanged,
                tRPOperPrefixListTableLastChanged,
                tRPOperPrefixListEntryLastChanged,
                tRPOperPolicyStatementTableLastChanged,
                tRPOperPolicyStatementEntryLastChanged,
                tRPOperPSDefaultActionParamsTableLastChanged,
                tRPOperPSDefaultActionParamsEntryLastChanged,
                tRPOperPSParamsTableLastChanged,
                tRPOperPSParamsEntryLastChanged,
                tRPOperPSAcceptActionParamsTableLastChanged,
                tRPOperPSAcceptActionParamsEntryLastChanged,
                tRPOperPSToCriteriaTableLastChanged,
                tRPOperPSToCriteriaEntryLastChanged,
                tRPOperPSFromCriteriaTableLastChanged,
                tRPOperPSFromCriteriaEntryLastChanged,
                tRPOperInetPrefixListTblLastChg,
                tRPOperInetPrefixListLastChg
            }
    STATUS      current
    DESCRIPTION
        "The group of objects in TIMETRA-ROUTE-POLICY-MIB which are obsoleted."
    ::= { tmnxRoutePolicyGroups 13 }

tmnxRPASPathObjectsV5v0Group OBJECT-GROUP
    OBJECTS {   tRPOperASPathRowStatus,
                tRPOperASPathRegEx,

                tRPAdminASPathRowStatus,
                tRPAdminASPathRegEx
            }
    STATUS      current
    DESCRIPTION
        "The group of objects supporting management of AS Paths
         on Alcatel-Lucent SROS series systems."
    ::= { tmnxRoutePolicyGroups 14 }

tmnxRPCommunityObjectsV5v0Group OBJECT-GROUP
    OBJECTS {   tRPOperCommunityRowStatus,
                tRPAdminCommunityRowStatus
            }
    STATUS      current
    DESCRIPTION
        "The group of objects supporting management of route policy 
         communities on Alcatel-Lucent SROS series systems."
    ::= { tmnxRoutePolicyGroups 15 }

tmnxRPDampingObjectsV5v0Group OBJECT-GROUP
    OBJECTS {   tRPOperDampingRowStatus,
                tRPOperDampingHalfLife,
                tRPOperDampingMaxSuppress,
                tRPOperDampingReuse,
                tRPOperDampingSuppress,
    
                tRPAdminDampingRowStatus,
                tRPAdminDampingHalfLife,
                tRPAdminDampingMaxSuppress,
                tRPAdminDampingReuse,
                tRPAdminDampingSuppress
            }
    STATUS      current
    DESCRIPTION
        "The group of objects supporting management route policy damping
         on Alcatel-Lucent SROS series systems."
    ::= { tmnxRoutePolicyGroups 16 }

tmnxRPPrefixListObjectsV5v0Group OBJECT-GROUP
    OBJECTS {   tRPOperPrefixListRowStatus,
                tRPOperPrefixListThroughLength,
                tRPOperPrefixListBeginLength,

                tRPAdminPrefixListRowStatus,
                tRPAdminPrefixListThroughLength,
                tRPAdminPrefixListBeginLength
            }
    STATUS      current
    DESCRIPTION
        "The group of objects supporting management of route policy
         prefix-lists on Alcatel-Lucent SROS series systems."
    ::= { tmnxRoutePolicyGroups 17 }

tmnxRPPolicyObjectsV5v0Group OBJECT-GROUP
    OBJECTS {   tRPOperPolicyStatementRowStatus,
                tRPOperPolicyStatementDescription,
                tRPOperPolicyStatementDefaultAction,
                
                tRPOperPSDefaultActionASPath,
                tRPOperPSDefaultActionASPathName,
                tRPOperPSDefaultActionASPathPrependAS,
                tRPOperPSDefaultActionASPathPrependCount,
                tRPOperPSDefaultActionCommunity1,
                tRPOperPSDefaultActionCommunityName1,
                tRPOperPSDefaultActionCommunity2,
                tRPOperPSDefaultActionCommunityName2,
                tRPOperPSDefaultActionOrigin,
                tRPOperPSDefaultActionLocalPreferenceSet,
                tRPOperPSDefaultActionLocalPreference,
                tRPOperPSDefaultActionMetric,
                tRPOperPSDefaultActionMetricValue,
                tRPOperPSDefaultActionPreference,
                tRPOperPSDefaultActionDamping,
                tRPOperPSDefaultActionNextHopSelf,
                tRPOperPSDefaultActionNextHop,
                tRPOperPSDefaultActionTag,
                tRPOperPSDefaultActionOspfType,
                tRPOperPSDefActInetNextHopType,
                tRPOperPSDefActInetNextHop,

                tRPAdminPolicyStatementRowStatus,
                tRPAdminPolicyStatementDescription,
                tRPAdminPolicyStatementDefaultAction,

                tRPAdminPSDefaultActionASPath,
                tRPAdminPSDefaultActionASPathName,
                tRPAdminPSDefaultActionASPathPrependAS,
                tRPAdminPSDefaultActionASPathPrependCount,
                tRPAdminPSDefaultActionCommunity1,
                tRPAdminPSDefaultActionCommunityName1,
                tRPAdminPSDefaultActionCommunity2,
                tRPAdminPSDefaultActionCommunityName2,
                tRPAdminPSDefaultActionOrigin,
                tRPAdminPSDefaultActionLocalPreferenceSet,
                tRPAdminPSDefaultActionLocalPreference,
                tRPAdminPSDefaultActionMetric,
                tRPAdminPSDefaultActionMetricValue,
                tRPAdminPSDefaultActionPreference,
                tRPAdminPSDefaultActionDamping,
                tRPAdminPSDefaultActionNextHopSelf,
                tRPAdminPSDefaultActionNextHop,
                tRPAdminPSDefaultActionTag,
                tRPAdminPSDefaultActionOspfType,
                tRPAdminPSDefActInetNextHopType,
                tRPAdminPSDefActInetNextHop
            }
    STATUS      obsolete
    DESCRIPTION
        "The group of objects supporting management of policy statements 
         and default action parameters on Alcatel-Lucent SROS series systems."
    ::= { tmnxRoutePolicyGroups 18 } 

tmnxRPInetPrefixListObjectsV5v0Group OBJECT-GROUP
    OBJECTS {   tRPOperInetPrefixListRowStatus,
                tRPOperInetPrefixListThroughLen,
                tRPOperInetPrefixListBeginLen,

                tRPAdminInetPrefixListRowStatus,
                tRPAdminInetPrefixListThroughLen,
                tRPAdminInetPrefixListBeginLen
            }
    STATUS      current
    DESCRIPTION
        "The group of objects supporting management of route policy
         prefix-lists on Alcatel-Lucent SROS series systems."
    ::= { tmnxRoutePolicyGroups 19 } 

tmnxRPPolicyObjectsV7v0Group OBJECT-GROUP
    OBJECTS {   tRPOperPolicyStatementRowStatus,
                tRPOperPolicyStatementDescription,
                tRPOperPolicyStatementDefaultAction,
                
                tRPOperPSDefaultActionASPath,
                tRPOperPSDefaultActionASPathName,                
                tRPOperPSDefaultActionASPathPrependCount,
                tRPOperPSDefaultActionCommunity1,
                tRPOperPSDefaultActionCommunityName1,
                tRPOperPSDefaultActionCommunity2,
                tRPOperPSDefaultActionCommunityName2,
                tRPOperPSDefaultActionOrigin,
                tRPOperPSDefaultActionLocalPreferenceSet,
                tRPOperPSDefaultActionLocalPreference,
                tRPOperPSDefaultActionMetric,
                tRPOperPSDefaultActionMetricValue,
                tRPOperPSDefaultActionPreference,
                tRPOperPSDefaultActionDamping,
                tRPOperPSDefaultActionNextHopSelf,
                tRPOperPSDefaultActionNextHop,
                tRPOperPSDefaultActionTag,
                tRPOperPSDefaultActionOspfType,
                tRPOperPSDefActInetNextHopType,
                tRPOperPSDefActInetNextHop,

                tRPAdminPolicyStatementRowStatus,
                tRPAdminPolicyStatementDescription,
                tRPAdminPolicyStatementDefaultAction,

                tRPAdminPSDefaultActionASPath,
                tRPAdminPSDefaultActionASPathName,                
                tRPAdminPSDefaultActionASPathPrependCount,
                tRPAdminPSDefaultActionCommunity1,
                tRPAdminPSDefaultActionCommunityName1,
                tRPAdminPSDefaultActionCommunity2,
                tRPAdminPSDefaultActionCommunityName2,
                tRPAdminPSDefaultActionOrigin,
                tRPAdminPSDefaultActionLocalPreferenceSet,
                tRPAdminPSDefaultActionLocalPreference,
                tRPAdminPSDefaultActionMetric,
                tRPAdminPSDefaultActionMetricValue,
                tRPAdminPSDefaultActionPreference,
                tRPAdminPSDefaultActionDamping,
                tRPAdminPSDefaultActionNextHopSelf,
                tRPAdminPSDefaultActionNextHop,
                tRPAdminPSDefaultActionTag,
                tRPAdminPSDefaultActionOspfType,
                tRPAdminPSDefActInetNextHopType,
                tRPAdminPSDefActInetNextHop,

                tRPAdminPSDefaultActionASPathPnd,
                tRPOperPSDefaultActionASPathPend
            }
    STATUS      current
    DESCRIPTION
        "The group of objects supporting management of policy statements 
         and default action parameters on Alcatel-Lucent SROS series systems."
    ::= { tmnxRoutePolicyGroups 20 }
    
tmnxRPPolicyEntryObjectsV7v0Group OBJECT-GROUP
    OBJECTS {   tRPOperPSParamsRowStatus,
                tRPOperPSParamsDescription,
                tRPOperPSParamsAction,
                
                tRPOperPSAcceptActionASPath,
                tRPOperPSAcceptActionASPathName,
                tRPOperPSAcceptActionASPathPrependCount,
                tRPOperPSAcceptActionCommunity1,
                tRPOperPSAcceptActionCommunityName1,
                tRPOperPSAcceptActionCommunity2,
                tRPOperPSAcceptActionCommunityName2,
                tRPOperPSAcceptActionOrigin,
                tRPOperPSAcceptActionLocalPreferenceSet,
                tRPOperPSAcceptActionLocalPreference,
                tRPOperPSAcceptActionMetric,
                tRPOperPSAcceptActionMetricValue,
                tRPOperPSAcceptActionPreference,
                tRPOperPSAcceptActionDamping,
                tRPOperPSAcceptActionNextHopSelf,
                tRPOperPSAcceptActionNextHop,
                tRPOperPSAcceptActionTag,
                tRPOperPSAcceptActionOspfType,
                tRPOperPSAcptActInetNextHopType,
                tRPOperPSAcptActInetNextHop,

                tRPOperPSToCriteriaRowStatus,
                tRPOperPSToCriteriaProtocol,
                tRPOperPSToCriteriaNeighborIpAddr,
                tRPOperPSToCriteriaNeighborPrefixList,
                tRPOperPSToCriteriaIsisLevel,
                tRPOperPSToCriteriaPrefixList1,
                tRPOperPSToCriteriaPrefixList2,
                tRPOperPSToCriteriaPrefixList3,
                tRPOperPSToCriteriaPrefixList4,
                tRPOperPSToCriteriaPrefixList5,
                tRPOperPSToCritNbrInetAddrType,
                tRPOperPSToCritNbrInetAddr,
                tRPOperPSToCriteriaInstanceId,                      
                  
                tRPOperPSFromCriteriaRowStatus,
                tRPOperPSFromCriteriaProtocol,
                tRPOperPSFromCriteriaNeighborIpAddr,
                tRPOperPSFromCriteriaNeighborPrefixList,
                tRPOperPSFromCriteriaPrefixList1,
                tRPOperPSFromCriteriaPrefixList2,
                tRPOperPSFromCriteriaPrefixList3,
                tRPOperPSFromCriteriaPrefixList4,
                tRPOperPSFromCriteriaPrefixList5,
                tRPOperPSFromCriteriaASPath,
                tRPOperPSFromCriteriaCommunity,
                tRPOperPSFromCriteriaOrigin,
                tRPOperPSFromCriteriaOspfRouteType,
                tRPOperPSFromCriteriaArea,
                tRPOperPSFromCriteriaAreaConfigured,
                tRPOperPSFromCriteriaIsisLevel,
                tRPOperPSFromCriteriaIsisExternal,
                tRPOperPSFromCriteriaIgmpHostPrefixList,
                tRPOperPSFromCriteriaGrpAddrPrefixList,
                tRPOperPSFromCriteriaSrcAddr,
                tRPOperPSFromCriteriaInterface,
                tRPOperPSFromCriteriaTag,
                tRPOperPSFromCritNbrInetAddrType,
                tRPOperPSFromCritNbrInetAddr,
                tRPOperPSFromCritSrcInetAddrType,
                tRPOperPSFromCritSrcInetAddr,
                tRPOperPSFromCriteriaFamily,
                tRPOperPSFromCriteriaInstanceId,  

                tRPAdminPSParamsRowStatus,
                tRPAdminPSParamsDescription,
                tRPAdminPSParamsAction,

                tRPAdminPSAcceptActionASPath,
                tRPAdminPSAcceptActionASPathName,
                tRPAdminPSAcceptActionASPathPrependCount,
                tRPAdminPSAcceptActionCommunity1,
                tRPAdminPSAcceptActionCommunityName1,
                tRPAdminPSAcceptActionCommunity2,
                tRPAdminPSAcceptActionCommunityName2,
                tRPAdminPSAcceptActionOrigin,
                tRPAdminPSAcceptActionLocalPreferenceSet,
                tRPAdminPSAcceptActionLocalPreference,
                tRPAdminPSAcceptActionMetric,
                tRPAdminPSAcceptActionMetricValue,
                tRPAdminPSAcceptActionPreference,
                tRPAdminPSAcceptActionDamping,
                tRPAdminPSAcceptActionNextHopSelf,
                tRPAdminPSAcceptActionNextHop,
                tRPAdminPSAcceptActionTag,
                tRPAdminPSAcceptActionOspfType,
                tRPAdminPSAcptActInetNextHopType,
                tRPAdminPSAcptActInetNextHop,

                tRPAdminPSToCriteriaRowStatus,
                tRPAdminPSToCriteriaProtocol,
                tRPAdminPSToCriteriaNeighborIpAddr,
                tRPAdminPSToCriteriaNeighborPrefixList,
                tRPAdminPSToCriteriaIsisLevel,
                tRPAdminPSToCriteriaPrefixList1,
                tRPAdminPSToCriteriaPrefixList2,
                tRPAdminPSToCriteriaPrefixList3,
                tRPAdminPSToCriteriaPrefixList4,
                tRPAdminPSToCriteriaPrefixList5,
                tRPAdminPSToCritNbrInetAddrType,
                tRPAdminPSToCritNbrInetAddr,
                tRPAdminPSToCriteriaInstanceId,

                
                tRPAdminPSFromCriteriaRowStatus,
                tRPAdminPSFromCriteriaProtocol,
                tRPAdminPSFromCriteriaNeighborIpAddr,
                tRPAdminPSFromCriteriaNeighborPrefixList,
                tRPAdminPSFromCriteriaPrefixList1,
                tRPAdminPSFromCriteriaPrefixList2,
                tRPAdminPSFromCriteriaPrefixList3,
                tRPAdminPSFromCriteriaPrefixList4,
                tRPAdminPSFromCriteriaPrefixList5,
                tRPAdminPSFromCriteriaASPath,
                tRPAdminPSFromCriteriaCommunity,
                tRPAdminPSFromCriteriaOrigin,
                tRPAdminPSFromCriteriaOspfRouteType,
                tRPAdminPSFromCriteriaArea,
                tRPAdminPSFromCriteriaAreaConfigured,
                tRPAdminPSFromCriteriaIsisLevel,
                tRPAdminPSFromCriteriaIsisExternal,
                tRPAdminPSFromCriteriaIgmpHostPrefixList,
                tRPAdminPSFromCriteriaGrpAddrPrefixList,
                tRPAdminPSFromCriteriaSrcAddr,
                tRPAdminPSFromCriteriaInterface,
                tRPAdminPSFromCriteriaTag,
                tRPAdminPSFromCritNbrInetAddrType,
                tRPAdminPSFromCritNbrInetAddr,
                tRPAdminPSFromCritSrcInetAddrType,
                tRPAdminPSFromCritSrcInetAddr,
                tRPAdminPSFromCriteriaFamily,
                tRPAdminPSFromCriteriaInstanceId,

                tRPAdminPSAcceptActionASPathPend,
                tRPOperPSAcceptActionASPathPend,
                tRPOperPSFromCriteriaMatchTag,
                tRPAdminPSFromCriteriaMatchTag
            }
    STATUS      obsolete
    DESCRIPTION
        "The group of objects supporting management of route policy 
         statement entries, 'to' filter parameters, 'from' filter 
         parameters, and accept action parameters on Alcatel-Lucent
         SROS series systems 7.0 release."
    ::= { tmnxRoutePolicyGroups 21 }

tmnxRPPolicyObsoleteV7v0Group OBJECT-GROUP
    OBJECTS {   
                tRPAdminPSDefaultActionASPathPrependAS,
                tRPAdminPSAcceptActionASPathPrependAS,
                tRPOperPSDefaultActionASPathPrependAS,
                tRPOperPSAcceptActionASPathPrependAS
            }
   STATUS       current
   DESCRIPTION
       "The group of objects in TIMETRA-ROUTE-POLICY-MIB which are obsoleted
        in Alcatel-Lucent SROS series systems 7.0 release."
   ::= { tmnxRoutePolicyGroups 22 }
   
tmnxRPPolicyObjectsV8v0Group OBJECT-GROUP
   OBJECTS {   
               tRPAdminPSDefActMcRedirSvcId,
               tRPAdminPSDefActMcRedirIfIndex,
               tRPOperPSDefActMcRedirSvcId,
               tRPOperPSDefActMcRedirIfIndex
           }
   STATUS      current
   DESCRIPTION
       "The group of objects supporting management of policy statements 
        and default action parameters on Alcatel-Lucent SROS series systems
        that were added in release 8.0."
   ::= { tmnxRoutePolicyGroups 25 }

tmnxRPQPPBV9v0R4Group    OBJECT-GROUP
    OBJECTS {   tRPAdminPSAcceptActionFC,
                tRPAdminPSAcceptActionFCPriority
            }
     STATUS     current
     DESCRIPTION
         "The group of objects supporting QoS policy propagation using BGP in 
          release 9.0R4 Alcatel-Lucent SROS series systems."
     ::= { tmnxRoutePolicyGroups 26 }
       
tmnxRPPolicyEntryObjectsV9v0Group OBJECT-GROUP
    OBJECTS {   tRPOperPSParamsRowStatus,
                tRPOperPSParamsDescription,
                tRPOperPSParamsAction,
                     
                tRPOperPSAcceptActionASPath,
                tRPOperPSAcceptActionASPathName,
                tRPOperPSAcceptActionASPathPrependCount,
                tRPOperPSAcceptActionCommunity1,
                tRPOperPSAcceptActionCommunityName1,
                tRPOperPSAcceptActionCommunity2,
                tRPOperPSAcceptActionCommunityName2,
                tRPOperPSAcceptActionOrigin,
                tRPOperPSAcceptActionLocalPreferenceSet,
                tRPOperPSAcceptActionLocalPreference,
                tRPOperPSAcceptActionMetric,
                tRPOperPSAcceptActionMetricValue,
                tRPOperPSAcceptActionPreference,
                tRPOperPSAcceptActionDamping,
                tRPOperPSAcceptActionNextHopSelf,
                tRPOperPSAcceptActionNextHop,
                tRPOperPSAcceptActionTag,
                tRPOperPSAcceptActionOspfType,
                tRPOperPSAcptActInetNextHopType,
                tRPOperPSAcptActInetNextHop,

                tRPOperPSToCriteriaRowStatus,
                tRPOperPSToCriteriaProtocol,
                tRPOperPSToCriteriaNeighborIpAddr,
                tRPOperPSToCriteriaNeighborPrefixList,
                tRPOperPSToCriteriaIsisLevel,
                tRPOperPSToCriteriaPrefixList1,
                tRPOperPSToCriteriaPrefixList2,
                tRPOperPSToCriteriaPrefixList3,
                tRPOperPSToCriteriaPrefixList4,
                tRPOperPSToCriteriaPrefixList5,
                tRPOperPSToCritNbrInetAddrType,
                tRPOperPSToCritNbrInetAddr,
                tRPOperPSToCriteriaInstanceId,                      
                       
                tRPOperPSFromCriteriaRowStatus,
                tRPOperPSFromCriteriaProtocol,
                tRPOperPSFromCriteriaNeighborIpAddr,
                tRPOperPSFromCriteriaNeighborPrefixList,
                tRPOperPSFromCriteriaPrefixList1,
                tRPOperPSFromCriteriaPrefixList2,
                tRPOperPSFromCriteriaPrefixList3,
                tRPOperPSFromCriteriaPrefixList4,
                tRPOperPSFromCriteriaPrefixList5,
                tRPOperPSFromCriteriaASPath,
                tRPOperPSFromCriteriaCommunity,
                tRPOperPSFromCriteriaOrigin,
                tRPOperPSFromCriteriaOspfRouteType,
                tRPOperPSFromCriteriaArea,
                tRPOperPSFromCriteriaAreaConfigured,
                tRPOperPSFromCriteriaIsisLevel,
                tRPOperPSFromCriteriaIsisExternal,
                tRPOperPSFromCriteriaIgmpHostPrefixList,
                tRPOperPSFromCriteriaGrpAddrPrefixList,
                tRPOperPSFromCriteriaSrcAddr,
                tRPOperPSFromCriteriaInterface,
                tRPOperPSFromCriteriaTag,
                tRPOperPSFromCritNbrInetAddrType,
                tRPOperPSFromCritNbrInetAddr,
                tRPOperPSFromCritSrcInetAddrType,
                tRPOperPSFromCritSrcInetAddr,
                tRPOperPSFromCriteriaFamily,
                tRPOperPSFromCriteriaInstanceId,  

                tRPAdminPSParamsRowStatus,
                tRPAdminPSParamsDescription,
                tRPAdminPSParamsAction,

                tRPAdminPSAcceptActionASPath,
                tRPAdminPSAcceptActionASPathName,
                tRPAdminPSAcceptActionASPathPrependCount,
                tRPAdminPSAcceptActionCommunity1,
                tRPAdminPSAcceptActionCommunityName1,
                tRPAdminPSAcceptActionCommunity2,
                tRPAdminPSAcceptActionCommunityName2,
                tRPAdminPSAcceptActionOrigin,
                tRPAdminPSAcceptActionLocalPreferenceSet,
                tRPAdminPSAcceptActionLocalPreference,
                tRPAdminPSAcceptActionMetric,
                tRPAdminPSAcceptActionMetricValue,
                tRPAdminPSAcceptActionPreference,
                tRPAdminPSAcceptActionDamping,
                tRPAdminPSAcceptActionNextHopSelf,
                tRPAdminPSAcceptActionNextHop,
                tRPAdminPSAcceptActionTag,
                tRPAdminPSAcceptActionOspfType,
                tRPAdminPSAcptActInetNextHopType,
                tRPAdminPSAcptActInetNextHop,

                tRPAdminPSToCriteriaRowStatus,
                tRPAdminPSToCriteriaProtocol,
                tRPAdminPSToCriteriaNeighborIpAddr,
                tRPAdminPSToCriteriaNeighborPrefixList,
                tRPAdminPSToCriteriaIsisLevel,
                tRPAdminPSToCriteriaPrefixList1,
                tRPAdminPSToCriteriaPrefixList2,
                tRPAdminPSToCriteriaPrefixList3,
                tRPAdminPSToCriteriaPrefixList4,
                tRPAdminPSToCriteriaPrefixList5,
                tRPAdminPSToCritNbrInetAddrType,
                tRPAdminPSToCritNbrInetAddr,
                tRPAdminPSToCriteriaInstanceId,

                     
                tRPAdminPSFromCriteriaRowStatus,
                tRPAdminPSFromCriteriaProtocol,
                tRPAdminPSFromCriteriaNeighborIpAddr,
                tRPAdminPSFromCriteriaNeighborPrefixList,
                tRPAdminPSFromCriteriaPrefixList1,
                tRPAdminPSFromCriteriaPrefixList2,
                tRPAdminPSFromCriteriaPrefixList3,
                tRPAdminPSFromCriteriaPrefixList4,
                tRPAdminPSFromCriteriaPrefixList5,
                tRPAdminPSFromCriteriaASPath,
                tRPAdminPSFromCriteriaCommunity,
                tRPAdminPSFromCriteriaOrigin,
                tRPAdminPSFromCriteriaOspfRouteType,
                tRPAdminPSFromCriteriaArea,
                tRPAdminPSFromCriteriaAreaConfigured,
                tRPAdminPSFromCriteriaIsisLevel,
                tRPAdminPSFromCriteriaIsisExternal,
                tRPAdminPSFromCriteriaIgmpHostPrefixList,
                tRPAdminPSFromCriteriaGrpAddrPrefixList,
                tRPAdminPSFromCriteriaSrcAddr,
                tRPAdminPSFromCriteriaInterface,
                tRPAdminPSFromCriteriaTag,
                tRPAdminPSFromCritNbrInetAddrType,
                tRPAdminPSFromCritNbrInetAddr,
                tRPAdminPSFromCritSrcInetAddrType,
                tRPAdminPSFromCritSrcInetAddr,
                tRPAdminPSFromCriteriaFamily,
                tRPAdminPSFromCriteriaInstanceId,

                tRPAdminPSAcceptActionASPathPend,
                tRPOperPSAcceptActionASPathPend,
                tRPOperPSFromCriteriaMatchTag,
                tRPAdminPSFromCriteriaMatchTag,
                tRPAdminPSFromCriteriaState,
                tRPOperPSFromCriteriaState
            }
    STATUS      current
    DESCRIPTION
        "The group of objects supporting management of route policy 
         statement entries, 'to' filter parameters, 'from' filter 
         parameters, and accept action parameters on Alcatel-Lucent SROS
         SR series systems 9.0 release."
    ::= { tmnxRoutePolicyGroups 27 }

tmnxRPPolicyObjectsV9v0Group OBJECT-GROUP
   OBJECTS {   
                tRPAdminPSAcptActMcRedirSvcId,  
                tRPAdminPSAcptActMcRedirIfIndex,
                tRPOperPSAcptActMcRedirSvcId,
                tRPOperPSAcptActMcRedirIfIndex
           }
   STATUS      current
   DESCRIPTION
       "The group of objects supporting management of policy statements 
        and default action parameters on Alcatel-Lucent SROS series systems
        that were added in release 9.0."
   ::= { tmnxRoutePolicyGroups 30 }

tmnxRPPolicyObjectsV10v0Group OBJECT-GROUP
  OBJECTS {
                tRPAdminPSAcptActnMetricSource,
                tRPAdminPSDefActionMetricSource,
                tRPOperPSAcptActnMetricSource,
                tRPOperPSDefActionMetricSource,
                tRPAdminPSAcptActionAigpMetric,
                tRPAdminPSAcptActnAigpMetricVal,
                tRPOperPSAcptActionAigpMetric,
                tRPOperPSAcptActnAigpMetricVal,
                tRPOperCommunityExprString1,
                tRPOperCommunityExprString2,
                tRPOperCommunityExprString3,
                tRPOperCommunityExprString4,
                tRPOperCommunityExprRowStatus,
                tRPAdminCommunityExprString1,
                tRPAdminCommunityExprString2,
                tRPAdminCommunityExprString3,
                tRPAdminCommunityExprString4,
                tRPAdminCommunityExprRowStatus,
                tRPAdminPSDefActionAigpMetric,
                tRPAdminPSDefActnAigpMetricVal,
                tRPOperPSDefActionAigpMetric,
                tRPOperPSDefActnAigpMetricVal
          }
  STATUS      current
  DESCRIPTION
      "The group of objects supporting management of policy statements 
       and default action parameters on Alcatel-Lucent SROS series systems
       that were added in release 10.0."
  ::= { tmnxRoutePolicyGroups 31 }

tmnxRPASPathGroupV10v0Group OBJECT-GROUP
  OBJECTS {
                tRPOperASPathGroupRowStatus,
                tRPOperASPathGroupASPathName,
                tRPAdminASPathGroupRowStatus,
                tRPAdminASPathGroupASPathName,
                tRPOperPSFromCritASPathGroup,
                tRPAdminPSFromCritASPathGroup
          }
  STATUS      current
  DESCRIPTION
      "The group of objects supporting management of AS-Path Groups
       on Alcatel-Lucent SROS series systems since release 10.0."
  ::= { tmnxRoutePolicyGroups 32 }

END
