TIMETRA-DA-MIB DEFINITIONS ::= BEGIN

IMPORTS
   MODULE-IDENTITY, OBJECT-TYPE, NOTIFICATION-TYPE,
   Unsigned32, Counter32, Counter64, Gauge32
       FROM SNMPv2-SMI

   MODULE-COMPLIANCE, OBJECT-GROUP, NOTIFICATION-GROUP
       FROM SNMPv2-CONF

   RowStatus, TimeStamp, TruthValue, TEXTUAL-CONVENTION, DisplayString, 
   MacAddress
       FROM SNMPv2-TC

   InetAddress, InetAddressType, InetAddressPrefixLength, InetPortNumber
       FROM INET-ADDRESS-MIB

   timetraSRMIBModules, tmnxSRObjs, tmnxSRConfs, 
   tmnxSRNotifyPrefix
       FROM TIMETRA-GLOBAL-MIB

   TItemDescription, TmnxAdminState, TNamedItem, TmnxEnabledDisabled,
   TNamedItemOrEmpty, TmnxOperState, TLNamedItemOrEmpty
       FROM TIMETRA-TC-MIB

   ;

timetraDAMIBModule    MODULE-IDENTITY
    LAST-UPDATED "201106010000Z"
    ORGANIZATION "Alcatel-Lucent"
    CONTACT-INFO
        "Alcatel-Lucent SROS Support
         Web: http://support.alcatel-lucent.com"
    DESCRIPTION
    "This document is the SNMP MIB module to manage and provision
    the Delivery Appliance features for Content Delivery Networks (CDN). 

    Copyright 2008-2011 Alcatel-Lucent. All rights reserved.
    Reproduction of this document is authorized on the condition that
    the foregoing copyright notice is included.

    This SNMP MIB module (Specification) embodies Alcatel-Lucent's
    proprietary intellectual property. Alcatel-Lucent retains all title and
    ownership in the Specification, including any revisions.

    Alcatel-Lucent grants all interested parties a non-exclusive
    license to use and distribute an unmodified copy of this
    Specification in connection with management of Alcatel-Lucent products,
    and without fee, provided this copyright notice and license appear
    on all copies.

    This Specification is supplied 'as is', and Alcatel-Lucent
    makes no warranty, either express or implied, as to the use,
    operation, condition, or performance of the Specification."

--
--  Revision History
--
    REVISION        "1105230000Z"
    DESCRIPTION     "Rev 0.1                23 May 2011 00:00
                     Initial version of the TIMETRA-DA-MIB."

    ::= { timetraSRMIBModules 82 }

-- ----------------------------------------------------------------------------
--  Alcatel-Lucent SROS series Delivery Appliance MIB structure
-- ----------------------------------------------------------------------------
tmnxDA                      OBJECT IDENTIFIER ::= { tmnxSRObjs 82 }
    tmnxDAObjs              OBJECT IDENTIFIER ::= { tmnxDA 1 }

tmnxDAConformance           OBJECT IDENTIFIER ::= { tmnxSRConfs 82 }
    tmnxDACompliances       OBJECT IDENTIFIER ::= { tmnxDAConformance 1 }
    tmnxDAGroups            OBJECT IDENTIFIER ::= { tmnxDAConformance 2 }

tmnxDANotifyPrefix          OBJECT IDENTIFIER ::= { tmnxSRNotifyPrefix 82 }
    tmnxDANotifications     OBJECT IDENTIFIER ::= { tmnxDANotifyPrefix 0 }

-- --------------------------
--  MIB objects
-- --------------------------

--
--  DA Server Group Table
--

tmnxDASvrGrpTableLastChanged    OBJECT-TYPE
    SYNTAX          TimeStamp
    MAX-ACCESS      read-only
    STATUS          current
    DESCRIPTION
        "The value of tmnxDASvrGrpTableLastChanged indicates the sysUpTime at 
         the time of the last modification to tmnxDASvrGrpTable by adding, 
         deleting an entry or change to a writable object in the table.

         If no changes were made to the table since the last re-initialization 
         of the local network management subsystem, then this object contains a 
         zero value."
    ::= { tmnxDAObjs 1 }

tmnxDASvrGrpTable    OBJECT-TYPE
    SYNTAX          SEQUENCE OF TmnxDASvrGrpEntry
    MAX-ACCESS      not-accessible
    STATUS          current
    DESCRIPTION
        "There can be multiple Delivery Appliance (DA) proxy server groups in a 
         system. One or more caching blades (DA servers) form a server group. A 
         caching blade can appear in only one server group. The 
         tmnxDASvrGrpTable has an entry for each such server group in the 
         system."
    ::= { tmnxDAObjs 2 }

tmnxDASvrGrpEntry    OBJECT-TYPE
    SYNTAX          TmnxDASvrGrpEntry
    MAX-ACCESS      not-accessible
    STATUS          current
    DESCRIPTION
        "Each row entry represents a DA server group in the system. Entries can 
         be created and deleted by the user."
    INDEX {  
            tmnxDASvrGrpIndex      
    }
    ::= { tmnxDASvrGrpTable 1 }

TmnxDASvrGrpEntry ::= SEQUENCE {
        tmnxDASvrGrpIndex                  Unsigned32,
        tmnxDASvrGrpRowStatus              RowStatus,
        tmnxDASvrGrpLastChanged            TimeStamp,
        tmnxDASvrGrpCardSlotNumber         BITS,
        tmnxDASvrGrpAdminState             TmnxAdminState,
        tmnxDASvrGrpOperState              TmnxOperState
    }

tmnxDASvrGrpIndex    OBJECT-TYPE
    SYNTAX          Unsigned32 (0|1..4)
    MAX-ACCESS      not-accessible
    STATUS          current
    DESCRIPTION
        "The value of tmnxDASvrGrpIndex specifies the server group index for 
         this server group."
    ::= { tmnxDASvrGrpEntry 1 }

tmnxDASvrGrpRowStatus    OBJECT-TYPE
    SYNTAX          RowStatus
    MAX-ACCESS      read-create
    STATUS          current
    DESCRIPTION
        "The value of tmnxDASvrGrpRowStatus specifies the row status of this 
         row in the DA Server Group Table. It is used to create and delete row 
         entries in this table."
    ::= { tmnxDASvrGrpEntry 2 }

tmnxDASvrGrpLastChanged    OBJECT-TYPE
    SYNTAX          TimeStamp
    MAX-ACCESS      read-only
    STATUS          current
    DESCRIPTION
        "The value of tmnxDASvrGrpLastChanged indicates the timestamp of last
         change to this row in tmnxDASvrGrpTable."
    ::= { tmnxDASvrGrpEntry 3 }

tmnxDASvrGrpCardSlotNumber    OBJECT-TYPE
    SYNTAX BITS {                    
                    card1  (0), -- numbering must start at zero.
                    card2  (1),
                    card3  (2),
                    card4  (3),
                    card5  (4),
                    card6  (5),
                    card7  (6),
                    card8  (7),
                    card9  (8),
                    card10 (9) 
                }
    MAX-ACCESS      read-create
    STATUS          current
    DESCRIPTION
        "The bit value of tmnxDASvrGrpCardSlotNumber specifies the card number 
         being used by the DA server."
    DEFVAL { {} }
    ::= { tmnxDASvrGrpEntry 4 }

tmnxDASvrGrpAdminState    OBJECT-TYPE
    SYNTAX          TmnxAdminState
    MAX-ACCESS      read-create
    STATUS          current
    DESCRIPTION
        "The value of tmnxDASvrGrpAdminState specifies the desired 
         administrative state of the DA server-group."
    DEFVAL { outOfService }
    ::= { tmnxDASvrGrpEntry 5 }

tmnxDASvrGrpOperState    OBJECT-TYPE
    SYNTAX          TmnxOperState
    MAX-ACCESS      read-only
    STATUS          current
    DESCRIPTION
        "The value of tmnxDASvrGrpOperState indicates the current operational 
         state of the DA server-group."
    ::= { tmnxDASvrGrpEntry 6 }

--
--  DA Group Table
--

tmnxDAGrpTableLastChanged    OBJECT-TYPE
    SYNTAX          TimeStamp
    MAX-ACCESS      read-only
    STATUS          current
    DESCRIPTION
        "The value of tmnxDAGrpTableLastChanged indicates the sysUpTime at the 
         time of the last modification to tmnxDAGrpTable by adding, deleting an 
         entry or change to a writable object in the table.

         If no changes were made to the table since the last re-initialization 
         of the local network management subsystem, then this object contains a 
         zero value."
    ::= { tmnxDAObjs 3 }

tmnxDAGrpTable    OBJECT-TYPE
    SYNTAX          SEQUENCE OF TmnxDAGrpEntry
    MAX-ACCESS      not-accessible
    STATUS          current
    DESCRIPTION
        "The tmnxDAGrpTable has an entry for each virtual Delivery Appliance 
         (DA) proxy server in a server group. There can be multiple virtual DA 
         proxy servers within a server group."
    ::= { tmnxDAObjs 4 }

tmnxDAGrpEntry    OBJECT-TYPE
    SYNTAX          TmnxDAGrpEntry
    MAX-ACCESS      not-accessible
    STATUS          current
    DESCRIPTION
        "Each row entry represents a virtual DA proxy server. Entries can be 
         created and deleted by the user."
    INDEX { 
            tmnxDAGrpName 
    }
    ::= { tmnxDAGrpTable 1 }

TmnxDAGrpEntry ::= SEQUENCE {
        tmnxDAGrpName                      TNamedItem,
        tmnxDAGrpRowStatus                 RowStatus,
        tmnxDAGrpLastChanged               TimeStamp,
        tmnxDAGrpServerGroupIndex          Unsigned32,
        tmnxDAGrpAdminState                TmnxAdminState,
        tmnxDAGrpDescription               TItemDescription,
        tmnxDAGrpDnsClientIsmLinkName      TNamedItemOrEmpty,
        tmnxDAGrpDCAuthCache               INTEGER,
        tmnxDAGrpDCAdminState              TmnxAdminState,
        tmnxDAGrpDCIsmLinkName             TNamedItemOrEmpty,
        tmnxDAGrpDCBootStrapPort           InetPortNumber,
        tmnxDAGrpDCConnRetryTimer          Unsigned32,
        tmnxDAGrpDCIdleTimeout             Unsigned32,
        tmnxDAGrpBytesFromCache            Counter64,
        tmnxDAGrpBytesFromCacheL32         Counter32,
        tmnxDAGrpBytesFromCacheH32         Counter32,
        tmnxDAGrpBytesNotFromCache         Counter64,
        tmnxDAGrpBytesNotFromCacheL32      Counter32,
        tmnxDAGrpBytesNotFromCacheH32      Counter32,
        tmnxDAGrpObjectsFromCache          Counter64,
        tmnxDAGrpObjectsFromCacheL32       Counter32,
        tmnxDAGrpObjectsFromCacheH32       Counter32,
        tmnxDAGrpObjectsNotFromCache       Counter64,
        tmnxDAGrpObjectsNotFromCacheL32    Counter32,
        tmnxDAGrpObjectsNotFromCacheH32    Counter32,
        tmnxDAGrpObjectByteCount           Counter64,
        tmnxDAGrpObjectByteCountL32        Counter32,
        tmnxDAGrpObjectByteCountH32        Counter32,
        tmnxDAGrpNumberOfOrigins           Counter64,
        tmnxDAGrpNumberOfOriginsL32        Counter32,
        tmnxDAGrpNumberOfOriginsH32        Counter32,
        tmnxDAGrpDCAuthCacheHit            Counter64,
        tmnxDAGrpDCAuthCacheHitL32         Counter32,
        tmnxDAGrpDCAuthCacheHitH32         Counter32,
        tmnxDAGrpDCAuthCacheMiss           Counter64,
        tmnxDAGrpDCAuthCacheMissL32        Counter32,
        tmnxDAGrpDCAuthCacheMissH32        Counter32,
        tmnxDAGrpDCDeniedAuth              Counter64,
        tmnxDAGrpDCDeniedAuthL32           Counter32,
        tmnxDAGrpDCDeniedAuthH32           Counter32,
        tmnxDAGrpDCMinRTTPerPeer           Counter32,
        tmnxDAGrpDCAvgRTTPerPeer           Counter32,
        tmnxDAGrpDCMaxRTTPerPeer           Counter32
    }

tmnxDAGrpName    OBJECT-TYPE
    SYNTAX          TNamedItem
    MAX-ACCESS      not-accessible
    STATUS          current
    DESCRIPTION
        "The value of tmnxDAGrpName specifies the group name for this virtual 
         DA proxy server in the specified server group."
    ::= { tmnxDAGrpEntry 1 }

tmnxDAGrpRowStatus    OBJECT-TYPE
    SYNTAX          RowStatus
    MAX-ACCESS      read-create
    STATUS          current
    DESCRIPTION
        "The value of tmnxDAGrpRowStatus specifies the row status of this 
         row in the DA group table. It is used to create and delete row entries 
         in this table.

         The value of the object tmnxDAGrpServerGroupIndex specifies the index 
         of the server group on which this DA Group must be instantiated. The 
         value of tmnxDAGrpServerGroupIndex must be specified when the row is 
         created and cannot be changed while tmnxDAGrpRowStatus is 'active'."
    ::= { tmnxDAGrpEntry 2 }

tmnxDAGrpLastChanged    OBJECT-TYPE
    SYNTAX          TimeStamp
    MAX-ACCESS      read-only
    STATUS          current
    DESCRIPTION
        "The value of tmnxDAGrpLastChanged indicates the timestamp of last
         change to this row in tmnxDAGrpTable."
    ::= { tmnxDAGrpEntry 3 }

tmnxDAGrpServerGroupIndex    OBJECT-TYPE
    SYNTAX          Unsigned32 (0|1..4)
    MAX-ACCESS      read-create
    STATUS          current
    DESCRIPTION
        "The value of tmnxDAGrpServerGroupIndex specifies the index of the 
         server group on which this DA Group must be instantiated. The value of 
         this object must be specified when the row is created and cannot be 
         changed while tmnxDAGrpRowStatus is 'active'. An 'inconsistentValue' 
         error is returned if an attempt is made to set this object 
         individually."
    DEFVAL { 0 }
    ::= { tmnxDAGrpEntry 4 }

tmnxDAGrpAdminState    OBJECT-TYPE
    SYNTAX          TmnxAdminState
    MAX-ACCESS      read-create
    STATUS          current
    DESCRIPTION
        "The value of tmnxDAGrpAdminState specifies the desired administrative
         state of the DA group."
    DEFVAL { outOfService }
    ::= { tmnxDAGrpEntry 5 }

tmnxDAGrpDescription    OBJECT-TYPE
    SYNTAX          TItemDescription
    MAX-ACCESS      read-create
    STATUS          current
    DESCRIPTION
        "The value of tmnxDAGrpDescription specifies the user provided
         description string for this DA group entry."
    DEFVAL { ''H }
    ::= { tmnxDAGrpEntry 6 }

tmnxDAGrpDnsClientIsmLinkName    OBJECT-TYPE
    SYNTAX          TNamedItemOrEmpty
    MAX-ACCESS      read-create
    STATUS          current
    DESCRIPTION
        "The value of tmnxDAGrpDnsClientIsmLinkName specifies the Integrated 
         Services Module (ISM) link name used in DNS lookup request packets. 
         The ISM link is an IP interface in the DA group on the ISM. The ISM 
         link must already be configured in the DA group before it is assigned 
         to this object."
    DEFVAL { ''H }
    ::= { tmnxDAGrpEntry 7 }

tmnxDAGrpDCAuthCache    OBJECT-TYPE
    SYNTAX          INTEGER {
                               none           (1),
                               useCache       (2)
                            }
    MAX-ACCESS      read-create
    STATUS          current
    DESCRIPTION
        "The value of tmnxDAGrpDCAuthCache specifies what happens when the DA
         loses connectivity to all DCs in the network. 

         A value of 'none' specifies that the cache is invalidated and all 
         incoming delivery requests will be rejected.
    
         A value of 'useCache' specifies that the DA will continue to use its 
         cached authorizations until they expire." 
    DEFVAL { none }
    ::= { tmnxDAGrpEntry 8 }

tmnxDAGrpDCAdminState    OBJECT-TYPE
    SYNTAX          TmnxAdminState
    MAX-ACCESS      read-create
    STATUS          current
    DESCRIPTION
        "The value of tmnxDAGrpDCAdminState specifies the desired administrative
         state of the DA group for this DC."
    DEFVAL { outOfService }
    ::= { tmnxDAGrpEntry 9 }

tmnxDAGrpDCIsmLinkName    OBJECT-TYPE
    SYNTAX          TNamedItemOrEmpty
    MAX-ACCESS      read-create
    STATUS          current
    DESCRIPTION
        "The value of tmnxDAGrpDCIsmLinkName specifies the Integrated Services 
         Module (ISM) link name used in the DA group for this DC. The ISM link 
         is an IP interface in the DA group on the ISM. The ISM link must 
         already be configured in the DA group before it is assigned to this 
         object."
    DEFVAL { ''H }
    ::= { tmnxDAGrpEntry 10 }

tmnxDAGrpDCBootStrapPort    OBJECT-TYPE
    SYNTAX          InetPortNumber
    MAX-ACCESS      read-create
    STATUS          current
    DESCRIPTION
        "The value of tmnxDAGrpDCBootStrapPort specifies the DC port number of 
         the bootstrap-servers."
    DEFVAL { 22345 }
    ::= { tmnxDAGrpEntry 11 }

tmnxDAGrpDCConnRetryTimer    OBJECT-TYPE
    SYNTAX          Unsigned32 (100..300000)
    UNITS           "milliseconds"
    MAX-ACCESS      read-create
    STATUS          current
    DESCRIPTION
        "The value of tmnxDAGrpDCConnRetryTimer specifies in milli-seconds the 
         amount of time after which the delivery-controller will retry 
         periodically to establish a connection with its client if not 
         initially successful."
    DEFVAL { 1000 }
    ::= { tmnxDAGrpEntry 12 }

tmnxDAGrpDCIdleTimeout    OBJECT-TYPE
    SYNTAX          Unsigned32 (10..300)
    UNITS           "seconds"
    MAX-ACCESS      read-create
    STATUS          current
    DESCRIPTION
        "The value of tmnxDAGrpDCIdleTimeout specifies the max time for any 
         outstanding requests to a delivery-controller to be replied. If a reply 
         is not received within this time after the request was sent, the 
         DA closes the TCP connection."
    DEFVAL { 30 }
    ::= { tmnxDAGrpEntry 13 }

tmnxDAGrpBytesFromCache    OBJECT-TYPE
    SYNTAX          Counter64
    MAX-ACCESS      read-only
    STATUS          current
    DESCRIPTION
        "The value of tmnxDAGrpBytesFromCache indicates the number of bytes that 
         are served from the cache."
    ::= { tmnxDAGrpEntry 14 }

tmnxDAGrpBytesFromCacheL32    OBJECT-TYPE
    SYNTAX          Counter32
    MAX-ACCESS      read-only
    STATUS          current
    DESCRIPTION
        "The value of tmnxDAGrpBytesFromCacheL32 indicates the lower 32 
         bits of the value of tmnxDAGrpBytesFromCache."
    ::= { tmnxDAGrpEntry 15 }

tmnxDAGrpBytesFromCacheH32    OBJECT-TYPE
    SYNTAX          Counter32
    MAX-ACCESS      read-only
    STATUS          current
    DESCRIPTION
        "The value of tmnxDAGrpBytesFromCacheH32 indicates the higher 32 
         bits of the value of tmnxDAGrpBytesFromCache."
    ::= { tmnxDAGrpEntry 16 }

tmnxDAGrpBytesNotFromCache    OBJECT-TYPE
    SYNTAX          Counter64
    MAX-ACCESS      read-only
    STATUS          current
    DESCRIPTION
        "The value of tmnxDAGrpBytesNotFromCache indicates the number of bytes 
         that are fetched from the server and not served from the cache."
    ::= { tmnxDAGrpEntry 17 }

tmnxDAGrpBytesNotFromCacheL32    OBJECT-TYPE
    SYNTAX          Counter32
    MAX-ACCESS      read-only
    STATUS          current
    DESCRIPTION
        "The value of tmnxDAGrpBytesNotFromCacheL32 indicates the lower 32 
         bits of the value of tmnxDAGrpBytesNotFromCache."
    ::= { tmnxDAGrpEntry 18 }

tmnxDAGrpBytesNotFromCacheH32    OBJECT-TYPE
    SYNTAX          Counter32
    MAX-ACCESS      read-only
    STATUS          current
    DESCRIPTION
        "The value of tmnxDAGrpBytesNotFromCacheH32 indicates the higher 32 
         bits of the value of tmnxDAGrpBytesNotFromCache."
    ::= { tmnxDAGrpEntry 19 }

tmnxDAGrpObjectsFromCache    OBJECT-TYPE
    SYNTAX          Counter64
    MAX-ACCESS      read-only
    STATUS          current
    DESCRIPTION
        "The value of tmnxDAGrpObjectsFromCache indicates the number of objects 
         that are served from the cache."
    ::= { tmnxDAGrpEntry 20 }

tmnxDAGrpObjectsFromCacheL32    OBJECT-TYPE
    SYNTAX          Counter32
    MAX-ACCESS      read-only
    STATUS          current
    DESCRIPTION
        "The value of tmnxDAGrpObjectsFromCacheL32 indicates the lower 32 
         bits of the value of tmnxDAGrpObjectsFromCache."
    ::= { tmnxDAGrpEntry 21 }

tmnxDAGrpObjectsFromCacheH32    OBJECT-TYPE
    SYNTAX          Counter32
    MAX-ACCESS      read-only
    STATUS          current
    DESCRIPTION
        "The value of tmnxDAGrpObjectsFromCacheH32 indicates the higher 32 
         bits of the value of tmnxDAGrpObjectsFromCache."
    ::= { tmnxDAGrpEntry 22 }

tmnxDAGrpObjectsNotFromCache    OBJECT-TYPE
    SYNTAX          Counter64
    MAX-ACCESS      read-only
    STATUS          current
    DESCRIPTION
        "The value of tmnxDAGrpObjectsNotFromCache indicates the number of  
         objects that are fetched from the server and not served from the 
         cache."
    ::= { tmnxDAGrpEntry 23 }

tmnxDAGrpObjectsNotFromCacheL32    OBJECT-TYPE
    SYNTAX          Counter32
    MAX-ACCESS      read-only
    STATUS          current
    DESCRIPTION
        "The value of tmnxDAGrpObjectsNotFromCacheL32 indicates the lower 32 
         bits of the value of tmnxDAGrpObjectsNotFromCache."
    ::= { tmnxDAGrpEntry 24 }

tmnxDAGrpObjectsNotFromCacheH32    OBJECT-TYPE
    SYNTAX          Counter32
    MAX-ACCESS      read-only
    STATUS          current
    DESCRIPTION
        "The value of tmnxDAGrpObjectsNotFromCacheH32 indicates the higher 32 
         bits of the value of tmnxDAGrpObjectsNotFromCache."
    ::= { tmnxDAGrpEntry 25 }

tmnxDAGrpObjectByteCount    OBJECT-TYPE
    SYNTAX          Counter64
    UNITS           "megabytes"
    MAX-ACCESS      read-only
    STATUS          current
    DESCRIPTION
        "The value of tmnxDAGrpObjectByteCount indicates object byte count."
    ::= { tmnxDAGrpEntry 26 }

tmnxDAGrpObjectByteCountL32    OBJECT-TYPE
    SYNTAX          Counter32
    UNITS           "megabytes"
    MAX-ACCESS      read-only
    STATUS          current
    DESCRIPTION
        "The value of tmnxDAGrpObjectByteCountL32 indicates the lower 32 
         bits of the value of tmnxDAGrpObjectByteCount."
    ::= { tmnxDAGrpEntry 27 }

tmnxDAGrpObjectByteCountH32    OBJECT-TYPE
    SYNTAX          Counter32
    UNITS           "megabytes"
    MAX-ACCESS      read-only
    STATUS          current
    DESCRIPTION
        "The value of tmnxDAGrpObjectByteCountH32 indicates the higher 32 
         bits of the value of tmnxDAGrpObjectByteCount."
    ::= { tmnxDAGrpEntry 28 }

tmnxDAGrpNumberOfOrigins    OBJECT-TYPE
    SYNTAX          Counter64
    MAX-ACCESS      read-only
    STATUS          current
    DESCRIPTION
        "The value of tmnxDAGrpNumberOfOrigins indicates the number of origin 
         servers."
    ::= { tmnxDAGrpEntry 29 }

tmnxDAGrpNumberOfOriginsL32    OBJECT-TYPE
    SYNTAX          Counter32
    MAX-ACCESS      read-only
    STATUS          current
    DESCRIPTION
        "The value of tmnxDAGrpNumberOfOriginsL32 indicates the lower 32 
         bits of the value of tmnxDAGrpNumberOfOrigins."
    ::= { tmnxDAGrpEntry 30 }

tmnxDAGrpNumberOfOriginsH32    OBJECT-TYPE
    SYNTAX          Counter32
    MAX-ACCESS      read-only
    STATUS          current
    DESCRIPTION
        "The value of tmnxDAGrpNumberOfOriginsH32 indicates the higher 32 
         bits of the value of tmnxDAGrpNumberOfOrigins."
    ::= { tmnxDAGrpEntry 31 }

tmnxDAGrpDCAuthCacheHit    OBJECT-TYPE
    SYNTAX          Counter64
    MAX-ACCESS      read-only
    STATUS          current
    DESCRIPTION
        "The value of tmnxDAGrpDCAuthCacheHit indicates the number of auth 
         cache hits."
    ::= { tmnxDAGrpEntry 32 }

tmnxDAGrpDCAuthCacheHitL32    OBJECT-TYPE
    SYNTAX          Counter32
    MAX-ACCESS      read-only
    STATUS          current
    DESCRIPTION
        "The value of tmnxDAGrpDCAuthCacheHitL32 indicates the lower 32 
         bits of the value of tmnxDAGrpDCAuthCacheHit."
    ::= { tmnxDAGrpEntry 33 }

tmnxDAGrpDCAuthCacheHitH32    OBJECT-TYPE
    SYNTAX          Counter32
    MAX-ACCESS      read-only
    STATUS          current
    DESCRIPTION
        "The value of tmnxDAGrpDCAuthCacheHitH32 indicates the higher 32 
         bits of the value of tmnxDAGrpDCAuthCacheHit."
    ::= { tmnxDAGrpEntry 34 }

tmnxDAGrpDCAuthCacheMiss    OBJECT-TYPE
    SYNTAX          Counter64
    MAX-ACCESS      read-only
    STATUS          current
    DESCRIPTION
        "The value of tmnxDAGrpDCAuthCacheMiss indicates the number of auth 
         cache misses."
    ::= { tmnxDAGrpEntry 35 }

tmnxDAGrpDCAuthCacheMissL32    OBJECT-TYPE
    SYNTAX          Counter32
    MAX-ACCESS      read-only
    STATUS          current
    DESCRIPTION
        "The value of tmnxDAGrpDCAuthCacheMissL32 indicates the lower 32 
         bits of the value of tmnxDAGrpDCAuthCacheMiss."
    ::= { tmnxDAGrpEntry 36 }

tmnxDAGrpDCAuthCacheMissH32    OBJECT-TYPE
    SYNTAX          Counter32
    MAX-ACCESS      read-only
    STATUS          current
    DESCRIPTION
        "The value of tmnxDAGrpDCAuthCacheMissH32 indicates the higher 32 
         bits of the value of tmnxDAGrpDCAuthCacheMiss."
    ::= { tmnxDAGrpEntry 37 }

tmnxDAGrpDCDeniedAuth    OBJECT-TYPE
    SYNTAX          Counter64
    MAX-ACCESS      read-only
    STATUS          current
    DESCRIPTION
        "The value of tmnxDAGrpDCDeniedAuth indicates the number of denied auth 
         sessions."
    ::= { tmnxDAGrpEntry 38 }

tmnxDAGrpDCDeniedAuthL32    OBJECT-TYPE
    SYNTAX          Counter32
    MAX-ACCESS      read-only
    STATUS          current
    DESCRIPTION
        "The value of tmnxDAGrpDCDeniedAuthL32 indicates the lower 32 
         bits of the value of tmnxDAGrpDCDeniedAuth."
    ::= { tmnxDAGrpEntry 39 }

tmnxDAGrpDCDeniedAuthH32    OBJECT-TYPE
    SYNTAX          Counter32
    MAX-ACCESS      read-only
    STATUS          current
    DESCRIPTION
        "The value of tmnxDAGrpDCDeniedAuthH32 indicates the higher 32 
         bits of the value of tmnxDAGrpDCDeniedAuth."
    ::= { tmnxDAGrpEntry 40 }

tmnxDAGrpDCMinRTTPerPeer    OBJECT-TYPE
    SYNTAX          Counter32
    MAX-ACCESS      read-only
    STATUS          current
    DESCRIPTION
        "The value of tmnxDAGrpDCMinRTTPerPeer indicates the minimum Round
         Trip Time per peer."
    ::= { tmnxDAGrpEntry 41 }

tmnxDAGrpDCAvgRTTPerPeer    OBJECT-TYPE
    SYNTAX          Counter32
    MAX-ACCESS      read-only
    STATUS          current
    DESCRIPTION
        "The value of tmnxDAGrpDCAvgRTTPerPeer indicates the average Round
         Trip Time per peer."
    ::= { tmnxDAGrpEntry 42 }

tmnxDAGrpDCMaxRTTPerPeer    OBJECT-TYPE
    SYNTAX          Counter32
    MAX-ACCESS      read-only
    STATUS          current
    DESCRIPTION
        "The value of tmnxDAGrpDCMaxRTTPerPeer indicates the maximum Round
         Trip Time per peer."
    ::= { tmnxDAGrpEntry 43 }


--
--  DA Group Dns-Server Table
--

tmnxDAGrpDnsSvrTableLastChanged    OBJECT-TYPE
    SYNTAX          TimeStamp
    MAX-ACCESS      read-only
    STATUS          current
    DESCRIPTION
        "The value of tmnxDAGrpDnsSvrTableLastChanged indicates the sysUpTime 
         at the time of the last modification to tmnxDAGrpDnsSvrTable by 
         adding, deleting an entry or change to a writable object in the table.

         If no changes were made to the table since the last re-initialization 
         of the local network management subsystem, then this object contains a 
         zero value."
    ::= { tmnxDAObjs 5 }

tmnxDAGrpDnsSvrTable    OBJECT-TYPE
    SYNTAX          SEQUENCE OF TmnxDAGrpDnsSvrEntry
    MAX-ACCESS      not-accessible
    STATUS          current
    DESCRIPTION
        "The tmnxDAGrpDnsSvrTable has an entry for each DNS server IP address 
         within a Delivery Appliance (DA) group network. A user can provision 
         up to four DNS server IP addresses per DA group."
    ::= { tmnxDAObjs 6 }

tmnxDAGrpDnsSvrEntry    OBJECT-TYPE
    SYNTAX          TmnxDAGrpDnsSvrEntry
    MAX-ACCESS      not-accessible
    STATUS          current
    DESCRIPTION
        "Each row entry represents a DNS server IP address within a DA group 
         network. Entries can be created and deleted by the user. A maximum of 
         four entries can be configured."
    INDEX { 
            tmnxDAGrpName,
            tmnxDAGrpDnsSvrAddrTyp,
            tmnxDAGrpDnsSvrAddress 
    }
    ::= { tmnxDAGrpDnsSvrTable 1 }

TmnxDAGrpDnsSvrEntry ::= SEQUENCE {
        tmnxDAGrpDnsSvrAddrTyp             InetAddressType,
        tmnxDAGrpDnsSvrAddress             InetAddress,
        tmnxDAGrpDnsSvrRowStatus           RowStatus,
        tmnxDAGrpDnsSvrLastChanged         TimeStamp
    }

tmnxDAGrpDnsSvrAddrTyp    OBJECT-TYPE
    SYNTAX          InetAddressType
    MAX-ACCESS      not-accessible
    STATUS          current
    DESCRIPTION
        "The value of tmnxDAGrpDnsSvrAddrTyp specifies the address-type of the 
         DNS server IP address."
    ::= { tmnxDAGrpDnsSvrEntry 1 }

tmnxDAGrpDnsSvrAddress    OBJECT-TYPE
    SYNTAX          InetAddress (SIZE(0|4|16))
    MAX-ACCESS      not-accessible
    STATUS          current
    DESCRIPTION
        "The value of tmnxDAGrpDnsSvrAddress specifies the IP address of a DNS 
         server in a DA group."
    ::= { tmnxDAGrpDnsSvrEntry 2 }

tmnxDAGrpDnsSvrRowStatus    OBJECT-TYPE
    SYNTAX          RowStatus
    MAX-ACCESS      read-create
    STATUS          current
    DESCRIPTION
        "The value of tmnxDAGrpDnsSvrRowStatus specifies the row status of this 
         row in the tmnxDAGrpDnsSvrTable. It is used to create and delete row 
         entries in this table."
    ::= { tmnxDAGrpDnsSvrEntry 3 }

tmnxDAGrpDnsSvrLastChanged    OBJECT-TYPE
    SYNTAX          TimeStamp
    MAX-ACCESS      read-only
    STATUS          current
    DESCRIPTION
        "The value of tmnxDAGrpDnsSvrLastChanged indicates the timestamp of  
         last change to this row in tmnxDAGrpDnsSvrTable."
    ::= { tmnxDAGrpDnsSvrEntry 4 }

--
--  DA Delivery Controller BootStrap Server Table
--

tmnxDADCBtStSvrTableLastChanged    OBJECT-TYPE
    SYNTAX          TimeStamp
    MAX-ACCESS      read-only
    STATUS          current
    DESCRIPTION
        "The value of tmnxDADCBtStSvrTableLastChanged indicates the sysUpTime 
         at the time of the last modification to tmnxDADCBtStSvrTable by adding, 
         deleting an entry or change to a writable object in the table.

         If no changes were made to the table since the last re-initialization 
         of the local network management subsystem, then this object contains a 
         zero value."
    ::= { tmnxDAObjs 7 }

tmnxDADCBtStSvrTable    OBJECT-TYPE
    SYNTAX          SEQUENCE OF TmnxDADCBtStSvrEntry
    MAX-ACCESS      not-accessible
    STATUS          current
    DESCRIPTION
        "The tmnxDADCBtStSvrTable has an entry for each Delivery Controller (DC) 
         bootstrap server. The bootstrap server is used at Delivery Appliance 
         (DA) initialization. The DA downloads the rest of the DC list from one 
         of the bootstrap servers. Multiple bootstrap servers can be specified 
         per DA Group for redundancy purposes."
    ::= { tmnxDAObjs 8 }

tmnxDADCBtStSvrEntry    OBJECT-TYPE
    SYNTAX          TmnxDADCBtStSvrEntry
    MAX-ACCESS      not-accessible
    STATUS          current
    DESCRIPTION
        "Each row entry represents a DC bootstrap server. Entries can be created 
         and deleted by the user."
    INDEX {  
            tmnxDAGrpName,
            tmnxDADCBtStSvrIndex
    }
    ::= { tmnxDADCBtStSvrTable 1 }

TmnxDADCBtStSvrEntry ::= SEQUENCE {
        tmnxDADCBtStSvrIndex               Unsigned32,
        tmnxDADCBtStSvrRowStatus           RowStatus,
        tmnxDADCBtStSvrLastChanged         TimeStamp,
        tmnxDADCBtStSvrAddrType            InetAddressType,
        tmnxDADCBtStSvrAddress             InetAddress
    }

tmnxDADCBtStSvrIndex    OBJECT-TYPE
    SYNTAX          Unsigned32 (0|1..4)
    MAX-ACCESS      not-accessible
    STATUS          current
    DESCRIPTION
        "The value of tmnxDADCBtStSvrIndex specifies a unique value which 
         identifies this bootstrap server entry."
    ::= { tmnxDADCBtStSvrEntry 1 }

tmnxDADCBtStSvrRowStatus    OBJECT-TYPE
    SYNTAX          RowStatus
    MAX-ACCESS      read-create
    STATUS          current
    DESCRIPTION
        "The value of tmnxDADCBtStSvrRowStatus specifies the row status of this 
         row in the tmnxDADCBtStSvrTable. It is used to create and delete row 
         entries in this table.

         The value of tmnxDADCBtStSvrAddrType and tmnxDADCBtStSvrAddress must 
         also be specified when the row is created."
    ::= { tmnxDADCBtStSvrEntry 2 }

tmnxDADCBtStSvrLastChanged    OBJECT-TYPE
    SYNTAX          TimeStamp
    MAX-ACCESS      read-only
    STATUS          current
    DESCRIPTION
        "The value of tmnxDADCBtStSvrLastChanged indicates the timestamp of last
         change to this row in tmnxDADCBtStSvrTable."
    ::= { tmnxDADCBtStSvrEntry 3 }

tmnxDADCBtStSvrAddrType    OBJECT-TYPE
    SYNTAX          InetAddressType
    MAX-ACCESS      read-create
    STATUS          current
    DESCRIPTION
        "The value of tmnxDADCBtStSvrAddrType specifies the type of address 
         represented by tmnxDADCBtStSvrAddress."
    DEFVAL { unknown }
    ::= { tmnxDADCBtStSvrEntry 4 }

tmnxDADCBtStSvrAddress    OBJECT-TYPE
    SYNTAX          InetAddress (SIZE(1..255))
    MAX-ACCESS      read-create
    STATUS          current
    DESCRIPTION
        "The value of tmnxDADCBtStSvrAddress specifies the IP Address or DNS 
         name of the bootstrap server. If the IP address is an IPv4 address, it 
         must be specified in the a.b.c.d dotted-decimal notation. An IPv6 
         address must be specified as defined in RFC1924."
    DEFVAL { ''H }
    ::= { tmnxDADCBtStSvrEntry 5 }

--
--  DA HTTP Table
--

tmnxDAHttpTableLastChanged    OBJECT-TYPE
    SYNTAX          TimeStamp
    MAX-ACCESS      read-only
    STATUS          current
    DESCRIPTION
        "The value of tmnxDAHttpTableLastChanged indicates the sysUpTime at the 
         time of the last modification to tmnxDAHttpTable by adding, deleting an 
         entry or change to a writable object in the table.

         If no changes were made to the table since the last re-initialization 
         of the local network management subsystem, then this object contains a 
         zero value."
    ::= { tmnxDAObjs 9 }

tmnxDAHttpTable    OBJECT-TYPE
    SYNTAX          SEQUENCE OF TmnxDAHttpEntry
    MAX-ACCESS      not-accessible
    STATUS          current
    DESCRIPTION
        "The tmnxDAHttpTable has an entry for each Delivery Appliance (DA) 
         group. Each row entry specifies the HTTP proxy configuration for this 
         DA group."
    ::= { tmnxDAObjs 10 }

tmnxDAHttpEntry    OBJECT-TYPE
    SYNTAX          TmnxDAHttpEntry
    MAX-ACCESS      not-accessible
    STATUS          current
    DESCRIPTION
        "Each row entry represents the HTTP proxy configuration for a DA group. 
         Entries can be created and deleted by the user."
    AUGMENTS  { tmnxDAGrpEntry }
    ::= { tmnxDAHttpTable 1 }

TmnxDAHttpEntry ::= SEQUENCE {
        tmnxDAHttpLastChanged              TimeStamp,
        tmnxDAHttpServerAdminState         TmnxAdminState,
        tmnxDAHttpServerOperState          TmnxOperState,
        tmnxDAHttpServerIdleTimeout        Unsigned32,
        tmnxDAHttpServerViaString          DisplayString,
        tmnxDAHttpServerStrBWInUse         Counter64,
        tmnxDAHttpServerStrBWInUseL32      Counter32,
        tmnxDAHttpServerStrBWInUseH32      Counter32,
        tmnxDAHttpServerXferInProg         Gauge32,
        tmnxDAHttpServerXferCompleted      Counter64,
        tmnxDAHttpServerXferCompletedL32   Counter32,
        tmnxDAHttpServerXferCompletedH32   Counter32,
        tmnxDAHttpServerXferTimeouts       Gauge32,
        tmnxDAHttpServerXferFailed         Gauge32,
        tmnxDAHttpServerValidRequests      Counter64,
        tmnxDAHttpServerValidRequestsL32   Counter32,
        tmnxDAHttpServerValidRequestsH32   Counter32,
        tmnxDAHttpServerInvalidRequests    Gauge32,
        tmnxDAHttpServerMethodNotSuppted   Gauge32,
        tmnxDAHttpServerHostNotSuppted     Gauge32,
        tmnxDAHttpServer1XXCountSent       Counter64,
        tmnxDAHttpServer1XXCountSentL32    Counter32,
        tmnxDAHttpServer1XXCountSentH32    Counter32,
        tmnxDAHttpServer2XXCountSent       Counter64,
        tmnxDAHttpServer2XXCountSentL32    Counter32,
        tmnxDAHttpServer2XXCountSentH32    Counter32,
        tmnxDAHttpServer3XXCountSent       Counter64,
        tmnxDAHttpServer3XXCountSentL32    Counter32,
        tmnxDAHttpServer3XXCountSentH32    Counter32,
        tmnxDAHttpServer4XXCountSent       Counter64,
        tmnxDAHttpServer4XXCountSentL32    Counter32,
        tmnxDAHttpServer4XXCountSentH32    Counter32,
        tmnxDAHttpServer5XXCountSent       Counter64,
        tmnxDAHttpServer5XXCountSentL32    Counter32,
        tmnxDAHttpServer5XXCountSentH32    Counter32,
        tmnxDAHttpIngestAdminState         TmnxAdminState,
        tmnxDAHttpIngestOperState          TmnxOperState,
        tmnxDAHttpIngestIsmLinkName        TNamedItemOrEmpty,
        tmnxDAHttpIngestIdleTimeout        Unsigned32,
        tmnxDAHttpIngestXferInProg         Gauge32,
        tmnxDAHttpIngestXferCompleted      Counter64,
        tmnxDAHttpIngestXferCompletedL32   Counter32,
        tmnxDAHttpIngestXferCompletedH32   Counter32,
        tmnxDAHttpIngestXferTimeouts       Gauge32,
        tmnxDAHttpIngestXferFailed         Gauge32,
        tmnxDAHttpIngest1XXCountRecd       Counter64,
        tmnxDAHttpIngest1XXCountRecdL32    Counter32,
        tmnxDAHttpIngest1XXCountRecdH32    Counter32,
        tmnxDAHttpIngest2XXCountRecd       Counter64,
        tmnxDAHttpIngest2XXCountRecdL32    Counter32,
        tmnxDAHttpIngest2XXCountRecdH32    Counter32,
        tmnxDAHttpIngest3XXCountRecd       Counter64,
        tmnxDAHttpIngest3XXCountRecdL32    Counter32,
        tmnxDAHttpIngest3XXCountRecdH32    Counter32,
        tmnxDAHttpIngest4XXCountRecd       Counter64,
        tmnxDAHttpIngest4XXCountRecdL32    Counter32,
        tmnxDAHttpIngest4XXCountRecdH32    Counter32,
        tmnxDAHttpIngest5XXCountRecd       Counter64,
        tmnxDAHttpIngest5XXCountRecdL32    Counter32,
        tmnxDAHttpIngest5XXCountRecdH32    Counter32      
    }

tmnxDAHttpLastChanged    OBJECT-TYPE
    SYNTAX         TimeStamp
    MAX-ACCESS     read-only
    STATUS         current
    DESCRIPTION
        "The value of tmnxDAHttpLastChanged indicates the timestamp of last
         change to this row in tmnxDAHttpTable."
    ::= { tmnxDAHttpEntry 1 }

tmnxDAHttpServerAdminState    OBJECT-TYPE
    SYNTAX         TmnxAdminState
    MAX-ACCESS     read-create
    STATUS         current
    DESCRIPTION
        "The value of tmnxDAHttpServerAdminState specifies the desired 
         administrative state of the HTTP server's configuration for this DA 
         group."
    DEFVAL { outOfService }
    ::= { tmnxDAHttpEntry 2 }

tmnxDAHttpServerOperState    OBJECT-TYPE
    SYNTAX         TmnxOperState
    MAX-ACCESS     read-only
    STATUS         current
    DESCRIPTION
        "The value of tmnxDAHttpServerOperState indicates the current 
         operational state of the HTTP server's configuration for this DA 
         group."
    ::= { tmnxDAHttpEntry 3 }

tmnxDAHttpServerIdleTimeout    OBJECT-TYPE
    SYNTAX          Unsigned32 (10..65535)
    UNITS           "seconds"
    MAX-ACCESS      read-create
    STATUS          current
    DESCRIPTION
        "The value of tmnxDAHttpServerIdleTimeout specifies the time interval 
         after which the http-server will timeout and close the HTTP connection 
         if there has been no activity on that connection for that time."
    DEFVAL { 120 }
    ::= { tmnxDAHttpEntry 4 }

tmnxDAHttpServerViaString    OBJECT-TYPE
    SYNTAX          DisplayString
    MAX-ACCESS      read-create
    STATUS          current
    DESCRIPTION
        "The value of tmnxDAHttpServerViaString specifies the HTTP via header."
    DEFVAL { ''H }
    ::= { tmnxDAHttpEntry 5 }

tmnxDAHttpServerStrBWInUse    OBJECT-TYPE
    SYNTAX          Counter64
    UNITS           "kbps"
    MAX-ACCESS      read-only
    STATUS          current
    DESCRIPTION
        "The value of tmnxDAHttpServerStrBWInUse indicates the amount of 
         bandwidth that is used by the HTTP server while streaming content.

         This object follows the behavior of a gauge64 in that its value can 
         increase or decrease with time."
    ::= { tmnxDAHttpEntry 6 }

tmnxDAHttpServerStrBWInUseL32    OBJECT-TYPE
    SYNTAX          Counter32
    UNITS           "kbps"
    MAX-ACCESS      read-only
    STATUS          current
    DESCRIPTION
        "The value of tmnxDAHttpServerStrBWInUseL32 indicates the lower 32 
         bits of the value of tmnxDAHttpServerStrBWInUse."
    ::= { tmnxDAHttpEntry 7 }

tmnxDAHttpServerStrBWInUseH32    OBJECT-TYPE
    SYNTAX          Counter32
    UNITS           "kbps"
    MAX-ACCESS      read-only
    STATUS          current
    DESCRIPTION
        "The value of tmnxDAHttpServerStrBWInUseH32 indicates the higher 32 
         bits of the value of tmnxDAHttpServerStrBWInUse."
    ::= { tmnxDAHttpEntry 8 }

tmnxDAHttpServerXferInProg    OBJECT-TYPE
    SYNTAX          Gauge32
    MAX-ACCESS      read-only
    STATUS          current
    DESCRIPTION
        "The value of tmnxDAHttpServerXferInProg indicates the number of 
         HTTP transfers that are in progress by the HTTP server."
    ::= { tmnxDAHttpEntry 9 }

tmnxDAHttpServerXferCompleted    OBJECT-TYPE
    SYNTAX          Counter64
    MAX-ACCESS      read-only
    STATUS          current
    DESCRIPTION
        "The value of tmnxDAHttpServerXferCompleted indicates the number of HTTP 
         transfers that have been completed by the HTTP server."
    ::= { tmnxDAHttpEntry 10 }

tmnxDAHttpServerXferCompletedL32    OBJECT-TYPE
    SYNTAX          Counter32
    MAX-ACCESS      read-only
    STATUS          current
    DESCRIPTION
        "The value of tmnxDAHttpServerXferCompletedL32 indicates the lower 32 
         bits of the value of tmnxDAHttpServerXferCompleted."
    ::= { tmnxDAHttpEntry 11 }

tmnxDAHttpServerXferCompletedH32    OBJECT-TYPE
    SYNTAX          Counter32
    MAX-ACCESS      read-only
    STATUS          current
    DESCRIPTION
        "The value of tmnxDAHttpServerXferCompletedH32 indicates the higher 32 
         bits of the value of tmnxDAHttpServerXferCompleted."
    ::= { tmnxDAHttpEntry 12 }

tmnxDAHttpServerXferTimeouts    OBJECT-TYPE
    SYNTAX          Gauge32
    MAX-ACCESS      read-only
    STATUS          current
    DESCRIPTION
        "The value of tmnxDAHttpServerXferTimeouts indicates the number of 
         HTTP server sessions that timed out due to inactivity."
    ::= { tmnxDAHttpEntry 13 }

tmnxDAHttpServerXferFailed    OBJECT-TYPE
    SYNTAX          Gauge32
    MAX-ACCESS      read-only
    STATUS          current
    DESCRIPTION
        "The value of tmnxDAHttpServerXferFailed indicates the number of 
         HTTP transfers that failed when the HTTP server was transferring 
         HTTP content."
    ::= { tmnxDAHttpEntry 14 }

tmnxDAHttpServerValidRequests    OBJECT-TYPE
    SYNTAX          Counter64
    MAX-ACCESS      read-only
    STATUS          current
    DESCRIPTION
        "The value of tmnxDAHttpServerValidRequests indicates the number of 
         valid HTTP requests that were received by the HTTP server."
    ::= { tmnxDAHttpEntry 15 }

tmnxDAHttpServerValidRequestsL32    OBJECT-TYPE
    SYNTAX          Counter32
    MAX-ACCESS      read-only
    STATUS          current
    DESCRIPTION
        "The value of tmnxDAHttpServerValidRequestsL32 indicates the lower 32 
         bits of the value of tmnxDAHttpServerValidRequests."
    ::= { tmnxDAHttpEntry 16 }

tmnxDAHttpServerValidRequestsH32    OBJECT-TYPE
    SYNTAX          Counter32
    MAX-ACCESS      read-only
    STATUS          current
    DESCRIPTION
        "The value of tmnxDAHttpServerValidRequestsH32 indicates the higher 32 
         bits of the value of tmnxDAHttpServerValidRequests."
    ::= { tmnxDAHttpEntry 17 }

tmnxDAHttpServerInvalidRequests    OBJECT-TYPE
    SYNTAX          Gauge32
    MAX-ACCESS      read-only
    STATUS          current
    DESCRIPTION
        "The value of tmnxDAHttpServerInvalidRequests indicates the number of 
         invalid HTTP requests that were received by the HTTP server."
    ::= { tmnxDAHttpEntry 18 }

tmnxDAHttpServerMethodNotSuppted    OBJECT-TYPE
    SYNTAX          Gauge32
    MAX-ACCESS      read-only
    STATUS          current
    DESCRIPTION
        "The value of  tmnxDAHttpServerMethodNotSuppted indicates the number of 
         times the HTTP server rejected the request because the requested 
         method is not supported."
    ::= { tmnxDAHttpEntry 19 }

tmnxDAHttpServerHostNotSuppted    OBJECT-TYPE
    SYNTAX          Gauge32
    MAX-ACCESS      read-only
    STATUS          current
    DESCRIPTION
        "The value of tmnxDAHttpServerHostNotSuppted indicates the number of 
         times the HTTP server rejected the request because the requested 
         host is not supported."
    ::= { tmnxDAHttpEntry 20 }

tmnxDAHttpServer1XXCountSent    OBJECT-TYPE
    SYNTAX          Counter64
    MAX-ACCESS      read-only
    STATUS          current
    DESCRIPTION
        "The value of tmnxDAHttpServer1XXCountSent indicates the count of type 
         1XX error responses sent by the HTTP Server."
    ::= { tmnxDAHttpEntry 21 }

tmnxDAHttpServer1XXCountSentL32    OBJECT-TYPE
    SYNTAX          Counter32
    MAX-ACCESS      read-only
    STATUS          current
    DESCRIPTION
        "The value of tmnxDAHttpServer1XXCountSentL32 indicates the lower 32 
         bits of the value of tmnxDAHttpServer1XXCountSent."
    ::= { tmnxDAHttpEntry 22 }

tmnxDAHttpServer1XXCountSentH32    OBJECT-TYPE
    SYNTAX          Counter32
    MAX-ACCESS      read-only
    STATUS          current
    DESCRIPTION
        "The value of tmnxDAHttpServer1XXCountSentH32 indicates the higher 32 
         bits of the value of tmnxDAHttpServer1XXCountSent."
    ::= { tmnxDAHttpEntry 23 }

tmnxDAHttpServer2XXCountSent    OBJECT-TYPE
    SYNTAX          Counter64
    MAX-ACCESS      read-only
    STATUS          current
    DESCRIPTION
        "The value of tmnxDAHttpServer2XXCountSent indicates the count of type 
         2XX error responses sent by the HTTP Server."
    ::= { tmnxDAHttpEntry 24 }

tmnxDAHttpServer2XXCountSentL32    OBJECT-TYPE
    SYNTAX          Counter32
    MAX-ACCESS      read-only
    STATUS          current
    DESCRIPTION
        "The value of tmnxDAHttpServer2XXCountSentL32 indicates the lower 32 
         bits of the value of tmnxDAHttpServer2XXCountSent."
    ::= { tmnxDAHttpEntry 25 }

tmnxDAHttpServer2XXCountSentH32    OBJECT-TYPE
    SYNTAX          Counter32
    MAX-ACCESS      read-only
    STATUS          current
    DESCRIPTION
        "The value of tmnxDAHttpServer2XXCountSentH32 indicates the higher 32 
         bits of the value of tmnxDAHttpServer2XXCountSent."
    ::= { tmnxDAHttpEntry 26 }

tmnxDAHttpServer3XXCountSent    OBJECT-TYPE
    SYNTAX          Counter64
    MAX-ACCESS      read-only
    STATUS          current
    DESCRIPTION
        "The value of tmnxDAHttpServer3XXCountSent indicates the count of type 
         3XX error responses sent by the HTTP Server."
    ::= { tmnxDAHttpEntry 27 }

tmnxDAHttpServer3XXCountSentL32    OBJECT-TYPE
    SYNTAX          Counter32
    MAX-ACCESS      read-only
    STATUS          current
    DESCRIPTION
        "The value of tmnxDAHttpServer3XXCountSentL32 indicates the lower 32 
         bits of the value of tmnxDAHttpServer3XXCountSent."
    ::= { tmnxDAHttpEntry 28 }

tmnxDAHttpServer3XXCountSentH32    OBJECT-TYPE
    SYNTAX          Counter32
    MAX-ACCESS      read-only
    STATUS          current
    DESCRIPTION
        "The value of tmnxDAHttpServer3XXCountSentH32 indicates the higher 32 
         bits of the value of tmnxDAHttpServer3XXCountSent."
    ::= { tmnxDAHttpEntry 29 }

tmnxDAHttpServer4XXCountSent    OBJECT-TYPE
    SYNTAX          Counter64
    MAX-ACCESS      read-only
    STATUS          current
    DESCRIPTION
        "The value of tmnxDAHttpServer4XXCountSent indicates the count of type 
         4XX error responses sent by the HTTP Server."
    ::= { tmnxDAHttpEntry 30 }

tmnxDAHttpServer4XXCountSentL32    OBJECT-TYPE
    SYNTAX          Counter32
    MAX-ACCESS      read-only
    STATUS          current
    DESCRIPTION
        "The value of tmnxDAHttpServer4XXCountSentL32 indicates the lower 32 
         bits of the value of tmnxDAHttpServer4XXCountSent."
    ::= { tmnxDAHttpEntry 31 }

tmnxDAHttpServer4XXCountSentH32    OBJECT-TYPE
    SYNTAX          Counter32
    MAX-ACCESS      read-only
    STATUS          current
    DESCRIPTION
        "The value of tmnxDAHttpServer4XXCountSentH32 indicates the higher 32 
         bits of the value of tmnxDAHttpServer4XXCountSent."
    ::= { tmnxDAHttpEntry 32 }

tmnxDAHttpServer5XXCountSent    OBJECT-TYPE
    SYNTAX          Counter64
    MAX-ACCESS      read-only
    STATUS          current
    DESCRIPTION
        "The value of tmnxDAHttpServer5XXCountSent indicates the count of type 
         5XX error responses sent by the HTTP Server."
    ::= { tmnxDAHttpEntry 33 }

tmnxDAHttpServer5XXCountSentL32    OBJECT-TYPE
    SYNTAX          Counter32
    MAX-ACCESS      read-only
    STATUS          current
    DESCRIPTION
        "The value of tmnxDAHttpServer5XXCountSentL32 indicates the lower 32 
         bits of the value of tmnxDAHttpServer5XXCountSent."
    ::= { tmnxDAHttpEntry 34 }

tmnxDAHttpServer5XXCountSentH32    OBJECT-TYPE
    SYNTAX          Counter32
    MAX-ACCESS      read-only
    STATUS          current
    DESCRIPTION
        "The value of tmnxDAHttpServer5XXCountSentH32 indicates the higher 32 
         bits of the value of tmnxDAHttpServer5XXCountSent."
    ::= { tmnxDAHttpEntry 35 }

tmnxDAHttpIngestAdminState    OBJECT-TYPE
    SYNTAX          TmnxAdminState
    MAX-ACCESS      read-create
    STATUS          current
    DESCRIPTION
        "The value of tmnxDAHttpIngestAdminState specifies the desired 
         administrative state of the HTTP proxy's ingest configuration for this 
         DA group."
    DEFVAL { outOfService }
    ::= { tmnxDAHttpEntry 36 }

tmnxDAHttpIngestOperState    OBJECT-TYPE
    SYNTAX          TmnxOperState
    MAX-ACCESS      read-only
    STATUS          current
    DESCRIPTION
        "The value of tmnxDAHttpIngestOperState indicates the current 
         operational state of the HTTP proxy's ingest configuration for this 
         DA group."
    ::= { tmnxDAHttpEntry 37 }

tmnxDAHttpIngestIsmLinkName    OBJECT-TYPE
    SYNTAX          TNamedItemOrEmpty
    MAX-ACCESS      read-create
    STATUS          current
    DESCRIPTION
        "The value of tmnxDAHttpIngestIsmLinkName specifies the Integrated 
         Services Module (ISM) link name used for HTTP ingest connections to 
         the origin server. The ISM link is an IP interface in the DA group on 
         the ISM. The ISM link must already be configured in the DA group 
         before it is assigned to this object."
    DEFVAL { ''H }
    ::= { tmnxDAHttpEntry 38 }

tmnxDAHttpIngestIdleTimeout    OBJECT-TYPE
    SYNTAX          Unsigned32 (10..65535)
    UNITS           "seconds"
    MAX-ACCESS      read-create
    STATUS          current
    DESCRIPTION
        "The value of tmnxDAHttpIngestIdleTimeout specifies the time interval 
         after which the HTTP proxy will timeout and close the HTTP connection 
         if there has been no activity from the origin server on that 
         connection for that time."
    DEFVAL { 120 }
    ::= { tmnxDAHttpEntry 39 }

tmnxDAHttpIngestXferInProg    OBJECT-TYPE
    SYNTAX          Gauge32
    MAX-ACCESS      read-only
    STATUS          current
    DESCRIPTION
        "The value of tmnxDAHttpIngestXferInProg indicates the number of 
         HTTP ingest transfers in progress from the origin server to the HTTP 
         proxy."
    ::= { tmnxDAHttpEntry 40 }

tmnxDAHttpIngestXferCompleted    OBJECT-TYPE
    SYNTAX          Counter64
    MAX-ACCESS      read-only
    STATUS          current
    DESCRIPTION
        "The value of tmnxDAHttpIngestXferCompleted indicates the number of HTTP 
         ingest transfers completed from the origin server to the HTTP proxy."
    ::= { tmnxDAHttpEntry 41 }

tmnxDAHttpIngestXferCompletedL32    OBJECT-TYPE
    SYNTAX          Counter32
    MAX-ACCESS      read-only
    STATUS          current
    DESCRIPTION
        "The value of tmnxDAHttpIngestXferCompletedL32 indicates the lower 32 
         bits of the value of tmnxDAHttpIngestXferCompleted."
    ::= { tmnxDAHttpEntry 42 }

tmnxDAHttpIngestXferCompletedH32    OBJECT-TYPE
    SYNTAX          Counter32
    MAX-ACCESS      read-only
    STATUS          current
    DESCRIPTION
        "The value of tmnxDAHttpIngestXferCompletedH32 indicates the higher 32 
         bits of the value of tmnxDAHttpIngestXferCompleted."
    ::= { tmnxDAHttpEntry 43 }

tmnxDAHttpIngestXferTimeouts    OBJECT-TYPE
    SYNTAX          Gauge32
    MAX-ACCESS      read-only
    STATUS          current
    DESCRIPTION
        "The value of tmnxDAHttpIngestXferTimeouts indicates the number of 
         HTTP ingest transfers from the origin server to the HTTP proxy that 
         timed-out."
    ::= { tmnxDAHttpEntry 44 }

tmnxDAHttpIngestXferFailed    OBJECT-TYPE
    SYNTAX          Gauge32
    MAX-ACCESS      read-only
    STATUS          current
    DESCRIPTION
        "The value of tmnxDAHttpIngestXferFailed indicates the number of 
         HTTP ingest transfers that failed from the origin server to the HTTP
         proxy."
    ::= { tmnxDAHttpEntry 45 }

tmnxDAHttpIngest1XXCountRecd    OBJECT-TYPE
    SYNTAX          Counter64
    MAX-ACCESS      read-only
    STATUS          current
    DESCRIPTION
        "The value of tmnxDAHttpIngest1XXCountRecd indicates the count of type  
         1XX errors that were received by the HTTP proxy from the origin 
         server."
    ::= { tmnxDAHttpEntry 46 }

tmnxDAHttpIngest1XXCountRecdL32    OBJECT-TYPE
    SYNTAX          Counter32
    MAX-ACCESS      read-only
    STATUS          current
    DESCRIPTION
        "The value of tmnxDAHttpIngest1XXCountRecdL32 indicates the lower 32 
         bits of the value of tmnxDAHttpIngest1XXCountRecd."
    ::= { tmnxDAHttpEntry 47 }

tmnxDAHttpIngest1XXCountRecdH32    OBJECT-TYPE
    SYNTAX          Counter32
    MAX-ACCESS      read-only
    STATUS          current
    DESCRIPTION
        "The value of tmnxDAHttpIngest1XXCountRecdH32 indicates the higher 32 
         bits of the value of tmnxDAHttpIngest1XXCountRecd."
    ::= { tmnxDAHttpEntry 48 }

tmnxDAHttpIngest2XXCountRecd    OBJECT-TYPE
    SYNTAX          Counter64
    MAX-ACCESS      read-only
    STATUS          current
    DESCRIPTION
        "The value of tmnxDAHttpIngest2XXCountRecd indicates the count of type  
         2XX errors that were received by the HTTP proxy from the origin 
         server."
    ::= { tmnxDAHttpEntry 49 }

tmnxDAHttpIngest2XXCountRecdL32    OBJECT-TYPE
    SYNTAX          Counter32
    MAX-ACCESS      read-only
    STATUS          current
    DESCRIPTION
        "The value of tmnxDAHttpIngest2XXCountRecdL32 indicates the lower 32 
         bits of the value of tmnxDAHttpIngest2XXCountRecd."
    ::= { tmnxDAHttpEntry 50 }

tmnxDAHttpIngest2XXCountRecdH32    OBJECT-TYPE
    SYNTAX          Counter32
    MAX-ACCESS      read-only
    STATUS          current
    DESCRIPTION
        "The value of tmnxDAHttpIngest2XXCountRecdH32 indicates the higher 32 
         bits of the value of tmnxDAHttpIngest2XXCountRecd."
    ::= { tmnxDAHttpEntry 51 }

tmnxDAHttpIngest3XXCountRecd    OBJECT-TYPE
    SYNTAX          Counter64
    MAX-ACCESS      read-only
    STATUS          current
    DESCRIPTION
        "The value of tmnxDAHttpIngest3XXCountRecd indicates the count of type  
         3XX errors that were received by the HTTP proxy from the origin 
         server."
    ::= { tmnxDAHttpEntry 52 }

tmnxDAHttpIngest3XXCountRecdL32    OBJECT-TYPE
    SYNTAX          Counter32
    MAX-ACCESS      read-only
    STATUS          current
    DESCRIPTION
        "The value of tmnxDAHttpIngest3XXCountRecdL32 indicates the lower 32 
         bits of the value of tmnxDAHttpIngest3XXCountRecd."
    ::= { tmnxDAHttpEntry 53 }

tmnxDAHttpIngest3XXCountRecdH32    OBJECT-TYPE
    SYNTAX          Counter32
    MAX-ACCESS      read-only
    STATUS          current
    DESCRIPTION
        "The value of tmnxDAHttpIngest3XXCountRecdH32 indicates the higher 32 
         bits of the value of tmnxDAHttpIngest3XXCountRecd."
    ::= { tmnxDAHttpEntry 54 }

tmnxDAHttpIngest4XXCountRecd    OBJECT-TYPE
    SYNTAX          Counter64
    MAX-ACCESS      read-only
    STATUS          current
    DESCRIPTION
        "The value of tmnxDAHttpIngest4XXCountRecd indicates the count of type  
         4XX errors that were received by the HTTP proxy from the origin 
         server."
    ::= { tmnxDAHttpEntry 55 }

tmnxDAHttpIngest4XXCountRecdL32    OBJECT-TYPE
    SYNTAX          Counter32
    MAX-ACCESS      read-only
    STATUS          current
    DESCRIPTION
        "The value of tmnxDAHttpIngest4XXCountRecdL32 indicates the lower 32 
         bits of the value of tmnxDAHttpIngest4XXCountRecd."
    ::= { tmnxDAHttpEntry 56 }

tmnxDAHttpIngest4XXCountRecdH32    OBJECT-TYPE
    SYNTAX          Counter32
    MAX-ACCESS      read-only
    STATUS          current
    DESCRIPTION
        "The value of tmnxDAHttpIngest4XXCountRecdH32 indicates the higher 32 
         bits of the value of tmnxDAHttpIngest4XXCountRecd."
    ::= { tmnxDAHttpEntry 57 }

tmnxDAHttpIngest5XXCountRecd    OBJECT-TYPE
    SYNTAX          Counter64
    MAX-ACCESS      read-only
    STATUS          current
    DESCRIPTION
        "The value of tmnxDAHttpIngest5XXCountRecd indicates the count of type  
         5XX errors that were received by the HTTP proxy from the origin 
         server."
    ::= { tmnxDAHttpEntry 58 }

tmnxDAHttpIngest5XXCountRecdL32    OBJECT-TYPE
    SYNTAX          Counter32
    MAX-ACCESS      read-only
    STATUS          current
    DESCRIPTION
        "The value of tmnxDAHttpIngest5XXCountRecdL32 indicates the lower 32 
         bits of the value of tmnxDAHttpIngest5XXCountRecd."
    ::= { tmnxDAHttpEntry 59 }

tmnxDAHttpIngest5XXCountRecdH32    OBJECT-TYPE
    SYNTAX          Counter32
    MAX-ACCESS      read-only
    STATUS          current
    DESCRIPTION
        "The value of tmnxDAHttpIngest5XXCountRecdH32 indicates the higher 32 
         bits of the value of tmnxDAHttpIngest5XXCountRecd."
    ::= { tmnxDAHttpEntry 60 }

--
--  DA ISM Link Table
--

tmnxDAIsmLinkTableLastChanged    OBJECT-TYPE
    SYNTAX          TimeStamp
    MAX-ACCESS      read-only
    STATUS          current
    DESCRIPTION
        "The value of tmnxDAIsmLinkTableLastChanged indicates the sysUpTime at 
         the time of the last modification to tmnxDAIsmLinkTable by adding, 
         deleting an entry or change to a writable object in the table.

         If no changes were made to the table since the last re-initialization 
         of the local network management subsystem, then this object contains a 
         zero value."
    ::= { tmnxDAObjs 11 }

tmnxDAIsmLinkTable    OBJECT-TYPE
    SYNTAX          SEQUENCE OF TmnxDAIsmLinkEntry
    MAX-ACCESS      not-accessible
    STATUS          current
    DESCRIPTION
        "The tmnxDAIsmLinkTable has an entry for each ISM-link within a group 
         configured in the Delivery Appliance (DA). Multiple IP ISM-links in 
         the same group are assumed to belong to the same network. IP ISM-links 
         in different groups are currently assumed to belong to different 
         networks."
    ::= { tmnxDAObjs 12 }

tmnxDAIsmLinkEntry    OBJECT-TYPE
    SYNTAX          TmnxDAIsmLinkEntry
    MAX-ACCESS      not-accessible
    STATUS          current
    DESCRIPTION
        "Each row entry represents an Integrated Services 
         Module (ISM) link within a group configured in the Delivery Appliance
        (DA). Entries can be created and deleted by the user."
    INDEX {  
            tmnxDAGrpName,
            tmnxDAIsmLinkName
    }
    ::= { tmnxDAIsmLinkTable 1 }

TmnxDAIsmLinkEntry ::= SEQUENCE {
        tmnxDAIsmLinkName                  TNamedItem,
        tmnxDAIsmLinkRowStatus             RowStatus,
        tmnxDAIsmLinkLastChanged           TimeStamp,
        tmnxDAIsmLinkAddrType              InetAddressType,
        tmnxDAIsmLinkAddress               InetAddress,
        tmnxDAIsmLinkAddrPrefixLength      InetAddressPrefixLength,
        tmnxDAIsmLinkDescription           TItemDescription,
        tmnxDAIsmLinkHttpd                 TruthValue,
        tmnxDAIsmLinkHttpListenPort        InetPortNumber,
        tmnxDAIsmLinkIpMtu                 Unsigned32,
        tmnxDAIsmLinkQtag                  Unsigned32,
        tmnxDAIsmLinkMacAddress            MacAddress,
        tmnxDAIsmLinkAdminState            TmnxAdminState,
        tmnxDAIsmLinkOperState             TmnxOperState,
        tmnxDAIsmLinkBindings              BITS
    }

tmnxDAIsmLinkName    OBJECT-TYPE 
    SYNTAX          TNamedItem
    MAX-ACCESS      not-accessible
    STATUS          current
    DESCRIPTION 
        "The value of tmnxDAIsmLinkName specifies the ISM-link name within a 
         group in the DA."
    ::= { tmnxDAIsmLinkEntry 1 }

tmnxDAIsmLinkRowStatus    OBJECT-TYPE
    SYNTAX          RowStatus
    MAX-ACCESS      read-create
    STATUS          current
    DESCRIPTION
        "The value of tmnxDAIsmLinkRowStatus specifies the row status of this 
         row in the tmnxDAIsmLinkTable. It is used to create and delete row 
         entries in this table."
    ::= { tmnxDAIsmLinkEntry 2 }

tmnxDAIsmLinkLastChanged    OBJECT-TYPE
    SYNTAX          TimeStamp
    MAX-ACCESS      read-only
    STATUS          current
    DESCRIPTION
        "The value of tmnxDAIsmLinkLastChanged indicates the timestamp of last
         change to this row in tmnxDAIsmLinkTable."
    ::= { tmnxDAIsmLinkEntry 3 }

tmnxDAIsmLinkAddrType    OBJECT-TYPE
    SYNTAX          InetAddressType
    MAX-ACCESS      read-create
    STATUS          current
    DESCRIPTION
        "The value of tmnxDAIsmLinkAddrType specifies the address-type of the 
         ISM-link address used in the DA group."
    DEFVAL { unknown }
    ::= { tmnxDAIsmLinkEntry 4 }

tmnxDAIsmLinkAddress    OBJECT-TYPE
    SYNTAX          InetAddress (SIZE(0|4|16))
    MAX-ACCESS      read-create
    STATUS          current
    DESCRIPTION
        "The value of tmnxDAIsmLinkAddress specifies the IP address used for the 
         ISM-link address in the DA group."
    DEFVAL { ''H }
    ::= { tmnxDAIsmLinkEntry 5 }

tmnxDAIsmLinkAddrPrefixLength    OBJECT-TYPE 
    SYNTAX          InetAddressPrefixLength
    MAX-ACCESS      read-create
    STATUS          current
    DESCRIPTION 
        "The value of tmnxDAIsmLinkAddrPrefixLength specifies the prefix length 
         of the ISM-link address used in the DA group."
    DEFVAL { 0 }
    ::= { tmnxDAIsmLinkEntry 6 }

tmnxDAIsmLinkDescription    OBJECT-TYPE 
    SYNTAX          TItemDescription
    MAX-ACCESS      read-create
    STATUS          current
    DESCRIPTION 
        "The value of tmnxDAIsmLinkDescription specifies the user provided
         description string for this ISM-link within the DA group."
    DEFVAL { ''H }
    ::= { tmnxDAIsmLinkEntry 7 }

tmnxDAIsmLinkHttpd    OBJECT-TYPE
    SYNTAX          TruthValue
    MAX-ACCESS      read-create
    STATUS          current
    DESCRIPTION
        "The value of tmnxDAIsmLinkHttpd specifies if the HTTP server should be 
         enabled on this ISM-link."
    DEFVAL { true }
    ::= { tmnxDAIsmLinkEntry 8 }

tmnxDAIsmLinkHttpListenPort    OBJECT-TYPE
    SYNTAX          InetPortNumber
    MAX-ACCESS      read-create
    STATUS          current
    DESCRIPTION
        "The value of tmnxDAIsmLinkHttpListenPort specifies the HTTP listner 
         port number on this ISM-link if HTTPD is enabled on this ISM-link."
    DEFVAL { 80 }
    ::= { tmnxDAIsmLinkEntry 9 }

tmnxDAIsmLinkIpMtu    OBJECT-TYPE 
    SYNTAX          Unsigned32 (512..9212)
    MAX-ACCESS      read-create
    STATUS          current
    DESCRIPTION 
        "The value of tmnxDAIsmLinkIpMtu specifies the Maximum Transmission Unit
         (MTU) value for this ISM-link within the DA group."
    DEFVAL { 1500 }
    ::= { tmnxDAIsmLinkEntry 10 }

tmnxDAIsmLinkQtag    OBJECT-TYPE 
    SYNTAX          Unsigned32 (0..4095)
    MAX-ACCESS      read-create
    STATUS          current
    DESCRIPTION 
        "The value of tmnxDAIsmLinkQtag specifies the ISM-link identifier for 
         this ISM-link within the DA group."
    DEFVAL { 0 }
    ::= { tmnxDAIsmLinkEntry 11 }

tmnxDAIsmLinkMacAddress    OBJECT-TYPE
    SYNTAX          MacAddress
    MAX-ACCESS      read-create
    STATUS          current
    DESCRIPTION
        "The value of the object tmnxDAIsmLinkMacAddress specifies the MAC 
         address for this ISM-link within the DA group. By default the system 
         will use an internally generated MAC address."
    DEFVAL { '000000000000'H }
    ::= { tmnxDAIsmLinkEntry 12 }

tmnxDAIsmLinkAdminState    OBJECT-TYPE
    SYNTAX          TmnxAdminState
    MAX-ACCESS      read-create
    STATUS          current
    DESCRIPTION
        "The value of tmnxDAIsmLinkAdminState specifies the desired 
         administrative state of the ISM-link used in the DA group."
    DEFVAL { outOfService }
    ::= { tmnxDAIsmLinkEntry 13 }

tmnxDAIsmLinkOperState    OBJECT-TYPE
    SYNTAX          TmnxOperState
    MAX-ACCESS      read-only
    STATUS          current
    DESCRIPTION
        "The value of tmnxDAIsmLinkOperState indicates the current operational 
         state of the ISM-link used in the DA group."
    ::= { tmnxDAIsmLinkEntry 14 }

tmnxDAIsmLinkBindings    OBJECT-TYPE
    SYNTAX BITS {                    
                    deliveryController  (0),
                    httpIngest          (1),
                    dnsClient           (2)
                }
    MAX-ACCESS      read-only
    STATUS          current
    DESCRIPTION
        "The value of tmnxDAIsmLinkBindings indicates whether the ism-link is 
         configured on the delivery-controller, http-ingest and dns-client. If
         the bit for an entity is set, it indicates that the ism-link has been 
         configured on that entity. If the bit for an entity is unset it 
         indicates that the ism-link is not configured on the entity."
    ::= { tmnxDAIsmLinkEntry 15 }

--
--  DA ISM-link Arp Table
--

tmnxDAIsmLinkArpTableLastChanged    OBJECT-TYPE
    SYNTAX          TimeStamp
    MAX-ACCESS      read-only
    STATUS          current
    DESCRIPTION
        "The value of tmnxDAIsmLinkArpTableLastChanged indicates the sysUpTime 
         at the time of the last modification to tmnxDAIsmLinkArpTable by 
         adding, deleting an entry or change to a writable object in the table.

         If no changes were made to the table since the last re-initialization 
         of the local network management subsystem, then this object contains a 
         zero value."
    ::= { tmnxDAObjs 13 }

tmnxDAIsmLinkArpTable    OBJECT-TYPE
    SYNTAX          SEQUENCE OF TmnxDAIsmLinkArpEntry
    MAX-ACCESS      not-accessible
    STATUS          current
    DESCRIPTION
        "The tmnxDAIsmLinkArpTable has an entry for each ARP address of an 
         interface within a Delivery Appliance (DA) group."
    ::= { tmnxDAObjs 14 }

tmnxDAIsmLinkArpEntry    OBJECT-TYPE
    SYNTAX          TmnxDAIsmLinkArpEntry
    MAX-ACCESS      not-accessible
    STATUS          current
    DESCRIPTION
        "Each row entry represents an ARP address of an interface within a DA 
         group. Entries can be created and deleted by the user."
    INDEX {  
            tmnxDAGrpName,
            tmnxDAIsmLinkName,
            tmnxDAIsmLinkArpAddrType,
            tmnxDAIsmLinkArpAddress
    }
    ::= { tmnxDAIsmLinkArpTable 1 }

TmnxDAIsmLinkArpEntry ::= SEQUENCE {
        tmnxDAIsmLinkArpAddrType           InetAddressType,
        tmnxDAIsmLinkArpAddress            InetAddress,
        tmnxDAIsmLinkArpRowStatus          RowStatus,
        tmnxDAIsmLinkArpLastChanged        TimeStamp,
        tmnxDAIsmLinkArpMacAddr            MacAddress,
        tmnxDAIsmLinkArpType               TruthValue
    }

tmnxDAIsmLinkArpAddrType    OBJECT-TYPE
    SYNTAX          InetAddressType
    MAX-ACCESS      not-accessible
    STATUS          current
    DESCRIPTION
        "The value of tmnxDAIsmLinkArpAddrType specifies the ARP address-type of 
         the interface used in the DA group."
    ::= { tmnxDAIsmLinkArpEntry 1 }

tmnxDAIsmLinkArpAddress    OBJECT-TYPE
    SYNTAX          InetAddress (SIZE(0|4|16))
    MAX-ACCESS      not-accessible
    STATUS          current
    DESCRIPTION
        "The value of tmnxDAIsmLinkArpAddress specifies the ARP address of the
         interface used in the DA group."
    ::= { tmnxDAIsmLinkArpEntry 2 }

tmnxDAIsmLinkArpRowStatus    OBJECT-TYPE
    SYNTAX          RowStatus
    MAX-ACCESS      read-create
    STATUS          current
    DESCRIPTION
        "The value of tmnxDAIsmLinkArpRowStatus specifies the row status of this 
         row in the tmnxDAIsmLinkArpTable. It is used to create and delete row 
         entries in this table."
    ::= { tmnxDAIsmLinkArpEntry 3 }

tmnxDAIsmLinkArpLastChanged    OBJECT-TYPE
    SYNTAX          TimeStamp
    MAX-ACCESS      read-only
    STATUS          current
    DESCRIPTION
        "The value of tmnxDAIsmLinkArpLastChanged indicates the timestamp of 
         last change to this row in tmnxDAIsmLinkArpTable."
    ::= { tmnxDAIsmLinkArpEntry 4 }

tmnxDAIsmLinkArpMacAddr    OBJECT-TYPE
    SYNTAX          MacAddress
    MAX-ACCESS      read-create
    STATUS          current
    DESCRIPTION
        "The value of the object tmnxDAIsmLinkArpMacAddr specifies the MAC 
         address for this ARP interface within the DA group."
    DEFVAL { '000000000000'H }
    ::= { tmnxDAIsmLinkArpEntry 5 }

tmnxDAIsmLinkArpType    OBJECT-TYPE
    SYNTAX          TruthValue
    MAX-ACCESS      read-only
    STATUS          current
    DESCRIPTION
        "The value of the object tmnxDAIsmLinkArpType indicates if the ARP entry 
         is static or dynamic. When the value of tmnxDAIsmLinkArpType is  'true' 
         the ARP entry is dynamic and when it is  'false' the ARP entry is 
         static."
    ::= { tmnxDAIsmLinkArpEntry 6 }

--
--  DA Static Route Table
--

tmnxDAStRouteTableLastChanged    OBJECT-TYPE
    SYNTAX          TimeStamp
    MAX-ACCESS      read-only
    STATUS          current
    DESCRIPTION
        "The value of tmnxDAStRouteTableLastChanged indicates the sysUpTime at 
         the time of the last modification to tmnxDAStRouteTable by adding, 
         deleting an entry or change to a writable object in the table.

         If no changes were made to the table since the last re-initialization 
         of the local network management subsystem, then this object contains a 
         zero value."
    ::= { tmnxDAObjs 15 }

tmnxDAStRouteTable    OBJECT-TYPE
    SYNTAX          SEQUENCE OF TmnxDAStRouteEntry
    MAX-ACCESS      not-accessible
    STATUS          current
    DESCRIPTION
        "The tmnxDAStRouteTable has an entry for each static-route address of an 
         interface within a Delivery Appliance (DA) group."
    ::= { tmnxDAObjs 16 }

tmnxDAStRouteEntry  OBJECT-TYPE
    SYNTAX          TmnxDAStRouteEntry
    MAX-ACCESS      not-accessible
    STATUS          current
    DESCRIPTION
        "Each row entry represents a static-route address of an interface within 
         a DA group. Entries can be created and deleted by the user."
    INDEX {  
            tmnxDAGrpName,
            tmnxDAStRouteAddrType,
            tmnxDAStRouteAddress,
            tmnxDAStRoutePrefixLength,
            tmnxDAStRouteNextHopAddrType,
            tmnxDAStRouteNextHopAddress
    }
    ::= { tmnxDAStRouteTable 1 }

TmnxDAStRouteEntry ::= SEQUENCE {
        tmnxDAStRouteAddrType              InetAddressType,
        tmnxDAStRouteAddress               InetAddress,
        tmnxDAStRoutePrefixLength          InetAddressPrefixLength,
        tmnxDAStRouteNextHopAddrType       InetAddressType,
        tmnxDAStRouteNextHopAddress        InetAddress,
        tmnxDAStRouteRowStatus             RowStatus,
        tmnxDAStRouteLastChanged           TimeStamp,
        tmnxDAStRouteMetric                Unsigned32
    }

tmnxDAStRouteAddrType    OBJECT-TYPE
    SYNTAX          InetAddressType
    MAX-ACCESS      not-accessible
    STATUS          current
    DESCRIPTION
        "The value of tmnxDAStRouteAddrType specifies the static-route
         address-type for a static-route the user wishes to create."
    ::= { tmnxDAStRouteEntry 1 }

tmnxDAStRouteAddress    OBJECT-TYPE
    SYNTAX          InetAddress (SIZE(0|4|16))
    MAX-ACCESS      not-accessible
    STATUS          current
    DESCRIPTION
        "The value of tmnxDAStRouteAddress specifies the route address for 
         which the user wishes to create a static-route."
    ::= { tmnxDAStRouteEntry 2 }

tmnxDAStRoutePrefixLength    OBJECT-TYPE 
    SYNTAX          InetAddressPrefixLength
    MAX-ACCESS      not-accessible
    STATUS          current
    DESCRIPTION 
        "The value of tmnxDAStRoutePrefixLength specifies the prefix length 
         of the static-route address."
    ::= { tmnxDAStRouteEntry 3 }

tmnxDAStRouteNextHopAddrType    OBJECT-TYPE
    SYNTAX          InetAddressType
    MAX-ACCESS      not-accessible
    STATUS          current
    DESCRIPTION
        "The value of tmnxDAStRouteNextHopAddrType specifies the next-hop 
         address-type for the static-route."
    ::= { tmnxDAStRouteEntry 4 }

tmnxDAStRouteNextHopAddress    OBJECT-TYPE
    SYNTAX          InetAddress (SIZE(0|4|16))
    MAX-ACCESS      not-accessible
    STATUS          current
    DESCRIPTION
        "The value of tmnxDAStRouteNextHopAddress specifies the next-hop 
         address for the specified static-route."
    ::= { tmnxDAStRouteEntry 5 }

tmnxDAStRouteRowStatus    OBJECT-TYPE
    SYNTAX          RowStatus
    MAX-ACCESS      read-create
    STATUS          current
    DESCRIPTION
        "The value of tmnxDAStRouteRowStatus specifies the row status of this 
         row in the tmnxDAStRouteTable. It is used to create and delete row 
         entries in this table."
    ::= { tmnxDAStRouteEntry 6 }

tmnxDAStRouteLastChanged    OBJECT-TYPE
    SYNTAX          TimeStamp
    MAX-ACCESS      read-only
    STATUS          current
    DESCRIPTION
        "The value of tmnxDAStRouteLastChanged indicates the timestamp of last
         change to this row in tmnxDAStRouteTable."
    ::= { tmnxDAStRouteEntry 7 }

tmnxDAStRouteMetric    OBJECT-TYPE 
    SYNTAX          Unsigned32 (0..65535)
    MAX-ACCESS      read-create
    STATUS          current
    DESCRIPTION 
        "The value of tmnxDAStRouteMetric specifies the route metric of the 
         static-route."
    DEFVAL { 0 }
    ::= { tmnxDAStRouteEntry 8 }

--
--  DA Server Group Card Table
--

tmnxDASGCardTable    OBJECT-TYPE
    SYNTAX          SEQUENCE OF TmnxDASGCardEntry
    MAX-ACCESS      not-accessible
    STATUS          current
    DESCRIPTION
        "There can be multiple Delivery Appliance (DA) proxy server groups in a 
         system. One or more caching blades (DA servers) form a server group. A 
         card can be part of multiple server groups. The tmnxDASGCardTable has 
         an entry for a card in every server group that it is associated with in 
         the system."
    ::= { tmnxDAObjs 17 }

tmnxDASGCardEntry    OBJECT-TYPE
    SYNTAX          TmnxDASGCardEntry
    MAX-ACCESS      not-accessible
    STATUS          current
    DESCRIPTION
        "Each row entry represents a DA server-group card entry in the system."
    INDEX {  
            tmnxDASvrGrpIndex,
            tmnxDASGCardNumber      
    }
    ::= { tmnxDASGCardTable 1 }

TmnxDASGCardEntry ::= SEQUENCE {
        tmnxDASGCardNumber                 INTEGER,
        tmnxDASGCardUpTime                 Gauge32,
        tmnxDASGCardTotNumTCPConn          Counter32,
        tmnxDASGCardTCPConnEstab           Counter64,
        tmnxDASGCardTCPConnEstabL32        Counter32,
        tmnxDASGCardTCPConnEstabH32        Counter32,
        tmnxDASGCardTCPConnClosed          Counter64,
        tmnxDASGCardTCPConnClosedL32       Counter32,
        tmnxDASGCardTCPConnClosedH32       Counter32,
        tmnxDASGCardTCPRetries             Counter64,
        tmnxDASGCardTCPRetriesL32          Counter32,
        tmnxDASGCardTCPRetriesH32          Counter32,
        tmnxDASGCardTCPAckTimeOut          Counter64,
        tmnxDASGCardTCPAckTimeOutL32       Counter32,
        tmnxDASGCardTCPAckTimeOutH32       Counter32,
        tmnxDASGCardTCPFarEndClosed        Counter64,
        tmnxDASGCardTCPFarEndClosedL32     Counter32,
        tmnxDASGCardTCPFarEndClosedH32     Counter32,
        tmnxDASGCardTCPLocalEndClosed      Counter64,
        tmnxDASGCardTCPLocalEndClosedL32   Counter32,
        tmnxDASGCardTCPLocalEndClosedH32   Counter32,
        tmnxDASGCardUsedStorageCpcty       Counter64,
        tmnxDASGCardUsedStorageCpctyL32    Counter32,
        tmnxDASGCardUsedStorageCpctyH32    Counter32,
        tmnxDASGCardRemStorageCpcty        Counter64,
        tmnxDASGCardRemStorageCpctyL32     Counter32,
        tmnxDASGCardRemStorageCpctyH32     Counter32,
        tmnxDASGCardNumberOfAssets         Gauge32,
        tmnxDASGCardNumberOfOrigins        Gauge32,
        tmnxDASGCardNumberOfURIs           Gauge32,
        tmnxDASGCardECCBlockCorrections    Gauge32,
        tmnxDASGCardECCBlockFailures       Gauge32,
        tmnxDASGCardPercentBadBlocks       Gauge32, 
        tmnxDASGCardFPGATotPktsSent        Counter64,
        tmnxDASGCardFPGATotPktsSentL32     Counter32,
        tmnxDASGCardFPGATotPktsSentH32     Counter32,
        tmnxDASGCardFPGATotBytesSent       Counter64,
        tmnxDASGCardFPGATotBytesSentL32    Counter32,
        tmnxDASGCardFPGATotBytesSentH32    Counter32,
        tmnxDASGCardFPGATotPktsRecd        Counter64,
        tmnxDASGCardFPGATotPktsRecdL32     Counter32,
        tmnxDASGCardFPGATotPktsRecdH32     Counter32,
        tmnxDASGCardFPGATotBytesRecd       Counter64,
        tmnxDASGCardFPGATotBytesRecdL32    Counter32,
        tmnxDASGCardFPGATotBytesRecdH32    Counter32,
        tmnxDASGCardFPGAUnderflowErrors    Gauge32,
        tmnxDASGCardFPGAOverflowErrors     Gauge32
    }

tmnxDASGCardNumber    OBJECT-TYPE
    SYNTAX          INTEGER {
                               card1          (1),
                               card2          (2),
                               card3          (3),
                               card4          (4),
                               card5          (5),
                               card6          (6),
                               card7          (7),
                               card8          (8),
                               card9          (9),
                               card10         (10)
                            }
    MAX-ACCESS      not-accessible
    STATUS          current
    DESCRIPTION
        "The value of tmnxDASGCardNumber specifies the card number that is 
         associated with the DA server-group." 
    ::= { tmnxDASGCardEntry 1 }

tmnxDASGCardUpTime    OBJECT-TYPE
    SYNTAX          Gauge32
    MAX-ACCESS      read-only
    STATUS          current
    DESCRIPTION
        "The value of tmnxDASGCardUpTime indicates the uptime of the card within
         this DA server-group."
    ::= { tmnxDASGCardEntry 2 }

tmnxDASGCardTotNumTCPConn    OBJECT-TYPE
    SYNTAX          Counter32
    MAX-ACCESS      read-only
    STATUS          current
    DESCRIPTION
        "The value of tmnxDASGCardTotNumTCPConn indicates the total number of 
         TCP connections for the card within this DA server-group."
    ::= { tmnxDASGCardEntry 3 }

tmnxDASGCardTCPConnEstab    OBJECT-TYPE
    SYNTAX          Counter64
    MAX-ACCESS      read-only
    STATUS          current
    DESCRIPTION
        "The value of tmnxDASGCardTCPConnEstab indicates the number of TCP 
         connections that have been established for the card within this DA 
         server-group."
    ::= { tmnxDASGCardEntry 4 }

tmnxDASGCardTCPConnEstabL32    OBJECT-TYPE
    SYNTAX          Counter32
    MAX-ACCESS      read-only
    STATUS          current
    DESCRIPTION
        "The value of tmnxDASGCardTCPConnEstabL32 indicates the lower 32 
         bits of the value of tmnxDASGCardTCPConnEstab."
    ::= { tmnxDASGCardEntry 5 }

tmnxDASGCardTCPConnEstabH32    OBJECT-TYPE
    SYNTAX          Counter32
    MAX-ACCESS      read-only
    STATUS          current
    DESCRIPTION
        "The value of tmnxDASGCardTCPConnEstabH32 indicates the higher 32 
         bits of the value of tmnxDASGCardTCPConnEstab."
    ::= { tmnxDASGCardEntry 6 }

tmnxDASGCardTCPConnClosed    OBJECT-TYPE
    SYNTAX          Counter64
    MAX-ACCESS      read-only
    STATUS          current
    DESCRIPTION
        "The value of tmnxDASGCardTCPConnClosed indicates the number of TCP 
         connections that have been closed for the card within this DA 
         server-group."
    ::= { tmnxDASGCardEntry 7 }

tmnxDASGCardTCPConnClosedL32    OBJECT-TYPE
    SYNTAX          Counter32
    MAX-ACCESS      read-only
    STATUS          current
    DESCRIPTION
        "The value of tmnxDASGCardTCPConnClosedL32 indicates the lower 32 
         bits of the value of tmnxDASGCardTCPConnClosed."
    ::= { tmnxDASGCardEntry 8 }

tmnxDASGCardTCPConnClosedH32    OBJECT-TYPE
    SYNTAX          Counter32
    MAX-ACCESS      read-only
    STATUS          current
    DESCRIPTION
        "The value of tmnxDASGCardTCPConnClosedH32 indicates the higher 32 
         bits of the value of tmnxDASGCardTCPConnClosed."
    ::= { tmnxDASGCardEntry 9 }

tmnxDASGCardTCPRetries    OBJECT-TYPE
    SYNTAX          Counter64
    MAX-ACCESS      read-only
    STATUS          current
    DESCRIPTION
        "The value of tmnxDASGCardTCPRetries indicates the number of TCP 
         retries that have been made for the card within this DA server-group."
    ::= { tmnxDASGCardEntry 10 }

tmnxDASGCardTCPRetriesL32    OBJECT-TYPE
    SYNTAX          Counter32
    MAX-ACCESS      read-only
    STATUS          current
    DESCRIPTION
        "The value of tmnxDASGCardTCPRetriesL32 indicates the lower 32 
         bits of the value of tmnxDASGCardTCPRetries."
    ::= { tmnxDASGCardEntry 11 }

tmnxDASGCardTCPRetriesH32    OBJECT-TYPE
    SYNTAX          Counter32
    MAX-ACCESS      read-only
    STATUS          current
    DESCRIPTION
        "The value of tmnxDASGCardTCPRetriesH32 indicates the higher 32 
         bits of the value of tmnxDASGCardTCPRetries."
    ::= { tmnxDASGCardEntry 12 }

tmnxDASGCardTCPAckTimeOut    OBJECT-TYPE
    SYNTAX          Counter64
    MAX-ACCESS      read-only
    STATUS          current
    DESCRIPTION
        "The value of tmnxDASGCardTCPAckTimeOut indicates the number of TCP 
         acknowledgement timeouts that have occured for the card within this DA 
         server-group."
    ::= { tmnxDASGCardEntry 13 }

tmnxDASGCardTCPAckTimeOutL32    OBJECT-TYPE
    SYNTAX          Counter32
    MAX-ACCESS      read-only
    STATUS          current
    DESCRIPTION
        "The value of tmnxDASGCardTCPAckTimeOutL32 indicates the lower 32 
         bits of the value of tmnxDASGCardTCPAckTimeOut."
    ::= { tmnxDASGCardEntry 14 }

tmnxDASGCardTCPAckTimeOutH32    OBJECT-TYPE
    SYNTAX          Counter32
    MAX-ACCESS      read-only
    STATUS          current
    DESCRIPTION
        "The value of tmnxDASGCardTCPAckTimeOutH32 indicates the higher 32 
         bits of the value of tmnxDASGCardTCPAckTimeOut."
    ::= { tmnxDASGCardEntry 15 }

tmnxDASGCardTCPFarEndClosed    OBJECT-TYPE
    SYNTAX          Counter64
    MAX-ACCESS      read-only
    STATUS          current
    DESCRIPTION
        "The value of tmnxDASGCardTCPFarEndClosed indicates the number of TCP 
         connections that have been closed at the receiving end for the card 
         within this DA server-group."
    ::= { tmnxDASGCardEntry 16 }

tmnxDASGCardTCPFarEndClosedL32    OBJECT-TYPE
    SYNTAX          Counter32
    MAX-ACCESS      read-only
    STATUS          current
    DESCRIPTION
        "The value of tmnxDASGCardTCPFarEndClosedL32 indicates the lower 32 
         bits of the value of tmnxDASGCardTCPFarEndClosed."
    ::= { tmnxDASGCardEntry 17 }

tmnxDASGCardTCPFarEndClosedH32    OBJECT-TYPE
    SYNTAX          Counter32
    MAX-ACCESS      read-only
    STATUS          current
    DESCRIPTION
        "The value of tmnxDASGCardTCPFarEndClosedH32 indicates the higher 32 
         bits of the value of tmnxDASGCardTCPFarEndClosed."
    ::= { tmnxDASGCardEntry 18 }

tmnxDASGCardTCPLocalEndClosed    OBJECT-TYPE
    SYNTAX          Counter64
    MAX-ACCESS      read-only
    STATUS          current
    DESCRIPTION
        "The value of tmnxDASGCardTCPLocalEndClosed indicates the number of TCP 
         connections that have been closed locally for the card within this DA 
         server-group."
    ::= { tmnxDASGCardEntry 19 }

tmnxDASGCardTCPLocalEndClosedL32    OBJECT-TYPE
    SYNTAX          Counter32
    MAX-ACCESS      read-only
    STATUS          current
    DESCRIPTION
        "The value of tmnxDASGCardTCPLocalEndClosedL32 indicates the lower 32 
         bits of the value of tmnxDASGCardTCPLocalEndClosed."
    ::= { tmnxDASGCardEntry 20 }

tmnxDASGCardTCPLocalEndClosedH32    OBJECT-TYPE
    SYNTAX          Counter32
    MAX-ACCESS      read-only
    STATUS          current
    DESCRIPTION
        "The value of tmnxDASGCardTCPLocalEndClosedH32 indicates the higher 32 
         bits of the value of tmnxDASGCardTCPLocalEndClosed."
    ::= { tmnxDASGCardEntry 21 }

tmnxDASGCardUsedStorageCpcty    OBJECT-TYPE
    SYNTAX          Counter64
    MAX-ACCESS      read-only
    STATUS          current
    DESCRIPTION
        "The value of tmnxDASGCardUsedStorageCpcty indicates the amount of used 
         storage capacity for the card within this DA server-group."
    ::= { tmnxDASGCardEntry 22 }

tmnxDASGCardUsedStorageCpctyL32    OBJECT-TYPE
    SYNTAX          Counter32
    MAX-ACCESS      read-only
    STATUS          current
    DESCRIPTION
        "The value of tmnxDASGCardUsedStorageCpctyL32 indicates the lower 32 
         bits of the value of tmnxDASGCardUsedStorageCpcty."
    ::= { tmnxDASGCardEntry 23 }

tmnxDASGCardUsedStorageCpctyH32    OBJECT-TYPE
    SYNTAX          Counter32
    MAX-ACCESS      read-only
    STATUS          current
    DESCRIPTION
        "The value of tmnxDASGCardUsedStorageCpctyH32 indicates the higher 32 
         bits of the value of tmnxDASGCardUsedStorageCpcty."
    ::= { tmnxDASGCardEntry 24 }

tmnxDASGCardRemStorageCpcty    OBJECT-TYPE
    SYNTAX          Counter64
    MAX-ACCESS      read-only
    STATUS          current
    DESCRIPTION
        "The value of tmnxDASGCardRemStorageCpcty indicates the amount of 
         remaining storage capacity that can be used for the card within this 
         DA server-group."
    ::= { tmnxDASGCardEntry 25 }

tmnxDASGCardRemStorageCpctyL32    OBJECT-TYPE
    SYNTAX          Counter32
    MAX-ACCESS      read-only
    STATUS          current
    DESCRIPTION
        "The value of tmnxDASGCardRemStorageCpctyL32 indicates the lower 32 
         bits of the value of tmnxDASGCardRemStorageCpcty."
    ::= { tmnxDASGCardEntry 26 }

tmnxDASGCardRemStorageCpctyH32    OBJECT-TYPE
    SYNTAX          Counter32
    MAX-ACCESS      read-only
    STATUS          current
    DESCRIPTION
        "The value of tmnxDASGCardRemStorageCpctyH32 indicates the higher 32 
         bits of the value of tmnxDASGCardRemStorageCpcty."
    ::= { tmnxDASGCardEntry 27 }

tmnxDASGCardNumberOfAssets    OBJECT-TYPE
    SYNTAX          Gauge32
    MAX-ACCESS      read-only
    STATUS          current
    DESCRIPTION
        "The value of tmnxDASGCardNumberOfAssets indicates the number of assets 
         for the card within this DA server-group."
    ::= { tmnxDASGCardEntry 28 }

tmnxDASGCardNumberOfOrigins    OBJECT-TYPE
    SYNTAX          Gauge32
    MAX-ACCESS      read-only
    STATUS          current
    DESCRIPTION
        "The value of tmnxDASGCardNumberOfOrigins indicates the number of 
         origin servers connected to this card within this DA server-group."
    ::= { tmnxDASGCardEntry 29 }

tmnxDASGCardNumberOfURIs    OBJECT-TYPE
    SYNTAX          Gauge32
    MAX-ACCESS      read-only
    STATUS          current
    DESCRIPTION
        "The value of tmnxDASGCardNumberOfURIs indicates the number of URI's 
         that are connected to this card within this DA server-group."
    ::= { tmnxDASGCardEntry 30 }

tmnxDASGCardECCBlockCorrections    OBJECT-TYPE
    SYNTAX          Gauge32
    MAX-ACCESS      read-only
    STATUS          current
    DESCRIPTION
        "The value of tmnxDASGCardECCBlockCorrections indicates the number of 
         ECC block corrections for the card within this DA server-group."
    ::= { tmnxDASGCardEntry 31 }

tmnxDASGCardECCBlockFailures    OBJECT-TYPE
    SYNTAX          Gauge32
    MAX-ACCESS      read-only
    STATUS          current
    DESCRIPTION
        "The value of tmnxDASGCardECCBlockFailures indicates the number of ECC 
         block failures for the card within this DA server-group."
    ::= { tmnxDASGCardEntry 32 }

tmnxDASGCardPercentBadBlocks    OBJECT-TYPE
    SYNTAX          Gauge32
    UNITS           "hundredths of a percent"
    MAX-ACCESS      read-only
    STATUS          current
    DESCRIPTION
        "The value of tmnxDASGCardPercentBadBlocks indicates the percent 
         amount of bad blocks on the card within this DA server-group."
    ::= { tmnxDASGCardEntry 33 }

tmnxDASGCardFPGATotPktsSent    OBJECT-TYPE
    SYNTAX          Counter64
    MAX-ACCESS      read-only
    STATUS          current
    DESCRIPTION
        "The value of tmnxDASGCardFPGATotPktsSent indicates the total number of 
         packets sent to the FPGA by connections on this card within this DA 
         server-group."
    ::= { tmnxDASGCardEntry 34 }

tmnxDASGCardFPGATotPktsSentL32    OBJECT-TYPE
    SYNTAX          Counter32
    MAX-ACCESS      read-only
    STATUS          current
    DESCRIPTION
        "The value of tmnxDASGCardFPGATotPktsSentL32 indicates the lower 32 
         bits of the value of tmnxDASGCardFPGATotPktsSent."
    ::= { tmnxDASGCardEntry 35 }

tmnxDASGCardFPGATotPktsSentH32    OBJECT-TYPE
    SYNTAX          Counter32
    MAX-ACCESS      read-only
    STATUS          current
    DESCRIPTION
        "The value of tmnxDASGCardFPGATotPktsSentH32 indicates the higher 32 
         bits of the value of tmnxDASGCardFPGATotPktsSent."
    ::= { tmnxDASGCardEntry 36 }

tmnxDASGCardFPGATotBytesSent    OBJECT-TYPE
    SYNTAX          Counter64
    MAX-ACCESS      read-only
    STATUS          current
    DESCRIPTION
        "The value of tmnxDASGCardFPGATotBytesSent indicates the total number of 
         bytes sent to the FPGA by connections on this card within this 
         DA server-group."
    ::= { tmnxDASGCardEntry 37 }

tmnxDASGCardFPGATotBytesSentL32    OBJECT-TYPE
    SYNTAX          Counter32
    MAX-ACCESS      read-only
    STATUS          current
    DESCRIPTION
        "The value of tmnxDASGCardFPGATotBytesSentL32 indicates the lower 32 
         bits of the value of tmnxDASGCardFPGATotBytesSent."
    ::= { tmnxDASGCardEntry 38 }

tmnxDASGCardFPGATotBytesSentH32    OBJECT-TYPE
    SYNTAX          Counter32
    MAX-ACCESS      read-only
    STATUS          current
    DESCRIPTION
        "The value of tmnxDASGCardFPGATotBytesSentH32 indicates the higher 32 
         bits of the value of tmnxDASGCardFPGATotBytesSent."
    ::= { tmnxDASGCardEntry 39 }

tmnxDASGCardFPGATotPktsRecd    OBJECT-TYPE
    SYNTAX          Counter64
    MAX-ACCESS      read-only
    STATUS          current
    DESCRIPTION
        "The value of tmnxDASGCardFPGATotPktsRecd indicates the total number of 
         packets received from the FPGA by connections on this card within this 
         DA server-group."
    ::= { tmnxDASGCardEntry 40 }

tmnxDASGCardFPGATotPktsRecdL32    OBJECT-TYPE
    SYNTAX          Counter32
    MAX-ACCESS      read-only
    STATUS          current
    DESCRIPTION
        "The value of tmnxDASGCardFPGATotPktsRecdL32 indicates the lower 32 
         bits of the value of tmnxDASGCardFPGATotPktsRecd."
    ::= { tmnxDASGCardEntry 41 }

tmnxDASGCardFPGATotPktsRecdH32    OBJECT-TYPE
    SYNTAX          Counter32
    MAX-ACCESS      read-only
    STATUS          current
    DESCRIPTION
        "The value of tmnxDASGCardFPGATotPktsRecdH32 indicates the higher 32 
         bits of the value of tmnxDASGCardFPGATotPktsRecd."
    ::= { tmnxDASGCardEntry 42 }

tmnxDASGCardFPGATotBytesRecd    OBJECT-TYPE
    SYNTAX          Counter64
    MAX-ACCESS      read-only
    STATUS          current
    DESCRIPTION
        "The value of tmnxDASGCardFPGATotBytesRecd indicates the total number of 
         bytes received from the FPGA by connections on this card within this 
         DA server-group."
    ::= { tmnxDASGCardEntry 43 }

tmnxDASGCardFPGATotBytesRecdL32    OBJECT-TYPE
    SYNTAX          Counter32
    MAX-ACCESS      read-only
    STATUS          current
    DESCRIPTION
        "The value of tmnxDASGCardFPGATotBytesRecdL32 indicates the lower 32 
         bits of the value of tmnxDASGCardFPGATotBytesRecd."
    ::= { tmnxDASGCardEntry 44 }

tmnxDASGCardFPGATotBytesRecdH32    OBJECT-TYPE
    SYNTAX          Counter32
    MAX-ACCESS      read-only
    STATUS          current
    DESCRIPTION
        "The value of tmnxDASGCardFPGATotBytesRecdH32 indicates the higher 32 
         bits of the value of tmnxDASGCardFPGATotBytesRecd."
    ::= { tmnxDASGCardEntry 45 }

tmnxDASGCardFPGAUnderflowErrors    OBJECT-TYPE
    SYNTAX          Gauge32
    MAX-ACCESS      read-only
    STATUS          current
    DESCRIPTION
        "The value of tmnxDASGCardFPGAUnderflowErrors indicates the number of 
         FPGA underflow errors that occured with connections on the card within 
         this DA server-group"
    ::= { tmnxDASGCardEntry 46 }

tmnxDASGCardFPGAOverflowErrors    OBJECT-TYPE
    SYNTAX          Gauge32
    MAX-ACCESS      read-only
    STATUS          current
    DESCRIPTION
        "The value of tmnxDASGCardFPGAOverflowErrors indicates the number of 
         FPGA overflow errors that occured with connections on the card within 
         this DA server-group."
    ::= { tmnxDASGCardEntry 47 }

--
--  DA Delivery Controller Interface Table
--

tmnxDADCIntfTable    OBJECT-TYPE
    SYNTAX          SEQUENCE OF TmnxDADCIntfEntry
    MAX-ACCESS      not-accessible
    STATUS          current
    DESCRIPTION
        "The tmnxDADCIntfTable has an entry for each Delivery Controller (DC) 
         interface type."
    ::= { tmnxDAObjs 18 }

tmnxDADCIntfEntry    OBJECT-TYPE
    SYNTAX          TmnxDADCIntfEntry
    MAX-ACCESS      not-accessible
    STATUS          current
    DESCRIPTION
        "Each row entry represents a DC Interface type."
    INDEX {  
            tmnxDAGrpName,
            tmnxDADCIntfServerIndex,
            tmnxDADCIntfType,
            tmnxDADCIntfIPAddrType,
            tmnxDADCIntfIPAddress
    }
    ::= { tmnxDADCIntfTable 1 }

TmnxDADCIntfEntry ::= SEQUENCE {
        tmnxDADCIntfServerIndex         Gauge32,
        tmnxDADCIntfType                INTEGER,
        tmnxDADCIntfIPAddrType          InetAddressType,
        tmnxDADCIntfIPAddress           InetAddress,
        tmnxDADCIntfFQDNType            InetAddressType,
        tmnxDADCIntfFQDN                InetAddress,
        tmnxDADCIntfSrcPort             InetPortNumber,
        tmnxDADCIntfDestPort            InetPortNumber,
        tmnxDADCIntfOperState           TmnxOperState,
        tmnxDADCIntfIPUpTime            Gauge32,
        tmnxDADCIntfIdleTime            Gauge32,
        tmnxDADCIntfRetry               Gauge32,
        tmnxDADCIntfTimeToLive          Gauge32,
        tmnxDADCIntfEtag                TLNamedItemOrEmpty,
        tmnxDADCIntfInterval            Gauge32,
        tmnxDADCIntfPriority            Gauge32,
        tmnxDADCIntfWeight              Gauge32,
        tmnxDADCIntfAttemptedSessStups  Counter32,
        tmnxDADCIntfFailedSessStups     Counter32,
        tmnxDADCIntfPingReqTxCount      Counter32,
        tmnxDADCIntfPingResRxCount      Counter32,
        tmnxDADCIntfReqMsgTxCount       Counter64,
        tmnxDADCIntfReqMsgTxCountL32    Counter32,
        tmnxDADCIntfReqMsgTxCountH32    Counter32,
        tmnxDADCIntfResMsgRxCount       Counter64,
        tmnxDADCIntfResMsgRxCountL32    Counter32,
        tmnxDADCIntfResMsgRxCountH32    Counter32,
        tmnxDADCIntfDecodeErrors        Counter32,
        tmnxDADCIntfConnectionBounce    Counter32,
        tmnxDADCIntfRemoteClose         Counter32,
        tmnxDADCIntfNoResponse          Counter32
    }

tmnxDADCIntfServerIndex    OBJECT-TYPE
    SYNTAX          Gauge32
    MAX-ACCESS      not-accessible
    STATUS          current
    DESCRIPTION
        "The value of tmnxDADCIntfServerIndex indicates the internal server 
         index of the delivery controller."
    ::= { tmnxDADCIntfEntry 1 }

tmnxDADCIntfType    OBJECT-TYPE
    SYNTAX          INTEGER {
                              service        (1),
                              config         (2),
                              health         (3),
                              job            (4),
                              metadata       (5),
                              auth           (6),
                              event          (7)
                           }

    MAX-ACCESS      not-accessible
    STATUS          current
    DESCRIPTION
        "The value of tmnxDADCIntfType indicates the type of interface asociated 
         with the delivery controller."
    ::= { tmnxDADCIntfEntry 2 }

tmnxDADCIntfIPAddrType    OBJECT-TYPE
    SYNTAX          InetAddressType
    MAX-ACCESS      not-accessible
    STATUS          current
    DESCRIPTION
        "The value of tmnxDADCIntfIPAddrType indicates the type of address 
         represented by tmnxDADCIntfIPAddress."
    ::= { tmnxDADCIntfEntry 3 }

tmnxDADCIntfIPAddress    OBJECT-TYPE
    SYNTAX          InetAddress (SIZE(0|4|16))
    MAX-ACCESS      not-accessible
    STATUS          current
    DESCRIPTION
        "The value of tmnxDADCIntfIPAddress indicates the IP Address of the
         interface of the delivery controller."
    ::= { tmnxDADCIntfEntry 4 }

tmnxDADCIntfFQDNType    OBJECT-TYPE
    SYNTAX          InetAddressType
    MAX-ACCESS      read-only
    STATUS          current
    DESCRIPTION
        "The value of tmnxDADCIntfFQDNType indicates the type of address 
         represented by tmnxDADCIntfFQDN."
    ::= { tmnxDADCIntfEntry 5 }

tmnxDADCIntfFQDN    OBJECT-TYPE
    SYNTAX          InetAddress (SIZE(1..255))
    MAX-ACCESS      read-only
    STATUS          current
    DESCRIPTION
        "The value of tmnxDADCIntfFQDN indicates the Fully Qualified Domain 
         Name (FQDN) of the interface associated with the delivery controller."
    ::= { tmnxDADCIntfEntry 6 }

tmnxDADCIntfSrcPort    OBJECT-TYPE
    SYNTAX          InetPortNumber
    MAX-ACCESS      read-only
    STATUS          current
    DESCRIPTION
        "The value of tmnxDADCIntfSrcPort indicates the source-port of the 
         interface associated with the delivery controller."
    ::= { tmnxDADCIntfEntry 7 }

tmnxDADCIntfDestPort    OBJECT-TYPE
    SYNTAX          InetPortNumber
    MAX-ACCESS      read-only
    STATUS          current
    DESCRIPTION
        "The value of tmnxDADCIntfDestPort indicates the destination-port of the 
         interface associated with the delivery controller."
    ::= { tmnxDADCIntfEntry 8 }

tmnxDADCIntfOperState    OBJECT-TYPE
    SYNTAX          TmnxOperState
    MAX-ACCESS      read-only
    STATUS          current
    DESCRIPTION
        "The value of tmnxDADCIntfOperState indicates the operational state of 
         the interface associated with the delivery controller."
    ::= { tmnxDADCIntfEntry 9 }

tmnxDADCIntfIPUpTime    OBJECT-TYPE 
    SYNTAX          Gauge32 
    UNITS           "seconds"
    MAX-ACCESS      read-only
    STATUS          current
    DESCRIPTION 
        "The value of tmnxDADCIntfIPUpTime indicates the up time for the 
         interface associated with the delivery controller."
    ::= { tmnxDADCIntfEntry 10 }

tmnxDADCIntfIdleTime    OBJECT-TYPE 
    SYNTAX          Gauge32 
    UNITS           "seconds"
    MAX-ACCESS      read-only
    STATUS          current
    DESCRIPTION 
        "The value of tmnxDADCIntfIdleTime indicates the idle time for the 
         interface associated with the delivery controller."
    ::= { tmnxDADCIntfEntry 11 }

tmnxDADCIntfRetry    OBJECT-TYPE 
    SYNTAX          Gauge32 
    UNITS           "seconds"
    MAX-ACCESS      read-only
    STATUS          current
    DESCRIPTION 
        "The value of tmnxDADCIntfRetry indicates the retry time for the 
         interface associated with the delivery controller."
    ::= { tmnxDADCIntfEntry 12 }

tmnxDADCIntfTimeToLive    OBJECT-TYPE 
    SYNTAX          Gauge32 (0..255)
    UNITS           "seconds"
    MAX-ACCESS      read-only
    STATUS          current
    DESCRIPTION 
        "The value of tmnxDADCIntfTimeToLive indicates Time To Live (TTL) for 
         the interface entry associated with the delivery controller."
    ::= { tmnxDADCIntfEntry 13 }

tmnxDADCIntfEtag    OBJECT-TYPE 
    SYNTAX          TLNamedItemOrEmpty 
    MAX-ACCESS      read-only
    STATUS          current
    DESCRIPTION 
        "The value of tmnxDADCIntfEtag indicates the Etag value for the 
         interface associated with the delivery controller."
    ::= { tmnxDADCIntfEntry 14 }

tmnxDADCIntfInterval    OBJECT-TYPE 
    SYNTAX          Gauge32 
    MAX-ACCESS      read-only
    STATUS          current
    DESCRIPTION 
        "The value of tmnxDADCIntfInterval indicates the interval for the 
         interface associated with the delivery controller."
    ::= { tmnxDADCIntfEntry 15 }

tmnxDADCIntfPriority    OBJECT-TYPE 
    SYNTAX          Gauge32 
    MAX-ACCESS      read-only
    STATUS          current
    DESCRIPTION 
        "The value of tmnxDADCIntfPriority indicates the priority for the 
         interface associated with the delivery controller."
    ::= { tmnxDADCIntfEntry 16 }

tmnxDADCIntfWeight    OBJECT-TYPE 
    SYNTAX          Gauge32
    MAX-ACCESS      read-only
    STATUS          current
    DESCRIPTION 
        "The value of tmnxDADCIntfWeight indicates the weight for the interface 
         associated with the delivery controller."
    ::= { tmnxDADCIntfEntry 17 }

tmnxDADCIntfAttemptedSessStups    OBJECT-TYPE 
    SYNTAX          Counter32 
    MAX-ACCESS      read-only
    STATUS          current
    DESCRIPTION 
        "The value of tmnxDADCIntfAttemptedSessStups indicates the number of 
         attempted session startups for the interface associated with the 
         delivery controller."
    ::= { tmnxDADCIntfEntry 18 }

tmnxDADCIntfFailedSessStups    OBJECT-TYPE 
    SYNTAX          Counter32 
    MAX-ACCESS      read-only
    STATUS          current
    DESCRIPTION 
        "The value of tmnxDADCIntfFailedSessStups indicates the number of failed 
         session startups for the interface associated with the delivery 
         controller."
    ::= { tmnxDADCIntfEntry 19 }

tmnxDADCIntfPingReqTxCount    OBJECT-TYPE 
    SYNTAX          Counter32 
    MAX-ACCESS      read-only
    STATUS          current
    DESCRIPTION 
        "The value of tmnxDADCIntfPingReqTxCount indicates the number of ping 
         requests transmitted for the interface associated with the delivery 
         controller."
    ::= { tmnxDADCIntfEntry 20 }

tmnxDADCIntfPingResRxCount    OBJECT-TYPE 
    SYNTAX          Counter32
    MAX-ACCESS      read-only
    STATUS          current
    DESCRIPTION 
        "The value of tmnxDADCIntfPingResRxCount indicates the number of ping 
         response counts received for the interface associated with the delivery 
         controller."
    ::= { tmnxDADCIntfEntry 21 }

tmnxDADCIntfReqMsgTxCount    OBJECT-TYPE 
    SYNTAX          Counter64
    MAX-ACCESS      read-only
    STATUS          current
    DESCRIPTION 
        "The value of tmnxDADCIntfReqMsgTxCount indicates the number of 
         interface request messages transmitted for the interface associated 
         with the delivery controller."
    ::= { tmnxDADCIntfEntry 22 }

tmnxDADCIntfReqMsgTxCountL32    OBJECT-TYPE 
    SYNTAX          Counter32
    MAX-ACCESS      read-only
    STATUS          current
    DESCRIPTION 
        "The value of tmnxDADCIntfReqMsgTxCountL32 indicates the lower 32 
         bits of the value of tmnxDADCIntfReqMsgTxCount."
    ::= { tmnxDADCIntfEntry 23 }

tmnxDADCIntfReqMsgTxCountH32    OBJECT-TYPE 
    SYNTAX          Counter32
    MAX-ACCESS      read-only
    STATUS          current
    DESCRIPTION 
        "The value of tmnxDADCIntfReqMsgTxCountH32 indicates the higher 32 
         bits of the value of tmnxDADCIntfReqMsgTxCount."
    ::= { tmnxDADCIntfEntry 24 }

tmnxDADCIntfResMsgRxCount    OBJECT-TYPE 
    SYNTAX          Counter64
    MAX-ACCESS      read-only
    STATUS          current
    DESCRIPTION 
        "The value of tmnxDADCIntfResMsgRxCount indicates the number of 
         interface request messages received for the interface associated 
         with the delivery controller."
    ::= { tmnxDADCIntfEntry 25 }

tmnxDADCIntfResMsgRxCountL32    OBJECT-TYPE 
    SYNTAX          Counter32
    MAX-ACCESS      read-only
    STATUS          current
    DESCRIPTION 
        "The value of tmnxDADCIntfResMsgRxCountL32 indicates the lower 32 
         bits of the value of tmnxDADCIntfResMsgRxCount."
    ::= { tmnxDADCIntfEntry 26 }

tmnxDADCIntfResMsgRxCountH32    OBJECT-TYPE 
    SYNTAX          Counter32
    MAX-ACCESS      read-only
    STATUS          current
    DESCRIPTION 
        "The value of tmnxDADCIntfResMsgRxCountH32 indicates the higher 32 
         bits of the value of tmnxDADCIntfResMsgRxCount."
    ::= { tmnxDADCIntfEntry 27 }

tmnxDADCIntfDecodeErrors    OBJECT-TYPE 
    SYNTAX          Counter32 
    MAX-ACCESS      read-only
    STATUS          current
    DESCRIPTION 
        "The value of tmnxDADCIntfDecodeErrors indicates the number of decode 
         errors for the interface associated with the delivery controller."
    ::= { tmnxDADCIntfEntry 28 }

tmnxDADCIntfConnectionBounce    OBJECT-TYPE 
    SYNTAX          Counter32 
    MAX-ACCESS      read-only
    STATUS          current
    DESCRIPTION 
        "The value of tmnxDADCIntfConnectionBounce indicates the number of 
         bounced connections for the interface associated with the delivery 
         controller."
    ::= { tmnxDADCIntfEntry 29 }

tmnxDADCIntfRemoteClose    OBJECT-TYPE 
    SYNTAX          Counter32 
    MAX-ACCESS      read-only
    STATUS          current
    DESCRIPTION 
        "The value of tmnxDADCIntfRemoteClose indicates the number of 
         connections remotely closed for the interface associated with the 
         delivery controller."
    ::= { tmnxDADCIntfEntry 30 }

tmnxDADCIntfNoResponse    OBJECT-TYPE 
    SYNTAX          Counter32
    MAX-ACCESS      read-only
    STATUS          current
    DESCRIPTION 
        "The value of tmnxDADCIntfNoResponse indicates the number of 
         non-responsive interfacs associated with the delivery controller."
    ::= { tmnxDADCIntfEntry 31 }

--
--  DA Group Origin Server Table
--
 
tmnxDAGrpOrigSvrTable    OBJECT-TYPE
    SYNTAX          SEQUENCE OF TmnxDAGrpOrigSvrEntry
    MAX-ACCESS      not-accessible
    STATUS          current
    DESCRIPTION
        "The tmnxDAGrpOrigSvrTable has an entry for each origin server."
    ::= { tmnxDAObjs 19 }

tmnxDAGrpOrigSvrEntry    OBJECT-TYPE
    SYNTAX          TmnxDAGrpOrigSvrEntry
    MAX-ACCESS      not-accessible
    STATUS          current
    DESCRIPTION
        "Each row entry represents a different origin server."
    INDEX {  
            tmnxDAGrpName,
            tmnxDAGrpOrigSvrName
    }
    ::= { tmnxDAGrpOrigSvrTable 1 }

TmnxDAGrpOrigSvrEntry ::= SEQUENCE {
        tmnxDAGrpOrigSvrName                DisplayString,
        tmnxDAGrpOrigSvrIPAddrType          InetAddressType,
        tmnxDAGrpOrigSvrIPAddress           InetAddress,
        tmnxDAGrpOrigSvrNumObjDelvred       Counter64,
        tmnxDAGrpOrigSvrNumObjDelvredL32    Counter32,
        tmnxDAGrpOrigSvrNumObjDelvredH32    Counter32,
        tmnxDAGrpOrigSvrNumObjFailed        Counter64,
        tmnxDAGrpOrigSvrNumObjFailedL32     Counter32,
        tmnxDAGrpOrigSvrNumObjFailedH32     Counter32,
        tmnxDAGrpOrigSvrNumCurTCPConn       Counter32
    }

tmnxDAGrpOrigSvrName    OBJECT-TYPE 
    SYNTAX          DisplayString (SIZE (1..94))
    MAX-ACCESS      not-accessible
    STATUS          current
    DESCRIPTION 
        "The value of tmnxDAGrpOrigSvrName indicates the Fully Qualified Domain
         name (FQDN) of the origin server. The length of the FQDN is restricted
         to 94 characters."
    ::= { tmnxDAGrpOrigSvrEntry 1 }

tmnxDAGrpOrigSvrIPAddrType    OBJECT-TYPE
    SYNTAX          InetAddressType
    MAX-ACCESS      read-only
    STATUS          current
    DESCRIPTION
        "The value of tmnxDAGrpOrigSvrIPAddrType indicates the type of address 
         represented by tmnxDAGrpOrigSvrIPAddress."
    ::= { tmnxDAGrpOrigSvrEntry 2 }

tmnxDAGrpOrigSvrIPAddress    OBJECT-TYPE
    SYNTAX          InetAddress (SIZE(0|4|16))
    MAX-ACCESS      read-only
    STATUS          current
    DESCRIPTION
        "The value of tmnxDAGrpOrigSvrIPAddress indicates the IP Address of the
         interface to the origin server."
    ::= { tmnxDAGrpOrigSvrEntry 3 }

tmnxDAGrpOrigSvrNumObjDelvred    OBJECT-TYPE 
    SYNTAX          Counter64
    MAX-ACCESS      read-only
    STATUS          current
    DESCRIPTION 
        "The value of tmnxDAGrpOrigSvrNumObjDelvred indicates the number of 
         objects delivered to the origin server."
    ::= { tmnxDAGrpOrigSvrEntry 4 }

tmnxDAGrpOrigSvrNumObjDelvredL32    OBJECT-TYPE 
    SYNTAX          Counter32
    MAX-ACCESS      read-only
    STATUS          current
    DESCRIPTION 
        "The value of tmnxDAGrpOrigSvrNumObjDelvredL32 indicates the lower 32 
         bits of the value of tmnxDAGrpOrigSvrNumObjDelvred."
    ::= { tmnxDAGrpOrigSvrEntry 5 }

tmnxDAGrpOrigSvrNumObjDelvredH32    OBJECT-TYPE 
    SYNTAX          Counter32
    MAX-ACCESS      read-only
    STATUS          current
    DESCRIPTION 
        "The value of tmnxDAGrpOrigSvrNumObjDelvredH32 indicates the higher 32 
         bits of the value of tmnxDAGrpOrigSvrNumObjDelvred."
    ::= { tmnxDAGrpOrigSvrEntry 6 }

tmnxDAGrpOrigSvrNumObjFailed    OBJECT-TYPE 
    SYNTAX          Counter64
    MAX-ACCESS      read-only
    STATUS          current
    DESCRIPTION 
        "The value of tmnxDAGrpOrigSvrNumObjFailed indicates the number of 
         objects that could not be delivered to the origin server."
    ::= { tmnxDAGrpOrigSvrEntry 7 }

tmnxDAGrpOrigSvrNumObjFailedL32    OBJECT-TYPE 
    SYNTAX          Counter32
    MAX-ACCESS      read-only
    STATUS          current
    DESCRIPTION 
        "The value of tmnxDAGrpOrigSvrNumObjFailedL32 indicates the lower 32 
         bits of the value of tmnxDAGrpOrigSvrNumObjFailed."
    ::= { tmnxDAGrpOrigSvrEntry 8 }

tmnxDAGrpOrigSvrNumObjFailedH32    OBJECT-TYPE 
    SYNTAX          Counter32
    MAX-ACCESS      read-only
    STATUS          current
    DESCRIPTION 
        "The value of tmnxDAGrpOrigSvrNumObjFailedH32 indicates the higher 32 
         bits of the value of tmnxDAGrpOrigSvrNumObjFailed."
    ::= { tmnxDAGrpOrigSvrEntry 9 }

tmnxDAGrpOrigSvrNumCurTCPConn    OBJECT-TYPE 
    SYNTAX          Counter32 
    MAX-ACCESS      read-only
    STATUS          current
    DESCRIPTION 
        "The value of tmnxDAGrpOrigSvrNumCurTCPConn indicates the number of  
         current TCP connections to the origin server."
    ::= { tmnxDAGrpOrigSvrEntry 10 }


-- ----------------------------------------------
-- Compliance Statements
-- ----------------------------------------------

tmnxDAV10v0Compliance    MODULE-COMPLIANCE
    STATUS      current
    DESCRIPTION
        "The compliance statement for management of cdn features on version 10.0 
         of the Alcatel-Lucent SROS series systems."
    MODULE      --this module
        MANDATORY-GROUPS {
            tmnxDAV10v0Group
        }
    ::= { tmnxDACompliances 1 }

-- ----------------------------------------------
-- Units of Conformance
-- ----------------------------------------------

tmnxDAV10v0Group    OBJECT-GROUP
    OBJECTS {
                 tmnxDASvrGrpTableLastChanged,
                 tmnxDASvrGrpRowStatus,
                 tmnxDASvrGrpLastChanged,
                 tmnxDASvrGrpCardSlotNumber,
                 tmnxDASvrGrpAdminState,
                 tmnxDASvrGrpOperState,
                 tmnxDAGrpTableLastChanged,
                 tmnxDAGrpRowStatus,
                 tmnxDAGrpLastChanged,
                 tmnxDAGrpServerGroupIndex,
                 tmnxDAGrpAdminState,
                 tmnxDAGrpDescription,                 
                 tmnxDAGrpDnsClientIsmLinkName,                 
                 tmnxDAGrpDCAuthCache,                 
                 tmnxDAGrpDCAdminState,
                 tmnxDAGrpDCIsmLinkName,
                 tmnxDAGrpDCBootStrapPort,
                 tmnxDAGrpDCConnRetryTimer,
                 tmnxDAGrpDCIdleTimeout,  
                 tmnxDAGrpBytesFromCache,
                 tmnxDAGrpBytesFromCacheL32,
                 tmnxDAGrpBytesFromCacheH32,
                 tmnxDAGrpBytesNotFromCache,
                 tmnxDAGrpBytesNotFromCacheL32,
                 tmnxDAGrpBytesNotFromCacheH32,
                 tmnxDAGrpObjectsFromCache,
                 tmnxDAGrpObjectsFromCacheL32,
                 tmnxDAGrpObjectsFromCacheH32,
                 tmnxDAGrpObjectsNotFromCache,
                 tmnxDAGrpObjectsNotFromCacheL32,
                 tmnxDAGrpObjectsNotFromCacheH32,
                 tmnxDAGrpObjectByteCount,
                 tmnxDAGrpObjectByteCountL32,
                 tmnxDAGrpObjectByteCountH32,
                 tmnxDAGrpNumberOfOrigins,
                 tmnxDAGrpNumberOfOriginsL32,
                 tmnxDAGrpNumberOfOriginsH32,
                 tmnxDAGrpDCAuthCacheHit,
                 tmnxDAGrpDCAuthCacheHitL32,
                 tmnxDAGrpDCAuthCacheHitH32,
                 tmnxDAGrpDCAuthCacheMiss,
                 tmnxDAGrpDCAuthCacheMissL32,
                 tmnxDAGrpDCAuthCacheMissH32,
                 tmnxDAGrpDCDeniedAuth,
                 tmnxDAGrpDCDeniedAuthL32,
                 tmnxDAGrpDCDeniedAuthH32,
                 tmnxDAGrpDCMinRTTPerPeer,
                 tmnxDAGrpDCAvgRTTPerPeer,
                 tmnxDAGrpDCMaxRTTPerPeer,               
                 tmnxDAGrpDnsSvrTableLastChanged,
                 tmnxDAGrpDnsSvrRowStatus,
                 tmnxDAGrpDnsSvrLastChanged,
                 tmnxDADCBtStSvrTableLastChanged,
                 tmnxDADCBtStSvrRowStatus,
                 tmnxDADCBtStSvrLastChanged,
                 tmnxDADCBtStSvrAddrType,
                 tmnxDADCBtStSvrAddress,
                 tmnxDAHttpTableLastChanged,                 
                 tmnxDAHttpLastChanged,
                 tmnxDAHttpServerAdminState,
                 tmnxDAHttpServerOperState,
                 tmnxDAHttpServerIdleTimeout,
                 tmnxDAHttpServerViaString,
                 tmnxDAHttpServerStrBWInUse,
                 tmnxDAHttpServerStrBWInUseL32,
                 tmnxDAHttpServerStrBWInUseH32,
                 tmnxDAHttpServerXferInProg,
                 tmnxDAHttpServerXferCompleted,
                 tmnxDAHttpServerXferCompletedL32,
                 tmnxDAHttpServerXferCompletedH32,
                 tmnxDAHttpServerXferTimeouts,
                 tmnxDAHttpServerXferFailed,
                 tmnxDAHttpServerValidRequests,
                 tmnxDAHttpServerValidRequestsL32,
                 tmnxDAHttpServerValidRequestsH32,
                 tmnxDAHttpServerInvalidRequests,
                 tmnxDAHttpServerMethodNotSuppted,
                 tmnxDAHttpServerHostNotSuppted,
                 tmnxDAHttpServer1XXCountSent,
                 tmnxDAHttpServer1XXCountSentL32,
                 tmnxDAHttpServer1XXCountSentH32,
                 tmnxDAHttpServer2XXCountSent,
                 tmnxDAHttpServer2XXCountSentL32,
                 tmnxDAHttpServer2XXCountSentH32,
                 tmnxDAHttpServer3XXCountSent,
                 tmnxDAHttpServer3XXCountSentL32,
                 tmnxDAHttpServer3XXCountSentH32,
                 tmnxDAHttpServer4XXCountSent,
                 tmnxDAHttpServer4XXCountSentL32,
                 tmnxDAHttpServer4XXCountSentH32,
                 tmnxDAHttpServer5XXCountSent,
                 tmnxDAHttpServer5XXCountSentL32,
                 tmnxDAHttpServer5XXCountSentH32,
                 tmnxDAHttpIngestAdminState,
                 tmnxDAHttpIngestOperState,
                 tmnxDAHttpIngestIsmLinkName,
                 tmnxDAHttpIngestIdleTimeout,
                 tmnxDAHttpIngestXferInProg,
                 tmnxDAHttpIngestXferCompleted,
                 tmnxDAHttpIngestXferCompletedL32,
                 tmnxDAHttpIngestXferCompletedH32,
                 tmnxDAHttpIngestXferTimeouts,
                 tmnxDAHttpIngestXferFailed,
                 tmnxDAHttpIngest1XXCountRecd,
                 tmnxDAHttpIngest1XXCountRecdL32,
                 tmnxDAHttpIngest1XXCountRecdH32,
                 tmnxDAHttpIngest2XXCountRecd,
                 tmnxDAHttpIngest2XXCountRecdL32,
                 tmnxDAHttpIngest2XXCountRecdH32,
                 tmnxDAHttpIngest3XXCountRecd,
                 tmnxDAHttpIngest3XXCountRecdL32,
                 tmnxDAHttpIngest3XXCountRecdH32,
                 tmnxDAHttpIngest4XXCountRecd,
                 tmnxDAHttpIngest4XXCountRecdL32,
                 tmnxDAHttpIngest4XXCountRecdH32,
                 tmnxDAHttpIngest5XXCountRecd,
                 tmnxDAHttpIngest5XXCountRecdL32,
                 tmnxDAHttpIngest5XXCountRecdH32,
                 tmnxDAIsmLinkTableLastChanged,
                 tmnxDAIsmLinkRowStatus,
                 tmnxDAIsmLinkLastChanged,
                 tmnxDAIsmLinkAddrType,
                 tmnxDAIsmLinkAddress,
                 tmnxDAIsmLinkAddrPrefixLength,
                 tmnxDAIsmLinkDescription,
                 tmnxDAIsmLinkHttpd,
                 tmnxDAIsmLinkHttpListenPort,
                 tmnxDAIsmLinkIpMtu,
                 tmnxDAIsmLinkQtag,
                 tmnxDAIsmLinkMacAddress,
                 tmnxDAIsmLinkAdminState,
                 tmnxDAIsmLinkOperState,
                 tmnxDAIsmLinkBindings,
                 tmnxDAIsmLinkArpTableLastChanged,
                 tmnxDAIsmLinkArpRowStatus,
                 tmnxDAIsmLinkArpLastChanged,
                 tmnxDAIsmLinkArpMacAddr,
                 tmnxDAIsmLinkArpType,
                 tmnxDAStRouteTableLastChanged,
                 tmnxDAStRouteRowStatus,
                 tmnxDAStRouteLastChanged,                 
                 tmnxDAStRouteMetric,
                 tmnxDASGCardUpTime,
                 tmnxDASGCardTotNumTCPConn,
                 tmnxDASGCardTCPConnEstab,
                 tmnxDASGCardTCPConnEstabL32,
                 tmnxDASGCardTCPConnEstabH32,
                 tmnxDASGCardTCPConnClosed,
                 tmnxDASGCardTCPConnClosedL32,
                 tmnxDASGCardTCPConnClosedH32,
                 tmnxDASGCardTCPRetries,
                 tmnxDASGCardTCPRetriesL32,
                 tmnxDASGCardTCPRetriesH32,
                 tmnxDASGCardTCPAckTimeOut,
                 tmnxDASGCardTCPAckTimeOutL32,
                 tmnxDASGCardTCPAckTimeOutH32,
                 tmnxDASGCardTCPFarEndClosed,
                 tmnxDASGCardTCPFarEndClosedL32,
                 tmnxDASGCardTCPFarEndClosedH32,
                 tmnxDASGCardTCPLocalEndClosed,
                 tmnxDASGCardTCPLocalEndClosedL32,
                 tmnxDASGCardTCPLocalEndClosedH32,
                 tmnxDASGCardUsedStorageCpcty,
                 tmnxDASGCardUsedStorageCpctyL32,
                 tmnxDASGCardUsedStorageCpctyH32,
                 tmnxDASGCardRemStorageCpcty,
                 tmnxDASGCardRemStorageCpctyL32,
                 tmnxDASGCardRemStorageCpctyH32,
                 tmnxDASGCardNumberOfAssets,
                 tmnxDASGCardNumberOfOrigins,
                 tmnxDASGCardNumberOfURIs,
                 tmnxDASGCardECCBlockCorrections,
                 tmnxDASGCardECCBlockFailures,
                 tmnxDASGCardPercentBadBlocks, 
                 tmnxDASGCardFPGATotPktsSent,
                 tmnxDASGCardFPGATotPktsSentL32,
                 tmnxDASGCardFPGATotPktsSentH32,
                 tmnxDASGCardFPGATotBytesSent,
                 tmnxDASGCardFPGATotBytesSentL32,
                 tmnxDASGCardFPGATotBytesSentH32,
                 tmnxDASGCardFPGATotPktsRecd,
                 tmnxDASGCardFPGATotPktsRecdL32,
                 tmnxDASGCardFPGATotPktsRecdH32,
                 tmnxDASGCardFPGATotBytesRecd,
                 tmnxDASGCardFPGATotBytesRecdL32,
                 tmnxDASGCardFPGATotBytesRecdH32,
                 tmnxDASGCardFPGAUnderflowErrors,
                 tmnxDASGCardFPGAOverflowErrors,
                 tmnxDADCIntfFQDNType,
                 tmnxDADCIntfFQDN,
                 tmnxDADCIntfSrcPort,
                 tmnxDADCIntfDestPort,
                 tmnxDADCIntfOperState,
                 tmnxDADCIntfIPUpTime,
                 tmnxDADCIntfIdleTime,
                 tmnxDADCIntfRetry,
                 tmnxDADCIntfTimeToLive,
                 tmnxDADCIntfEtag,
                 tmnxDADCIntfInterval,
                 tmnxDADCIntfPriority,
                 tmnxDADCIntfWeight,
                 tmnxDADCIntfAttemptedSessStups,
                 tmnxDADCIntfFailedSessStups,
                 tmnxDADCIntfPingReqTxCount,
                 tmnxDADCIntfPingResRxCount,
                 tmnxDADCIntfReqMsgTxCount,
                 tmnxDADCIntfReqMsgTxCountL32,
                 tmnxDADCIntfReqMsgTxCountH32,
                 tmnxDADCIntfResMsgRxCount,
                 tmnxDADCIntfResMsgRxCountL32,
                 tmnxDADCIntfResMsgRxCountH32,
                 tmnxDADCIntfDecodeErrors,
                 tmnxDADCIntfConnectionBounce,
                 tmnxDADCIntfRemoteClose,
                 tmnxDADCIntfNoResponse,
                 tmnxDAGrpOrigSvrIPAddrType,
                 tmnxDAGrpOrigSvrIPAddress,
                 tmnxDAGrpOrigSvrNumObjDelvred,
                 tmnxDAGrpOrigSvrNumObjDelvredL32,
                 tmnxDAGrpOrigSvrNumObjDelvredH32,
                 tmnxDAGrpOrigSvrNumObjFailed,
                 tmnxDAGrpOrigSvrNumObjFailedL32,
                 tmnxDAGrpOrigSvrNumObjFailedH32,
                 tmnxDAGrpOrigSvrNumCurTCPConn  
            }
    STATUS      current
    DESCRIPTION
        "The group of objects supporting management of Delivery Appliance 
         features on version 10.0 of the Alcatel-Lucent SROS series systems."
    ::= { tmnxDAGroups 1 }

END
