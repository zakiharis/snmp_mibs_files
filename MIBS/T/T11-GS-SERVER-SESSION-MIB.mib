-- extracted from draft-kzm-imss-fc-zs-mib-02.txt
-- at Sat Dec  3 06:40:12 2005

T11-GS-SERVER-SESSION-MIB  DEFINITIONS ::= BEGIN

IMPORTS
    MODULE-IDENTITY, OBJECT-TYPE,
    mib-2                              FROM SNMPv2-SMI   -- [RFC2578]
    MODULE-COMPLIANCE, OBJECT-GROUP    FROM SNMPv2-CONF  -- [RFC2580]
    fcmInstanceIndex, fcmSwitchIndex   FROM FC-MGMT-MIB  -- [FC-MGMT]
    T11FabricIndex                     FROM T11-TC-MIB;  -- [FC-FAM-MIB]

t11GsServerSessionMIB  MODULE-IDENTITY
    LAST-UPDATED  "200510130000Z"
    ORGANIZATION  "T11"
    CONTACT-INFO
             "     Claudio DeSanti
                   Cisco Systems, Inc.
                   170 West Tasman Drive
                   San Jose, CA 95134 USA
                   EMail: cds@cisco.com

                   Keith McCloghrie
                   Cisco Systems, Inc.
                   170 West Tasman Drive
                   San Jose, CA 95134 USA
                   Email: kzm@cisco.com"
    DESCRIPTION
            "The MIB module for the management of Fibre Channel
             Server Sessions as defined generically in FC-GS-5
             to represent a collection of one or more requests
             for the session's server.  Such a session is
             started by a Server Session Begin (SSB) request and
             terminated by a Server Session End (SSE) request.
             In particular, GS-5 Server Sessions are used by
             Enhanced Zoning Management."
    REVISION  "200510130000Z"
    DESCRIPTION
            "Initial version of this MIB."
    ::= { mib-2 1 } -- to be determined later

t11GssMIBObjects       OBJECT IDENTIFIER ::= { t11GsServerSessionMIB 1 }
t11GssMIBConformance   OBJECT IDENTIFIER ::= { t11GsServerSessionMIB 2 }
t11GssMIBNotifications OBJECT IDENTIFIER ::= { t11GsServerSessionMIB 0 }
t11GssConfiguration    OBJECT IDENTIFIER ::= { t11GssMIBObjects 1 }
--
-- The table of Server Sessions
--

t11GssSessionTable OBJECT-TYPE
    SYNTAX       SEQUENCE OF T11GssSessionEntry
    MAX-ACCESS   not-accessible
    STATUS       current
    DESCRIPTION
            "A table containing information about the active
             GS-5 Server sessions on one or more switches on
             all fabrics known to those switches."
    REFERENCE
             "ANSI INCITS xxx/200x, T11/Project 1677-D/Rev 8.2,
              Fibre Channel - Generic Services-5 (FC-GS-5),
              4 October 2005, sections 4.9.5 and 6.4.10.2."
    ::= { t11GssConfiguration 1 }

t11GssSessionEntry OBJECT-TYPE
    SYNTAX       T11GssSessionEntry
    MAX-ACCESS   not-accessible
    STATUS       current
    DESCRIPTION
            "Each entry contains information specific to a
             GS-5 Server session for a particular fabric on
             a particular switch (identified by values of
             fcmInstanceIndex and fcmSwitchIndex).  Note that
             each switch can have at most one Server session
             per fabric.

             Several different types of Servers are defined in
             FC-GS-5.  The behavior of a Server with respect to
             commands received within a Server session is specified for
             each type of Server.  For some types, parameter changes
             can only be made within the context of a session.  That
             is, some types of changes can only made while a session is
             established.  So, in order to make such changes via an
             SNMP SetRequest, some types of Servers require that a
             corresponding entry in this table exist, and in such
             cases, the required entry in this table is created
             implicitly (by the agent on receipt of the SetRequest)
             as and when necessary, with t11GssSessionOwnerType
             having a value of 'snmp'."
    REFERENCE
             "ANSI INCITS xxx/200x, T11/Project 1677-D/Rev 8.2,
              Fibre Channel - Generic Services-5 (FC-GS-5),
              4 October 2005, sections 4.9.5.5."
    INDEX   { fcmInstanceIndex, fcmSwitchIndex,
              t11GssSessionFabricIndex }
    ::= { t11GssSessionTable 1 }

T11GssSessionEntry ::= SEQUENCE {
    t11GssSessionFabricIndex     T11FabricIndex,
    t11GssSessionOwnerType       INTEGER,
    t11GssSessionOwner           OCTET STRING,
    t11GssSessionControl         INTEGER,
    t11GssSessionCommitResult    INTEGER
}

t11GssSessionFabricIndex OBJECT-TYPE
    SYNTAX       T11FabricIndex
    MAX-ACCESS   not-accessible
    STATUS       current
    DESCRIPTION
           "A unique index value which uniquely identifies a
           particular fabric.

           In a fabric conformant to FC-SW-4, multiple Virtual Fabrics
           can operate within one (or more) physical infrastructures,
           and this index value is used to uniquely identify a
           particular (physical or virtual) fabric within a physical
           infrastructure.

           In a fabric conformant to versions earlier than FC-SW-4,
           only a single fabric could operate within a physical
           infrastructure, and thus, the value of this fabric index
           was defined to always be 1."
    ::= { t11GssSessionEntry 1 }

t11GssSessionOwnerType OBJECT-TYPE
    SYNTAX        INTEGER {
                      other(1),
                      gsClient(2),
                      cli(3),
                      snmp(4)
                  }
    MAX-ACCESS    read-only
    STATUS        current
    DESCRIPTION
            "This object specifies the owner type for this
             session:

               other     - none of the following.
               gsClient  - a Fibre Channel Generic Services
                           (e.g., GS-5) client.
               cli       - Command Line Interface (CLI).
               snmp      - this session was established due to
                           an SNMP SetRequest.
            "
    ::= { t11GssSessionEntry 2 }

t11GssSessionOwner OBJECT-TYPE
    SYNTAX          OCTET STRING (SIZE(0..64))
    MAX-ACCESS      read-only
    STATUS          current
    DESCRIPTION
            "This object specifies the owner for this session.

             If the value of the corresponding instance
             of t11GssSessionOwnerType is 'gs5Client', this
             object will contain the FC_ID of the GS-5 client
             which issued the Server Session Begin (SSB)
             which initiated this session.

             If the value of the corresponding instance
             of t11GssSessionOwnerType object is 'cli', this
             object will contain the user name of the CLI
             (Command Line Interface) user on whose behalf
             the session was setup.

             If the value of the corresponding instance
             of t11GssSessionOwnerType is 'snmp', this object
             will contain the source IP address of the SNMP
             SetRequests which initiated the setup of this
             session, in the form: for IPv4, n.n.n.n, or,
             for IPv6, in any of the three conventional forms
             listed in section 2.2 of RFC 3513."
    REFERENCE
            "ANSI INCITS xxx/200x, T11/Project 1677-D/Rev 8.2,
             Fibre Channel - Generic Services-5 (FC-GS-5),
             4 October 2005, section 4.9.5.2.

             RFC 3513, Internet Protocol Version 6 (IPv6)
             Addressing Architecture, April 2003."
    ::= { t11GssSessionEntry 3 }

t11GssSessionControl OBJECT-TYPE
    SYNTAX        INTEGER {
                      commitZoneChanges(1),
                      terminateSession(2),
                      noop(3)
                  }
    MAX-ACCESS    read-write
    STATUS        current
    DESCRIPTION
            "This object can not be modified unless the corresponding
             instance of t11GssSessionOwnerType has the value 'snmp',
             and even then, only by the SNMP entity identified by the
             value of t11GssSessionOwner.  A particular Server may
             impose additional constraints, e.g., a Zone Server will
             reject a commit when it is operating in Basic mode.

             Setting the object requests an action:

              commitZoneChanges - requests that the changes made
                                  within this session to the Zone
                                  Set Database be committed.
              terminateSession  - requests that the session be
                                  terminated, with any outstanding
                                  changes made within this session
                                  being discarded.
              noop              - requests nothing.

             When read, the value is always 'noop'."
    REFERENCE
             "ANSI INCITS xxx/200x, T11/Project 1677-D/Rev 8.2,
              Fibre Channel - Generic Services-5 (FC-GS-5),
              4 October 2005, section 6.4.10.2."
    ::= { t11GssSessionEntry 4 }

t11GssSessionCommitResult OBJECT-TYPE
    SYNTAX        INTEGER {
                      commitSuccessful(1),
                      commitInProgress(2),
                      commitFailed(3),
                      none(4)
                  }
    MAX-ACCESS    read-only
    STATUS        current
    DESCRIPTION
            "This object indicates the current state/outcome of the
             most recent 'commitChanges' request which was invoked via
             the corresponding instance of t11GssSessionControl:

              'commitSuccessful' -- commit successful,
              'commitInProgress' -- commit still in progress,
              'commitFailed'     -- commit failed,
              'none'             -- no request has been invoked
                                    via the corresponding instance
                                    of t11GssSessionControl."
    REFERENCE
             "ANSI INCITS xxx/200x, T11/Project 1677-D/Rev 8.2,
              Fibre Channel - Generic Services-5 (FC-GS-5),
              4 October 2005, section 6.4.10.2.3."
    ::= { t11GssSessionEntry 5 }

-- Conformance

t11GssMIBCompliances OBJECT IDENTIFIER ::= { t11GssMIBConformance 1 }
t11GssMIBGroups      OBJECT IDENTIFIER ::= { t11GssMIBConformance 2 }

t11GssMIBCompliance MODULE-COMPLIANCE
    STATUS       current
    DESCRIPTION
            "The compliance statement for entities which support
             GS-5 Server sessions."
    MODULE MANDATORY-GROUPS { t11GssActiveGroup }

    OBJECT       t11GssSessionControl
    MIN-ACCESS   read-only
    DESCRIPTION
            "Write access is not required."

    ::= { t11GssMIBCompliances 1 }

-- Units of Conformance

t11GssActiveGroup OBJECT-GROUP
    OBJECTS  { t11GssSessionOwnerType,
               t11GssSessionOwner,
               t11GssSessionControl,
               t11GssSessionCommitResult
             }
    STATUS   current
    DESCRIPTION
            "A collection of objects containing information
             about active GS-5 Server sessions."
    ::= { t11GssMIBGroups 1 }

END

-- 
--    Copyright (C) The Internet Society (2005).  This document is subject
--    to the rights, licenses and restrictions contained in BCP 78, and
--    except as set forth therein, the authors retain all their rights.
-- 
--    This document and the information contained herein are provided on an
--    "AS IS" basis and THE CONTRIBUTOR, THE ORGANIZATION HE/SHE REPRESENTS
--    OR IS SPONSORED BY (IF ANY), THE INTERNET SOCIETY AND THE INTERNET
--    ENGINEERING TASK FORCE DISCLAIM ALL WARRANTIES, EXPRESS OR IMPLIED,
--    INCLUDING BUT NOT LIMITED TO ANY WARRANTY THAT THE USE OF THE
--    INFORMATION HEREIN WILL NOT INFRINGE ANY RIGHTS OR ANY IMPLIED
--    WARRANTIES OF MERCHANTABILITY OR FITNESS FOR A PARTICULAR PURPOSE.
-- 
-- Disclaimer of validity
--    The IETF takes no position regarding the validity or scope of any
--    Intellectual Property Rights or other rights that might be claimed to
--    pertain to the implementation or use of the technology described in
--    this document or the extent to which any license under such rights
--    might or might not be available; nor does it represent that it has
--    made any independent effort to identify any such rights.  Information
--    on the procedures with respect to rights in RFC documents can be
--    found in BCP 78 and BCP 79.
-- 
--    Copies of IPR disclosures made to the IETF Secretariat and any
--    assurances of licenses to be made available, or the result of an
--    attempt made to obtain a general license or permission for the use of
--    such proprietary rights by implementers or users of this
--    specification can be obtained from the IETF on-line IPR repository at
--    http://www.ietf.org/ipr.
-- 
--    The IETF invites any interested party to bring to its attention any
--    copyrights, patents or patent applications, or other proprietary
--    rights that may cover technology that may be required to implement
--    this standard.  Please address the information to the IETF at
--    ietf-ipr@ietf.org.
-- 
-- Acknowledgment
-- 
--    Funding for the RFC Editor function is currently provided by the
--    Internet Society.
