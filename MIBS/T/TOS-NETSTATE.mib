-- **********************************************************************
-- TOS-NETSTATE.mib
--
-- Topsec Enterprise Specific MIB: Structure of Management Information
--
-- Copyright (c) 1998-2008, Beijing Topsec Network Security Technology Co.,Ltd. 
-- All Rights Reserved
--
-- The contents of this document are subject to change without notice.
-- **********************************************************************
--
--  Change History:
--
--	Mar 14,2008 - Edit by tos lk 
--
--  Mar 14,2008 - splited from old mib TOSVI-new.mib
--
-- **********************************************************************

TOS-NETSTATE DEFINITIONS ::= BEGIN

	IMPORTS
	    MODULE-IDENTITY,NOTIFICATION-TYPE,OBJECT-TYPE,                                       
	    Integer32, Opaque,Gauge,IpAddress   
	    FROM SNMPv2-SMI
	    
	    TEXTUAL-CONVENTION,DisplayString,DateAndTime
			FROM SNMPv2-TC
			
			tosMib
			FROM TOS-SMI;

--start list TOS MAC table information
	
	tosMACTable	MODULE-IDENTITY
		  LAST-UPDATED "08-03-14" 
	    ORGANIZATION "TOPSEC"
	    CONTACT-INFO
	            " Topsec Beijing
	              China
	              E-mail: support@topsec.com.cn "
		  DESCRIPTION
		          "The (conceptual) table containing information on MAC table."
		        	    
	    REVISION     "05-09-14" 
	    DESCRIPTION
	            "Initial version."
	            
	    REVISION    "20080314"
	    DESCRIPTION
	            "split the whole mib file into several part"

		::= { tosMib 6 }

		
	tosMACEntry	OBJECT-TYPE
	    SYNTAX     TosMACEntry
	    MAX-ACCESS not-accessible
	    STATUS     current
	    DESCRIPTION
	            "An entry (conceptual row) containing the information of a MAC information."
	    INDEX      { macIndex }
	    ::= { tosMACTable 1 }
	    
	TosMACEntry ::= SEQUENCE {
		macIndex           INTEGER,
		macAddress         DisplayString,
		macVlanID          INTEGER,
		macDevName         DisplayString
	}

	macIndex    OBJECT-TYPE
		SYNTAX	INTEGER
		MAX-ACCESS	read-only
		STATUS	current
		DESCRIPTION  
		"Index of the Tos MAC table ."
		::= { tosMACEntry 1  } 

	macAddress      OBJECT-TYPE
		SYNTAX	DisplayString
		MAX-ACCESS	read-only
		STATUS	current
		DESCRIPTION  
		"The MAC address."
		::= { tosMACEntry 2  } 

	macVlanID    OBJECT-TYPE
		SYNTAX		INTEGER	
		MAX-ACCESS	read-only
		STATUS	current
		DESCRIPTION  
		"The VLAN id of the MAC."
		::= { tosMACEntry 3  } 

	macDevName    OBJECT-TYPE
		SYNTAX	DisplayString
		MAX-ACCESS	read-only
		STATUS	current
		DESCRIPTION  
		"The dev name of the MAC."
		::= { tosMACEntry 4  } 

	--end list TOS MAC table information
	
	
	--start list TOS VLAN table information
	tosVLANTable MODULE-IDENTITY
		  LAST-UPDATED "08-03-14"  
	    ORGANIZATION "TOPSEC"
	    CONTACT-INFO
	            " Topsec Beijing
	              China
	              E-mail: support@topsec.com.cn "
		  DESCRIPTION
		        "The (conceptual) table containing information on VLAN table."
		        	    
	    REVISION     "05-09-14" 
	    DESCRIPTION
	            "Initial version."
	            
	    REVISION    "20080314"
	    DESCRIPTION
	            "split the whole mib file into several part"

		::= { tosMib 7 }

	tosVLANEntry OBJECT-TYPE
		SYNTAX     TosVLANEntry
		MAX-ACCESS not-accessible
		STATUS     current
		DESCRIPTION
		        "An entry (conceptual row) containing the information of a VLAN information."
		INDEX      { vlanIndex }
		::= { tosVLANTable 1 }

	TosVLANEntry ::= SEQUENCE {
		vlanIndex          INTEGER,
		vlanId	           INTEGER,
		vlanStatus         DisplayString,
		vlanPorts          DisplayString
	}
		             
	vlanIndex    OBJECT-TYPE
		SYNTAX	INTEGER
		MAX-ACCESS	read-only
		STATUS	current
		DESCRIPTION  
		"Index of the Tos VLAN table ."
		::= { tosVLANEntry 1  } 

	vlanId    OBJECT-TYPE
		SYNTAX	INTEGER
		MAX-ACCESS	read-only
		STATUS	current
		DESCRIPTION  
		"The VLAN id."
		::= { tosVLANEntry 2  } 


	vlanStatus     OBJECT-TYPE
		SYNTAX	DisplayString
		MAX-ACCESS	read-only
		STATUS	current
		DESCRIPTION  
		"The VLAN status."
		::= { tosVLANEntry 3  } 

	vlanPorts    OBJECT-TYPE
		SYNTAX	 DisplayString
		MAX-ACCESS	read-only
		STATUS	current
		DESCRIPTION  
		"The VLAN ports."
		::= { tosVLANEntry 4  } 
	--end list TOS VLAN table information
	
	--start list TOS Route table information
	tosRouteTable MODULE-IDENTITY
		  LAST-UPDATED "08-03-14"  
	    ORGANIZATION "TOPSEC"
	    CONTACT-INFO
	            " Topsec Beijing
	              China
	              E-mail: support@topsec.com.cn "
		  DESCRIPTION
		          "The (conceptual) table containing Route information ."
		        	    
	    REVISION     "05-09-14" 
	    DESCRIPTION
	            "Initial version."
	            
	    REVISION    "20080314"
	    DESCRIPTION
	            "split the whole mib file into several part"

		::= {  tosMib 8 }

	tosRouteEntry OBJECT-TYPE
		SYNTAX     TosRouteEntry
		MAX-ACCESS not-accessible
		STATUS     current
		DESCRIPTION
		        "An entry (conceptual row) containing the Route table ."
		INDEX      { routeIndex }
		::= { tosRouteTable 1 }
		
	TosRouteEntry ::= SEQUENCE {
		routeIndex              INTEGER,
		routeId                 Integer32,
		routeNetSrc		DisplayString,
		routeNetDst             DisplayString,
		routeGateway		DisplayString,
		routeFlags              DisplayString,
		routeMetric             Integer32,
		routeIface              DisplayString
		}
		
		
	routeIndex OBJECT-TYPE
		SYNTAX      INTEGER (0..10000)
		MAX-ACCESS  read-only
		STATUS      current
		DESCRIPTION
		    "Index of Route Table ."
		::= { tosRouteEntry 1 }


	routeId OBJECT-TYPE
		SYNTAX     Integer32
		MAX-ACCESS read-only
		STATUS     current
		DESCRIPTION
		        "Id of the route ."
		::= { tosRouteEntry 2 }

	routeNetSrc OBJECT-TYPE
		SYNTAX     DisplayString
		MAX-ACCESS read-only
		STATUS     current
		DESCRIPTION
		        "the source of route ."
		::= { tosRouteEntry 3 }

	routeNetDst OBJECT-TYPE
		SYNTAX     DisplayString
		MAX-ACCESS read-only
		STATUS     current
		DESCRIPTION
		        "the destination of route ."
		::= { tosRouteEntry 4 }


	routeGateway OBJECT-TYPE
		SYNTAX	DisplayString
		MAX-ACCESS	read-only
		STATUS	current
		DESCRIPTION  
		"the gateway of route ."
		::= { tosRouteEntry 5  } 

	routeFlags OBJECT-TYPE
		SYNTAX		DisplayString
		MAX-ACCESS	read-only
		STATUS	current
		DESCRIPTION  
		"the flags of route ."
		::= { tosRouteEntry 6  } 

	routeMetric OBJECT-TYPE
		SYNTAX		Integer32
		MAX-ACCESS	read-only
		STATUS	current
		DESCRIPTION  
		" the metric of route."
		::= { tosRouteEntry 7 } 

	routeIface OBJECT-TYPE
		SYNTAX		DisplayString
		MAX-ACCESS	read-only
		STATUS	current
		DESCRIPTION  
		" the interface name."
		::= { tosRouteEntry 8 } 
	--end list TOS Route table information
	
	
	--start list TOS ARP table information
	tosARPTable MODULE-IDENTITY
		  LAST-UPDATED "08-03-14"  
	    ORGANIZATION "TOPSEC"
	    CONTACT-INFO
	            " Topsec Beijing
	              China
	              E-mail: support@topsec.com.cn "
		  DESCRIPTION
		          "The (conceptual) table containing ARP information."
		          	    
	    REVISION     "05-09-14" 
	    DESCRIPTION
	            "Initial version."
	            
	    REVISION    "20080314"
	    DESCRIPTION
	            "split the whole mib file into several part"

		::= { tosMib 9  }
	
	tosARPEntry OBJECT-TYPE
		SYNTAX     TosARPEntry
		MAX-ACCESS not-accessible
		STATUS     current
		DESCRIPTION
		        "An entry (conceptual row) containing the information on ARP."
		INDEX      {  arpIndex }
		::= {  tosARPTable 1 }
	
	TosARPEntry ::= SEQUENCE {
		arpIndex                INTEGER,
		arpDevName		DisplayString,
		arpIpAdrress		DisplayString,
		arpMacAddress		DisplayString,
		arpStatus               DisplayString
	     }
	     
	arpIndex OBJECT-TYPE
		SYNTAX      INTEGER (0..1000)
		MAX-ACCESS  read-only
		STATUS      current
		DESCRIPTION
		    "The Index of the ARP table ."
		::= { tosARPEntry 1 }


	arpDevName  OBJECT-TYPE
		SYNTAX      DisplayString (SIZE (0..255))
		MAX-ACCESS  read-only
		STATUS      current
		DESCRIPTION
		        "The device name of the ARP."
		::= { tosARPEntry 2 }

	arpIpAdrress OBJECT-TYPE
		SYNTAX      DisplayString   
		MAX-ACCESS  read-only
		STATUS      current
		DESCRIPTION
		        "The IP address."
		::= { tosARPEntry 3 }

	arpMacAddress  OBJECT-TYPE
		SYNTAX      DisplayString (SIZE (0..255))
		MAX-ACCESS  read-only
		STATUS      current
		DESCRIPTION
		        "The MAC address of the ARP."
		::= { tosARPEntry 4}

	arpStatus  OBJECT-TYPE
		SYNTAX      DisplayString (SIZE (0..255))
		MAX-ACCESS  read-only
		STATUS      current
		DESCRIPTION
		        "Status."
		::= { tosARPEntry 5 }
	--end list TOS ARP table information


	--start list TOS ARP proxy table information
	tosARPProxyTable MODULE-IDENTITY
		  LAST-UPDATED "08-03-14"  
	    ORGANIZATION "TOPSEC"
	    CONTACT-INFO
	            " Topsec Beijing
	              China
	              E-mail: support@topsec.com.cn "
			DESCRIPTION
		          "The (conceptual) table containing ARPProxy information."
		        	    
	    REVISION     "05-09-14" 
	    DESCRIPTION
	            "Initial version."
	            
	    REVISION    "20080314"
	    DESCRIPTION
	            "split the whole mib file into several part"

		::= { tosMib 10  }

	tosARPProxyEntry OBJECT-TYPE
		SYNTAX     TosARPProxyEntry
		MAX-ACCESS not-accessible
		STATUS     current
		DESCRIPTION
		        "An entry (conceptual row) containing the information on ARPProxy."
		INDEX      {  arpProxyIndex }
		::= {  tosARPProxyTable 1 }

	TosARPProxyEntry ::= SEQUENCE {
		arpProxyIndex                   INTEGER,
		arpProxyDevName			DisplayString,
		arpProxyMaxIpAddress		IpAddress,
		arpProxyMinIpAddress		IpAddress,
		arpProxyStat        		DisplayString
	     }

	arpProxyIndex OBJECT-TYPE
		SYNTAX      INTEGER 
		MAX-ACCESS  read-only
		STATUS      current
		DESCRIPTION
		        "The Index of the ARPProxy table ."
		::= { tosARPProxyEntry 1 }

	arpProxyMaxIpAdrress OBJECT-TYPE
		SYNTAX      IpAddress   
		MAX-ACCESS  read-only
		STATUS      current
		DESCRIPTION
		        "The Max IP address."
		::= { tosARPProxyEntry 2 }

	arpProxyMinIpAddress  OBJECT-TYPE
		SYNTAX      IpAddress   
		MAX-ACCESS  read-only
		STATUS      current
		DESCRIPTION
		        "The Min IP address."
		::= { tosARPProxyEntry 3 }

	arpProxyHWaddress  OBJECT-TYPE
		SYNTAX      DisplayString (SIZE (0..255))
		MAX-ACCESS  read-only
		STATUS      current
		DESCRIPTION
		        "The HWaddress."
		::= { tosARPProxyEntry 4 }

	arpProxyStat  OBJECT-TYPE
		SYNTAX      DisplayString (SIZE (0..255))
		MAX-ACCESS  read-only
		STATUS      current
		DESCRIPTION
		        "The device arp proxy status."
		::= { tosARPProxyEntry 5 }
	--end list TOS ARP proxy table information
	
END
