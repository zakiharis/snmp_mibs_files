TM63-MIB DEFINITIONS ::= BEGIN

-- Title:       Lanex OptiLine 16 (TM63) MIB
-- Date:        January 01, 2002
-- Contact:	Dariusz Kusinski, 


IMPORTS
    MODULE-IDENTITY, OBJECT-TYPE, NOTIFICATION-TYPE,
    ObjectName, Integer32,IpAddress, enterprises
        FROM SNMPv2-SMI
    DisplayString, TEXTUAL-CONVENTION, DateAndTime
        FROM SNMPv2-TC;
 

-- groups in MIB-II
lanex       	OBJECT IDENTIFIER ::= { enterprises 5746 }
telecom       	OBJECT IDENTIFIER ::= { lanex 1 }

--- OptiLine16       	OBJECT IDENTIFIER ::= { telecom 2 }

main       		OBJECT IDENTIFIER ::= { optiLine16 1 }
configuration	        OBJECT IDENTIFIER ::= { optiLine16 2 }
status  		OBJECT IDENTIFIER ::= { optiLine16 3 }
eventLog  		OBJECT IDENTIFIER ::= { optiLine16 4 }
es  			OBJECT IDENTIFIER ::= { optiLine16 5 }
test			OBJECT IDENTIFIER ::= { optiLine16 6 }



Hundredths ::= TEXTUAL-CONVENTION
DISPLAY-HINT "d-2"
STATUS       current
DESCRIPTION
           "np. przeksztalc 1234 na 12.34"
SYNTAX     INTEGER (0..65535)


optiLine16 MODULE-IDENTITY
    LAST-UPDATED "0112140000Z"
    ORGANIZATION "Lanex"
    CONTACT-INFO
	   "         Technical Support

	     Postal: Lanex
		     Ceramiczna 8 Str.
		     20-150 Lublin
		     Poland

		Tel: +48 (81) 441 10 11
		Fax: +48 (81) 740 35 70

	     E-mail: snmp@lanex.pl"

    DESCRIPTION
	    ""
    ::= { telecom 2 }



------------------------------------------------------------------------------
-- Grupa MAIN
--
--
mainDeviceName OBJECT-TYPE
    SYNTAX  	DisplayString (SIZE (0..16))
    MAX-ACCESS  read-write
    STATUS  	current
    DESCRIPTION
	    "Nazwa urzadzenia (tekst - 16 znakow)"
    ::= { main 1 }

mainDeviceDescription  OBJECT-TYPE
    SYNTAX  	DisplayString (SIZE (0..16))
    MAX-ACCESS  read-only
    STATUS  	current
    DESCRIPTION
	    "Tekstowy opis urzadzenia (tekst - 16 znakow)"
    ::= { main 2 }

mainDeviceType OBJECT-TYPE
    SYNTAX  	INTEGER (0..255)
    MAX-ACCESS	read-only
    STATUS  	current
    DESCRIPTION
	    "Typ urzadzenia:
	     44 - TM-44
	     49 - TM-60
	     60 - TM-60
             61 - TM-61
	     62 - OptiLine 4 (TM-62)
             63 - OptiLine 16 (TM-63)"
    ::= { main 3 }

mainHardwareVersion OBJECT-TYPE
    SYNTAX	INTEGER (0..255)
    MAX-ACCESS  read-only
    STATUS	current
    DESCRIPTION
	    "Wersja produkcyjna urzadzenia 
             (np.TM-63.x ,gdzie x-wersja produkcyjna"
    ::= { main 4 }

mainLNMPAddress OBJECT-TYPE
    SYNTAX  	Integer32
    MAX-ACCESS  read-only
    STATUS  	current
    DESCRIPTION
	    "Adres urzdzenia wykorzystany w protokole LNMP dla LanWin"
    ::= { main 5 }

mainDevicePhysicalNumber OBJECT-TYPE
    SYNTAX  	INTEGER (0..65535)
    MAX-ACCESS  read-only
    STATUS  	current
    DESCRIPTION
	    "Numer fabryczny urzadzenia"
    ::= { main 6 }

mainDeviceSoftwareVersion OBJECT-TYPE
    SYNTAX       INTEGER (0..65535)
    MAX-ACCESS   read-only
    STATUS       current
    DESCRIPTION  
	    	"Wersja kodu ukladu programowalnego
             np. 101 oznacza wersje 1.01
             "	    
	    ::= {main 7 }

mainSoftwareVersion OBJECT-TYPE
    SYNTAX       INTEGER (0..65535)
    MAX-ACCESS   read-only
    STATUS       current
    DESCRIPTION  
	    "Wersja oprogramowania
	    	np. wartosc 101 oznacza wersje 1.01"	    
       ::= { main 8 }

mainPasswordActivity OBJECT-TYPE
       SYNTAX       INTEGER (0..1)
       MAX-ACCESS   read-write
       STATUS       current
       DESCRIPTION  
		"Aktywacja hasa dostepu do urzdzenia: 0 - haso nieaktywne 1- haso aktywne"

       ::= { main 9 }

   mainPassword  OBJECT-TYPE
       SYNTAX       OCTET STRING (SIZE (0..8))
       MAX-ACCESS   read-write
       STATUS       current
       DESCRIPTION  "Haslo dostepu do urzadzenia"
       ::= { main 10 }


   mainDateTime OBJECT-TYPE
    SYNTAX       DateAndTime 
    MAX-ACCESS   read-write
    STATUS       current
    DESCRIPTION  
		"Data i czas systemowy"
     ::= { main 11 }



------------------------------------------------------------------------------
-- Grupa KONFIGURACJA
--
--

   confLOES OBJECT-TYPE
       SYNTAX       INTEGER (0..65535)
       MAX-ACCESS   read-write
       STATUS       current
       DESCRIPTION  "Zalaczanie/blokowanie kanalow skladowych 1-16
                     Rejestr ZKS jest 16 bitowy i ustawienie poszczegolnych 
                     bitow od bitu nr 0 do 15 na wartooeae 1 powoduje zalonczenie,
                     a ustawienie na 0 wylonczenie odpowiednio  kanalu 1-16.

                     bit   :   15    14    13    12    11    10    9     8
                     nazwa : ZKS16 ZKS15 ZKS14 ZKS13 ZKS12 ZKS11 ZKS10 ZKS9

                     bit   :   7     6     5     4     3     2      1     0
                     nazwa : ZKS8  ZKS7   ZKS6  ZKS5 ZKS4   ZKS3   ZKS2  ZKS1"
       ::= { configuration 1 }

   confAISL OBJECT-TYPE
       SYNTAX       INTEGER (0..65535)
       MAX-ACCESS   read-write
       STATUS       current
       DESCRIPTION  "Generowanie sygnalu AIS w odpowiednim kanale skladowym 1-16
                     Wymuszenie przesania sygnau AIS do odpowiednich kanaow 
                     skadowych (AISLKx = 1 -wymuszenie przesyania sygnau AIS 
                     do kanau skadowego nr x)
                     bit   :   15      14       13       12      11      10      9       8
                     nazwa : AISL16  AISL15   AISL14  AISL13   AISL12  AISL11  AISL10   AISL9

                     bit   :   7       6       5      4      3      2      1      0
                     nazwa : AISL8   AISL7   AISL6  AISL5  AISL4  AISL3  AISL2  AISL1"
       ::= { configuration 2 }


  confAlarmConfirm OBJECT-TYPE
       SYNTAX       INTEGER (0..1)
       MAX-ACCESS   read-write
       STATUS       current
       DESCRIPTION  "Kasowanie (potwierdzanie) alarmu
                     1- kasowanie"
       ::= { configuration 3 }

confTransmitterType OBJECT-TYPE
       SYNTAX       INTEGER (0..2)
       MAX-ACCESS   read-write
       STATUS       current
       DESCRIPTION  "Typ nadajnika bloku zbiorczego: 
                     0-dioda laserowa, 
                     1-dioda LED, 
                     2-elektryczny E3
                    "
       ::= { configuration 4 }

   confTransmitterStatus OBJECT-TYPE
       SYNTAX       INTEGER (0..2)
       MAX-ACCESS   read-write
       STATUS       current
       DESCRIPTION  "Ustawienie nadajnika laserowego: 
                     0-wylaczony/automatyka, 
                     1-pelna moc, 
                     2-obnizona moc"
       ::= { configuration 5 }

   confProgMAXTemperature OBJECT-TYPE
       SYNTAX       INTEGER (0..65535)
       MAX-ACCESS   read-only
       STATUS       current
       DESCRIPTION  "Gorny dopuszczalny poziom temperatury w systemie
                     (wartooeae np. 2758 oznacza temperature 27.58 stopni C)"
       ::= { configuration 6 }

confProgMINTemperature    OBJECT-TYPE
       SYNTAX       INTEGER (0..65535)
       MAX-ACCESS   read-only
       STATUS       current
       DESCRIPTION  "Dolny dopuszczalny poziom temperatury w systemie
                     (wartooeae np. 2758 oznacza temperature 27.58 stopni C)"
       ::= { configuration 7 }

   confProgMAX3V OBJECT-TYPE
       SYNTAX       INTEGER (0..65535)
       MAX-ACCESS   read-only
       STATUS       current
       DESCRIPTION  "Gorny dopuszczalny poziom napiecia 3.3V
                     (wartooeae np. 327 oznacza napiecie 3.27V)"
       ::= { configuration 8 }

   confProgMIN3V OBJECT-TYPE
       SYNTAX       INTEGER (0..65535)
       MAX-ACCESS   read-only
       STATUS       current
       DESCRIPTION  "Dolny dopuszczalny poziom napiecia 3.3V
                     (wartooeae np. 327 oznacza napiecie 3.27V)"
       ::= { configuration 9 }

   confProgMAX5V OBJECT-TYPE
       SYNTAX       INTEGER (0..65535)
       MAX-ACCESS   read-only
       STATUS       current
       DESCRIPTION  "Gorny dopuszczalny poziom napiecia 5V
                     (wartooeae np. 527 oznacza napiecie 5.27V)"
       ::= { configuration 10 }

   confProgMIN5V OBJECT-TYPE
       SYNTAX       INTEGER (0..65535)
       MAX-ACCESS   read-only
       STATUS       current
       DESCRIPTION  "Dolny dopuszczalny poziom napiecia 5V
                     (wartooeae np. 527 oznacza napiecie 5.27V)"
       ::= { configuration 11 }

 



------------------------------------------------------------------------------
-- Grupa STATUS
--
--

   statLOES OBJECT-TYPE
       SYNTAX       INTEGER (0..65535)
       MAX-ACCESS   read-only
       STATUS       current
       DESCRIPTION  "Stan rejestru Sygnalow Skladowych 1-16
                    Zanik sygnau skadowego przychodzcego 
                    do wejoecia (ZSSx=1 - zanik sygnau, ZSSx=0 - sygna obecny, gdzie: x - numer kanalu).
                    bit   :     15      14      13      12      11      10     9      8
                    nazwa :   ZSS16    ZSS15   ZSS14   ZSS13   ZSS12   ZSS11  ZSS10 ZSS9

                    bit   :      7      6       5       4       3        2     1     0
                    nazwa :    ZSS8    ZSS7    ZSS6    ZSS5    ZSS4    ZSS3   ZSS2  ZSS1"
       ::= { status 1 }

   statAISLM OBJECT-TYPE
       SYNTAX       INTEGER (0..65535)
       MAX-ACCESS   read-only
       STATUS       current
       DESCRIPTION  "Stan rejestru Sygnalow AIS Lokalnych 1-16
                    Odbior sygnau AIS przez  urzdzenie lokalne 
                    na wejoeciu (AISLx=1 - urzdzenie odbiera sygna AIS, 
                    AISLx=0 - brak sygnau AIS, gdzie: x - numer kanalu).
                    bit   :   15     14       13      12      11      10      9       8
                    nazwa : AISL16 AISL15   AISL14  AISL13  AISL12  AISL11  AISL10  AISL9
                    
                    bit   :   7       6        5       4        3        2        1       0
                    nazwa : AISL8   AISL7    AISL6   AISL5    AISL4    AISL3    AISL2   AISL1"

       ::= { status 2 }

   statVIOL OBJECT-TYPE
       SYNTAX       INTEGER (0..65535)
       MAX-ACCESS   read-only
       STATUS       current
       DESCRIPTION  "Stan rejestru Blad Wiolacji Sygnalu Skladowego 1-16
                     (BWSSx=1 - jest blad na kanale x, 
                     BWSSx=0 - brak bledu na kanale x, gdzie: x - numer kanalu).
                     bit   :   15      14       13      12      11      10      9       8
                     nazwa : BWSS16  BWSS15   BWSS14  BWSS13  BWSS12  BWSS11  BWSS10  BWSS9

                     bit   :   7       6        5       4        3        2        1   	  0
                     nazwa : BWSS8   BWSS7    BWSS6   BWSS5    BWSS4    BWSS3    BWSS2   BWSS1"

       ::= { status 4 }

   statBZSTAT OBJECT-TYPE
       SYNTAX       INTEGER (0..255)
       MAX-ACCESS   read-only
       STATUS       current
       DESCRIPTION  "Stan rejestru Status Bloku Zbiorczego
                     BZSTAT jest rejestrem 8 bitowym. Znaczenie jego bitow:
                     bit 7: L_OFF - stan pracy lasera (0 wczony, 1-wyczony)
                     bit 6: BWSS - Bd wiolacji kodu 5B-6B sygnau zbiorczego 
                     bit 5: ALZUZ-Alarm Zwrotny Z Urzdzenia Zdalnego (ALZUZ=1 - urzdzenie otrzymao sygna alarmu zwrotnego, ALZUZ=0 - brak sygnau alarmu zwrotnego).
                     bit 4: 106K - Przekroczenie stopy 10-6 bedow kodowych w odebranym sygnale zbiorczym (E10_6=1 - nastpio przekroczenie, E10_6=0 - przekroczenie nie nastpio).
                     bit 3: 103K - Przekroczenie stopy 10-3 bedow kodowych w odebranym sygnale zbiorczym (E10_3=1 - nastpio przekroczenie, E10_3=0 - przekroczenie nie nastpio).
                     bit 2: USR - Utrata Synchronizacji Ramki
                     bit 1: ZMN - Zanik Mocy Nadajnika (0 moc poprawna, 1 moc niepoprawna)
                     bit 0: ZSO - Zanik Sygnau Optycznego na wejoeciu oewiatowodowym"

       ::= { status 5 }

   statSUS OBJECT-TYPE
       SYNTAX       INTEGER (0..255)
       MAX-ACCESS   read-only
       STATUS       current
       DESCRIPTION  "Stan rejestru Status Ukladu Sygnalizacji
                     Bity sygnalizacji alarmow:
                       bit 0: DALP  - bit sygnalizacji alarmu pilnego lub zaniku alarmu po potwierdzeniu
                       bit 1: DPALP - bit sygnalizacji przypomnienia alarmu pilnego
                       bit 2: PALP  - bit zaczenia przekaYnika alarmu pilnego
                       bit 3: DALN  - bit sygnalizacji alarmu niepilnego lub zaniku alarmu po potwierdzeniu
                       bit 4: DPALN - bit sygnalizacji przypomnienia alarmu niepilnego
                       bit 5: PALN  - bit zaczenia przekaYnika alarmu niepilnego"

       ::= { status 6 }

   statKJT OBJECT-TYPE
       SYNTAX       INTEGER (0..255)
       MAX-ACCESS   read-only
       STATUS       current
       DESCRIPTION  "Stan rejestru Kontrola Jakosci Transmisji
                     Bity rejestru:
                     bit 7: PSES24O - Wystpienie przekroczenia wartooeci progowej dla rejestru SES,24 godzinnego, dla kierunku odbiorczego 
                                      (PSES24O=1 - nastpio przekroczenie, PSES24O=0 - przekroczenie nie nastpio)
                     bit 6: PSES24N - Wstpienie przekroczenia wartooeci progowej dla rejestru SES, 24 godzinnego, dla kierunku nadawczego
                                       (PSES24N=1 - nastpio przekroczenie, PSES24N=0 - przekroczenie nie nastpio)
                     bit 5: PES24O  - Wystpienie przekroczenia wartooeci progowej dla rejestru ES, 24 godzinnego, dla kierunku odbiorczego
                                      (PES24O=1 - nastpio przekroczenie, PES24O=0 - przekroczenie nie nastpio)
                     bit 4: PES24N  - Wystpienie przekroczenia wartooeci progowej dla rejestru ES, 24 godzinnego, dla kierunku nadawczego 
                                      (PES24N=1 - nastpio przekroczenie, PES24N=0 - przekroczenie nie nastpio)
                     bit 3: PSES15O - Wystpienie przekroczenia wartooeci progowej dla rejestru SES, 15 minutowego, dla kierunku odbiorczego
                                      (PSES15O=1 - nastpio przekroczenie, PSES15O=0 - przekroczenie nie nastpio)
                     bit 2: PSES15N - Wystpienie przekroczenia wartooeci progowej dla rejestru SES, 15 minutowego, dla kierunku nadawczego
                                      (PSES15N=1 - nastpio przekroczenie, PSES15N=0 - przekroczenie nie nastpio)
                     bit 1: PES15O  - Wystpienie przekroczenia wartooeci progowej dla rejestru ES, 15 minutowego, dla kierunku odbiorczego
                                      (PES15O=1 - nastpio przekroczenie, PES15O=0 - przekroczenie nie nastpio)
                     bit 0: PES15N  - Wystpienie przekroczenia wartooeci progowej dla rejestru ES, 15 minutowego, dla kierunku nadawczego
                                      (PES15N=1 - nastpio przekroczenie, PES15N=0 - przekroczenie nie nastpio)"

       ::= { status 7 }

   statTemperature OBJECT-TYPE
       SYNTAX       Hundredths 
       MAX-ACCESS   read-only
       STATUS       current
       DESCRIPTION  "Temperatura otoczenia systemu
                     (wartooeae np. 2758 oznacza temperature 27.58 stopni C)"
       ::= { status 8 }

stat3VVoltage OBJECT-TYPE
       SYNTAX       INTEGER (0..65535)
       MAX-ACCESS   read-only
       STATUS       current
       DESCRIPTION  "Napiecie zasilania 3.3V
                    (wartooeae np. 327 oznacza napiecie 3.27 V)"
       ::= { status 9 }

stat5VVoltage OBJECT-TYPE
       SYNTAX       INTEGER (0..65535)
       MAX-ACCESS   read-only
       STATUS       current
       DESCRIPTION  "Napiecie zasilania 5V
                     (wartooeae np. 527 oznacza napiecie 5.27 V)"
       ::= { status 10 }

statExtremLevel OBJECT-TYPE
       SYNTAX       INTEGER (0..255)
       MAX-ACCESS   read-only
       STATUS       current
       DESCRIPTION  "Stan napieae zasilajcych i temperatury otoczenia.
                      Poszczegolne bity oznaczaj przekroczenie wartooeci dopuszczalnej (progowej):
                      (1 - przekroczenie wartosci progowej, 0 - wrtosc ponizej ustawionego progu)  
                      bit 0: - stan napiecia 3.3V
                      bit 1: - stan napiecia 5V
                      bit 7: - stan temperatury otoczenia"

       ::= { status 13 }

   statLOESmask OBJECT-TYPE
       SYNTAX       INTEGER (0..65535)
       MAX-ACCESS   read-only
       STATUS       current
       DESCRIPTION  "Maska rejestru Sygnalow skladowych 1-16"
       ::= { status 14 }

   statBZSTATmask OBJECT-TYPE
       SYNTAX       INTEGER (0..255)
       MAX-ACCESS   read-only
       STATUS       current
       DESCRIPTION  "Maska rejestru Status Bloku Zbiorczego"
       ::= { status 15 }


   statAISE3 OBJECT-TYPE
       SYNTAX       INTEGER (0..1)
       MAX-ACCESS   read-only
       STATUS       current
       DESCRIPTION  "Sygnal AIS w module E3"
       ::= { status 16 }
------------------------------------------------------------------------------
-- Grupa DZIENNIK
--
--

logIndexLastEvent OBJECT-TYPE
    SYNTAX	INTEGER (-1..1999)
    MAX-ACCESS	read-only
    STATUS	current
    DESCRIPTION
	    "Indeks do ostatnio wpisanego zdarzenia w historii dziennika zdarzen.
             -1 oznacza dziennik pusty"
    ::= { eventLog 1 }

logErase OBJECT-TYPE
    SYNTAX  	INTEGER {
			  kasowanie(1)
			}
    MAX-ACCESS	read-write
    STATUS	current
    DESCRIPTION	    "Kasowanie dziennika zdarzen ustawienie. 1 - kasowanie"
    ::= { eventLog 2 }

logTable OBJECT-TYPE
    SYNTAX  SEQUENCE OF LogEntry
    MAX-ACCESS	not-accessible
    STATUS	current
    DESCRIPTION
	    "Tabela opisuje dziennik zdarzen"
    ::= { eventLog 3 }

logEntry OBJECT-TYPE
    SYNTAX	LogEntry
    MAX-ACCESS	not-accessible
    STATUS	current
    DESCRIPTION
	    ""
    INDEX   { dzIndex }
    ::= { logTable 1 }

LogEntry ::= SEQUENCE {
	 logIndex			INTEGER (0..1999),
	 logEventDescription	DisplayString (SIZE (0..23))
	    }

logIndex OBJECT-TYPE
       SYNTAX       INTEGER (0..1999)
       MAX-ACCESS   read-only
       STATUS       current
       DESCRIPTION  "Indeks zdarzenia"
       ::= { logEntry 1 }

logEventDescription OBJECT-TYPE
    SYNTAX  	DisplayString (SIZE (0..23))
    MAX-ACCESS  read-only
    STATUS  	current
    DESCRIPTION
	    "Opis Zdarzenia:
             YYYY/MM/DD HH:MM.SS ZZZ
		 YYYY - rok
		 MM   - miesiac
		 DD   - dzien
		 HH   - godzina
		 MM   - minuta
		 SS   - sekunda
		 ZZZ  - identyfikator zdarzenia
            "
    ::= { logEntry 2 }


------------------------------------------------------------------------------
-- Grupa SES
--
--

esLastES15T OBJECT-TYPE
    SYNTAX	INTEGER (0..15)
    MAX-ACCESS	read-only
    STATUS	current
    DESCRIPTION
	    "Indeks ostatniego zapisanego rejestru ES15N w tablicy licznikow"
    ::= { es 1 }

esLastES15R OBJECT-TYPE
    SYNTAX	INTEGER (0..15)
    MAX-ACCESS	read-only
    STATUS	current
    DESCRIPTION
	    "Indeks ostatniego zapisanego rejestru ES15O w tablicy licznikow"
    ::= { es 2 }

esLastSES15T OBJECT-TYPE
    SYNTAX	INTEGER (0..15)
    MAX-ACCESS	read-only
    STATUS	current
    DESCRIPTION
	    "Indeks ostatniego zapisanego rejestru SES15N w tablicy licznikow"
    ::= { es 3 }

esLastSES15R OBJECT-TYPE
    SYNTAX	INTEGER (0..15)
    MAX-ACCESS	read-only
    STATUS	current
    DESCRIPTION
	    "Indeks ostatniego zapisanego rejestru SES15O w tablicy licznikow"
    ::= { es 4 }

esLastES24T OBJECT-TYPE
    SYNTAX	INTEGER (0..1)
    MAX-ACCESS	read-only
    STATUS	current
    DESCRIPTION
	    "Indeks ostatniego zapisanego rejestru ES24N w tablicy licznikow"
    ::= { es 5 }

esLastES24R OBJECT-TYPE
    SYNTAX	INTEGER (0..1)
    MAX-ACCESS	read-only
    STATUS	current
    DESCRIPTION
	    "Indeks ostatniego zapisanego rejestru ES24O w tablicy licznikow"
    ::= { es 6 }

esLastSES24T OBJECT-TYPE
    SYNTAX	INTEGER (0..1)
    MAX-ACCESS	read-only
    STATUS	current
    DESCRIPTION
	    "Indeks ostatniego zapisanego rejestru SES24N  w tablicy licznikow"
    ::= { es 7 }

esLastSES24R OBJECT-TYPE
    SYNTAX	INTEGER (0..1)
    MAX-ACCESS	read-only
    STATUS	current
    DESCRIPTION
	    "Indeks ostatniego zapisanego rejestru SES24O w tablicy licznikow"
    ::= { es 8 }

esErase OBJECT-TYPE
    SYNTAX	INTEGER {
			 kasowanie(1)
			}
    MAX-ACCESS	read-write
    STATUS	current
    DESCRIPTION	  "Kasowanie rejestrow Es/Ses ustawienie 1 - kasowanie"
    ::= { es 9 }

esESAlarm OBJECT-TYPE
    SYNTAX	INTEGER (0..1)
    MAX-ACCESS	read-write
    STATUS	current 
    DESCRIPTION	   "Aktywacja alarmu przekroczenia wartooeci progowej ES lub SES 
                    0 - nieaktywny
                    1 - aktywny"
    ::= { es 10 }

  esES15On OBJECT-TYPE
       SYNTAX       INTEGER (0..900)
       MAX-ACCESS   read-write
       STATUS       current
       DESCRIPTION  "Wartosc progowa zalaczenia alarmu niepilnego w okresie 15 min. (0-900)"
       ::= { es 11 }

   esES15Off OBJECT-TYPE
       SYNTAX       INTEGER (0..900)
       MAX-ACCESS   read-write
       STATUS       current
       DESCRIPTION  "Wartosc progowa wylaczenia alarmu niepilnego w okresie 15 min. (0-900)"
       ::= { es 12 }

   esSES15On OBJECT-TYPE
       SYNTAX       INTEGER (0..900)
       MAX-ACCESS   read-write
       STATUS       current
       DESCRIPTION  "Wartosc progowa zalaczenia alarmu pilnego w okresie 15 min. (0-900)"
       ::= { es 13 }

   esSES15Off OBJECT-TYPE
       SYNTAX       INTEGER (0..900)
       MAX-ACCESS   read-write
       STATUS       current
       DESCRIPTION  "Wartosc progowa wylaczenia alarmu pilnego w okresie 15 min. (0-900)"
       ::= { es 14 }

   esES24On OBJECT-TYPE
       SYNTAX       INTEGER (0..86400)
       MAX-ACCESS   read-write
       STATUS       current
       DESCRIPTION  "Wartosc progowa zalaczenia alarmu niepilnego w okresie 24 h. (0-86400)"
       ::= { es 15 }

   esES24Off OBJECT-TYPE
       SYNTAX       INTEGER (0..86400)
       MAX-ACCESS   read-write
       STATUS       current
       DESCRIPTION  "Wartosc progowa wylaczenia alarmu niepilnego w okresie 24 h. (0-86400)"
       ::= { es 16 }

   esSES24On OBJECT-TYPE
       SYNTAX       INTEGER (0..86400)
       MAX-ACCESS   read-write
       STATUS       current
       DESCRIPTION  "Wartosc progowa zalaczenia alarmu pilnego w okresie 24 h. (0-86400)"
       ::= { es 17 }

   esSES24Off OBJECT-TYPE
       SYNTAX       INTEGER (0..86400)
       MAX-ACCESS   read-write
       STATUS       current
       DESCRIPTION  "Wartosc progowa wylaczenia alarmu pilnego w okresie 24 h. (0-86400)"
       ::= { es 18 }

  esESSESHour OBJECT-TYPE
       SYNTAX       INTEGER (0..23)
       MAX-ACCESS   read-write
       STATUS       current
       DESCRIPTION  "Godzina rozpoczecia zliczania w rejestrach ES i SES"
       ::= { es 19 }

   esESSESMinute OBJECT-TYPE
       SYNTAX       INTEGER (0..59)
       MAX-ACCESS   read-write
       STATUS       current
       DESCRIPTION  "Minuta rozpoczecia zliczania w rejestrach ES i SES"
       ::= { es 20 }

---------------
-- Table ES15N
---------------

esTableES15T OBJECT-TYPE
    SYNTAX  SEQUENCE OF EsEntryES15N
    MAX-ACCESS	not-accessible
    STATUS	current
    DESCRIPTION
	    "Tabela opisuje zapis licznikow ES15N"
    ::= { es 21 }

esEntryES15T OBJECT-TYPE
    SYNTAX	EsEntryES15N
    MAX-ACCESS	not-accessible
    STATUS	current
    DESCRIPTION	    ""
    INDEX   { esIndexES15T }
    ::= { esTableES15T 1 }


EsEntryES15N ::= SEQUENCE {
	 esIndexES15T			INTEGER (0..16),
	 esOpisEventDescriptionES15T	DisplayString (SIZE (0..22))
    }

esIndexES15T OBJECT-TYPE
       SYNTAX       INTEGER (0..16)
       MAX-ACCESS   read-only
       STATUS       current
       DESCRIPTION  "Indeks"
       ::= { esEntryES15T 1 }

esEventDescriptionES15T OBJECT-TYPE
    SYNTAX  	DisplayString (SIZE (0..22))
    MAX-ACCESS  read-only
    STATUS  	current
    DESCRIPTION
	    "Opis:
             YYYY/MM/DD HH:MM LLL A
		 YYYY - rok
		 MM   - miesiac
		 DD   - dzien
		 HH   - godzina
		 MM   - minuta
		 LLL  - licznik sekund z bledami
            "
    ::= { esEntryES15T 2 }

---------------
-- Table ES15R
---------------

esTableES15R OBJECT-TYPE
    SYNTAX  SEQUENCE OF EsEntryES15R
    MAX-ACCESS	not-accessible
    STATUS	current
    DESCRIPTION
	    "Tabela opisuje zapis licznika ES15O"
    ::= { es 22 }

esEntryES15R OBJECT-TYPE
    SYNTAX	EsEntryES15R
    MAX-ACCESS	not-accessible
    STATUS	current
    DESCRIPTION
	    ""
    INDEX   { esIndexES15R }
    ::= { esTableES15R 1 }


EsEntryES15R ::= SEQUENCE {
	 esIndexES15R		INTEGER (0..16),
	 esEventDescriptionES15R	DisplayString (SIZE (0..22))
    }

esIndexES15R OBJECT-TYPE
       SYNTAX       INTEGER (0..16)
       MAX-ACCESS   read-only
       STATUS       current
       DESCRIPTION  "Indeks"
       ::= { esEntryES15R 1 }

esEventDescriptionES15R OBJECT-TYPE
    SYNTAX  	DisplayString (SIZE (0..22))
    MAX-ACCESS  read-only
    STATUS  	current
    DESCRIPTION
	    "Opis:
             YYYY/MM/DD HH:MM LLL A
		 YYYY - rok
		 MM   - miesiac
		 DD   - dzien
		 HH   - godzina
		 MM   - minuta
		 LLL  - licznik sekund z bledami
        "
    ::= { esEntryES15R 2 }

---------------
-- Table SES15T
---------------

esTableSES15T OBJECT-TYPE
    SYNTAX  SEQUENCE OF EsEntrySES15T
    MAX-ACCESS	not-accessible
    STATUS	current
    DESCRIPTION
	    "Tabela opisuje zapis licznika SES15N"
    ::= { es 23 }

esEntrySES15T OBJECT-TYPE
    SYNTAX	EsEntrySES15T
    MAX-ACCESS	not-accessible
    STATUS	current
    DESCRIPTION
	    ""
    INDEX   { esIndexSES15T }
    ::= { esTableSES15T 1 }


EsEntrySES15T ::= SEQUENCE {
	 esIndexSES15T		INTEGER (0..16),
	 esEventDescriptionSES15T	DisplayString (SIZE (0..22))
    }

esIndexSES15T OBJECT-TYPE
       SYNTAX       INTEGER (0..16)
       MAX-ACCESS   read-only
       STATUS       current
       DESCRIPTION  "Indeks"
       ::= { esEntrySES15T 1 }

esEventDescriptionSES15T OBJECT-TYPE
    SYNTAX  	DisplayString (SIZE (0..22))
    MAX-ACCESS  read-only
    STATUS  	current
    DESCRIPTION
	    "Opis:
             YYYY/MM/DD HH:MM LLL A
		 YYYY - rok
		 MM   - miesiac
		 DD   - dzien
		 HH   - godzina
		 MM   - minuta
		 LLL  - licznik sekund z bledami
        "
    ::= { esEntrySES15T 2 }

---------------
-- Table SES15R
---------------

esTableSES15R OBJECT-TYPE
    SYNTAX  SEQUENCE OF EsEntrySES15R
    MAX-ACCESS	not-accessible
    STATUS	current
    DESCRIPTION
	    "Tabela opisuje zapis licznika SES15O"
    ::= { es 24 }

esEntrySES15R OBJECT-TYPE
    SYNTAX	EsEntrySES15R
    MAX-ACCESS	not-accessible
    STATUS	current
    DESCRIPTION
	    ""
    INDEX   { esIndexSES15R }
    ::= { esTableSES15R 1 }


EsEntrySES15R ::= SEQUENCE {
	 esIndexSES15R			INTEGER (0..16),
	 esEventDescriptionSES15R	DisplayString (SIZE (0..22))
    }

esIndexSES15R OBJECT-TYPE
       SYNTAX       INTEGER (0..16)
       MAX-ACCESS   read-only
       STATUS       current
       DESCRIPTION  "Indeks"
       ::= { esEntrySES15R 1 }

esEventDescriptionSES15R OBJECT-TYPE
    SYNTAX  	DisplayString (SIZE (0..22))
    MAX-ACCESS  read-only
    STATUS  	current
    DESCRIPTION
	    "Opis:
             YYYY/MM/DD HH:MM LLL A
		 YYYY - rok
		 MM   - miesiac
		 DD   - dzien
		 HH   - godzina
		 MM   - minuta
		 LLL  - licznik sekund z bledami
        "
    ::= { esEntrySES15R 2 }

---------------
-- Table ES24T
---------------

esTableES24T OBJECT-TYPE
    SYNTAX  SEQUENCE OF EsEntryES24T
    MAX-ACCESS	not-accessible
    STATUS	current
    DESCRIPTION
	    "Tabela opisuje zapis licznika ES24N"
    ::= { es 25 }

esEntryES24T OBJECT-TYPE
    SYNTAX	EsEntryES24T
    MAX-ACCESS	not-accessible
    STATUS	current
    DESCRIPTION
	    ""
    INDEX   { esIndexES24T }
    ::= { esTableES24T 1 }


EsEntryES24T ::= SEQUENCE {
	 esIndexES24T			INTEGER (0..1),
	 esEventDescriptionES24T	DisplayString (SIZE (0..24))
    }

esIndexES24T OBJECT-TYPE
       SYNTAX       INTEGER (0..1)
       MAX-ACCESS   read-only
       STATUS       current
       DESCRIPTION  "Indeks"
       ::= { esEntryES24T 1 }

esEventDescriptionES24T OBJECT-TYPE
    SYNTAX  	DisplayString (SIZE (0..24))
    MAX-ACCESS  read-only
    STATUS  	current
    DESCRIPTION
	    "Opis:
             YYYY/MM/DD HH:MM LLLLL A
		 YYYY - rok
		 MM   - miesiac
		 DD   - dzien
		 HH   - godzina
		 MM   - minuta
		 LLLLL- licznik sekund z bledami
        "
    ::= { esEntryES24T 2 }

---------------
-- Table ES24R
---------------

esTableES24R OBJECT-TYPE
    SYNTAX  SEQUENCE OF EsEntryES24R
    MAX-ACCESS	not-accessible
    STATUS	current
    DESCRIPTION
	    "Tabela opisuje zapis licznika ES24O"
    ::= { es 26 }

esEntryES24R OBJECT-TYPE
    SYNTAX	EsEntryES24R
    MAX-ACCESS	not-accessible
    STATUS	current
    DESCRIPTION
	    ""
    INDEX   { esIndexES24R }
    ::= { esTableES24R 1 }


EsEntryES24R ::= SEQUENCE {
	 esIndexES24R			INTEGER (0..1),
	 esEventDescriptionES24R	DisplayString (SIZE (0..24))
    }

esIndexES24R OBJECT-TYPE
       SYNTAX       INTEGER (0..1)
       MAX-ACCESS   read-only
       STATUS       current
       DESCRIPTION  "Indeks"
       ::= { esEntryES24R 1 }

esEventDescriptionES24R OBJECT-TYPE
    SYNTAX  	DisplayString (SIZE (0..24))
    MAX-ACCESS  read-only
    STATUS  	current
    DESCRIPTION
	    "Opis:
             YYYY/MM/DD HH:MM LLLLL A
		 YYYY - rok
		 MM   - miesiac
		 DD   - dzien
		 HH   - godzina
		 MM   - minuta
		 LLLLL- licznik sekund z bledami
        "
    ::= { esEntryES24R 2 }

---------------
-- Table SES24T
---------------

esTableSES24T OBJECT-TYPE
    SYNTAX  SEQUENCE OF EsEntrySES24T
    MAX-ACCESS	not-accessible
    STATUS	current
    DESCRIPTION
	    "Tabela opisuje zapis licznika SES24N"
    ::= { es 27 }

esEntrySES24T OBJECT-TYPE
    SYNTAX	EsEntrySES24T
    MAX-ACCESS	not-accessible
    STATUS	current
    DESCRIPTION
	    ""
    INDEX   { esIndexSES24T }
    ::= { esTableSES24T 1 }


EsEntrySES24T ::= SEQUENCE {
	 esIndexSES24T			INTEGER (0..1),
	 esEventDescriptionSES24T	DisplayString (SIZE (0..24))
    }

esIndexSES24T OBJECT-TYPE
       SYNTAX       INTEGER (0..11)
       MAX-ACCESS   read-only
       STATUS       current
       DESCRIPTION  "Indeks"
       ::= { esEntrySES24T 1 }

esEventDescriptionSES24T OBJECT-TYPE
    SYNTAX  	DisplayString (SIZE (0..24))
    MAX-ACCESS  read-only
    STATUS  	current
    DESCRIPTION
	    "Opis:
             YYYY/MM/DD HH:MM LLLLL A
		 YYYY - rok
		 MM   - miesiac
		 DD   - dzien
		 HH   - godzina
		 MM   - minuta
		 LLLLL- licznik sekund z bledami
        "
    ::= { esEntrySES24T 2 }


---------------
-- Table SES24R
---------------

esTableSES24R OBJECT-TYPE
    SYNTAX  SEQUENCE OF EsEntrySES24R
    MAX-ACCESS	not-accessible
    STATUS	current
    DESCRIPTION
	    "Tabela opisuje zapis licznika SES24O"
    ::= { es 28 }

esEntrySES24R OBJECT-TYPE
    SYNTAX	EsEntrySES24R
    MAX-ACCESS	not-accessible
    STATUS	current
    DESCRIPTION
	    ""
    INDEX   { esIndexSES24R }
    ::= { esTableSES24R 1 }


EsEntrySES24R ::= SEQUENCE {
	 esIndexSES24R			INTEGER (0..1),
	 esEventDescriptionSES24R	DisplayString (SIZE (0..24))
    }

esIndexSES24R OBJECT-TYPE
       SYNTAX       INTEGER (0..1)
       MAX-ACCESS   read-only
       STATUS       current
       DESCRIPTION  "Indeks"
       ::= { esEntrySES24R 1 }

esEventDescriptionSES24R OBJECT-TYPE
    SYNTAX  	DisplayString (SIZE (0..24))
    MAX-ACCESS  read-only
    STATUS  	current
    DESCRIPTION
	    "Opis:
             YYYY/MM/DD HH:MM LLLLL A
		 YYYY - rok
		 MM   - miesiac
		 DD   - dzien
		 HH   - godzina
		 MM   - minuta
		 LLLLL- licznik sekund z bledami
        "
    ::= { esEntrySES24R 2 }


------------------------------------------------------------------------------
-- Grupa TEST 
--
-- 

testTributaryChannelLoopType1 	OBJECT-TYPE
	    SYNTAX  INTEGER (0..65535)
	    MAX-ACCESS  read-write
	    STATUS  current
	    DESCRIPTION
	    	"Zalaczenie petli  kanalu
	    	 skladowego 1 - 16 do interfejsu.
                 (ALx = 1 zaczenie petli, ALx = 0 wyczene petli na kanale x)
                    bit   :   15     14       13      12      11      10      9       8
                    nazwa :  AL16   AL15     AL14    AL13    AL12    AL11    AL10    AL9
                    
                    bit   :   7       6        5       4        3        2        1   	  0
                    nazwa :  AL8     AL7      AL6     AL5      AL4      AL3      AL2     AL1"

	    ::= {test 1}
	    
testTributaryChannelLoopType2			OBJECT-TYPE
	    SYNTAX  INTEGER (0..65535)
	    MAX-ACCESS  read-write
	    STATUS  current
	    DESCRIPTION
	    	"Zalaczenie petli  kanalu
	    	 skladowego 1 - 16 od interfejsu.
                 (RLx = 1 zaczenie petli, RLx = 0 wyczene petli na kanale x)
                    bit   :   15     14       13      12      11      10      9       8
                    nazwa :  RL16   RL15     RL14    RL13    RL12    RL11    RL10    RL9
                    
                    bit   :   7       6        5       4        3        2        1   	  0
                    nazwa :  RL8     RL7      RL6     RL5      RL4      RL3      RL2     RL1"
	    ::= {test 2}

testMainChannelLoopType1				OBJECT-TYPE
	    SYNTAX  INTEGER (0..1)
	    MAX-ACCESS  read-write
	    STATUS  current
	    DESCRIPTION
	    	"Zalaczenie petli kanalu
	    	zbiorczego do interfejsu"
	    ::= {test 3}

testMainChannelLoopType2			OBJECT-TYPE
	    SYNTAX  INTEGER (0..1)
	    MAX-ACCESS  read-write
	    STATUS  current
	    DESCRIPTION
	    	"Zalaczenie petli kanalu
	    	zbiorczego od interfejsu"
	    ::= {test 4}



	testGeneratorDetector		OBJECT-TYPE
	    SYNTAX  INTEGER (0..17)
	    MAX-ACCESS  read-write
	    STATUS  current
	    DESCRIPTION
	    	"numer generatora/detektora
	    	wykorzystywanego do testu
                 1..16 - generator w kierunku kanalu skladowego (E1) 1..16
                 17 - generator w kierunku kanalu zbiorczego (E3)"
	    ::= {test 5}

	testGCT				OBJECT-TYPE
	    SYNTAX  INTEGER (0..1)
	    MAX-ACCESS  read-write
	    STATUS  current
	    DESCRIPTION
	    	"Sterowanie zaczaniem/wyczaniem generatorow testowych wybranych kanaow E1/E3:
                 1 - generator zaczony
                 0 - generator wyczony"

	    ::= {test 6}

       testTime		OBJECT-TYPE
	    SYNTAX  INTEGER (0..86400)
	    MAX-ACCESS  read-write
	    STATUS  current
	    DESCRIPTION
	    	"Deklarowany czas trwania testu w sekundach. Maks. 24 godziny"
	    ::= {test 7}

	testSyncTime		OBJECT-TYPE
	    SYNTAX  INTEGER (0..86400)
	    MAX-ACCESS  read-only
	    STATUS  current
	    DESCRIPTION
	    	"czas pomiaru gdy jest synchronizacja"
	    ::= {test 8}

	testNoSyncTime		OBJECT-TYPE
	    SYNTAX  INTEGER (0..86400) 
	    MAX-ACCESS  read-only
	    STATUS  current
	    DESCRIPTION
	    	"czas pomiaru gdy brak synchronizacji"
	    ::= {test 9}

	testErrorsPerSec		OBJECT-TYPE
	    SYNTAX  Integer32 
	    MAX-ACCESS  read-only
	    STATUS  current
	    DESCRIPTION
	    	"Biezaca liczba bledow w cyklu sekundowym"
	    ::= {test 10}

	testTotalErrorNumber		OBJECT-TYPE
	    SYNTAX  Integer32
	    MAX-ACCESS  read-only
	    STATUS  current
	    DESCRIPTION
	    	"Calkowita liczba bledow"
	    ::= {test 11}

	testBER		OBJECT-TYPE
	    SYNTAX  DisplayString (SIZE(0..7)) 
	    MAX-ACCESS  read-write
	    STATUS  current
	    DESCRIPTION
	    	"Stopa bledow w formacie:
                 P.Pe-LL (notacja naukowa)
                 przyklad: 2.3e-09"
	    ::= {test 12}

	testErrorsPerSecBWSZ		OBJECT-TYPE
	    SYNTAX  Integer32 
	    MAX-ACCESS  read-only
	    STATUS  current
	    DESCRIPTION
	    	"Biezaca liczba bledow BWSZ w cyklu sekundowym"
	    ::= {test 13}

	testTotalErrorNumberBWSZ		OBJECT-TYPE
	    SYNTAX  Integer32 
	    MAX-ACCESS  read-only
	    STATUS  current
	    DESCRIPTION
	    	"Calkowita liczba bledow BWSZ"
	    ::= {test 14}



	testBERBWSZ		OBJECT-TYPE
	    SYNTAX  DisplayString (SIZE(0..7)) 
	    MAX-ACCESS  read-write
	    STATUS  current
	    DESCRIPTION
	    	"Stopa bledow BWSZ w formacie:
                 P.Pe-LL (notacja naukowa)
                 przyklad: 2.3e-09"
	    ::= {test 15}



	testSyncYesNo		OBJECT-TYPE
	    SYNTAX  INTEGER
	    { 
	      brakSynchronizacja(0),
	      jestSynchronizacja(1)
	    }
	    MAX-ACCESS  read-only
	    STATUS  current
	    DESCRIPTION
	    	"Flaga synchronizacji (1 - oznacza detekcje cigu testowego)"
	    ::= {test 16}

	testStatus			OBJECT-TYPE
	    SYNTAX  INTEGER (0..6)
	    MAX-ACCESS  read-only
	    STATUS  current
	    DESCRIPTION
	    	"status wykonywania testu
                 0 - OFF  - test wyczony
                 1 - ON   - test zaczony 
                 2 - RUN - test trwa
                 3 - READY - gotowooeae do rozpoczecia testu
                 4 - WAIT_ON - oczekiwanie na zaczenie testu
                 5 - WAIT_OFF - oczekiwanie na wyczenie testu
                 6 - WAIT - oczekiwanie"

	    ::= {test 17}

------------------------------------------------------------------------------
-- Grupa TRAPy
--
-- 


optiLine16MIBNotifications               	 OBJECT IDENTIFIER ::= { optiLine16 7 }
mibNotificationsPrefix               OBJECT IDENTIFIER ::= { optiLine16MIBNotifications 0 }
optiLine16MIBObjects               		 OBJECT IDENTIFIER ::= { optiLine16MIBNotifications 1 }


obEventIdn OBJECT-TYPE
       SYNTAX       INTEGER (0..65535)
       MAX-ACCESS   read-only
       STATUS       current
       DESCRIPTION  "Nr zdarzenia"
       ::= { optiLine16MIBObjects 1 }

obEventDescription OBJECT-TYPE
       SYNTAX       DisplayString (SIZE (0..60))
       MAX-ACCESS   read-only
       STATUS       current
       DESCRIPTION  "Opis zdarzenia"
       ::= { optiLine16MIBObjects 2 }


   trapOptiLine16ALPActive NOTIFICATION-TYPE
       STATUS  current
       DESCRIPTION "Aktywny Alarm pilny"

       	--#TYPE "Aktywny Alarm pilny"
	--#SUMMARY "Aktywny Alarm pilny "
	--#SEVERITY CRITICAL
	--#TIMEINDEX 1
	--#HELP "lanexalarm.hlp"
	--#HELPTAG 1
	--#STATE  DEGRADED
	--#CATEGORY "Status Events"
      --- ::= { optiLine16MIBNotifications 0 1 }
          ::= { mibNotificationsPrefix 1 }

   trapOptiLine16ALNActive NOTIFICATION-TYPE
       STATUS  current
       DESCRIPTION "Aktywny Alarm niepilny"
       	--#TYPE "Aktywny Alarm niepilny"
	--#SUMMARY "Aktywny Alarm niepilny "
	--#SEVERITY MINOR
	--#TIMEINDEX 1
	--#HELP "lanexalarm.hlp"
	--#HELPTAG 1
	--#STATE  DEGRADED
	--#CATEGORY "Status Events"
       ::= { optiLine16MIBNotifications 0 2 }

  trapOptiLine16LogIdn NOTIFICATION-TYPE
	OBJECTS {
		   obEventIdn, --identyfikator zdarzenia
		   obEventDescription 

		}
       STATUS  current
       DESCRIPTION "Wystapienie zdarzenia w urzadzeniu:
                    1.Zapis do lokalnego dziennika zdarzen
                    2.Przekazanie identyfikatora zdarzenia w trapie
                    "
      	--#TYPE "Memory: Wystapienie zdarzenia"
	--#SUMMARY "Zdarzenie nr %d: %s"
	--#ARGUMENTS {0,1}
	--#CATEGORY "Status Events"
	--#SEVERITY NORMAL
	--#TIMEINDEX 1
	--#HELP "lanexalarm.hlp"
	--#HELPTAG 1
	--#STATE  DEGRADED
       ::= { optiLine16MIBNotifications 0 3 }

  trapOptiLine16Es NOTIFICATION-TYPE
       STATUS  current
       DESCRIPTION "Zmiana w licznikach es/ses"
       ::= { optiLine16MIBNotifications 0 4 }

 trapOptiLine16confn NOTIFICATION-TYPE
       STATUS  current
       DESCRIPTION "Zapis do zmiennej z grupy knfiguracja, 
                    n - identyfikator elementu, ktory zostal zmodyfikowany"
       ::= { optiLine16MIBNotifications 0 5 }

  trapOptiLine16ALPInactive NOTIFICATION-TYPE
       STATUS  current
       DESCRIPTION "Nieaktywny Alarm pilny"
       	--#TYPE "Nieaktywny Alarm pilny"
	--#SUMMARY "Nieaktywny Alarm pilny "
	--#SEVERITY NORMAL
	--#TIMEINDEX 1
	--#HELP "nwalarm.hlp"
	--#HELPTAG 1
	--#STATE  DEGRADED
	--#CATEGORY "Status Events"

       ::= { optiLine16MIBNotifications 0 6 }

   trapOptiLine16ALNInactive NOTIFICATION-TYPE
       STATUS  current
       DESCRIPTION "Nieaktywny Alarm niepilny"
       	--#TYPE "Nieaktywny Alarm pilny"
	--#SUMMARY "Nieaktywny Alarm pilny "
	--#SEVERITY NORMAL
	--#TIMEINDEX 1
	--#HELP "lanexalarm.hlp"
	--#HELPTAG 1
	--#STATE  DEGRADED
	--#CATEGORY "Status Events"

       ::= { optiLine16MIBNotifications 0 7 }

END
