--
-- This SMIv1 module has been generated by smidump 0.4.1. Do not edit.
--

FASTTRAK-MIB DEFINITIONS ::= BEGIN

IMPORTS
    OBJECT-TYPE
        FROM RFC-1212
    TRAP-TYPE
        FROM RFC-1215
    enterprises 
	FROM RFC1155-SMI
    DisplayString
        FROM RFC1213-MIB;

promise OBJECT IDENTIFIER
    ::= { enterprises 7933 }

fasttrak OBJECT IDENTIFIER
    ::= { promise 2 }

fasttrakManufacturer OBJECT-TYPE
    SYNTAX      DisplayString
    ACCESS      read-only
    STATUS      mandatory
    DESCRIPTION 
        "The name of the product's manufacturer. For instance,
         Promise Technology Inc."
    ::= { fasttrak 1 }

fasttrakModelNumber OBJECT-TYPE
    SYNTAX      DisplayString
    ACCESS      read-only
    STATUS      mandatory
    DESCRIPTION 
        "The name of the fasttrak's model. For instance,
         FastTrak100"
    ::= { fasttrak 2 }

fasttrakVerify OBJECT-TYPE
    SYNTAX      INTEGER { error(0), does-not-exist(1), 
                    verification-not-supported(2), reserved(3), 
                    exists-functionality-not-tested(4), 
                    exists-functionality-unknown(5), 
                    exists-not-functioning-correctly(6), 
                    exists-functioning-correctly(7) }
    ACCESS      read-only
    STATUS      mandatory
    DESCRIPTION 
        "A code that provides a level of verification that the
         component is still installed and working"
    ::= { fasttrak 3 }

fasttrakArrayTable OBJECT-TYPE
    SYNTAX      SEQUENCE OF FasttrakArrayEntry
    ACCESS      not-accessible
    STATUS      mandatory
    DESCRIPTION 
        "A table containing RAID Arrays Information."
    ::= { fasttrak 4 }

fasttrakArrayEntry OBJECT-TYPE
    SYNTAX      FasttrakArrayEntry
    ACCESS      read-only
    STATUS      mandatory
    DESCRIPTION 
        "Individual Array Entry"
    INDEX       { arrayId }
    ::= { fasttrakArrayTable 1 }

FasttrakArrayEntry ::= SEQUENCE {
    arrayId                 INTEGER,
    arrayName               DisplayString,
    arrayRaidMode           INTEGER,
    arrayActivityStatus     INTEGER,
    arrayFunctionalStatus   INTEGER,
    arrayArraySize          INTEGER,
    arrayStripeBlockSize    INTEGER,
    arrayPercentDone        INTEGER
}

arrayId OBJECT-TYPE
    SYNTAX      INTEGER (1..8)
    ACCESS      read-only
    STATUS      mandatory
    DESCRIPTION 
        "Unique Identifier for Array"
    ::= { fasttrakArrayEntry 1 }

arrayName OBJECT-TYPE
    SYNTAX      DisplayString
    ACCESS      read-only
    STATUS      mandatory
    DESCRIPTION 
        "Description string for Array"
    ::= { fasttrakArrayEntry 2 }

arrayRaidMode OBJECT-TYPE
    SYNTAX      INTEGER { unknown(-1), stripe(0), mirror(1), 
                    stripe-mirror(2), span(3), parity-dedicated(4), 
                    parity-distributed(5) }
    ACCESS      read-only
    STATUS      mandatory
    DESCRIPTION 
        "RAID Mode, eg. stripe mirror etc"
    ::= { fasttrakArrayEntry 3 }

arrayActivityStatus OBJECT-TYPE
    SYNTAX      INTEGER { unknown(-1), idle(0), manual-rebuild(1), 
                    engine-rebuild(2), synchronize(3), expanding(4) }
    ACCESS      read-only
    STATUS      mandatory
    DESCRIPTION 
        "Activity status, eg. idle, under maintenance etc."
    ::= { fasttrakArrayEntry 4 }

arrayFunctionalStatus OBJECT-TYPE
    SYNTAX      INTEGER { unknown(-1), functional(0), critical(1), 
                    offline(2) }
    ACCESS      read-only
    STATUS      mandatory
    DESCRIPTION 
        "Functional status, under maintenance, performance is degraded"
    ::= { fasttrakArrayEntry 5 }

arrayArraySize OBJECT-TYPE
    SYNTAX      INTEGER
    ACCESS      read-only
    STATUS      mandatory
    DESCRIPTION 
        "Size of Array, in MB"
    ::= { fasttrakArrayEntry 6 }

arrayStripeBlockSize OBJECT-TYPE
    SYNTAX      INTEGER
    ACCESS      read-only
    STATUS      mandatory
    DESCRIPTION 
        "Stripe Block Size for striping and parity striping in KB"
    ::= { fasttrakArrayEntry 7 }

arrayPercentDone OBJECT-TYPE
    SYNTAX      INTEGER
    ACCESS      read-only
    STATUS      mandatory
    DESCRIPTION 
        "Percent completed for rebuild or synchronize"
    ::= { fasttrakArrayEntry 8 }

fasttrakDiskTable OBJECT-TYPE
    SYNTAX      SEQUENCE OF FasttrakDiskEntry
    ACCESS      not-accessible
    STATUS      mandatory
    DESCRIPTION 
        "A table containing one entry for every disk attached to the FastTrak Controller"
    ::= { fasttrak 5 }

fasttrakDiskEntry OBJECT-TYPE
    SYNTAX      FasttrakDiskEntry
    ACCESS      read-only
    STATUS      mandatory
    DESCRIPTION 
        "A conceptual row of the fasttrakDiskTable"
    INDEX       { diskId }
    ::= { fasttrakDiskTable 1 }

FasttrakDiskEntry ::= SEQUENCE {
    diskId              INTEGER,
    diskChannel         INTEGER,
    diskMasSlaveId      INTEGER,
    diskName            DisplayString,
    diskSMARTStatus     INTEGER,
    diskSize            INTEGER,
    diskAssigned        INTEGER,
    diskTiming          INTEGER,
    diskMaintenance     INTEGER,
    diskFunctional      INTEGER,
    diskArrayID         DisplayString,
    diskControllerID    INTEGER
}

diskId OBJECT-TYPE
    SYNTAX      INTEGER (0..7)
    ACCESS      read-only
    STATUS      mandatory
    DESCRIPTION 
        "ID of disk, 0=pri mas, thru 3=sec slave"
    ::= { fasttrakDiskEntry 1 }

diskChannel OBJECT-TYPE
    SYNTAX      INTEGER (0..1)
    ACCESS      read-only
    STATUS      mandatory
    DESCRIPTION 
        "Channel Number 0=pri, 1=sec"
    ::= { fasttrakDiskEntry 2 }

diskMasSlaveId OBJECT-TYPE
    SYNTAX      INTEGER (0..1)
    ACCESS      read-only
    STATUS      mandatory
    DESCRIPTION 
        "ID of disk, 0=mas, 1=slave"
    ::= { fasttrakDiskEntry 3 }

diskName OBJECT-TYPE
    SYNTAX      DisplayString
    ACCESS      read-only
    STATUS      mandatory
    DESCRIPTION 
        "Disk Model, Identify information from Disk"
    ::= { fasttrakDiskEntry 4 }

diskSMARTStatus OBJECT-TYPE
    SYNTAX      INTEGER { unknown(-1), sMARTFail(0), sMARTOK(1), 
                    sMARTNotSupported(2), sMARTNotAvailable(3) }
    ACCESS      read-only
    STATUS      mandatory
    DESCRIPTION 
        "Disk S.M.A.R.T Status (Self Monitoring Status)"
    ::= { fasttrakDiskEntry 5 }

diskSize OBJECT-TYPE
    SYNTAX      INTEGER
    ACCESS      read-only
    STATUS      mandatory
    DESCRIPTION 
        "Disk Size, in MB"
    ::= { fasttrakDiskEntry 6 }

diskAssigned OBJECT-TYPE
    SYNTAX      INTEGER { unknown(-1), free(0), assigned(1) }
    ACCESS      read-only
    STATUS      mandatory
    DESCRIPTION 
        "Whether or not disk is assigned to an RAID Array"
    ::= { fasttrakDiskEntry 7 }

diskTiming OBJECT-TYPE
    SYNTAX      INTEGER { unknown(-1), udma4(0), udma3(1), udma2(2), 
                    udma1(3), udma0(4), dma2(5), dma1(6), dma0(7), 
                    udma5(8) }
    ACCESS      read-only
    STATUS      mandatory
    DESCRIPTION 
        "DMA or UDMA mode of Disk"
    ::= { fasttrakDiskEntry 8 }

diskMaintenance OBJECT-TYPE
    SYNTAX      INTEGER { unknown(-1), idle(0), rebuilding(1), 
                    synchronizing(2) }
    ACCESS      read-only
    STATUS      mandatory
    DESCRIPTION 
        "Whether Disk is idle or under maintenance activity"
    ::= { fasttrakDiskEntry 9 }

diskFunctional OBJECT-TYPE
    SYNTAX      INTEGER { unknown(-1), functional(0), offline(1), 
                    functionalneedsrebuild(2) }
    ACCESS      read-only
    STATUS      mandatory
    DESCRIPTION 
        "Functional Status of Disk"
    ::= { fasttrakDiskEntry 10 }

diskArrayID OBJECT-TYPE
    SYNTAX      DisplayString
    ACCESS      read-only
    STATUS      mandatory
    DESCRIPTION 
        "Array disk is associated with"
    ::= { fasttrakDiskEntry 11 }

diskControllerID OBJECT-TYPE
    SYNTAX      INTEGER
    ACCESS      read-only
    STATUS      mandatory
    DESCRIPTION 
        "Associates the physical controller with the disk"
    ::= { fasttrakDiskEntry 12 }

fasttrakControllerTable OBJECT-TYPE
    SYNTAX      SEQUENCE OF FasttrakControllerEntry
    ACCESS      not-accessible
    STATUS      mandatory
    DESCRIPTION 
        "A table containing one entry for each FastTrak Controller"
    ::= { fasttrak 6 }

fasttrakControllerEntry OBJECT-TYPE
    SYNTAX      FasttrakControllerEntry
    ACCESS      read-only
    STATUS      mandatory
    DESCRIPTION 
        "A conceptual row of the FastTrak controller"
    INDEX       { controllerID }
    ::= { fasttrakControllerTable 1 }

FasttrakControllerEntry ::= SEQUENCE {
    controllerID            INTEGER,
    controllerIRQ           INTEGER,
    controllerPCIBus        INTEGER,
    controllerPCIDev        INTEGER,
    controllerPCIFunc       INTEGER,
    controllerBIOSAddress   DisplayString,
    controllerBaseAddress   DisplayString
}

controllerID OBJECT-TYPE
    SYNTAX      INTEGER (0..1)
    ACCESS      read-only
    STATUS      mandatory
    DESCRIPTION 
        "ID of the controller in the system"
    ::= { fasttrakControllerEntry 1 }

controllerIRQ OBJECT-TYPE
    SYNTAX      INTEGER
    ACCESS      read-only
    STATUS      mandatory
    DESCRIPTION 
        "IRQ assigned to this specific controller"
    ::= { fasttrakControllerEntry 2 }

controllerPCIBus OBJECT-TYPE
    SYNTAX      INTEGER
    ACCESS      read-only
    STATUS      mandatory
    DESCRIPTION 
        "PCI Bus assigned to this controller"
    ::= { fasttrakControllerEntry 3 }

controllerPCIDev OBJECT-TYPE
    SYNTAX      INTEGER
    ACCESS      read-only
    STATUS      mandatory
    DESCRIPTION 
        "PCI Dev assigned to this controller"
    ::= { fasttrakControllerEntry 4 }

controllerPCIFunc OBJECT-TYPE
    SYNTAX      INTEGER
    ACCESS      read-only
    STATUS      mandatory
    DESCRIPTION 
        "PCI Func assigned to this controller"
    ::= { fasttrakControllerEntry 5 }

controllerBIOSAddress OBJECT-TYPE
    SYNTAX      DisplayString
    ACCESS      read-only
    STATUS      mandatory
    DESCRIPTION 
        "The BIOS ROM Start address for this specific controller"
    ::= { fasttrakControllerEntry 6 }

controllerBaseAddress OBJECT-TYPE
    SYNTAX      DisplayString
    ACCESS      read-only
    STATUS      mandatory
    DESCRIPTION 
        "The controller base address"
    ::= { fasttrakControllerEntry 7 }

traps OBJECT IDENTIFIER
    ::= { fasttrak 12 }

trapType OBJECT-TYPE
    SYNTAX      INTEGER { e-unknown(-1), e-ecc-error(0), e-disk-down(1), 
                    e-disk-plugin(2), e-bad-sector(3), 
                    e-rebuild-start(4), e-synchronize-start(5), 
                    e-disk-retry(6), e-array-critical(7), 
                    e-array-offline(8), e-rebuild-completed(9), 
                    e-synchronize-completed(10), e-disk-media-error(11), 
                    e-reserved-sector-error(12), e-rebuild-aborted(13), 
                    e-synchronize-aborted(14), e-sync-compare-error(15), 
                    e-disk-SMART-fail(16), 
                    e-swap-enclosure-powerdown(17), 
                    e-swap-enclosure-powerup(18), 
                    e-swap-enclosure-badswap(19), 
                    e-swap-enclosure-over-temp(20), 
                    e-swap-enclosure-fan-stopped(21), 
                    e-swap-enclosure-12v-outofrange(22), 
                    e-swap-enclosure-5v-outofrange(23) }
    ACCESS      read-only
    STATUS      mandatory
    DESCRIPTION 
        "Value which indicate the nature of the event causing the Trap"
    ::= { traps 1 }

trapArrayId OBJECT-TYPE
    SYNTAX      INTEGER
    ACCESS      read-only
    STATUS      mandatory
    DESCRIPTION 
        "Array ID of event source, if relevant, if not -1"
    ::= { traps 2 }

trapDiskId OBJECT-TYPE
    SYNTAX      INTEGER
    ACCESS      read-only
    STATUS      mandatory
    DESCRIPTION 
        "Disk ID of event source, if relevant, if not -1"
    ::= { traps 3 }

trapDescription OBJECT-TYPE
    SYNTAX      INTEGER { smart-error(1), ecc-error(2), disk-down(3), 
                    disk-plugin(5), disk-badsector(6), rebuild-start(7), 
                    sync-start(8), disk-retry(9), array-offline(10), 
                    array-critical(11), rebuild-complete(12), 
                    sync-complete(13), disk-mediaerror(14), 
                    disk-reservedsectorerror(15), rebuild-aborted(16), 
                    sync-aborted(17), sync-comparisonerror(19), 
                    swap-powerdown(20), swap-powerup(21), 
                    swap-badswap(22), swap-overtemp(23), 
                    swap-fanstop(24), swap-12voltoutofrange(25), 
                    swap-5voltoutofrange(26) }
    ACCESS      read-only
    STATUS      mandatory
    DESCRIPTION 
        "Description of Error, with parameters
         smart-error(1) is the SMART disk error event.
         ecc-error(2) is the disk ECC Error error event.
         disk-down(3) is the disk offline error event.
         disk-plugin(5) is the disk plugged in event.
         disk-badsector(6) is the bad sector on disk error event.
         rebuild-start(7) is the rebuild start event.
         sync-start(8) is the sync start event.
         disk-retry(9) is the disk retry event.
         array-offline(10) is the array offline error event.
         array-critical(11) is the array critical error event.
         rebuild-complete(12) is the rebuild complete event.
         sync-complete(13) is the sync complete event.
         disk-mediaerror(14) is the disk media error event.
         disk-reservedsectorerror(15) is the disk reserved sector error event.
         rebuild-aborted(16) is the rebuild aborted error event.
         sync-aborted(17) is the sync aborted error event.
         sync-comparisonerror(19) is the sync comparison error event.
         swap-powerdown(20) is the swap power down event.
         swap-powerup(21) is the swap power up event.
         swap-badswap(22) is the bad swap error event.
         swap-overtemp(23) is the over temperature error event.
         swap-fanstop(24) is the swap fan stop error event.
         swap-12voltoutofrange(25) is the out of range 12 volts error event.
         swap-5voltoutofrange(26) is the out of range 5 volts error event."
    ::= { traps 4 }

fasttrakDriverVersion OBJECT-TYPE
    SYNTAX      DisplayString
    ACCESS      read-only
    STATUS      mandatory
    DESCRIPTION 
        "Is the driver version currently installed in the system"
    ::= { fasttrak 15 }


	trpUnknown	TRAP-TYPE
		ENTERPRISE	promise
		DESCRIPTION
			 "Unknown - possibly new driver error code"
			 --#SUMMARY  "Unknown"
			 --#ARGUMENTS { }
			 --#SEVERITY INFORMATIONAL
		::= 1



	trpEccError	TRAP-TYPE
		ENTERPRISE	promise
		DESCRIPTION
			 "ECC Error on Disk <name> LBA <lba>"
			--#SUMMARY  "ECC Error on Disk"
			--#ARGUMENTS { }
			--#SEVERITY CRITICAL
		::= 2



	trpDiskDown	TRAP-TYPE
		ENTERPRISE	promise
		DESCRIPTION
			 "Disk Down <disk_name>"
			--#SUMMARY  "Disk Set Down by Driver"
			--#ARGUMENTS { }
			--#SEVERITY MAJOR
		::= 3


	trpDiskOffline	TRAP-TYPE
		ENTERPRISE	promise
		VARIABLES	{trapDiskId, trapArrayId, trapType,trapDescription}
		DESCRIPTION
			"Disk Offline <disk_name>"
			--#SUMMARY  "Disk %d of array %d set offline by driver. Description: %d"
			--#ARGUMENTS {0, 1, 3 }
			--#SEVERITY MAJOR
		::= 4


	trpDiskPlugin	TRAP-TYPE
			ENTERPRISE	promise
			DESCRIPTION
			"Disk Plugin <disk_name>"
			--#SUMMARY  "New Disk Plugged In"
			--#ARGUMENTS { }
			--#SEVERITY MINOR
		::= 5

	trpAryBadSector	TRAP-TYPE
			ENTERPRISE	promise
			DESCRIPTION
			 "Array <num> had BadSector at LBA <lba>"
			--#SUMMARY  "Bad sector encountered"
			--#ARGUMENTS { }
			--#SEVERITY INFORMATIONAL
		::= 6

	trpRebuildStart	TRAP-TYPE
			ENTERPRISE	promise
			DESCRIPTION
			 "Rebuild Started Array <array> disk <disk>"
			--#SUMMARY  "Rebuild started"
			--#ARGUMENTS { }
			--#SEVERITY INFORMATIONAL
		::= 7

	trpSyncStart	TRAP-TYPE
			ENTERPRISE	promise
			DESCRIPTION
			"Synchronization Started, Array <array>"
			--#SUMMARY  "Synchronization Started"
			--#ARGUMENTS { }
			--#SEVERITY INFORMATIONAL
		::= 8

	trpRetryDisk	TRAP-TYPE
			ENTERPRISE	promise
			DESCRIPTION
			 "Retry Disk Task, disk <disk> lba <lba>"
			--#SUMMARY  "Retry Disk Task"
			--#ARGUMENTS { }
			--#SEVERITY MINOR
		::= 9

	trpArrayOffline	TRAP-TYPE
			ENTERPRISE	promise
			DESCRIPTION
			 "Array Offline <array>"
			--#SUMMARY  "Array Offline"
			--#ARGUMENTS { }
			--#SEVERITY MAJOR
		::= 10

	trpArrayCritical	TRAP-TYPE
			ENTERPRISE	promise
			DESCRIPTION
			"Array Critical <array>"
			--#SUMMARY  "Array Critical"
			--#ARGUMENTS { }
			--#SEVERITY CRITICAL
	::= 11

	trpArrayRebuildComplete	TRAP-TYPE
			ENTERPRISE	promise
			DESCRIPTION
			"Rebuild Completed, Array <array>, disk <disk>"
			--#SUMMARY  "Rebuild Completed"
			--#ARGUMENTS { }
			--#SEVERITY INFORMATIONAL
	::= 12

	trpArraySyncComplete	TRAP-TYPE
			ENTERPRISE	promise
			DESCRIPTION
			"Sync Completed, array <array>"
			--#SUMMARY  "Synchronization Completed"
			--#ARGUMENTS { }
			--#SEVERITY INFORMATIONAL
	::= 13

	trpMediaError	TRAP-TYPE
			ENTERPRISE	promise
			DESCRIPTION
			"Array <array>, disk <disk> has Media Error at LBA <lba>, cmd=<cmd>, status=<status>"
			--#SUMMARY  "Media Error on Disk"
			--#ARGUMENTS { }
			--#SEVERITY CRITICAL
	::= 14

	trpReserveSectorError	TRAP-TYPE
			ENTERPRISE	promise
			DESCRIPTION
			 "Reserved Sector Error, Disk <disk> lba <lba>"
			--#SUMMARY  "Reserved Sector Error"
			--#ARGUMENTS { }
			--#SEVERITY MINOR
	::= 15

	trpRebuildAborted	TRAP-TYPE
			ENTERPRISE	promise
			DESCRIPTION
			"Rebuild Aborted, Array <array>, disk <disk>, percent <percent>"
			--#SUMMARY  "Rebuild Aborted"
			--#ARGUMENTS { }
			--#SEVERITY CRITICAL
	::= 16

	trpSyncAborted	TRAP-TYPE
			ENTERPRISE	promise
			DESCRIPTION
			"Synchronization Aborted, array <array>, percent <percent>"
			--#SUMMARY  "Sync. Aborted"
			--#ARGUMENTS { }
			--#SEVERITY CRITICAL
	::= 17

	trpECCFixFail	TRAP-TYPE
			ENTERPRISE	promise
			DESCRIPTION
			"ECC Fix Failed"
			--#SUMMARY  "ECC Fix Failed"
			--#ARGUMENTS { }
			--#SEVERITY CRITICAL
	::= 18

	trpSyncCompError	TRAP-TYPE
			ENTERPRISE	promise
			DESCRIPTION
			 "Sync Compare Error, Array <array>, LBA= <lba>"
			--#SUMMARY  "Sync. Compare Error"
			--#ARGUMENTS { }
			--#SEVERITY MINOR
	::= 19

	trpSwapBoxPowerDown		TRAP-TYPE
			ENTERPRISE	promise
			DESCRIPTION
			 "Swap Box Power Down, channel <ch>, msl <msl>"
			--#SUMMARY  "Swap Box Power Down"
			--#ARGUMENTS { }
			--#SEVERITY INFORMATIONAL
	::= 20

	trpSwapBoxPowerUp		TRAP-TYPE
			ENTERPRISE	promise
			DESCRIPTION
			"Swap Box Power Up, channel <ch>, msl <msl>"
			--#SUMMARY  "Swap Box Power Up"
			--#ARGUMENTS { }
			--#SEVERITY INFORMATIONAL
	::= 21

	trpSwapBoxBadSwap		TRAP-TYPE
			ENTERPRISE	promise
			DESCRIPTION
			"Swap Box, Bad Swap, channel <ch>, msl <msl>"
			--#SUMMARY  "Swap Box, Bad Swap"
			--#ARGUMENTS { }
			--#SEVERITY MINOR
	::= 22

	trpSwapBoxOverTemp		TRAP-TYPE
			ENTERPRISE	promise
			DESCRIPTION
			"Swap Box, Over Temp, channel <ch>, msl <msl>, Temp <fahr>, C <cent>"
			--#SUMMARY  "Swap Box Over Temp"
			--#ARGUMENTS { }
			--#SEVERITY MINOR
	::= 23

	trpSwapBoxFanStopped	TRAP-TYPE
			ENTERPRISE	promise
			DESCRIPTION
			"Swap Box Fan Stop, channel <ch>, msl <msl>, RPM= <rpm>"
			--#SUMMARY  "Swap Box Fan Stop"
			--#ARGUMENTS { }
			--#SEVERITY MINOR
	::= 24

	trpSwapBox12VOutOfRange	TRAP-TYPE
			ENTERPRISE	promise
			DESCRIPTION
			"Swap Box, 12V Out of Range, channel <ch>, msl <msl>, 12V=<volts>"
			--#SUMMARY  "12V Out of Range"
			--#ARGUMENTS { }
			--#SEVERITY MINOR
	::= 25

	trpSwapBox5VOutOfRange	TRAP-TYPE
			ENTERPRISE	promise
			DESCRIPTION
			"Swap Box, 5V Out of Range, channel <ch>, msl <msl>, 5V=<volts>"
			--#SUMMARY  "5V Out of Range"
			--#ARGUMENTS { }
			--#SEVERITY MINOR
	::= 26

END -- end of module FASTTRAK-MIB.
