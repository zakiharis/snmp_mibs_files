FOUNDRY-CAR-MIB DEFINITIONS ::= BEGIN

IMPORTS

	MODULE-IDENTITY, OBJECT-TYPE,Gauge32, Counter64,Integer32
		FROM SNMPv2-SMI
	MacAddress, TEXTUAL-CONVENTION
		FROM SNMPv2-TC
	snSwitch
		FROM FOUNDRY-SN-SWITCH-GROUP-MIB
	InterfaceIndex, ifIndex
		FROM IF-MIB;

snCAR MODULE-IDENTITY
    LAST-UPDATED "201006020000Z"  -- 04 June 2010
    ORGANIZATION "Brocade Communications Systems, Inc."
    CONTACT-INFO
             "Technical Support Center
              130 Holger Way,
              San Jose, CA  95134
              Email:  ipsupport@brocade.com
              Phone: 1-800-752-8061
              URL:  www.brocade.com"
    DESCRIPTION
             "Copyright 1996-2010 Brocade Communications Systems, Inc.
              All rights reserved.
              This Brocade Communications Systems SNMP Management Information Base Specification
              embodies Brocade Communications Systems' confidential and proprietary
              intellectual property. Brocade Communications Systems retains all
              title and ownership in the Specification, including any revisions.

              This Specification is supplied AS IS, and Brocade Communications Systems makes
              no warranty, either express or implied, as to the use,
              operation, condition, or performance of the specification, and any unintended
              consequence it may on the user environment."

    REVISION        "201006020000Z"  -- 04 June 2010
    DESCRIPTION
        "Changed the ORGANIZATION, CONTACT-INFO and DESCRIPTION fields."

    REVISION     "200909300000Z" -- September 30, 2009
    DESCRIPTION
			"convert from SMIv1 to SMIv2"

   ::= { snSwitch 16}
snPortCARs	OBJECT IDENTIFIER ::= { snCAR 1 }

	--  Textual Conventions

	PacketSource::= TEXTUAL-CONVENTION
	STATUS      current
	DESCRIPTION
		"
		"
	SYNTAX  INTEGER {
		input(0), --for inbound traffic
		output(1) --for outbound traffic
	}


	RateLimitType::= TEXTUAL-CONVENTION
	STATUS      current
	DESCRIPTION
		"
		"
	SYNTAX   INTEGER{
		all(3), 		--	all traffic.
		quickAcc(2), 	--	traffic matches rate-limit's access list.
		standardAcc(1) 	--	traffic matches standard access list.
	}

	RateLimitAction::= TEXTUAL-CONVENTION
	STATUS      current
	DESCRIPTION
		"
		"
	SYNTAX  INTEGER {
		continue(1),
		drop(2),
		precedCont(3),
		precedXmit(4),
		xmit(5)
	}

	BUMPacketType::= TEXTUAL-CONVENTION
	STATUS      current
	DESCRIPTION
		"
		"
	SYNTAX  INTEGER {
		unknownunicast(1),
		multicast(2),
		unknownunicastmulticast(3),
		broadcast(4),
		broadcastunknownunicast(5),
		broadcastmulticast(6),
		broadcastunknownunicastmulticast(7)
	}

snPortCARTable OBJECT-TYPE
	SYNTAX  SEQUENCE OF SnPortCAREntry
	MAX-ACCESS  not-accessible
		STATUS  current
		DESCRIPTION
		"A table of rate limit configuration entries.
	Rate Limit is a method of traffic control.  It allows a set
	of rate limits to be configured and applied to packets flowing
	into/out of an interface to regulate network traffic."

		::= { snPortCARs 1 }

snPortCAREntry OBJECT-TYPE
		SYNTAX SnPortCAREntry
		MAX-ACCESS  not-accessible
		STATUS  current
		DESCRIPTION
			"A collection of rate-limit configuration objects on this
		interface."
		INDEX { snPortCARifIndex, snPortCARDirection, snPortCARRowIndex }
		::= { snPortCARTable 1 }

SnPortCAREntry ::=
	SEQUENCE {
		snPortCARifIndex
						InterfaceIndex,
		snPortCARDirection
					PacketSource,
		snPortCARRowIndex
						INTEGER,
		snPortCARType
						RateLimitType,
		snPortCARAccIdx
						Integer32,
		snPortCARRate
						Integer32,
		snPortCARLimit
						Integer32,
		snPortCARExtLimit
						Integer32,
		snPortCARConformAction
						RateLimitAction,
		snPortCARExceedAction
						RateLimitAction,
		snPortCARStatSwitchedPkts
						Counter64,
		snPortCARStatSwitchedBytes
						Counter64,
		snPortCARStatFilteredPkts
						Counter64,
		snPortCARStatFilteredBytes
						Counter64,
		snPortCARStatCurBurst
						Gauge32
	}
snPortCARifIndex OBJECT-TYPE
	SYNTAX     InterfaceIndex
	MAX-ACCESS     read-only
	STATUS     current
	DESCRIPTION
			"The ifIndex value for this rate limit entry."
	::= { snPortCAREntry 1 }

snPortCARDirection OBJECT-TYPE
	SYNTAX  PacketSource
		MAX-ACCESS  read-only
		STATUS  current
		DESCRIPTION
			"The input or output transmission direction for the
				Rate Limit object.
				input (0), --for inbound traffic
				output(1) --for outbound traffic "
		::= { snPortCAREntry 2 }

snPortCARRowIndex OBJECT-TYPE
	SYNTAX  INTEGER (1..2147483647)
		MAX-ACCESS  read-only
		STATUS  current
		DESCRIPTION
				"The table index for rate limit objects.
		It increases as the rate limit entries are added.
		Skips the number when a row is deleted."

		::= { snPortCAREntry 3 }

snPortCARType OBJECT-TYPE
	SYNTAX  RateLimitType
		MAX-ACCESS  read-only
		STATUS  current
		DESCRIPTION
		"The type of traffic rate-limited against."

	::= { snPortCAREntry 4 }

snPortCARAccIdx OBJECT-TYPE
	SYNTAX  Integer32
		MAX-ACCESS  read-only
		STATUS  current
		DESCRIPTION
		"The index to the access list if RateLimitType is either
		quickAcc or standardAcc."

	::= { snPortCAREntry 5 }

snPortCARRate OBJECT-TYPE
	SYNTAX  Integer32
		MAX-ACCESS  read-only
		STATUS  current
		DESCRIPTION
		"The comitted access rate. This determines the long term
		average transmission rate. Traffic that falls under this
		rate always conforms. This is average rate in bits per
		second."

	::= { snPortCAREntry 6 }

snPortCARLimit OBJECT-TYPE
	SYNTAX  Integer32
		MAX-ACCESS  read-only
		STATUS  current
		DESCRIPTION
		"This is the normal burst size that determines how large traffic
		bursts can be before some traffic exceeds the rate limit. This
		specifies the number of bytes that are guaranteed to be transported
		by the network at the average rate under normal conditions during
		committed time interval. This normal burst size is in bytes."

	::= { snPortCAREntry 7 }

snPortCARExtLimit OBJECT-TYPE
	SYNTAX  Integer32
	MAX-ACCESS  read-only
	STATUS  current
	DESCRIPTION
		"This is the extended burst limit that determines how large traffic
		bursts can be before all the traffic exceeds the rate limit. This
		burst size is in bytes."

	::= { snPortCAREntry 8 }

snPortCARConformAction OBJECT-TYPE
	SYNTAX	RateLimitAction
	MAX-ACCESS  read-only
	STATUS	current
	DESCRIPTION
		"Action to be taken when the traffic is within
		the Rate Limit.
		drop		drop the packet.
		xmit		transmit the packet.
		continue	continue to evaluate to the subsequent
					rate limits.
		precedXmit	rewrite the IP precedence and transmit
					the packet.
		precedCont	rewrite the IP precedence and allow it
					evaluated by subsequent rate limits."

	::= { snPortCAREntry 9 }

snPortCARExceedAction OBJECT-TYPE
	SYNTAX	RateLimitAction
	MAX-ACCESS  read-only
	STATUS	current
	DESCRIPTION
		"Action to be taken when the traffic exceeds
		the Rate Limit.drop
		drop the packet.
		xmit		transmit the packet.
		continue	continue to evaluate to the subsequent
					rate limits.
		precedXmit	rewrite the IP precedence and transmit
					the packet.
		precedCont	rewrite the IP precedence and allow it
					evaluated by subsequent rate limits."

	::= { snPortCAREntry 10 }

snPortCARStatSwitchedPkts OBJECT-TYPE
	SYNTAX  Counter64
	MAX-ACCESS  read-only
	STATUS  current
	DESCRIPTION
		"The counter of packets permitted by this rate limit."

	::= { snPortCAREntry 11 }

snPortCARStatSwitchedBytes OBJECT-TYPE
	SYNTAX  Counter64
	MAX-ACCESS  read-only
	STATUS  current
	DESCRIPTION
		"The counter of bytes permitted by this interface."

	::= { snPortCAREntry 12 }

snPortCARStatFilteredPkts OBJECT-TYPE
	SYNTAX  Counter64
	--UNITS	"packets"
	MAX-ACCESS  read-only
	STATUS  current
	DESCRIPTION
		"The counter of packets which exceeded this rate limit."

	::= { snPortCAREntry 13 }

snPortCARStatFilteredBytes OBJECT-TYPE
	SYNTAX  Counter64
	MAX-ACCESS  read-only
	STATUS  current
	DESCRIPTION
		"The counter of bytes which exceeded this rate limit."

	::= { snPortCAREntry 14 }

snPortCARStatCurBurst OBJECT-TYPE
	SYNTAX  Gauge32
	MAX-ACCESS  read-only
	STATUS  current
	DESCRIPTION
		"The current received burst size."
	::= { snPortCAREntry 15 }

-- end of snPortCARTable

-- RL Counter Table

agRateLimitCounterTable OBJECT-TYPE
	SYNTAX		SEQUENCE OF AgRateLimitCounterEntry
	MAX-ACCESS		not-accessible
	STATUS		current
	DESCRIPTION
	"A table of rate limit counter entries."
	::= { snPortCARs 2 }

agRateLimitCounterEntry OBJECT-TYPE
	SYNTAX		AgRateLimitCounterEntry
	MAX-ACCESS		not-accessible
	STATUS		current
	DESCRIPTION
	"A collection of rate-limit counter objects on a 
	interface, direction and configuration row index within that interface."
	INDEX { ifIndex, snPortCARRowIndex }
	::= { agRateLimitCounterTable 1 }

AgRateLimitCounterEntry ::=
	SEQUENCE {
		agRateLimitCounterFwdedOctets
			Counter64,
		agRateLimitCounterDroppedOctets
			Counter64,
		agRateLimitCounterReMarkedOctets
			Counter64,
		agRateLimitCounterTotalOctets
			Counter64
	}

agRateLimitCounterFwdedOctets OBJECT-TYPE
	SYNTAX	Counter64
	MAX-ACCESS	read-only
	STATUS	current
	DESCRIPTION
	"The forwarded octet count for this rate limit entry."
	::= { agRateLimitCounterEntry 1 }

agRateLimitCounterDroppedOctets OBJECT-TYPE
	SYNTAX	Counter64
	MAX-ACCESS	read-only
	STATUS	current
	DESCRIPTION
	"The dropped octet count for this rate limit entry."
	::= { agRateLimitCounterEntry 2 }

agRateLimitCounterReMarkedOctets OBJECT-TYPE
	SYNTAX	Counter64
	MAX-ACCESS	read-only
	STATUS	current
	DESCRIPTION
	"The remarked octet count for this rate limit entry."
	::= { agRateLimitCounterEntry 3 }

agRateLimitCounterTotalOctets OBJECT-TYPE
	SYNTAX	Counter64
	MAX-ACCESS	read-only
	STATUS	current
	DESCRIPTION
	"The total octet count for this rate limit entry."
	::= { agRateLimitCounterEntry 4 }

-- RL Counter index Table

agRateLimitCounterIndexTable OBJECT-TYPE
	SYNTAX		SEQUENCE OF AgRateLimitCounterIndexEntry
	MAX-ACCESS		not-accessible
	STATUS		current
	DESCRIPTION
	"A table to map each rowindexes of rate limit counter entries to their 
	corresponding ACL ID (or) VLAN ID (or) VLAN Group ID."
	::= { snPortCARs 3 }

agRateLimitCounterIndexEntry OBJECT-TYPE
	SYNTAX		AgRateLimitCounterIndexEntry
	MAX-ACCESS		not-accessible
	STATUS		current
	DESCRIPTION
	"A collection of rate-limit counter objects on a
	interface, direction and configuration row index within that interface."
	INDEX { ifIndex, snPortCARRowIndex }
	::= { agRateLimitCounterIndexTable 1 }

AgRateLimitCounterIndexEntry ::=
	SEQUENCE {
		agRateLimitCounterIndexRowIndex
			INTEGER,
		agRateLimitCounterIndexDirection
			PacketSource,
		agRateLimitCounterIndexACLID
			Integer32,
		agRateLimitCounterIndexVLANID
			Integer32,
		agRateLimitCounterIndexVLANGroupID
			Integer32,
		agRateLimitCounterIndexMACAddress
			MacAddress
	}

agRateLimitCounterIndexRowIndex OBJECT-TYPE
	SYNTAX  INTEGER (1..2147483647)
		MAX-ACCESS  read-only
		STATUS  current
		DESCRIPTION
				"The table index for rate limit objects.
		It increases as the rate limit entries are added.
		Skips the number when a row is deleted."

		::= { agRateLimitCounterIndexEntry 1 }

agRateLimitCounterIndexDirection  OBJECT-TYPE
	SYNTAX  PacketSource
		MAX-ACCESS  read-only
		STATUS  current
		DESCRIPTION
			"The input or output transmission direction for the
				Rate Limit object.
				input (0), --for inbound traffic
				output(1) --for outbound traffic "
		::= { agRateLimitCounterIndexEntry 2 }

agRateLimitCounterIndexACLID OBJECT-TYPE
	SYNTAX	Integer32
	MAX-ACCESS	read-only
	STATUS	current
	DESCRIPTION
	"The corresponding ACL ID to match with the row index of the ratelimit 
	counter table."
	::= { agRateLimitCounterIndexEntry 3 }

agRateLimitCounterIndexVLANID OBJECT-TYPE
	SYNTAX	Integer32
	MAX-ACCESS	read-only
	STATUS	current
	DESCRIPTION
	"The corresponding VLAN ID to match with the row index of the ratelimit 
	counter table."
	::= { agRateLimitCounterIndexEntry 4 }

agRateLimitCounterIndexVLANGroupID OBJECT-TYPE
	SYNTAX	Integer32
	MAX-ACCESS	read-only
	STATUS	current
	DESCRIPTION
	"The corresponding VLAN Group ID to match with the row index of the 
	ratelimit counter table."
	::= { agRateLimitCounterIndexEntry 5 }

agRateLimitCounterIndexMACAddress OBJECT-TYPE
	SYNTAX	MacAddress
	MAX-ACCESS	read-only
	STATUS	current
	DESCRIPTION
	"The corresponding MAC Address for Source MAC based rate limit to match 
	with the row index of the ratelimit counter table."	
	DEFVAL  { '000000000000'H }
	::= { agRateLimitCounterIndexEntry 6 }

-- BUM RL Counter Table
agRateLimitBUMCounterTable OBJECT-TYPE
    SYNTAX      SEQUENCE OF AgRateLimitBUMCounterEntry
    MAX-ACCESS  not-accessible
    STATUS      current
    DESCRIPTION
            "This table displays 
  The number of bytes dropped due to BUM rate-limit on the port, based on configured packet type and VLANID
  Committed Burst Size(CBS) in bits
  Committed Information Rate(CIR) in bits
  AlertLowLevelThreshold in bits
  AlertHighLevelThreshold in bits
  ShutdownTimeout in minutes"
    ::= { snPortCARs 4}
agRateLimitBUMCounterEntry OBJECT-TYPE
    SYNTAX      AgRateLimitBUMCounterEntry
    MAX-ACCESS  not-accessible
    STATUS      current
    DESCRIPTION
            "An entry containing the number of bytes dropped due to BUM rate-limit, followed by CBS ,CIR, AlertLowLevelThreshold, AlertHighLevelThreshold in terms of bits, and ShutdownTimeout in minutes"
    INDEX   {  agRateLimitBUMCounterIfindex,
	        agRateLimitBUMCounterVLANID,
                   agRateLimitBUMCounterPacketType }
    ::= { agRateLimitBUMCounterTable 1 }
AgRateLimitBUMCounterEntry ::=
SEQUENCE {
	agRateLimitBUMCounterIfindex			InterfaceIndex,
	agRateLimitBUMCounterVLANID			Integer32,
	agRateLimitBUMCounterPacketType			BUMPacketType,
	agRateLimitBUMCounterDroppedOctets		Counter64,
	agRateLimitBUMCounterCBS			Counter64,
	agRateLimitBUMCounterCIR			Counter64,
	agRateLimitBUMCounterAlertLowLevelThreshold	Counter64,
	agRateLimitBUMCounterAlertHighLevelThreshold	Counter64,
	agRateLimitBUMCounterShutdownTimeout		Integer32
}
agRateLimitBUMCounterIfindex OBJECT-TYPE
    SYNTAX  InterfaceIndex
    MAX-ACCESS  not-accessible
    STATUS      current
    DESCRIPTION
            "Ifindex, a count which uniquely identifies the ports
	     in the chassis. Ranges from 1 to 2048"
    ::= { agRateLimitBUMCounterEntry 1 }
agRateLimitBUMCounterVLANID OBJECT-TYPE
    SYNTAX  Integer32
    MAX-ACCESS  not-accessible
    STATUS      current
    DESCRIPTION
            " VLANID, a ID which is used to represent the 
              corresponding VLAN in the chassis. Ranges 
              from 1 to 4096"
    ::= { agRateLimitBUMCounterEntry 2 }
agRateLimitBUMCounterPacketType OBJECT-TYPE
    SYNTAX  BUMPacketType
    MAX-ACCESS  not-accessible
    STATUS      current
    DESCRIPTION
            " PacketType, used to represent the type of the packet i.e. B(1) or U(2) or BU(3) or M(4) or BM(5) or UM(6) or BUM(7) U?Unknown-Unicast, B?Broadcast and M?Multicast"
    ::= { agRateLimitBUMCounterEntry 3 }
agRateLimitBUMCounterDroppedOctets OBJECT-TYPE
    SYNTAX  Counter64
    MAX-ACCESS  read-only
    STATUS      current
    DESCRIPTION
            " A count used to represent the number of bytes dropped due to BUM rate-limit in bytes."
    ::= { agRateLimitBUMCounterEntry 4 }
agRateLimitBUMCounterCBS OBJECT-TYPE
    SYNTAX  Counter64
    MAX-ACCESS  read-only
    STATUS      current
    DESCRIPTION
            " A count used to represent the Committed Burst Size in bits."
    ::= { agRateLimitBUMCounterEntry 5 }
agRateLimitBUMCounterCIR OBJECT-TYPE
    SYNTAX  Counter64
    MAX-ACCESS  read-only
    STATUS      current
    DESCRIPTION
            " A count used to represent the Committed Information Rate in bits."
    ::= { agRateLimitBUMCounterEntry 6 }
agRateLimitBUMCounterAlertLowLevelThreshold OBJECT-TYPE
    SYNTAX  Counter64
    MAX-ACCESS  read-only
    STATUS      current
    DESCRIPTION
            " A count used to represent the configured lower threshold level in bits, to generate the Alert."
    ::= { agRateLimitBUMCounterEntry 7 }
agRateLimitBUMCounterAlertHighLevelThreshold OBJECT-TYPE
    SYNTAX  Counter64
    MAX-ACCESS  read-only
    STATUS      current
    DESCRIPTION
            " A count used to represent the configured Higher threshold level in bits, to generate the Alert."
    ::= { agRateLimitBUMCounterEntry 8 }
agRateLimitBUMCounterShutdownTimeout OBJECT-TYPE
    SYNTAX  Integer32
    MAX-ACCESS  read-only
    STATUS      current
    DESCRIPTION
            " A count used to represent the Timeout value in terms of minutes,
              which is the time interval after which the shutdown port will 
              be enabled."
    ::= { agRateLimitBUMCounterEntry 9 }
-- end of RL Counter Table
snBUMRLNotifications OBJECT IDENTIFIER ::= { snPortCARs 5 }
snTrapBUMratelimitAlertLowThreshold NOTIFICATION-TYPE
       OBJECTS {
	agRateLimitBUMCounterCIR,
	agRateLimitBUMCounterAlertLowLevelThreshold
	}
       STATUS  current
       DESCRIPTION
               "A snTrapBUMratelimitAlertLowThreshold trap signifies that the
                ingress packets interms of bits have reached the configured 
                low level threshold."
	::= { snBUMRLNotifications 1 }
snTrapBUMratelimitAlertHighThreshold NOTIFICATION-TYPE
       OBJECTS {
         agRateLimitBUMCounterCIR,
         agRateLimitBUMCounterAlertHighLevelThreshold
       }
       STATUS  current
       DESCRIPTION
               "A snTrapBUMratelimitAlertHighThreshold trap signifies that the 
                ingress packets interms of bits, have reached the configured 
                high level threshold."
	::= { snBUMRLNotifications 2 }
snTrapBUMratelimitShutdownLinkDown NOTIFICATION-TYPE
       OBJECTS {
         agRateLimitBUMCounterCIR
       }
       STATUS  current
       DESCRIPTION
               "A snTrapBUMratelimitShutdownLinkDown trap signifies that the
                port is shutdown after reaching the configured CIR in bps."
	::= { snBUMRLNotifications 3 }
snTrapBUMratelimitShutdownLinkUp NOTIFICATION-TYPE
       OBJECTS {
          agRateLimitBUMCounterCIR
       }
       STATUS  current
       DESCRIPTION
               "A snTrapBUMratelimitAlertHighThreshold trap signifies that the 
                port is UP after the specified shutdown timeout in minutes."
	::= { snBUMRLNotifications 4 }
END
