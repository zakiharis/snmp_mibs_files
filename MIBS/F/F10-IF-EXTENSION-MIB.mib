F10-IF-EXTENSION-MIB DEFINITIONS ::= BEGIN
    --  This module provides authoritative definitions for 
    --  Dell Networking OS extenstion to the IF MIB.
    --
    --  This module will be extended, as needed.
    --  

    IMPORTS
        MODULE-IDENTITY, OBJECT-TYPE, 
        Counter64, Unsigned32 
            FROM SNMPv2-SMI
        TimeStamp, DisplayString, TruthValue
            FROM SNMPv2-TC
        MODULE-COMPLIANCE, OBJECT-GROUP
            FROM SNMPv2-CONF
        ifIndex
            FROM IF-MIB
        Integer32
            FROM SNMPv2-SMI
        f10Mgmt
            FROM FORCE10-SMI;     
        
    f10IfExtensionMib MODULE-IDENTITY
    LAST-UPDATED "201203061200Z"  -- Mar 6, 2012 12:00:00 GMT
    ORGANIZATION
      "Dell Inc"
    CONTACT-INFO
      "http://www.force10networks.com/support" 

    DESCRIPTION
       "Dell Networking OS IF Extenstion MIB. "
    
    REVISION     "201203061200Z"
    DESCRIPTION
          "Added DHCP Client attributes."

    REVISION     "201008111200Z"
    DESCRIPTION
        "Add f10IfOutThrottles."
        
    REVISION     "201008101200Z"
    DESCRIPTION
          "Initial version of this mib module."
    
           ::= { f10Mgmt 11 }   


    -- ### Groups ###

    f10IfExtensionMibObject OBJECT IDENTIFIER ::={ f10IfExtensionMib 1 }
    f10IfExtensionParams    OBJECT IDENTIFIER ::={ f10IfExtensionMibObject 1 }
    f10IfExtensionStats     OBJECT IDENTIFIER ::={ f10IfExtensionMibObject 2 }
        
    -- ### Dell Networking OS IF Extenstion Tables
    
    --
    -- Interface Table
    --

      f10IfTable     OBJECT-TYPE
        SYNTAX        SEQUENCE OF F10IfEntry
        MAX-ACCESS    not-accessible
        STATUS        current
        DESCRIPTION
            "Dell Networking OS Extension ifTable contains
            generic interface parameters."
        ::= { f10IfExtensionParams 1 }

      f10IfEntry  OBJECT-TYPE 
        SYNTAX        F10IfEntry
        MAX-ACCESS    not-accessible
        STATUS        current
        DESCRIPTION
            " A row defintion of Dell Networking OS Interface
            Extension parameters." 
        INDEX    { ifIndex }
        ::= { f10IfTable 1 }
      F10IfEntry    ::=
        SEQUENCE {
           f10IfIpMtu                 Unsigned32,
           f10IfDuplexMode            INTEGER,
           f10IfQueueingStrategy      DisplayString,
           f10IfRxFlowCtrl            TruthValue,
           f10IfTxFlowCtrl            TruthValue,
           f10IfDescr                 OCTET STRING,
           f10IfAdminStatus           INTEGER,
           f10IfRateInterval          Unsigned32,
           f10IfSpeed                 INTEGER,
           f10IfDhcpAdminStatus       INTEGER,
           f10IfDhcpOperStatus        INTEGER
        }
        
       f10IfIpMtu     OBJECT-TYPE
        SYNTAX        Unsigned32 (594..9252)
        MAX-ACCESS    read-write
        STATUS        current
        DESCRIPTION
            "The IP (Internet Protocol), Maximum 
            Transmission Unit value."
        ::= { f10IfEntry 1 }

       f10IfDuplexMode  OBJECT-TYPE
        SYNTAX        INTEGER {
                      half(1),
                      full(2),
                      auto(3)
                      }
        MAX-ACCESS    read-write
        STATUS        current
        DESCRIPTION
            "Duplex mode of the interface. 
            This will be read-write only for s60"
        ::= { f10IfEntry 2 }

       f10IfQueueingStrategy OBJECT-TYPE
        SYNTAX        DisplayString (SIZE (0..32))
        MAX-ACCESS    read-only
        STATUS        current
        DESCRIPTION
            "Queueing strategy used for packets."
        ::= { f10IfEntry 3 }

       f10IfRxFlowCtrl OBJECT-TYPE
        SYNTAX        TruthValue
        MAX-ACCESS    read-write
        STATUS        current
        DESCRIPTION
            "Flow control receive. This will be read-write only for s60"
        ::= { f10IfEntry 4 }

       f10IfTxFlowCtrl OBJECT-TYPE
        SYNTAX        TruthValue
        MAX-ACCESS    read-write
        STATUS        current
        DESCRIPTION
            "Flow Control transmit.This will be read-only only for s60"
        ::= { f10IfEntry 5 }
                
       f10IfDescr  OBJECT-TYPE
        SYNTAX        OCTET STRING (SIZE (0..241))
        MAX-ACCESS    read-write
        STATUS        current
        DESCRIPTION
            "A textual string containing information about the interface.
            This will be read-write only for s60"
        ::= { f10IfEntry 6 }

       f10IfAdminStatus OBJECT-TYPE
        SYNTAX        INTEGER{
                        up (1),
                        down(2)
                        }
        MAX-ACCESS    read-write
        STATUS        current
        DESCRIPTION
            "A admin status of any interface.
            This will be read-write only for s60"
        ::= { f10IfEntry 7 }

       f10IfRateInterval  OBJECT-TYPE
        SYNTAX        Unsigned32 (30..299)
        MAX-ACCESS    read-write
        STATUS        current
        DESCRIPTION
            "The rate info interval for the interface.
            This will be read-write only for s60"
        ::= { f10IfEntry 8 }

       f10IfSpeed  OBJECT-TYPE
        SYNTAX        INTEGER{
                  auto (1),
                  tenMbps (10),
                  hundredMbps (100),
                  thousandMbps (1000)
               }
        MAX-ACCESS    read-write
        STATUS        current
        DESCRIPTION
            "The interface's current bandwidth in bits per second.
            This will be read-write only for s60"
        ::= { f10IfEntry 9 }

       f10IfDhcpAdminStatus  OBJECT-TYPE
        SYNTAX        INTEGER {
                   enable (1),
                   disable (2),
                   renew (3),
                   release (4)
                }
        MAX-ACCESS    read-write
        STATUS        current
        DESCRIPTION
        "The desired state of DHCP on an interface. 
        The values mean:
          
            enable 
               Enable IP address acquisition through DHCP. 
               If DHCP is enabled on an interface, the attribute ipAddressOrigin 
               of ipAddressTable in rfc4293.mib shall hold the value dhcp(4).

            disable
               Disable IP address acquistion through DHCP.   

            renew
               Renew the IP address so that same IP address is retained. 
        
            release            
               Release the IP back to the server. 
               
               Renew or release shall be configured only if DHCP is already 
               enabled and IP address is present. To acquire IP through DHCP 
               after a release, the object should again be set to enable or
               renew. Even after a release, the value of ipAddressOrigin shall 
               remain as dhcp(4). 
               
        A read of this object shall always hold the last valid configuration.
        This attribute is specific to MXL and IOA Aggregator platform."
		DEFVAL { disable }
        ::= { f10IfEntry 10 }

       f10IfDhcpOperStatus OBJECT-TYPE
        SYNTAX         INTEGER {
                   enabled(1),
                   disabled(2),
                   bound(3),
                   released(4),
                   unknown(5)
                }
        MAX-ACCESS    read-only
        STATUS        current
        DESCRIPTION
        "The current state of DHCP on an interface.
        The values mean:

            enabled
               DHCP is enabled on an interface. 

            disabled
               DHCP is disabled on an interface.

            bound
               IP address has been acquired from the DHCP server.

            released
               IP address has been released to the DHCP server. 

            unknown   
               DHCP is enabled on an interface and operational 
               status of the interface is down.
        This attribute is specific to MXL and IOA Aggregator platform."
        ::= { f10IfEntry 11 }

    --
    -- Interface Statistics Table
    --
    
      f10IfStaticsTable     OBJECT-TYPE
        SYNTAX        SEQUENCE OF F10IfStaticsEntry
        MAX-ACCESS    not-accessible
        STATUS        current
        DESCRIPTION
            "The statistcs information of the interfaces for performance monitoring." 
        ::= { f10IfExtensionStats 1 }

      f10IfStaticsEntry  OBJECT-TYPE 
        SYNTAX        F10IfStaticsEntry
        MAX-ACCESS    not-accessible
        STATUS        current
        DESCRIPTION
            "A row defintion of Dell Networking OS Extension 
             interface statistics."
        INDEX    { ifIndex }
        ::= { f10IfStaticsTable 1 }

      F10IfStaticsEntry    ::=
        SEQUENCE {
           f10IfInVlanPkts                Counter64,
           f10IfIn64BytePkts              Counter64,
           f10ifIn65To127BytePkts         Counter64,
           f10IfIn128To255BytePkts        Counter64,
           f10IfIn256To511BytePkts        Counter64, 
           f10IfIn512To1023BytePkts       Counter64,
           f10IfInOver1023BytePkts        Counter64,
           f10IfInThrottles               Counter64,
           f10IfInRunts                   Counter64,
           f10IfInGiants                  Counter64,
           f10IfInCRC                     Counter64,
           f10IfInOverruns                Counter64, 
           f10IfOutVlanPkts               Counter64,
           f10IfOutUnderruns              Counter64,
           f10IfOutUnicasts               Counter64,
           f10IfOutCollisions             Counter64,
           f10IfOutWredDrops              Counter64,
           f10IfOut64BytePkts             Counter64,
           f10IfOut65To127BytePkts        Counter64,
           f10IfOut128To255BytePkts       Counter64,
           f10IfOut256To511BytePkts       Counter64,
           f10IfOut512To1023BytePkts      Counter64,
           f10IfOutOver1023BytePkts       Counter64,
           f10IfOutThrottles              Counter64,
           f10IfLastDiscontinuityTime     TimeStamp,
           f10IfInCentRate                Integer32,
           f10IfOutCentRate               Integer32
        }
       
       f10IfInVlanPkts OBJECT-TYPE
        SYNTAX        Counter64
        MAX-ACCESS    read-only
        STATUS        current
        DESCRIPTION
             "The total number of valid VLAN Tagged 
             frames received." 
        ::= { f10IfStaticsEntry 1 }
        
       f10IfIn64BytePkts OBJECT-TYPE
        SYNTAX        Counter64
        MAX-ACCESS    read-only
        STATUS        current
        DESCRIPTION
             "The total number of frames (including bad
             frames) received that were 64 octets in length 
             (excluding framing bits but in-cluding FCS octets)." 
        ::= { f10IfStaticsEntry 2 }

       f10ifIn65To127BytePkts OBJECT-TYPE
        SYNTAX        Counter64
        MAX-ACCESS    read-only
        STATUS        current
        DESCRIPTION
             "The total number of frames (including bad 
             frames) received that were between 65 and 127
             octets in length inclusive (ex-cluding framing
             bits but including FCS octets)." 
        ::= { f10IfStaticsEntry 3 }
                
       f10IfIn128To255BytePkts OBJECT-TYPE
        SYNTAX        Counter64
        MAX-ACCESS    read-only
        STATUS        current
        DESCRIPTION
             "The total number of frames (including bad
             frames) received that were between 128 and 255 
             octets in length inclusive (excluding framing
             bits but including FCS octets)." 
        ::= { f10IfStaticsEntry 4 }
        
       f10IfIn256To511BytePkts OBJECT-TYPE
        SYNTAX        Counter64
        MAX-ACCESS    read-only
        STATUS        current
        DESCRIPTION
             "The total number of frames (including bad 
             frames) received that were between 256 and 511 
             octets in length inclusive (excluding framing 
             bits but including FCS octets)." 
        ::= { f10IfStaticsEntry 5 }        
        
       f10IfIn512To1023BytePkts OBJECT-TYPE
        SYNTAX        Counter64
        MAX-ACCESS    read-only
        STATUS        current
        DESCRIPTION
             "The total number of frames (including bad 
             frames) received that were between 512 and 1023
             octets in length inclusive (excluding framing 
             bits but including FCS octets)." 
        ::= { f10IfStaticsEntry 6 }
                
       f10IfInOver1023BytePkts OBJECT-TYPE
        SYNTAX        Counter64
        MAX-ACCESS    read-only
        STATUS        current
        DESCRIPTION
             "The total number of frames received that
              were longer than 1023 (1025 Bytes in case of
              VLAN Tag) octets (excluding framing bits, but
              including FCS octets) and were otherwise
              well formed. This counter is not incremented 
              for too long frames."  
        ::= { f10IfStaticsEntry 7 }
                
       f10IfInThrottles OBJECT-TYPE
        SYNTAX        Counter64
        MAX-ACCESS    read-only
        STATUS        current
        DESCRIPTION
             "This counter is incremented when a valid 
             frame with a length or type field value equal
             to 0x8808 (Control Frame) is re-ceived." 
        ::= { f10IfStaticsEntry 8 }
                
       f10IfInRunts OBJECT-TYPE
        SYNTAX        Counter64
        MAX-ACCESS    read-only
        STATUS        current
        DESCRIPTION
             "The total number of frames received that were
             less than 64 octets long (excluding framing bits, 
             but including FCS octets) and were otherwise 
             well formed."  
        ::= { f10IfStaticsEntry 9 }
                
       f10IfInGiants OBJECT-TYPE
        SYNTAX        Counter64
        MAX-ACCESS    read-only
        STATUS        current
        DESCRIPTION
             "The total number of frames received that were 
             longer than 1518 (1522 Bytes in case of VLAN Tag) 
             octets (excluding framing bits, but including FCS
             octets) and were otherwise well formed. This counter
             is not incremented for too long frames."  
        ::= { f10IfStaticsEntry 10 }
                
       f10IfInCRC OBJECT-TYPE
        SYNTAX        Counter64
        MAX-ACCESS    read-only
        STATUS        current
        DESCRIPTION
             "The total number of frames received that had
             a length (ex-cluding framing bits, but including
             FCS octets) of between 64 and 1518 octets, 
             inclusive, but had a bad CRC."  
        ::= { f10IfStaticsEntry 11 }
                
       f10IfInOverruns OBJECT-TYPE
        SYNTAX        Counter64
        MAX-ACCESS    read-only
        STATUS        current
        DESCRIPTION
             "The total number of frames dropped because 
             of buffer issue." 
        ::= { f10IfStaticsEntry 12 }
                
       f10IfOutVlanPkts OBJECT-TYPE
        SYNTAX        Counter64
        MAX-ACCESS    read-only
        STATUS        current
        DESCRIPTION
             "The Number of Good VLAN Tagged Frames sent 
             successfully." 
        ::= { f10IfStaticsEntry 13 }
                
       f10IfOutUnderruns OBJECT-TYPE
        SYNTAX        Counter64
        MAX-ACCESS    read-only
        STATUS        current
        DESCRIPTION
             "The total number of frames dropped because 
             of buffer underrun." 
        ::= { f10IfStaticsEntry 14 }
                
       f10IfOutUnicasts OBJECT-TYPE
        SYNTAX        Counter64
        MAX-ACCESS    read-only
        STATUS        current
        DESCRIPTION
             "The Number of Good Unicast Frames sent successfully." 
        ::= { f10IfStaticsEntry 15 }
                
       f10IfOutCollisions OBJECT-TYPE
        SYNTAX        Counter64
        MAX-ACCESS    read-only
        STATUS        current
        DESCRIPTION
             "A count of the frames that due to excessive 
             or late collisions are not transmitted successfully."  
        ::= { f10IfStaticsEntry 16 }
                
       f10IfOutWredDrops OBJECT-TYPE
        SYNTAX        Counter64
        MAX-ACCESS    read-only
        STATUS        current
        DESCRIPTION
             "A count of the frames that are dropped using 
             WRED policy because of to excessive traffic." 
        ::= { f10IfStaticsEntry 17 }
                
       f10IfOut64BytePkts OBJECT-TYPE
        SYNTAX        Counter64
        MAX-ACCESS    read-only
        STATUS        current
        DESCRIPTION
             "The Number of Good Frames sent successfully 
             whose size was 64 Bytes." 
        ::= { f10IfStaticsEntry 18 }
                
       f10IfOut65To127BytePkts OBJECT-TYPE
        SYNTAX        Counter64
        MAX-ACCESS    read-only
        STATUS        current
        DESCRIPTION
             "The Number of Good Frames sent successfully 
             whose size was in the range of 65 to 127 Bytes." 
        ::= { f10IfStaticsEntry 19 } 
               
       f10IfOut128To255BytePkts OBJECT-TYPE
        SYNTAX        Counter64
        MAX-ACCESS    read-only
        STATUS        current
        DESCRIPTION
             "The Number of Good Frames sent successfully 
             whose size was in the range of 128 to 255 Bytes." 
        ::= { f10IfStaticsEntry 20 }
               
       f10IfOut256To511BytePkts OBJECT-TYPE
        SYNTAX        Counter64
        MAX-ACCESS    read-only
        STATUS        current
        DESCRIPTION
             "The Number of Good Frames sent successfully 
             whose size was in the range of 256 to 511 Bytes." 
        ::= { f10IfStaticsEntry 21 }
                       
       f10IfOut512To1023BytePkts OBJECT-TYPE
        SYNTAX        Counter64
        MAX-ACCESS    read-only
        STATUS        current
        DESCRIPTION
             "The Number of Good Frames sent successfully 
             whose size was in the range of 512 to 1023 Bytes." 
        ::= { f10IfStaticsEntry 22 }             
          
       f10IfOutOver1023BytePkts OBJECT-TYPE
        SYNTAX        Counter64
        MAX-ACCESS    read-only
        STATUS        current
        DESCRIPTION
             "The Number of Good Frames sent successfully 
             whose size was greater than 1023 Bytes." 
        ::= { f10IfStaticsEntry 23 }               
                
       f10IfOutThrottles OBJECT-TYPE
        SYNTAX        Counter64
        MAX-ACCESS    read-only
        STATUS        current
        DESCRIPTION
             "This counter is incremented when a valid 
             frame with a length or type field value equal
             to 0x8808 (Control Frame) is sent." 
        ::= { f10IfStaticsEntry 24 }
               
       f10IfLastDiscontinuityTime OBJECT-TYPE
        SYNTAX        TimeStamp
        MAX-ACCESS    read-only
        STATUS        current
        DESCRIPTION
            "The value of sysUpTime on the most recent occasion
            at which this interface's counters suffered a 
            discontinuity via a reset. If no such discontinuities 
            have occurred since the last reinitialization of 
            the local management subsystem, then this object
            contains a zero value."
        ::= { f10IfStaticsEntry 25 }

       f10IfInCentRate OBJECT-TYPE
        SYNTAX        Integer32 (0..100)
        MAX-ACCESS    read-only
        STATUS        current
        DESCRIPTION
             "This is the ingress rate in percentage.
             This is an integer value which can go from 0 to 100." 
        ::= { f10IfStaticsEntry 26 }

       f10IfOutCentRate OBJECT-TYPE
        SYNTAX        Integer32 (0..100)
        MAX-ACCESS    read-only
        STATUS        current
        DESCRIPTION
             "This is the egress rate in percentage.
             This is an integer value which can go from 0 to 100." 
        ::= { f10IfStaticsEntry 27 }



    -- ### conformance information ###
    f10IfExtensionMibConformance OBJECT IDENTIFIER ::= { f10IfExtensionMib 2 }
    f10IfExtensionMibCompliances OBJECT IDENTIFIER ::= { f10IfExtensionMibConformance 1 }
    f10IfExtensionMibGroups      OBJECT IDENTIFIER ::= { f10IfExtensionMibConformance 2 }

    -- ## compliance statements
    f10IfExtensionMibCompliance    MODULE-COMPLIANCE
        STATUS                  current
        DESCRIPTION
            "The compliance statement for Dell Networking OS
            IF Extension MIB."
        MODULE    -- this module
        MANDATORY-GROUPS {
            f10IfParamsGroup,
            f10IfStatsGroup
        }
        ::= { f10IfExtensionMibCompliances 1 }

    -- ## units of conformance

    f10IfParamsGroup OBJECT-GROUP
        OBJECTS {
           f10IfIpMtu,
           f10IfDuplexMode,
           f10IfQueueingStrategy,
           f10IfRxFlowCtrl,
           f10IfTxFlowCtrl,
           f10IfDescr,
           f10IfAdminStatus,
           f10IfRateInterval,
           f10IfSpeed, 
           f10IfDhcpAdminStatus,    
           f10IfDhcpOperStatus
        }
        STATUS    current
        DESCRIPTION
            "A collection of objects providing the
            Dell Networking OS IF Extenstion parameters."
        ::= { f10IfExtensionMibGroups 1 }

    f10IfStatsGroup    OBJECT-GROUP
        OBJECTS {
           f10IfInVlanPkts,
           f10IfIn64BytePkts,
           f10ifIn65To127BytePkts,
           f10IfIn128To255BytePkts,
           f10IfIn256To511BytePkts, 
           f10IfIn512To1023BytePkts,
           f10IfInOver1023BytePkts,
           f10IfInThrottles,
           f10IfInRunts,
           f10IfInGiants,
           f10IfInCRC,
           f10IfInOverruns, 
           f10IfOutVlanPkts,
           f10IfOutUnderruns,
           f10IfOutUnicasts,
           f10IfOutCollisions,
           f10IfOutWredDrops,
           f10IfOut64BytePkts,
           f10IfOut65To127BytePkts,
           f10IfOut128To255BytePkts,
           f10IfOut256To511BytePkts,
           f10IfOut512To1023BytePkts,
           f10IfOutOver1023BytePkts,
           f10IfOutThrottles,
           f10IfLastDiscontinuityTime,
           f10IfInCentRate,
           f10IfOutCentRate
        }
        STATUS    current
        DESCRIPTION
            "A collection of objects providing the
            interface statistics."
        ::= { f10IfExtensionMibGroups 2 }

    END
