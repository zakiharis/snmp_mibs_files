FJ-BBU-MIB DEFINITIONS ::= BEGIN

--#FILENAME        "FJBBU.MIB"
--#DESCRIPTION     "Fujitsu Battery Backup Unit MIB"
--#REVISION        "1.00.00.00"
--#VENDOR          "Fujitsu"
--#TRAP-ENTERPRISE fjbbuNotifications
--#TRAP-VARIABLES  fjbbuNotificationsTrapInfo

-----------------------------------------------------------------------
-- fjbbu.mib  Copyright (C) FUJITSU LIMITED 2012.
-- Fujitsu PRIMERGY BBU MIB Definition
-- iso(1).org(3).dod(6).internet(1).private(4).enterprises(1).fujitsu(211).products(1).iaServer(31).primergy(3).iBBU(1)
-- 2012/12/04 V1.00
-----------------------------------------------------------------------

IMPORTS
   OBJECT-TYPE                            FROM RFC-1212
   mib-2                                  FROM RFC1213-MIB
   DisplayString                          FROM RFC1213-MIB
   Counter, Gauge, IpAddress, enterprises FROM RFC1155-SMI;

-- The Windows MIB compiler doesn't support IMPORTS.
-- In this case uncomment the next few lines.
-- 
-- DisplayString ::=  OCTET STRING
-- enterprises        OBJECT IDENTIFIER   ::= { iso org(3) dod(6) internet(1) private(4) 1 }
   
   fujitsu            OBJECT IDENTIFIER   ::= { enterprises 211 }
   products           OBJECT IDENTIFIER   ::= { fujitsu       1 }
   iaServer           OBJECT IDENTIFIER   ::= { products     31 }
   primergy           OBJECT IDENTIFIER   ::= { iaServer      3 }
   iBBU               OBJECT IDENTIFIER   ::= { primergy      1 }
   
   
-- groups in iBBU
   connectionInfo     OBJECT IDENTIFIER   ::= { iBBU          1 }
   batteryError       OBJECT IDENTIFIER   ::= { iBBU          2 }
   batteryWarning     OBJECT IDENTIFIER   ::= { iBBU          3 }
   batteryInfo        OBJECT IDENTIFIER   ::= { iBBU          4 }
   managementInfo     OBJECT IDENTIFIER   ::= { iBBU          5 }
   fjbbuNotifications OBJECT IDENTIFIER   ::= { iBBU          6 }


-- the connectionInfo group

connectionError OBJECT-TYPE
    SYNTAX  INTEGER
    {
        unknown(1),
        ok(2),
        error(3)
    }
    ACCESS  read-only
    STATUS  mandatory
    DESCRIPTION
            "Connection error with the Internal Battery Unit"
    ::= { connectionInfo 1 }


-- the batteryError group

overTempDDC OBJECT-TYPE
    SYNTAX  INTEGER
    {
        unknown(1),
        ok(2),
        error(3)
    }
    ACCESS  read-only
    STATUS  mandatory
    DESCRIPTION
            "Over temperature in DC/DC converter"
    ::= { batteryError 1 }

overVoltDDC OBJECT-TYPE
    SYNTAX  INTEGER
    {
        unknown(1),
        ok(2),
        error(3)
    }
    ACCESS  read-only
    STATUS  mandatory
    DESCRIPTION
            "Over voltage protection in DC/DC converter"
    ::= { batteryError 2 }

chargePassError OBJECT-TYPE
    SYNTAX  INTEGER
    {
        unknown(1),
        ok(2),
        error(3)
    }
    ACCESS  read-only
    STATUS  mandatory
    DESCRIPTION
            "Charge path failed"
    ::= { batteryError 3 }

dischargePassError OBJECT-TYPE
    SYNTAX  INTEGER
    {
        unknown(1),
        ok(2),
        error(3)
    }
    ACCESS  read-only
    STATUS  mandatory
    DESCRIPTION
            "Discharge path failed"
    ::= { batteryError 4 }

thermistorError OBJECT-TYPE
    SYNTAX  INTEGER
    {
        unknown(1),
        ok(2),
        error(3)
    }
    ACCESS  read-only
    STATUS  mandatory
    DESCRIPTION
            "Thermistor failed"
    ::= { batteryError 5 }

chargeCircuitError OBJECT-TYPE
    SYNTAX  INTEGER
    {
        unknown(1),
        ok(2),
        error(3)
    }
    ACCESS  read-only
    STATUS  mandatory
    DESCRIPTION
            "Charge circuit failed"
    ::= { batteryError 6 }

dc12VError OBJECT-TYPE
    SYNTAX  INTEGER
    {
        unknown(1),
        ok(2),
        error(3)
    }
    ACCESS  read-only
    STATUS  mandatory
    DESCRIPTION
            "DC12V failed"
    ::= { batteryError 7 }

fanError OBJECT-TYPE
    SYNTAX  INTEGER
    {
        unknown(1),
        ok(2),
        error(3)
    }
    ACCESS  read-only
    STATUS  mandatory
    DESCRIPTION
            "FAN alarm"
    ::= { batteryError 8 }

trickleChargeError OBJECT-TYPE
    SYNTAX  INTEGER
    {
        unknown(1),
        ok(2),
        error(3)
    }
    ACCESS  read-only
    STATUS  mandatory
    DESCRIPTION
            "Tricle charge failed"
    ::= { batteryError 9 }

eepromAccessError OBJECT-TYPE
    SYNTAX  INTEGER
    {
        unknown(1),
        ok(2),
        error(3)
    }
    ACCESS  read-only
    STATUS  mandatory
    DESCRIPTION
            "EEPROM access failed"
    ::= { batteryError 10 }

dischargeCurrentError OBJECT-TYPE
    SYNTAX  INTEGER
    {
        unknown(1),
        ok(2),
        error(3)
    }
    ACCESS  read-only
    STATUS  mandatory
    DESCRIPTION
            "Over current (SW) in discharging"
    ::= { batteryError 11 }

chargeCurrentError OBJECT-TYPE
    SYNTAX  INTEGER
    {
        unknown(1),
        ok(2),
        error(3)
    }
    ACCESS  read-only
    STATUS  mandatory
    DESCRIPTION
            "Over current (SW) in charging"
    ::= { batteryError 12 }


-- the batteryWarning group

capacityWarning OBJECT-TYPE
    SYNTAX  INTEGER
    {
        unknown(1),
        ok(2),
        warning(3)
    }
    ACCESS  read-only
    STATUS  mandatory
    DESCRIPTION
            "Battery capacity failed"
    ::= { batteryWarning 1 }

voltageDropBatteryWarning OBJECT-TYPE
    SYNTAX  INTEGER
    {
        unknown(1),
        ok(2),
        warning(3)
    }
    ACCESS  read-only
    STATUS  mandatory
    DESCRIPTION
            "Voltage dropped"
    ::= { batteryWarning 2 }

overTempWarning OBJECT-TYPE
    SYNTAX  INTEGER
    {
        unknown(1),
        ok(2),
        warning(3)
    }
    ACCESS  read-only
    STATUS  mandatory
    DESCRIPTION
            "Over temperature"
    ::= { batteryWarning 3 }

impedanceWarning OBJECT-TYPE
    SYNTAX  INTEGER
    {
        unknown(1),
        ok(2),
        warning(3)
    }
    ACCESS  read-only
    STATUS  mandatory
    DESCRIPTION
            "Impedance alarm"
    ::= { batteryWarning 4 }


-- the batteryInfo group

relativeStateOfCharge OBJECT-TYPE
    SYNTAX  DisplayString
    ACCESS  read-only
    STATUS  mandatory
    DESCRIPTION
            "Relative state of charge(percent)"
    ::= { batteryInfo 1 }

manufactureDate OBJECT-TYPE
    SYNTAX  DisplayString
    ACCESS  read-only
    STATUS  mandatory
    DESCRIPTION
            "Manufacture date (e.g. '20120202')"
    ::= { batteryInfo 2 }

serialNumber OBJECT-TYPE
    SYNTAX  DisplayString
    ACCESS  read-only
    STATUS  mandatory
    DESCRIPTION
            "Serial number (e.g. '00017')"
    ::= { batteryInfo 3 }

manufacturerName OBJECT-TYPE
    SYNTAX  DisplayString
    ACCESS  read-only
    STATUS  mandatory
    DESCRIPTION
            "Manufacturer name (e.g. 'FDK')"
    ::= { batteryInfo 4 }

deviceName OBJECT-TYPE
    SYNTAX  DisplayString
    ACCESS  read-only
    STATUS  mandatory
    DESCRIPTION
            "Device name (e.g. 'TW181FJ2')"
    ::= { batteryInfo 5 }

deviceChemistry OBJECT-TYPE
    SYNTAX  DisplayString
    ACCESS  read-only
    STATUS  mandatory
    DESCRIPTION
            "Device chemistry (e.g. 'NiMH')"
    ::= { batteryInfo 6 }

firmwareVersion OBJECT-TYPE
    SYNTAX  DisplayString
    ACCESS  read-only
    STATUS  mandatory
    DESCRIPTION
            "Firmware version (e.g. '4807')"
    ::= { batteryInfo 7 }

boardSerialNumber OBJECT-TYPE
    SYNTAX  DisplayString
    ACCESS  read-only
    STATUS  mandatory
    DESCRIPTION
            "Board Serial Number (e.g. 'BU1816AC31001')"
    ::= { batteryInfo 8 }

boardPartNumber OBJECT-TYPE
    SYNTAX  DisplayString
    ACCESS  read-only
    STATUS  mandatory
    DESCRIPTION
            "Board Part Number (e.g. 'CA05950-1414')"
    ::= { batteryInfo 9 }

boardVersion OBJECT-TYPE
    SYNTAX  DisplayString
    ACCESS  read-only
    STATUS  mandatory
    DESCRIPTION
            "Board Version (e.g. '01A')"
    ::= { batteryInfo 10 }


-- the managementInfo group

i2cAddress OBJECT-TYPE
    SYNTAX  DisplayString
    ACCESS  read-only
    STATUS  mandatory
    DESCRIPTION
            "I2C address of this BBU (e.g. '0xB2')"
    ::= { managementInfo 1 }

systemStatus OBJECT-TYPE
    SYNTAX  INTEGER
    {
        unknown(1),
        normal(2),
        alarm(3)
    }
    ACCESS  read-only
    STATUS  mandatory
    DESCRIPTION
            "System status. When BBU system error detected, it returns the value 'alarm'."
    ::= { managementInfo 2 }

batteryStatus OBJECT-TYPE
    SYNTAX  INTEGER
    {
        unknown(1),
        normal(2),
        alarm(3)
    }
    ACCESS  read-only
    STATUS  mandatory
    DESCRIPTION
            "Battery status. When BBU battery error detected, it returns the value 'alarm'."
    ::= { managementInfo 3 }

workStatus OBJECT-TYPE
    SYNTAX  INTEGER
    {
        unknown(1),
        waiting(2),
        charging(3),
        discharging(4)
    }
    ACCESS  read-only
    STATUS  mandatory
    DESCRIPTION
            "Work status. When AC fail detected, it returns the value 'discharging'."
    ::= { managementInfo 4 }

informationUrl OBJECT-TYPE
    SYNTAX  DisplayString
    ACCESS  read-only
    STATUS  mandatory
    DESCRIPTION
            "URL of information HTML interface (e.g. 'http://127.0.0.1:20080/bbuview/jsp/index.jsp')"
    ::= { managementInfo 5 }

deviceName OBJECT-TYPE
    SYNTAX  DisplayString
    ACCESS  read-only
    STATUS  mandatory
    DESCRIPTION
            "Device name (e.g. 'BBU')"
    ::= { managementInfo 6 }



-- **********************************************************************************************
--
-- GROUP        fjbbuNotificationsTrapInfo
-- DESCRIPTION  "This group defines the notifications/traps and their parameter variables.
--               They are not accessible directly, but sent together with traps."
--
--      fjbbuNotificationsTrapInfo group: 1.3.6.1.4.1.211.1.31.3.1.6.1
--
-- **********************************************************************************************

fjbbuNotificationsTrapInfo OBJECT IDENTIFIER ::= { fjbbuNotifications 1 }


fjbbuTrapInfoServerName OBJECT-TYPE
    SYNTAX       DisplayString
    ACCESS       not-accessible
    STATUS       mandatory
    DESCRIPTION  "Name of the server the trap comes from"
    ::= { fjbbuNotificationsTrapInfo 1 }

fjbbuTrapInfoTime OBJECT-TYPE
    SYNTAX       INTEGER
    ACCESS       not-accessible
    STATUS       mandatory
    DESCRIPTION  "Time when the trap occured (in seconds since 01/01/1970 00:00h)"
    ::= { fjbbuNotificationsTrapInfo 2 }

fjbbuTrapInfoDetail OBJECT-TYPE
    SYNTAX       DisplayString
    ACCESS       not-accessible
    STATUS       mandatory
    DESCRIPTION  "Problem detail of the trap"
    ::= { fjbbuNotificationsTrapInfo 3 }

fjbbuTrapInfoInformationUrl OBJECT-TYPE
    SYNTAX       DisplayString
    ACCESS       not-accessible
    STATUS       mandatory
    DESCRIPTION  "URL of information HTML interface (e.g. 'http://127.0.0.1:20080/bbuview/jsp/index.jsp')"
    ::= { fjbbuNotificationsTrapInfo 4 }


--
-- Trap number range for this MIB: 2000..2005
--

fjbbuTrapTest TRAP-TYPE
    ENTERPRISE fjbbuNotifications
    VARIABLES {
        fjbbuTrapInfoServerName,
        fjbbuTrapInfoTime
        }
    DESCRIPTION     "Test trap to verify trap connection."
    --#TYPE         "Test trap"
    --#SUMMARY      "Test trap from server %s (no error)."
    --#ARGUMENTS    { 0 }
    --#SEVERITY     INFORMATIONAL
    --#TIMEINDEX    1
    --#HELP         "Note: This is no error condition."
    --#STATE        OPERATIONAL
    ::= 2000

fjbbuTrapCommunicationFailure TRAP-TYPE
    ENTERPRISE fjbbuNotifications
    VARIABLES {
        fjbbuTrapInfoServerName,
        fjbbuTrapInfoTime,
        fjbbuTrapInfoInformationUrl
        }
    DESCRIPTION     "The communication with the Internal Battery Unit failed!"
    --#TYPE         "Communication lost"
    --#SUMMARY      "Communication with the Internal Battery Unit of server %s lost. Information URL: %s."
    --#ARGUMENTS    { 0, 2 }
    --#SEVERITY     MINOR
    --#TIMEINDEX    1
    --#STATE        OPERATIONAL
    ::= 2001

fjbbuTrapCommunicationEstablished TRAP-TYPE
    ENTERPRISE fjbbuNotifications
    VARIABLES {
        fjbbuTrapInfoServerName,
        fjbbuTrapInfoTime,
        fjbbuTrapInfoInformationUrl
        }
    DESCRIPTION     "The communication with the Internal Battery Unit was reestablished"
    --#TYPE         "Communication established"
    --#SUMMARY      "Communication with the Internal Battery Unit of server %s established again. Information URL: %s."
    --#ARGUMENTS    { 0, 2 }
    --#SEVERITY     INFORMATIONAL
    --#TIMEINDEX    1
    --#STATE        OPERATIONAL
    ::= 2002

fjbbuBatteryWarning TRAP-TYPE
    ENTERPRISE fjbbuNotifications
    VARIABLES {
        fjbbuTrapInfoServerName,
        fjbbuTrapInfoTime,
        fjbbuTrapInfoDetail,
        fjbbuTrapInfoInformationUrl
        }
    DESCRIPTION     "Internal Battery Unit warning."
    --#TYPE         "Internal Battery Unit warning"
    --#SUMMARY      "The Internal Battery Unit has detected an minor problem of server %s(detail: %s). Information URL: %s."
    --#ARGUMENTS    { 0, 2, 3 }
    --#SEVERITY     MINOR
    --#TIMEINDEX    1
    --#HELP         ""
    --#STATE        OPERATIONAL
    ::= 2003

fjbbuBatteryError TRAP-TYPE
    ENTERPRISE fjbbuNotifications
    VARIABLES {
        fjbbuTrapInfoServerName,
        fjbbuTrapInfoTime,
        fjbbuTrapInfoDetail,
        fjbbuTrapInfoInformationUrl
        }
    DESCRIPTION     "Internal Battery Unit error."
    --#TYPE         "Internal Battery Unit error"
    --#SUMMARY      "The Internal Battery Unit has detected an major problem of server %s(detail: %s). Information URL: %s."
    --#ARGUMENTS    { 0, 2, 3 }
    --#SEVERITY     MAJOR
    --#TIMEINDEX    1
    --#HELP         ""
    --#STATE        OPERATIONAL
    ::= 2004

END
