FASTPATH-MIB DEFINITIONS ::= BEGIN

-- Title:	FASTPATH MIB
-- Date:	April 4, 1990
-- By:		Brian Holmes <BHOLMES@CMS.CC.WAYNE.EDU>

IMPORTS
	OBJECT-TYPE FROM RFC-1212
	enterprises, NetworkAddress, IpAddress, Counter, Gauge,
	TimeTicks 
		FROM RFC1065-SMI;

	    
excelan		OBJECT	IDENTIFIER ::= { enterprises 23 }
genericGroup	OBJECT IDENTIFIER ::= { excelan 2 }
fastpathMib	OBJECT IDENTIFIER ::= { genericGroup 11 }

scc		OBJECT IDENTIFIER ::= { fastpathMib 1 }
alap		OBJECT IDENTIFIER ::= { fastpathMib 2 }
ethernet	OBJECT IDENTIFIER ::= { fastpathMib 3 }
aarp		OBJECT IDENTIFIER ::= { fastpathMib 4 }
atif		OBJECT IDENTIFIER ::= { fastpathMib 5 }
ddp	        OBJECT IDENTIFIER ::= { fastpathMib 6 }
rtmp		OBJECT IDENTIFIER ::= { fastpathMib 7 }
kip		OBJECT IDENTIFIER ::= { fastpathMib 8 }
zip		OBJECT IDENTIFIER ::= { fastpathMib 9 }
nbp	        OBJECT IDENTIFIER ::= { fastpathMib 10 }
echo		OBJECT IDENTIFIER ::= { fastpathMib 11 }
buffer		OBJECT IDENTIFIER ::= { fastpathMib 12 }

    sccInterruptCount OBJECT-TYPE
	    SYNTAX  Counter
	    ACCESS  read-only
	    STATUS  mandatory
DESCRIPTION ""
	    ::= { scc 1 }

    sccAbortCount OBJECT-TYPE
	    SYNTAX  Counter
	    ACCESS  read-only
	    STATUS  mandatory
DESCRIPTION ""
	    ::= { scc 2 }

    sccSpuriousCount OBJECT-TYPE
	    SYNTAX  Counter
	    ACCESS  read-only
	    STATUS  mandatory
DESCRIPTION ""
	    ::= { scc 3 }

    sccCRCCount OBJECT-TYPE
	    SYNTAX  Counter
	    ACCESS  read-only
	    STATUS  mandatory
DESCRIPTION ""
	    ::= { scc 4 }

    sccOverrunCount OBJECT-TYPE
	    SYNTAX  Counter
	    ACCESS  read-only
	    STATUS  mandatory
DESCRIPTION ""
	    ::= { scc 5 }

    sccUnderrunCount OBJECT-TYPE
	    SYNTAX  Counter
	    ACCESS  read-only
	    STATUS  mandatory
DESCRIPTION ""
	    ::={ scc 6 }

    alapReceiveCount OBJECT-TYPE
	    SYNTAX  Counter
	    ACCESS  read-only
	    STATUS  mandatory
DESCRIPTION ""
	    ::= { alap 1 }

    alapTransmitCount OBJECT-TYPE
	    SYNTAX  Counter
	    ACCESS  read-only
	    STATUS  mandatory
DESCRIPTION ""
	    ::= { alap 2 }

    alapNoHandlerCount OBJECT-TYPE
	    SYNTAX  Counter
	    ACCESS  read-only
	    STATUS  mandatory
DESCRIPTION ""
	    ::= { alap 3 }

    alapLengthErrorCount OBJECT-TYPE
	    SYNTAX  Counter
	    ACCESS  read-only
	    STATUS  mandatory
DESCRIPTION ""
	    ::= { alap 4 }

    alapBadCount OBJECT-TYPE
	    SYNTAX  Counter
	    ACCESS  read-only
	    STATUS  mandatory
DESCRIPTION ""
	    ::= { alap 5 }

    alapCollisionCount OBJECT-TYPE
	    SYNTAX  Counter
	    ACCESS  read-only
	    STATUS  mandatory
DESCRIPTION ""
	    ::= { alap 6 }

    alapDeferCount OBJECT-TYPE
	    SYNTAX  Counter
	    ACCESS  read-only
	    STATUS  mandatory
DESCRIPTION ""
	    ::= { alap 7 }

    alapNoDataCount OBJECT-TYPE
	    SYNTAX  Counter
	    ACCESS  read-only
	    STATUS  mandatory
DESCRIPTION ""
	    ::= { alap 8 }

    alapRandomCTS OBJECT-TYPE
	    SYNTAX  Counter
	    ACCESS  read-only
	    STATUS  mandatory
DESCRIPTION ""
	    ::= { alap 9 }

    etherCRCErrors OBJECT-TYPE
	    SYNTAX  Counter
	    ACCESS  read-only
	    STATUS  mandatory
DESCRIPTION ""
	    ::= { ethernet 1 }

    etherAlignErrors OBJECT-TYPE
	    SYNTAX  Counter
	    ACCESS  read-only
	    STATUS  mandatory
DESCRIPTION ""
	    ::= { ethernet 2 }

    etherResourceErrors OBJECT-TYPE
	    SYNTAX  Counter
	    ACCESS  read-only
	    STATUS  mandatory
DESCRIPTION ""
	    ::= { ethernet 3 }

    etherOverrunErrors OBJECT-TYPE
	    SYNTAX  Counter
	    ACCESS  read-only
	    STATUS  mandatory
DESCRIPTION ""
	    ::= { ethernet 4 }

    etherInPackets OBJECT-TYPE
	    SYNTAX  Counter
	    ACCESS  read-only
	    STATUS  mandatory
DESCRIPTION ""
	    ::= { ethernet 5 }

    etherOutPackets OBJECT-TYPE
	    SYNTAX  Counter
	    ACCESS  read-only
	    STATUS  mandatory
DESCRIPTION ""
	    ::= { ethernet 6 }

    etherBadTransmits OBJECT-TYPE
	    SYNTAX  Counter
	    ACCESS  read-only
	    STATUS  mandatory
DESCRIPTION ""
	    ::= { ethernet 7 }

    etherOversizeFrames OBJECT-TYPE
	    SYNTAX  Counter
	    ACCESS  read-only
	    STATUS  mandatory
DESCRIPTION ""
	    ::= { ethernet 8 }

    etherSpurRUReadys OBJECT-TYPE
	    SYNTAX  Counter
	    ACCESS  read-only
	    STATUS  mandatory
DESCRIPTION ""
	    ::= { ethernet 9 }

    etherSpurCUActives OBJECT-TYPE
	    SYNTAX  Counter
	    ACCESS  read-only
	    STATUS  mandatory
DESCRIPTION ""
	    ::= { ethernet 10 }

    etherSpurUnknown OBJECT-TYPE
	    SYNTAX  Counter
	    ACCESS  read-only
	    STATUS  mandatory
DESCRIPTION ""
	    ::= { ethernet 11 }

    etherBcastDrops OBJECT-TYPE
	    SYNTAX  Counter
	    ACCESS  read-only
	    STATUS  mandatory
DESCRIPTION ""
	    ::= { ethernet 12 }

    etherReceiverRestarts OBJECT-TYPE
	    SYNTAX  Counter
	    ACCESS  read-only
	    STATUS  mandatory
DESCRIPTION ""
	    ::= { ethernet 13 }

    etherReinterrupts OBJECT-TYPE
	    SYNTAX  Counter
	    ACCESS  read-only
	    STATUS  mandatory
DESCRIPTION ""
	    ::= { ethernet 14 }

    etherBufferReroutes OBJECT-TYPE
	    SYNTAX  Counter
	    ACCESS  read-only
	    STATUS  mandatory
DESCRIPTION ""
	    ::= { ethernet 15 }

    etherBufferDrops OBJECT-TYPE
	    SYNTAX  Counter
	    ACCESS  read-only
	    STATUS  mandatory
DESCRIPTION ""
	    ::= { ethernet 16 }

    etherCollisions OBJECT-TYPE
	    SYNTAX  Counter
	    ACCESS  read-only
	    STATUS  mandatory
DESCRIPTION ""
	    ::= { ethernet 17 }

    etherDefers OBJECT-TYPE
	    SYNTAX  Counter
	    ACCESS  read-only
	    STATUS  mandatory
DESCRIPTION ""
	    ::= { ethernet 18 }

    etherDMAUnderruns OBJECT-TYPE
	    SYNTAX  Counter
	    ACCESS  read-only
	    STATUS  mandatory
DESCRIPTION ""
	    ::= { ethernet 19 }

    etherMaxCollisions OBJECT-TYPE
	    SYNTAX  Counter
	    ACCESS  read-only
	    STATUS  mandatory
DESCRIPTION ""
	    ::= { ethernet 20 }

    etherNoCarriers OBJECT-TYPE
	    SYNTAX  Counter
	    ACCESS  read-only
	    STATUS  mandatory
DESCRIPTION ""
	    ::= { ethernet 21 }

    etherNoCTS OBJECT-TYPE
	    SYNTAX  Counter
	    ACCESS  read-only
	    STATUS  mandatory
DESCRIPTION ""
	    ::= { ethernet 22 }

    etherNoSQEs OBJECT-TYPE
	    SYNTAX  Counter
	    ACCESS  read-only
	    STATUS  mandatory
DESCRIPTION ""
	    ::= { ethernet 23 }

    aarpTable OBJECT-TYPE
	    SYNTAX  SEQUENCE OF AarpEntry
	    ACCESS  read-write
	    STATUS  mandatory
DESCRIPTION ""
	    ::= { aarp 1 }

    aarpEntry OBJECT-TYPE
	    SYNTAX  AarpEntry
	    ACCESS  read-write
	    STATUS  mandatory
DESCRIPTION ""
	    ::= { aarpTable 1 }

    AarpEntry ::= SEQUENCE {
	    aarpIfIndex	INTEGER,
	    aarpPhysAddress	OCTET STRING,
	    aarpNetAddress	OCTET STRING
    }

    aarpIfIndex OBJECT-TYPE
	    SYNTAX  INTEGER
	    ACCESS  read-only
	    STATUS  mandatory
DESCRIPTION ""
	    ::= { aarpEntry 1 }

    aarpPhysAddress OBJECT-TYPE
	    SYNTAX  OCTET STRING
	    ACCESS  read-only
	    STATUS  mandatory
DESCRIPTION ""
	    ::= { aarpEntry 2 }

    aarpNetAddress OBJECT-TYPE
	    SYNTAX  OCTET STRING
	    ACCESS  read-only
	    STATUS  mandatory
DESCRIPTION ""
	    ::= { aarpEntry 3 }

    atifTable OBJECT-TYPE
	    SYNTAX  SEQUENCE OF AtifEntry
	    ACCESS  read-write
	    STATUS  mandatory
DESCRIPTION ""
	    ::= { atif 1 }

    atifEntry OBJECT-TYPE
	    SYNTAX  AtifEntry
	    ACCESS  read-write
	    STATUS  mandatory
DESCRIPTION ""
	    ::= { atifTable 1 }

    AtifEntry ::= SEQUENCE {
	    atifIndex		INTEGER,
	    atifDescr		OCTET STRING,
	    atifType		INTEGER,
	    atifNetStart	OCTET STRING,
	    atifNetEnd		OCTET STRING,
	    atifNetAddress	OCTET STRING,
	    atifStatus		INTEGER,
	    atifNetConfig	INTEGER,
	    atifZoneConfig	INTEGER,
	    atifZone		OCTET STRING,
	    atifIfIndex		INTEGER
    }

    atifIndex OBJECT-TYPE
	    SYNTAX  INTEGER
	    ACCESS  read-only
	    STATUS  mandatory
DESCRIPTION ""
	    ::= { atifEntry 1 }

    atifDescr OBJECT-TYPE
	    SYNTAX  OCTET STRING
	    ACCESS  read-only
	    STATUS  mandatory
DESCRIPTION ""
	    ::= { atifEntry 2 }

    atifType OBJECT-TYPE
	    SYNTAX  INTEGER {
		other(1),	-- none of the following
		localtalk(2),
		ethertalk1(3),
		ethertalk2(4),
		tokentalk(5),
		iptalk(6)
	    }
	    ACCESS	read-only
	    STATUS	mandatory
DESCRIPTION ""
	    ::= { atifEntry 3 }

    atifNetStart OBJECT-TYPE
	    SYNTAX  OCTET STRING
	    ACCESS  read-write
	    STATUS  mandatory
DESCRIPTION ""
	    ::= { atifEntry 4 }

    atifNetEnd OBJECT-TYPE
	    SYNTAX  OCTET STRING
	    ACCESS  read-write
	    STATUS  mandatory
DESCRIPTION ""
	    ::= { atifEntry 5 }

    atifNetAddress OBJECT-TYPE
	    SYNTAX  OCTET STRING
	    ACCESS  read-write
	    STATUS  mandatory
DESCRIPTION ""
	    ::= { atifEntry 6 }

    atifStatus OBJECT-TYPE
	    SYNTAX  INTEGER
	    ACCESS  read-only
	    STATUS  mandatory
DESCRIPTION ""
	    ::= { atifEntry 7 }

    atifNetConfig OBJECT-TYPE
	    SYNTAX  INTEGER {
		configured(1),
		garnered(2),
		guessed(3),
		unconfigured(4)
	    }
	    ACCESS  read-only
	    STATUS  mandatory
DESCRIPTION ""
	    ::= { atifEntry 8 }

    atifZoneConfig OBJECT-TYPE
	    SYNTAX  INTEGER {
		configured(1),
		garnered(2),
		guessed(3),
		unconfigured(4)
	    }		
	    ACCESS  read-only
	    STATUS  mandatory
DESCRIPTION ""
	    ::= { atifEntry 9 }

    atifZone OBJECT-TYPE
	    SYNTAX  OCTET STRING
	    ACCESS  read-write
	    STATUS  mandatory
DESCRIPTION ""
	    ::= { atifEntry 10 }

    atifIfIndex OBJECT-TYPE
	    SYNTAX  INTEGER
	    ACCESS  read-write
	    STATUS  mandatory
DESCRIPTION ""
	    ::= { atifEntry 11 }

    ddpOutRequests OBJECT-TYPE
	    SYNTAX  Counter
	    ACCESS  read-only
	    STATUS  mandatory
DESCRIPTION ""
	    ::= { ddp 1 }

    ddpOutShort OBJECT-TYPE
	    SYNTAX  Counter
	    ACCESS  read-only
	    STATUS  mandatory
DESCRIPTION ""
	    ::= { ddp 2 }

    ddpOutLong OBJECT-TYPE
	    SYNTAX  Counter
	    ACCESS  read-only
	    STATUS  mandatory
DESCRIPTION ""
	    ::={ ddp 3 }

    ddpReceived OBJECT-TYPE
	    SYNTAX  Counter
	    ACCESS  read-only
	    STATUS  mandatory
DESCRIPTION ""
	    ::= { ddp 4 }

    ddpToForward OBJECT-TYPE
	    SYNTAX  Counter
	    ACCESS  read-only
	    STATUS  mandatory
DESCRIPTION ""
	    ::={ ddp 5 }

    ddpForwards OBJECT-TYPE
	    SYNTAX  Counter
	    ACCESS  read-only
	    STATUS  mandatory
DESCRIPTION ""
	    ::= { ddp 6 }

    ddpForMe OBJECT-TYPE
	    SYNTAX  Counter
	    ACCESS  read-only
	    STATUS  mandatory
DESCRIPTION ""
	    ::= { ddp 7 }

    ddpOutNoRoutes OBJECT-TYPE
	    SYNTAX  Counter
	    ACCESS  read-only
	    STATUS  mandatory
DESCRIPTION ""
	    ::= { ddp 9 }

    ddpTooShortDrops OBJECT-TYPE
	    SYNTAX  Counter
	    ACCESS  read-only
	    STATUS  mandatory
DESCRIPTION ""
	    ::= { ddp 10 }

    ddpTooLongDrops OBJECT-TYPE
	    SYNTAX  Counter
	    ACCESS  read-only
	    STATUS  mandatory
DESCRIPTION ""
	    ::= { ddp 11 }

    ddpBroadcastDrops OBJECT-TYPE
	    SYNTAX  Counter
	    ACCESS  read-only
	    STATUS  mandatory
DESCRIPTION ""
	    ::= { ddp 12 }

    ddpShortDDPDrops OBJECT-TYPE
	    SYNTAX  Counter
	    ACCESS  read-only
	    STATUS  mandatory
DESCRIPTION ""
	    ::= { ddp 13 }

    ddpHopCountDrops OBJECT-TYPE
	    SYNTAX  Counter
	    ACCESS  read-only
	    STATUS  mandatory
DESCRIPTION ""
	    ::= { ddp 14 }

    rtmpTable OBJECT-TYPE
	    SYNTAX  SEQUENCE OF RtmpEntry
	    ACCESS  read-write
	    STATUS  mandatory
DESCRIPTION ""
	    ::= { rtmp 1 }

    rtmpEntry OBJECT-TYPE
	    SYNTAX  RtmpEntry
	    ACCESS  read-write
	    STATUS  mandatory
DESCRIPTION ""
	    ::= { rtmpTable 1 }

    RtmpEntry ::= SEQUENCE {
	    rtmpRangeStart	OCTET STRING,
	    rtmpRangeEnd	OCTET STRING,
	    rtmpNextHop		OCTET STRING,
	    rtmpInterface	INTEGER,
	    rtmpHops		INTEGER,
	    rtmpState		INTEGER
    }

    rtmpRangeStart OBJECT-TYPE
	    SYNTAX  OCTET STRING
	    ACCESS  read-write
	    STATUS  mandatory
DESCRIPTION ""
	    ::= { rtmpEntry 1 }

    rtmpRangeEnd OBJECT-TYPE
	    SYNTAX  OCTET STRING
	    ACCESS  read-write
	    STATUS  mandatory
DESCRIPTION ""
	    ::= { rtmpEntry 2 }

    rtmpNextHop OBJECT-TYPE
	    SYNTAX  OCTET STRING
	    ACCESS  read-write
	    STATUS  mandatory
DESCRIPTION ""
	    ::= { rtmpEntry 3 }

    rtmpInterface OBJECT-TYPE
	    SYNTAX  INTEGER
	    ACCESS  read-write
	    STATUS  mandatory
DESCRIPTION ""
	    ::= { rtmpEntry 4 }

    rtmpHops OBJECT-TYPE
	    SYNTAX  INTEGER
	    ACCESS  read-write
	    STATUS  mandatory
DESCRIPTION ""
	    ::= { rtmpEntry 5 }

    rtmpState OBJECT-TYPE
	    SYNTAX  INTEGER {
		good(1),
		suspect(2),
		bad(3)
	    }
	    ACCESS  read-write
	    STATUS  mandatory
DESCRIPTION ""
	    ::= { rtmpEntry 6 }

    kipTable OBJECT-TYPE
	    SYNTAX  SEQUENCE OF KipEntry
	    ACCESS  read-write
	    STATUS  mandatory
DESCRIPTION ""
	    ::= { kip 1 }

    kipEntry OBJECT-TYPE
	    SYNTAX  KipEntry
	    ACCESS  read-write
	    STATUS  mandatory
DESCRIPTION ""
	    ::= { kipTable 1 }

    KipEntry ::= SEQUENCE {
	    kipNet		OCTET STRING,
	    kipNextHop		IpAddress,
	    kipHopCount		INTEGER,
	    kipBCastAddr	IpAddress,
	    kipCore		INTEGER,
	    kipKfps		INTEGER
    }

    kipNet OBJECT-TYPE
	    SYNTAX  OCTET STRING
	    ACCESS  read-write
	    STATUS  mandatory
DESCRIPTION ""
	    ::= { kipEntry 1 }

    kipNextHop OBJECT-TYPE
	    SYNTAX  IpAddress
	    ACCESS  read-write
	    STATUS  mandatory
DESCRIPTION ""
	    ::= { kipEntry 2 }

    kipHopCount OBJECT-TYPE
	    SYNTAX  INTEGER
	    ACCESS  read-write
	    STATUS  mandatory
DESCRIPTION ""
	    ::= { kipEntry 3 }

    kipBCastAddr OBJECT-TYPE
	    SYNTAX  IpAddress
	    ACCESS  read-write
	    STATUS  mandatory
DESCRIPTION ""
	    ::= { kipEntry 4 }

    kipCore OBJECT-TYPE
	    SYNTAX  INTEGER {
		core(1),
		notcore(2)
	    }
	    ACCESS  read-write
	    STATUS  mandatory
DESCRIPTION ""
	    ::= { kipEntry 5 }

    kipKfps OBJECT-TYPE
	    SYNTAX  INTEGER
	    ACCESS  read-write
	    STATUS  mandatory
DESCRIPTION ""
	    ::= { kipEntry 6 }

    zipTable OBJECT-TYPE
	    SYNTAX  SEQUENCE OF ZipEntry
	    ACCESS  read-write
	    STATUS  mandatory
DESCRIPTION ""
	    ::= { zip 1 }

    zipEntry OBJECT-TYPE
	    SYNTAX  ZipEntry
	    ACCESS  read-write
	    STATUS  mandatory
DESCRIPTION ""
	    ::= { zipTable 1 }

    ZipEntry ::= SEQUENCE {
	    zipZoneName	    OCTET STRING,
	    zipZoneIndex    INTEGER,
	    zipNetStart	    OCTET STRING,
	    zipNetEnd	    OCTET STRING
    }

    zipZoneName OBJECT-TYPE
	    SYNTAX  OCTET STRING
	    ACCESS  read-write
	    STATUS  mandatory
DESCRIPTION ""
	    ::= { zipEntry 1 }

    zipZoneIndex OBJECT-TYPE
	    SYNTAX  INTEGER
	    ACCESS  read-only
	    STATUS  mandatory
DESCRIPTION ""
	    ::= { zipEntry 2 }

    zipZoneNetStart OBJECT-TYPE
	    SYNTAX  OCTET STRING
	    ACCESS  read-write
	    STATUS  mandatory
DESCRIPTION ""
	    ::= { zipEntry 3 }

    zipZoneNetEnd OBJECT-TYPE
	    SYNTAX  OCTET STRING
	    ACCESS  read-write
	    STATUS  mandatory
DESCRIPTION ""
	    ::= { zipEntry 4 }

    nbpTable OBJECT-TYPE
	    SYNTAX  SEQUENCE OF NbpEntry
	    ACCESS  read-write
	    STATUS  mandatory
DESCRIPTION ""
	    ::= { nbp 1 }

    nbpEntry OBJECT-TYPE
	    SYNTAX  NbpEntry
	    ACCESS  read-write
	    STATUS  mandatory
DESCRIPTION ""
	    ::= { nbpTable  1 }


    NbpEntry ::= SEQUENCE {
	    nbpIndex	INTEGER,
	    nbpObject	OCTET STRING,
	    nbpType 	OCTET STRING,
	    nbpZone	OCTET STRING
    }

    nbpIndex OBJECT-TYPE
	    SYNTAX  INTEGER
	    ACCESS  read-only
	    STATUS  mandatory
DESCRIPTION ""
	    ::= { nbpEntry 1 }

    nbpObject OBJECT-TYPE
	    SYNTAX  OCTET STRING
	    ACCESS  read-write
	    STATUS  mandatory
DESCRIPTION ""
	    ::= { nbpEntry 2 }

    nbpType OBJECT-TYPE
	    SYNTAX  OCTET STRING
	    ACCESS  read-write
	    STATUS  mandatory
DESCRIPTION ""
	    ::= { nbpEntry 3 }

    nbpZone OBJECT-TYPE
	    SYNTAX  OCTET STRING
	    ACCESS  read-write
	    STATUS  mandatory
DESCRIPTION ""
	    ::= { nbpEntry 4 }

    echoRequests OBJECT-TYPE
	    SYNTAX  Counter
	    ACCESS  read-only
	    STATUS  mandatory
DESCRIPTION ""
	    ::= { echo 1 }

    echoReplies OBJECT-TYPE
	    SYNTAX  Counter
	    ACCESS  read-only
	    STATUS  mandatory
DESCRIPTION ""
	    ::= { echo 2 }

    bufferSize OBJECT-TYPE
	    SYNTAX  INTEGER
	    ACCESS  read-only
	    STATUS  mandatory
DESCRIPTION ""
	    ::= { buffer 1 }

    bufferAvail OBJECT-TYPE
	    SYNTAX  INTEGER
	    ACCESS  read-only
	    STATUS  mandatory
DESCRIPTION ""
	    ::= { buffer 2 }

    bufferDrops OBJECT-TYPE
	    SYNTAX  Counter
	    ACCESS  read-only
	    STATUS  mandatory
DESCRIPTION ""
	    ::= { buffer 3 }

    bufferTypeTable OBJECT-TYPE
	    SYNTAX  SEQUENCE OF BufferTypeEntry
	    ACCESS  read-only
	    STATUS  mandatory
DESCRIPTION ""
	    ::= { buffer 4 }

    bufferTypeEntry OBJECT-TYPE
	    SYNTAX  BufferTypeEntry
	    ACCESS  read-only
	    STATUS  mandatory
DESCRIPTION ""
	    ::= { bufferTypeTable 1 }

    BufferTypeEntry ::= SEQUENCE {
	    bufferTypeIndex	INTEGER,
	    bufferType		INTEGER,
	    bufferTypeDescr	OCTET STRING,
	    bufferTypeCount	INTEGER
    }

    bufferTypeIndex OBJECT-TYPE
	    SYNTAX  INTEGER
	    ACCESS  read-only
	    STATUS  mandatory
DESCRIPTION ""
	    ::= { bufferTypeEntry 1 }

    bufferType OBJECT-TYPE
	    SYNTAX  INTEGER {
		other(1),
		free(2),
		localtalk(3),
		ethernet(4),
		arp(5),
		data(6),	-- general data
		erbf(7),	-- ethernet receive
		etbf(8),	-- ethernet transmit complete
		malloc(9),
		tkbf(10),	-- token ring receive packet
		token(11)	-- token ring packet
	    }
	    ACCESS  read-only
	    STATUS  mandatory
DESCRIPTION ""
	    ::= { bufferTypeEntry 2 }

    bufferTypeDescr OBJECT-TYPE
	    SYNTAX  OCTET STRING
	    ACCESS  read-only
	    STATUS  mandatory
DESCRIPTION ""
	    ::= { bufferTypeEntry 3 }

    bufferTypeCount OBJECT-TYPE
	    SYNTAX  INTEGER
	    ACCESS  read-only
	    STATUS  mandatory
DESCRIPTION ""
	    ::= { bufferTypeEntry 4 }

END
