-------------------------------------------------------------------------------
-- Fjdary-E50 extended-MIB definition                                        --
-- All Rights Reserved, Copyright FUJITSU LIMITED 2008-2009.                 --
--                                                                           --
-- Modification History :                                                    --
--  v1.0 Initial version.                                                    --
--  v1.1 The erratum in the comment part is corrected.                       --
--  v1.2 Add fjdarySspMaintenanceServiceLevel.                               --
-------------------------------------------------------------------------------
FJDARY-E50 DEFINITIONS ::= BEGIN

IMPORTS
    enterprises,IpAddress
        FROM RFC1155-SMI
    DisplayString
        FROM RFC1213-MIB
    OBJECT-TYPE
        FROM RFC-1212
    TRAP-TYPE
        FROM RFC-1215;

-- Textual Conventions
FjdaryComponentStatus ::= INTEGER{
    normal(1),      -- Normal state
    alarm(2),       -- Abnormal state
    warning(3),     -- Warning state
    invalid(4),     -- Not installed state
    maintenance(5), -- Maintenance state
    undefined(6)    -- Undefined state
}

-- FUJITSU Specific Object Identifier

fujitsu                      OBJECT IDENTIFIER ::= { enterprises 211 }
product                      OBJECT IDENTIFIER ::= { fujitsu 1 }
storage                      OBJECT IDENTIFIER ::= { product 21 }

-- User Specific Object Identifier(1)

nsp                          OBJECT IDENTIFIER ::= { storage 1 }
fjdarye50                    OBJECT IDENTIFIER ::= { nsp 50 }

--
fjdarySsp                    OBJECT IDENTIFIER ::= { fjdarye50 1 }

--
fjdaryPconfig                OBJECT IDENTIFIER ::= { fjdarye50 2 }
fjdaryCm                     OBJECT IDENTIFIER ::= { fjdaryPconfig 1 }
fjdaryCa                     OBJECT IDENTIFIER ::= { fjdaryPconfig 2 }
fjdaryFrt                    OBJECT IDENTIFIER ::= { fjdaryPconfig 3 }
fjdaryBrt                    OBJECT IDENTIFIER ::= { fjdaryPconfig 4 }
fjdaryCmmemory               OBJECT IDENTIFIER ::= { fjdaryPconfig 5 }
fjdaryCmfan                  OBJECT IDENTIFIER ::= { fjdaryPconfig 6 }
fjdaryCf                     OBJECT IDENTIFIER ::= { fjdaryPconfig 7 }
fjdaryOpnl                   OBJECT IDENTIFIER ::= { fjdaryPconfig 8 }
fjdaryCefan                  OBJECT IDENTIFIER ::= { fjdaryPconfig 9 }
fjdarySvc                    OBJECT IDENTIFIER ::= { fjdaryPconfig 10 }
fjdarySmc                    OBJECT IDENTIFIER ::= { fjdaryPconfig 11 }
fjdaryBcu                    OBJECT IDENTIFIER ::= { fjdaryPconfig 12 }
fjdaryBtu                    OBJECT IDENTIFIER ::= { fjdaryPconfig 13 }
fjdaryCe                     OBJECT IDENTIFIER ::= { fjdaryPconfig 14 }
fjdaryCeinletthml            OBJECT IDENTIFIER ::= { fjdaryPconfig 15 }
fjdaryCethermal              OBJECT IDENTIFIER ::= { fjdaryPconfig 16 }
fjdaryCpsu                   OBJECT IDENTIFIER ::= { fjdaryPconfig 17 }
fjdarySccb                   OBJECT IDENTIFIER ::= { fjdaryPconfig 18 }
fjdaryDe                     OBJECT IDENTIFIER ::= { fjdaryPconfig 19 }
fjdaryPbc                    OBJECT IDENTIFIER ::= { fjdaryPconfig 20 }
fjdaryDpsu                   OBJECT IDENTIFIER ::= { fjdaryPconfig 21 }
fjdaryDefan                  OBJECT IDENTIFIER ::= { fjdaryPconfig 22 }
fjdaryDeinletthml            OBJECT IDENTIFIER ::= { fjdaryPconfig 23 }
fjdaryDethermal              OBJECT IDENTIFIER ::= { fjdaryPconfig 24 }
fjdaryDisk                   OBJECT IDENTIFIER ::= { fjdaryPconfig 25 }
fjdaryLanport                OBJECT IDENTIFIER ::= { fjdaryPconfig 26 }

--
fjdaryLconfig                OBJECT IDENTIFIER ::= { fjdarye50 3 }
fjdaryCaPort                 OBJECT IDENTIFIER ::= { fjdaryLconfig 1 }
fjdaryOlu                    OBJECT IDENTIFIER ::= { fjdaryLconfig 2 }
fjdaryMlu                    OBJECT IDENTIFIER ::= { fjdaryLconfig 3 }
fjdarySlu                    OBJECT IDENTIFIER ::= { fjdaryLconfig 4 }
fjdaryRlu                    OBJECT IDENTIFIER ::= { fjdaryLconfig 5 }
fjdaryDlu                    OBJECT IDENTIFIER ::= { fjdaryLconfig 6 }
fjdaryOpenmap                OBJECT IDENTIFIER ::= { fjdaryLconfig 7 }
fjdaryLunolu                 OBJECT IDENTIFIER ::= { fjdaryLconfig 8 }
fjdaryHostwwn                OBJECT IDENTIFIER ::= { fjdaryLconfig 9 }
fjdaryResetpath              OBJECT IDENTIFIER ::= { fjdaryLconfig 10 }
fjdaryLcu                    OBJECT IDENTIFIER ::= { fjdaryLconfig 11 }
fjdaryIoamlu                 OBJECT IDENTIFIER ::= { fjdaryLconfig 12 }
fjdaryHostiscsi              OBJECT IDENTIFIER ::= { fjdaryLconfig 13 }
fjdaryHostResponse           OBJECT IDENTIFIER ::= { fjdaryLconfig 14 }

--
fjdaryFirm                   OBJECT IDENTIFIER ::= { fjdarye50 4 }

--
fjdaryPerformance            OBJECT IDENTIFIER ::= { fjdarye50 5 }
fjdaryPfhead                 OBJECT IDENTIFIER ::= { fjdaryPerformance 1 }
fjdaryPfopca                 OBJECT IDENTIFIER ::= { fjdaryPerformance 2 }
fjdaryPfocca                 OBJECT IDENTIFIER ::= { fjdaryPerformance 3 }
fjdaryPfflca                 OBJECT IDENTIFIER ::= { fjdaryPerformance 4 }
fjdaryPfdi                   OBJECT IDENTIFIER ::= { fjdaryPerformance 5 }
fjdaryPfbrt                  OBJECT IDENTIFIER ::= { fjdaryPerformance 6 }
fjdaryPfdisk                 OBJECT IDENTIFIER ::= { fjdaryPerformance 7 }
fjdaryPfdisktime             OBJECT IDENTIFIER ::= { fjdaryPerformance 8 }
fjdaryPfcm                   OBJECT IDENTIFIER ::= { fjdaryPerformance 9 }
fjdaryPfcacheolu             OBJECT IDENTIFIER ::= { fjdaryPerformance 10 }
fjdaryPfrscolu               OBJECT IDENTIFIER ::= { fjdaryPerformance 11 }
fjdaryPfrscrlu               OBJECT IDENTIFIER ::= { fjdaryPerformance 12 }
fjdaryPfcopycm               OBJECT IDENTIFIER ::= { fjdaryPerformance 13 }
fjdaryPfcopyslu              OBJECT IDENTIFIER ::= { fjdaryPerformance 14 }
fjdaryPfcacheslu             OBJECT IDENTIFIER ::= { fjdaryPerformance 15 }
fjdaryPfrscslu               OBJECT IDENTIFIER ::= { fjdaryPerformance 16 }
fjdaryPfcachecopyslu         OBJECT IDENTIFIER ::= { fjdaryPerformance 17 }
fjdaryPfcachesdvslu          OBJECT IDENTIFIER ::= { fjdaryPerformance 18 }
fjdaryPfcachecopyolu         OBJECT IDENTIFIER ::= { fjdaryPerformance 19 }
fjdaryPfcachecommonolu       OBJECT IDENTIFIER ::= { fjdaryPerformance 20 }
fjdaryPfcachecommonslu       OBJECT IDENTIFIER ::= { fjdaryPerformance 21 }

--
application                  OBJECT IDENTIFIER ::= { fujitsu 4 }
aplNetwork                   OBJECT IDENTIFIER ::= { application 1 }
aplNetDevice                 OBJECT IDENTIFIER ::= { aplNetwork 1 }
aplNetStorage                OBJECT IDENTIFIER ::= { aplNetDevice 126 }
aplNetNsp                    OBJECT IDENTIFIER ::= { aplNetStorage 1 }
aplNetFjdarye50              OBJECT IDENTIFIER ::= { aplNetNsp 50 }

--***************************************************************************--
--   Unit Status                                                             --
--***************************************************************************--
fjdaryUnitStatus OBJECT-TYPE
    SYNTAX INTEGER {
        unknown(1),
        unused(2),
        ok(3),
        warning(4),
        failed(5)
    }
    ACCESS read-only
    STATUS mandatory
    DESCRIPTION
        "Overall status of this system."
    ::= { fjdarye50 6 }

--***************************************************************************--
--   Trap Specific Object                                                    --
--***************************************************************************--
fjdaryTrapItemId OBJECT-TYPE
    SYNTAX INTEGER
    ACCESS read-only
    STATUS mandatory
    DESCRIPTION
        "This object is used to store the identification number of parts for
         which maintenance is necessary when trap is transmitted."
    ::= { fjdarye50 7 }

fjdaryTrapSensorInfo OBJECT-TYPE
    SYNTAX INTEGER
    ACCESS read-only
    STATUS mandatory
    DESCRIPTION
        "This object is used to store detail information of sensor when trap is
         transmitted."
    ::= { fjdarye50 8 }

fjdaryTrapMaintenanceInfo OBJECT-TYPE
    SYNTAX INTEGER
    ACCESS read-only
    STATUS mandatory
    DESCRIPTION
        "This object is used to store detail information of maintenance when
         trap is transmitted."
    ::= { fjdarye50 9 }

fjdaryTrapWarningInfo OBJECT-TYPE
    SYNTAX INTEGER
    ACCESS read-only
    STATUS mandatory
    DESCRIPTION
        "This object is used to store detail information of warning when trap
         is transmitted."
    ::= { fjdarye50 10 }

fjdaryTrapMessage OBJECT-TYPE
    SYNTAX DisplayString
    ACCESS read-only
    STATUS mandatory
    DESCRIPTION
        "This object is used to store detail messages when all trap is
         transmitted."
    ::= { fjdarye50 11 }

--***************************************************************************--
--   Subsystem Parameter                                                     --
--***************************************************************************--
fjdarySspMachineId OBJECT-TYPE
    SYNTAX OCTET STRING
    ACCESS read-only
    STATUS mandatory
    DESCRIPTION
        "This value indicates the identification number of this system.
         ttssssssssssssmmmmmmmmmmmmccssssssssssss
         | |           |           | |
         | |           |           | +-serial number(12byte)
         | |           |           +-check code(2byte)
         | |           +-model name(12byte)
         | +-series name(12byte)
         +-type code(2byte)"
    ::= { fjdarySsp 1 }

fjdarySspConfigDate OBJECT-TYPE
    SYNTAX DisplayString
    ACCESS read-only
    STATUS mandatory
    DESCRIPTION
        "The last date when the configuration was applied.
         yyyymmddHHMMSS
         |   | | | | |
         |   | | | | +-second
         |   | | | +-minute
         |   | | +-hour
         |   | +-day
         |   +-month
         +-year"
    ::= { fjdarySsp 2 }

fjdarySspWwnn OBJECT-TYPE
    SYNTAX OCTET STRING
    ACCESS read-only
    STATUS mandatory
    DESCRIPTION
        "The value of this object indecates the World Wide Node Name."
    ::= { fjdarySsp 3 }

fjdarySspVenderId OBJECT-TYPE
    SYNTAX OCTET STRING
    ACCESS read-only
    STATUS mandatory
    DESCRIPTION
        "The value of this object indecates the Vender ID."
    ::= { fjdarySsp 4 }

fjdarySspProductId OBJECT-TYPE
    SYNTAX OCTET STRING
    ACCESS read-only
    STATUS mandatory
    DESCRIPTION
        "The value of this object indecates the Product ID."
    ::= { fjdarySsp 5 }

fjdarySspBoxId OBJECT-TYPE
    SYNTAX OCTET STRING
    ACCESS read-only
    STATUS mandatory
    DESCRIPTION
        "This value of a meaning within a user system. An initial value is the
         same as fjdarySspMachineId."
    ::= { fjdarySsp 6 }

fjdarySspMaintenanceServiceLevel OBJECT-TYPE
    SYNTAX INTEGER {
        level1(1),
        level2(2)
    }
    ACCESS read-only
    STATUS mandatory
    DESCRIPTION
        "The value of this object indecates the support level of maintenance
         service. Level2 supports interface that strengthens the security
         level from level1."
    ::= { fjdarySsp 7 }

--***************************************************************************--
--   Physical Component                                                      --
--***************************************************************************--
-------------------------------------------------------------------------------
--   fjdaryCm                                                                --
-------------------------------------------------------------------------------
fjdaryCmCount OBJECT-TYPE
    SYNTAX INTEGER
    ACCESS read-only
    STATUS mandatory
    DESCRIPTION
        "The number of CM(controller module)'s informations (regardless of
         their current state) present on this system."
    ::= { fjdaryCm 1 }

fjdaryCmTable OBJECT-TYPE
    SYNTAX SEQUENCE OF FjdaryCmEntry
    ACCESS not-accessible
    STATUS mandatory
    DESCRIPTION
        ""
    ::= { fjdaryCm 2 }

fjdaryCmEntry OBJECT-TYPE
    SYNTAX FjdaryCmEntry
    ACCESS not-accessible
    STATUS mandatory
    DESCRIPTION
        ""
    INDEX { fjdaryCmIndex }
    ::= { fjdaryCmTable 1 }

FjdaryCmEntry ::=
    SEQUENCE{
        fjdaryCmIndex    INTEGER,
        fjdaryCmItemId   INTEGER,
        fjdaryCmStatus   FjdaryComponentStatus,
        fjdaryCmModuleId INTEGER,
        fjdaryCmRole     INTEGER,
        fjdaryCmPtId     OCTET STRING
    }

fjdaryCmIndex OBJECT-TYPE
    SYNTAX INTEGER
    ACCESS read-only
    STATUS mandatory
    DESCRIPTION
        "The value of this object uniquely identifies this fjdaryCm entry."
    ::= { fjdaryCmEntry 1 }

fjdaryCmItemId OBJECT-TYPE
    SYNTAX INTEGER
    ACCESS read-only
    STATUS mandatory
    DESCRIPTION
        "The value of this object indicates the identification number of this
         CM."
    ::= { fjdaryCmEntry 2 }

fjdaryCmStatus OBJECT-TYPE
    SYNTAX FjdaryComponentStatus
    ACCESS read-only
    STATUS mandatory
    DESCRIPTION
        "The value of this object indicates the state of this CM."
    ::= { fjdaryCmEntry 3 }

fjdaryCmModuleId OBJECT-TYPE
    SYNTAX INTEGER
    ACCESS read-only
    STATUS mandatory
    DESCRIPTION
        "The value of this object indicates the module indicates of this CM."
    ::= { fjdaryCmEntry 4 }

fjdaryCmRole OBJECT-TYPE
    SYNTAX INTEGER
    ACCESS read-only
    STATUS mandatory
    DESCRIPTION
        "The value of this object indicates the role of this CM."
    ::= { fjdaryCmEntry 5 }
    
fjdaryCmPtId OBJECT-TYPE
    SYNTAX OCTET STRING
    ACCESS read-only
    STATUS mandatory
    DESCRIPTION
        "The value of this object indicates the PT management informatiom of
         this CM."
    ::= { fjdaryCmEntry 6 }

-------------------------------------------------------------------------------
--   fjdaryCa                                                                --
-------------------------------------------------------------------------------
fjdaryCaCount OBJECT-TYPE
    SYNTAX INTEGER
    ACCESS read-only
    STATUS mandatory
    DESCRIPTION
        "The number of CA(channel adapter)'s informations (regardless of their
         current state) present on this system."
    ::= { fjdaryCa 1 }

fjdaryCaTable OBJECT-TYPE
    SYNTAX SEQUENCE OF FjdaryCaEntry
    ACCESS not-accessible
    STATUS mandatory
    DESCRIPTION
        ""
    ::= { fjdaryCa 2 }

fjdaryCaEntry OBJECT-TYPE
    SYNTAX FjdaryCaEntry
    ACCESS not-accessible
    STATUS mandatory
    DESCRIPTION
        ""
    INDEX { fjdaryCaIndex }
    ::= { fjdaryCaTable 1 }

FjdaryCaEntry ::=
    SEQUENCE{
        fjdaryCaIndex    INTEGER,
        fjdaryCaItemId   INTEGER,
        fjdaryCaStatus   FjdaryComponentStatus,
        fjdaryCaModuleId INTEGER,
        fjdaryCaType     INTEGER,
        fjdaryCaPtId     OCTET STRING
    }

fjdaryCaIndex OBJECT-TYPE
    SYNTAX INTEGER
    ACCESS read-only
    STATUS mandatory
    DESCRIPTION
        "The value of this object uniquely identifies this fjdaryCa entry."
    ::= { fjdaryCaEntry 1 }

fjdaryCaItemId OBJECT-TYPE
    SYNTAX INTEGER
    ACCESS read-only
    STATUS mandatory
    DESCRIPTION
        "The value of this object indicates the identification number of this
         CA."
    ::= { fjdaryCaEntry 2 }

fjdaryCaStatus OBJECT-TYPE
    SYNTAX FjdaryComponentStatus
    ACCESS read-only
    STATUS mandatory
    DESCRIPTION
        "The value of this object indicates the state of this CA."
    ::= { fjdaryCaEntry 3 }

fjdaryCaModuleId OBJECT-TYPE
    SYNTAX INTEGER
    ACCESS read-only
    STATUS mandatory
    DESCRIPTION
        "The value of this object indicates the module indicates of this CA."
    ::= { fjdaryCaEntry 4 }

fjdaryCaType OBJECT-TYPE
    SYNTAX INTEGER
    ACCESS read-only
    STATUS mandatory
    DESCRIPTION
        "The value of this object indicates the type of this CA."
    ::= { fjdaryCaEntry 5 }
    
fjdaryCaPtId OBJECT-TYPE
    SYNTAX OCTET STRING
    ACCESS read-only
    STATUS mandatory
    DESCRIPTION
        "The value of this object indicates the PT management informatiom of
         this CA."
    ::= { fjdaryCaEntry 6 }

-------------------------------------------------------------------------------
--   fjdaryFrt                                                               --
-------------------------------------------------------------------------------
fjdaryFrtCount OBJECT-TYPE
    SYNTAX INTEGER
    ACCESS read-only
    STATUS mandatory
    DESCRIPTION
        "The number of FRT(front-end router)'s informations (regardless of
         their current state) present on this system."
    ::= { fjdaryFrt 1 }

fjdaryFrtTable OBJECT-TYPE
    SYNTAX SEQUENCE OF FjdaryFrtEntry
    ACCESS not-accessible
    STATUS mandatory
    DESCRIPTION
        ""
    ::= { fjdaryFrt 2 }

fjdaryFrtEntry OBJECT-TYPE
    SYNTAX FjdaryFrtEntry
    ACCESS not-accessible
    STATUS mandatory
    DESCRIPTION
        ""
    INDEX { fjdaryFrtIndex }
    ::= { fjdaryFrtTable 1 }

FjdaryFrtEntry ::=
    SEQUENCE{
        fjdaryFrtIndex  INTEGER,
        fjdaryFrtItemId INTEGER,
        fjdaryFrtStatus FjdaryComponentStatus
    }

fjdaryFrtIndex OBJECT-TYPE
    SYNTAX INTEGER
    ACCESS read-only
    STATUS mandatory
    DESCRIPTION
        "The value of this object uniquely identifies this fjdaryFrt entry."
    ::= { fjdaryFrtEntry 1 }

fjdaryFrtItemId OBJECT-TYPE
    SYNTAX INTEGER
    ACCESS read-only
    STATUS mandatory
    DESCRIPTION
        "The value of this object indicates the identification number of this
         FRT."
    ::= { fjdaryFrtEntry 2 }

fjdaryFrtStatus OBJECT-TYPE
    SYNTAX FjdaryComponentStatus
    ACCESS read-only
    STATUS mandatory
    DESCRIPTION
        "The value of this object indicates the state of this FRT."
    ::= { fjdaryFrtEntry 3 }

-------------------------------------------------------------------------------
--   fjdaryBrt                                                               --
-------------------------------------------------------------------------------
fjdaryBrtCount OBJECT-TYPE
    SYNTAX INTEGER
    ACCESS read-only
    STATUS mandatory
    DESCRIPTION
        "The number of BRT(back-end router)'s informations (regardless of their
         current state) present on this system."
    ::= { fjdaryBrt 1 }

fjdaryBrtTable OBJECT-TYPE
    SYNTAX SEQUENCE OF FjdaryBrtEntry
    ACCESS not-accessible
    STATUS mandatory
    DESCRIPTION
        ""
    ::= { fjdaryBrt 2 }

fjdaryBrtEntry OBJECT-TYPE
    SYNTAX FjdaryBrtEntry
    ACCESS not-accessible
    STATUS mandatory
    DESCRIPTION
        ""
    INDEX { fjdaryBrtIndex }
    ::= { fjdaryBrtTable 1 }

FjdaryBrtEntry ::=
    SEQUENCE{
        fjdaryBrtIndex  INTEGER,
        fjdaryBrtItemId INTEGER,
        fjdaryBrtStatus FjdaryComponentStatus
    }

fjdaryBrtIndex OBJECT-TYPE
    SYNTAX INTEGER
    ACCESS read-only
    STATUS mandatory
    DESCRIPTION
        "The value of this object uniquely identifies this fjdaryBrt entry."
    ::= { fjdaryBrtEntry 1 }

fjdaryBrtItemId OBJECT-TYPE
    SYNTAX INTEGER
    ACCESS read-only
    STATUS mandatory
    DESCRIPTION
        "The value of this object indicates the identification number of this
         BRT."
    ::= { fjdaryBrtEntry 2 }

fjdaryBrtStatus OBJECT-TYPE
    SYNTAX FjdaryComponentStatus
    ACCESS read-only
    STATUS mandatory
    DESCRIPTION
        "The value of this object indicates the state of this BRT."
    ::= { fjdaryBrtEntry 3 }

-------------------------------------------------------------------------------
--   fjdaryCmmemory                                                          --
-------------------------------------------------------------------------------
fjdaryCmmemoryCount OBJECT-TYPE
    SYNTAX INTEGER
    ACCESS read-only
    STATUS mandatory
    DESCRIPTION
        "The number of CM memory's informations (regardless of their current
         state) present on this system."
    ::= { fjdaryCmmemory 1 }

fjdaryCmmemoryTable OBJECT-TYPE
    SYNTAX SEQUENCE OF FjdaryCmmemoryEntry
    ACCESS not-accessible
    STATUS mandatory
    DESCRIPTION
        ""
    ::= { fjdaryCmmemory 2 }

fjdaryCmmemoryEntry OBJECT-TYPE
    SYNTAX FjdaryCmmemoryEntry
    ACCESS not-accessible
    STATUS mandatory
    DESCRIPTION
        ""
    INDEX { fjdaryCmmemoryIndex }
    ::= { fjdaryCmmemoryTable 1 }

FjdaryCmmemoryEntry ::=
    SEQUENCE{
        fjdaryCmmemoryIndex    INTEGER,
        fjdaryCmmemoryItemId   INTEGER,
        fjdaryCmmemoryStatus   FjdaryComponentStatus,
        fjdaryCmmemoryCapacity OCTET STRING
    }

fjdaryCmmemoryIndex OBJECT-TYPE
    SYNTAX INTEGER
    ACCESS read-only
    STATUS mandatory
    DESCRIPTION
        "The value of this object uniquely identifies this fjdaryCmmemory
         entry."
    ::= { fjdaryCmmemoryEntry 1 }

fjdaryCmmemoryItemId OBJECT-TYPE
    SYNTAX INTEGER
    ACCESS read-only
    STATUS mandatory
    DESCRIPTION
        "The value of this object indicates the identification number of this
         CM memory."
    ::= { fjdaryCmmemoryEntry 2 }

fjdaryCmmemoryStatus OBJECT-TYPE
    SYNTAX FjdaryComponentStatus
    ACCESS read-only
    STATUS mandatory
    DESCRIPTION
        "The value of this object indicates the state of this CM memory."
    ::= { fjdaryCmmemoryEntry 3 }

fjdaryCmmemoryCapacity OBJECT-TYPE
    SYNTAX OCTET STRING
    ACCESS read-only
    STATUS mandatory
    DESCRIPTION
        "The value of this object indicates the capacity of this CM memory."
    ::= { fjdaryCmmemoryEntry 4 }

-------------------------------------------------------------------------------
--   fjdaryCmfan                                                             --
-------------------------------------------------------------------------------
fjdaryCmfanCount OBJECT-TYPE
    SYNTAX INTEGER
    ACCESS read-only
    STATUS mandatory
    DESCRIPTION
        "The number of CM FAN's informations (regardless of their current
         state) present on this system."
    ::= { fjdaryCmfan 1 }

fjdaryCmfanTable OBJECT-TYPE
    SYNTAX SEQUENCE OF FjdaryCmfanEntry
    ACCESS not-accessible
    STATUS mandatory
    DESCRIPTION
        ""
    ::= { fjdaryCmfan 2 }

fjdaryCmfanEntry OBJECT-TYPE
    SYNTAX FjdaryCmfanEntry
    ACCESS not-accessible
    STATUS mandatory
    DESCRIPTION
        ""
    INDEX { fjdaryCmfanIndex }
    ::= { fjdaryCmfanTable 1 }

FjdaryCmfanEntry ::=
    SEQUENCE{
        fjdaryCmfanIndex  INTEGER,
        fjdaryCmfanItemId INTEGER,
        fjdaryCmfanStatus FjdaryComponentStatus
    }

fjdaryCmfanIndex OBJECT-TYPE
    SYNTAX INTEGER
    ACCESS read-only
    STATUS mandatory
    DESCRIPTION
        "The value of this object uniquely identifies this fjdaryCmfan entry."
    ::= { fjdaryCmfanEntry 1 }

fjdaryCmfanItemId OBJECT-TYPE
    SYNTAX INTEGER
    ACCESS read-only
    STATUS mandatory
    DESCRIPTION
        "The value of this object indicates the identification number of this
         CM FAN."
    ::= { fjdaryCmfanEntry 2 }

fjdaryCmfanStatus OBJECT-TYPE
    SYNTAX FjdaryComponentStatus
    ACCESS read-only
    STATUS mandatory
    DESCRIPTION
        "The value of this object indicates the state of this CM FAN."
    ::= { fjdaryCmfanEntry 3 }

-------------------------------------------------------------------------------
--   fjdaryCf                                                                --
-------------------------------------------------------------------------------
fjdaryCfCount OBJECT-TYPE
    SYNTAX INTEGER
    ACCESS read-only
    STATUS mandatory
    DESCRIPTION
        "The number of CF(compact flash)'s informations (regardless of their
         current state) present on this system."
    ::= { fjdaryCf 1 }

fjdaryCfTable OBJECT-TYPE
    SYNTAX SEQUENCE OF FjdaryCfEntry
    ACCESS not-accessible
    STATUS mandatory
    DESCRIPTION
        ""
    ::= { fjdaryCf 2 }

fjdaryCfEntry OBJECT-TYPE
    SYNTAX FjdaryCfEntry
    ACCESS not-accessible
    STATUS mandatory
    DESCRIPTION
        ""
    INDEX { fjdaryCfIndex }
    ::= { fjdaryCfTable 1 }

FjdaryCfEntry ::=
    SEQUENCE{
        fjdaryCfIndex  INTEGER,
        fjdaryCfItemId INTEGER,
        fjdaryCfStatus FjdaryComponentStatus
    }

fjdaryCfIndex OBJECT-TYPE
    SYNTAX INTEGER
    ACCESS read-only
    STATUS mandatory
    DESCRIPTION
        "The value of this object uniquely identifies this fjdaryCf entry."
    ::= { fjdaryCfEntry 1 }

fjdaryCfItemId OBJECT-TYPE
    SYNTAX INTEGER
    ACCESS read-only
    STATUS mandatory
    DESCRIPTION
        "The value of this object indicates the identification number of this
         CF."
    ::= { fjdaryCfEntry 2 }

fjdaryCfStatus OBJECT-TYPE
    SYNTAX FjdaryComponentStatus
    ACCESS read-only
    STATUS mandatory
    DESCRIPTION
        "The value of this object indicates the state of this CF."
    ::= { fjdaryCfEntry 3 }

-------------------------------------------------------------------------------
--   fjdaryOpnl                                                              --
-------------------------------------------------------------------------------
fjdaryOpnlCount OBJECT-TYPE
    SYNTAX INTEGER
    ACCESS read-only
    STATUS mandatory
    DESCRIPTION
        "The number of OPNL(operation panel)'s informations (regardless of
         their current state) present on this system."
    ::= { fjdaryOpnl 1 }

fjdaryOpnlTable OBJECT-TYPE
    SYNTAX SEQUENCE OF FjdaryOpnlEntry
    ACCESS not-accessible
    STATUS mandatory
    DESCRIPTION
        ""
    ::= { fjdaryOpnl 2 }

fjdaryOpnlEntry OBJECT-TYPE
    SYNTAX FjdaryOpnlEntry
    ACCESS not-accessible
    STATUS mandatory
    DESCRIPTION
        ""
    INDEX { fjdaryOpnlIndex }
    ::= { fjdaryOpnlTable 1 }

FjdaryOpnlEntry ::=
    SEQUENCE{
        fjdaryOpnlIndex  INTEGER,
        fjdaryOpnlItemId INTEGER,
        fjdaryOpnlStatus INTEGER
    }

fjdaryOpnlIndex OBJECT-TYPE
    SYNTAX INTEGER
    ACCESS read-only
    STATUS mandatory
    DESCRIPTION
        "The value of this object uniquely identifies this fjdaryOpnl entry."
    ::= { fjdaryOpnlEntry 1 }

fjdaryOpnlItemId OBJECT-TYPE
    SYNTAX INTEGER
    ACCESS read-only
    STATUS mandatory
    DESCRIPTION
        "The value of this object indicates the identification number of this
         OPNL."
    ::= { fjdaryOpnlEntry 2 }

fjdaryOpnlStatus OBJECT-TYPE
    SYNTAX FjdaryComponentStatus
    ACCESS read-only
    STATUS mandatory
    DESCRIPTION
        "The value of this object indicates the state of this OPNL."
    ::= { fjdaryOpnlEntry 3 }

-------------------------------------------------------------------------------
--   fjdaryCefan                                                             --
-------------------------------------------------------------------------------
fjdaryCefanCount OBJECT-TYPE
    SYNTAX INTEGER
    ACCESS read-only
    STATUS mandatory
    DESCRIPTION
        "The number of CE FAN's informations (regardless of their current
         state) present on this system."
    ::= { fjdaryCefan 1 }

fjdaryCefanTable OBJECT-TYPE
    SYNTAX SEQUENCE OF FjdaryCefanEntry
    ACCESS not-accessible
    STATUS mandatory
    DESCRIPTION
        ""
    ::= { fjdaryCefan 2 }

fjdaryCefanEntry OBJECT-TYPE
    SYNTAX FjdaryCefanEntry
    ACCESS not-accessible
    STATUS mandatory
    DESCRIPTION
        ""
    INDEX { fjdaryCefanIndex }
    ::= { fjdaryCefanTable 1 }

FjdaryCefanEntry ::=
    SEQUENCE{
        fjdaryCefanIndex  INTEGER,
        fjdaryCefanItemId INTEGER,
        fjdaryCefanStatus FjdaryComponentStatus
    }

fjdaryCefanIndex OBJECT-TYPE
    SYNTAX INTEGER
    ACCESS read-only
    STATUS mandatory
    DESCRIPTION
        "The value of this object uniquely identifies this fjdaryCefan entry."
    ::= { fjdaryCefanEntry 1 }

fjdaryCefanItemId OBJECT-TYPE
    SYNTAX INTEGER
    ACCESS read-only
    STATUS mandatory
    DESCRIPTION
        "The value of this object indicates the identification number of this
         CE FAN."
    ::= { fjdaryCefanEntry 2 }

fjdaryCefanStatus OBJECT-TYPE
    SYNTAX FjdaryComponentStatus
    ACCESS read-only
    STATUS mandatory
    DESCRIPTION
        "The value of this object indicates the state of this CE FAN."
    ::= { fjdaryCefanEntry 3 }

-------------------------------------------------------------------------------
--   fjdarySvc                                                               --
-------------------------------------------------------------------------------
fjdarySvcCount OBJECT-TYPE
    SYNTAX INTEGER
    ACCESS read-only
    STATUS mandatory
    DESCRIPTION
        "The number of SVC(service controller)'s informations (regardless of
         their current state) present on this system."
    ::= { fjdarySvc 1 }

fjdarySvcTable OBJECT-TYPE
    SYNTAX SEQUENCE OF FjdarySvcEntry
    ACCESS not-accessible
    STATUS mandatory
    DESCRIPTION
        ""
    ::= { fjdarySvc 2 }

fjdarySvcEntry OBJECT-TYPE
    SYNTAX FjdarySvcEntry
    ACCESS not-accessible
    STATUS mandatory
    DESCRIPTION
        ""
    INDEX { fjdarySvcIndex }
    ::= { fjdarySvcTable 1 }

FjdarySvcEntry ::=
    SEQUENCE{
        fjdarySvcIndex    INTEGER,
        fjdarySvcItemId   INTEGER,
        fjdarySvcStatus   FjdaryComponentStatus,
        fjdarySvcFirmInfo OCTET STRING
    }

fjdarySvcIndex OBJECT-TYPE
    SYNTAX INTEGER
    ACCESS read-only
    STATUS mandatory
    DESCRIPTION
        "The value of this object uniquely identifies this fjdarySvc entry."
    ::= { fjdarySvcEntry 1 }

fjdarySvcItemId OBJECT-TYPE
    SYNTAX INTEGER
    ACCESS read-only
    STATUS mandatory
    DESCRIPTION
        "The value of this object indicates the identification number of this
         SVC."
    ::= { fjdarySvcEntry 2 }

fjdarySvcStatus OBJECT-TYPE
    SYNTAX FjdaryComponentStatus
    ACCESS read-only
    STATUS mandatory
    DESCRIPTION
        "The value of this object indicates the state of this SVC."
    ::= { fjdarySvcEntry 3 }

fjdarySvcFirmInfo OBJECT-TYPE
    SYNTAX OCTET STRING
    ACCESS read-only
    STATUS mandatory
    DESCRIPTION
        "The value of this object indicates the firmware information of this
         SVC."
    ::= { fjdarySvcEntry 4 }

-------------------------------------------------------------------------------
--   fjdarySmc                                                               --
-------------------------------------------------------------------------------
fjdarySmcCount OBJECT-TYPE
    SYNTAX INTEGER
    ACCESS read-only
    STATUS mandatory
    DESCRIPTION
        "The number of SMC(system management controller)'s informations
         (regardless of their current state) present on this system."
    ::= { fjdarySmc 1 }

fjdarySmcTable OBJECT-TYPE
    SYNTAX SEQUENCE OF FjdarySmcEntry
    ACCESS not-accessible
    STATUS mandatory
    DESCRIPTION
        ""
    ::= { fjdarySmc 2 }

fjdarySmcEntry OBJECT-TYPE
    SYNTAX FjdarySmcEntry
    ACCESS not-accessible
    STATUS mandatory
    DESCRIPTION
        ""
    INDEX { fjdarySmcIndex }
    ::= { fjdarySmcTable 1 }

FjdarySmcEntry ::=
    SEQUENCE{
        fjdarySmcIndex    INTEGER,
        fjdarySmcItemId   INTEGER,
        fjdarySmcStatus   FjdaryComponentStatus,
        fjdarySmcFirmInfo OCTET STRING
    }

fjdarySmcIndex OBJECT-TYPE
    SYNTAX INTEGER
    ACCESS read-only
    STATUS mandatory
    DESCRIPTION
        "The value of this object uniquely identifies this fjdarySmc entry."
    ::= { fjdarySmcEntry 1 }

fjdarySmcItemId OBJECT-TYPE
    SYNTAX INTEGER
    ACCESS read-only
    STATUS mandatory
    DESCRIPTION
        "The value of this object indicates the identification number of this
         SMC."
    ::= { fjdarySmcEntry 2 }

fjdarySmcStatus OBJECT-TYPE
    SYNTAX FjdaryComponentStatus
    ACCESS read-only
    STATUS mandatory
    DESCRIPTION
        "The value of this object indicates the state of this SMC."
    ::= { fjdarySmcEntry 3 }

fjdarySmcFirmInfo OBJECT-TYPE
    SYNTAX OCTET STRING
    ACCESS read-only
    STATUS mandatory
    DESCRIPTION
        "The value of this object indicates the firmware information of this
         SMC."
    ::= { fjdarySmcEntry 4 }

-------------------------------------------------------------------------------
--   fjdaryBcu                                                               --
-------------------------------------------------------------------------------
fjdaryBcuCount OBJECT-TYPE
    SYNTAX INTEGER
    ACCESS read-only
    STATUS mandatory
    DESCRIPTION
        "The number of BCU(battery control unit)'s informations (regardless of
         their current state) present on this system."
    ::= { fjdaryBcu 1 }

fjdaryBcuTable OBJECT-TYPE
    SYNTAX SEQUENCE OF FjdaryBcuEntry
    ACCESS not-accessible
    STATUS mandatory
    DESCRIPTION
        ""
    ::= { fjdaryBcu 2 }

fjdaryBcuEntry OBJECT-TYPE
    SYNTAX FjdaryBcuEntry
    ACCESS not-accessible
    STATUS mandatory
    DESCRIPTION
        ""
    INDEX { fjdaryBcuIndex }
    ::= { fjdaryBcuTable 1 }

FjdaryBcuEntry ::=
    SEQUENCE{
        fjdaryBcuIndex  INTEGER,
        fjdaryBcuItemId INTEGER,
        fjdaryBcuStatus FjdaryComponentStatus
    }

fjdaryBcuIndex OBJECT-TYPE
    SYNTAX INTEGER
    ACCESS read-only
    STATUS mandatory
    DESCRIPTION
        "The value of this object uniquely identifies this fjdaryBcu entry."
    ::= { fjdaryBcuEntry 1 }

fjdaryBcuItemId OBJECT-TYPE
    SYNTAX INTEGER
    ACCESS read-only
    STATUS mandatory
    DESCRIPTION
        "The value of this object indicates the identification number of this
         BCU."
    ::= { fjdaryBcuEntry 2 }

fjdaryBcuStatus OBJECT-TYPE
    SYNTAX FjdaryComponentStatus
    ACCESS read-only
    STATUS mandatory
    DESCRIPTION
        "The value of this object indicates the state of this BCU."
    ::= { fjdaryBcuEntry 3 }

-------------------------------------------------------------------------------
--   fjdaryBtu                                                               --
-------------------------------------------------------------------------------
fjdaryBtuCount OBJECT-TYPE
    SYNTAX INTEGER
    ACCESS read-only
    STATUS mandatory
    DESCRIPTION
        "The number of BTU(battery unit)'s informations (regardless of their
         current state) present on this system."
    ::= { fjdaryBtu 1 }

fjdaryBtuTable OBJECT-TYPE
    SYNTAX SEQUENCE OF FjdaryBtuEntry
    ACCESS not-accessible
    STATUS mandatory
    DESCRIPTION
        ""
    ::= { fjdaryBtu 2 }

fjdaryBtuEntry OBJECT-TYPE
    SYNTAX FjdaryBtuEntry
    ACCESS not-accessible
    STATUS mandatory
    DESCRIPTION
        ""
    INDEX { fjdaryBtuIndex }
    ::= { fjdaryBtuTable 1 }

FjdaryBtuEntry ::=
    SEQUENCE{
        fjdaryBtuIndex  INTEGER,
        fjdaryBtuItemId INTEGER,
        fjdaryBtuStatus FjdaryComponentStatus
    }

fjdaryBtuIndex OBJECT-TYPE
    SYNTAX INTEGER
    ACCESS read-only
    STATUS mandatory
    DESCRIPTION
        "The value of this object uniquely identifies this fjdaryBtu entry."
    ::= { fjdaryBtuEntry 1 }

fjdaryBtuItemId OBJECT-TYPE
    SYNTAX INTEGER
    ACCESS read-only
    STATUS mandatory
    DESCRIPTION
        "The value of this object indicates the identification number of this
         BTU."
    ::= { fjdaryBtuEntry 2 }

fjdaryBtuStatus OBJECT-TYPE
    SYNTAX FjdaryComponentStatus
    ACCESS read-only
    STATUS mandatory
    DESCRIPTION
        "The value of this object indicates the state of this BTU."
    ::= { fjdaryBtuEntry 3 }

-------------------------------------------------------------------------------
--   fjdaryCe                                                                --
-------------------------------------------------------------------------------
fjdaryCeCount OBJECT-TYPE
    SYNTAX INTEGER
    ACCESS read-only
    STATUS mandatory
    DESCRIPTION
        "The number of CE(controller enclosure)'s informations (regardless of
         their current state) present on this system."
    ::= { fjdaryCe 1 }

fjdaryCeTable OBJECT-TYPE
    SYNTAX SEQUENCE OF FjdaryCeEntry
    ACCESS not-accessible
    STATUS mandatory
    DESCRIPTION
        ""
    ::= { fjdaryCe 2 }

fjdaryCeEntry OBJECT-TYPE
    SYNTAX FjdaryCeEntry
    ACCESS not-accessible
    STATUS mandatory
    DESCRIPTION
        ""
    INDEX { fjdaryCeIndex }
    ::= { fjdaryCeTable 1 }

FjdaryCeEntry ::=
    SEQUENCE{
        fjdaryCeIndex  INTEGER,
        fjdaryCeItemId INTEGER,
        fjdaryCeStatus FjdaryComponentStatus
    }

fjdaryCeIndex OBJECT-TYPE
    SYNTAX INTEGER
    ACCESS read-only
    STATUS mandatory
    DESCRIPTION
        "The value of this object uniquely identifies this fjdaryCe entry."
    ::= { fjdaryCeEntry 1 }

fjdaryCeItemId OBJECT-TYPE
    SYNTAX INTEGER
    ACCESS read-only
    STATUS mandatory
    DESCRIPTION
        "The value of this object indicates the identification number of this
         CE."
    ::= { fjdaryCeEntry 2 }

fjdaryCeStatus OBJECT-TYPE
    SYNTAX FjdaryComponentStatus
    ACCESS read-only
    STATUS mandatory
    DESCRIPTION
        "The value of this object indicates the state of this CE."
    ::= { fjdaryCeEntry 3 }

-------------------------------------------------------------------------------
--   fjdaryCeinletthml                                                       --
-------------------------------------------------------------------------------
fjdaryCeinletthmlCount OBJECT-TYPE
    SYNTAX INTEGER
    ACCESS read-only
    STATUS mandatory
    DESCRIPTION
        "The number of CE inlet thermal sensor's informations (regardless of
         their current state) present on this system."
    ::= { fjdaryCeinletthml 1 }

fjdaryCeinletthmlTable OBJECT-TYPE
    SYNTAX SEQUENCE OF FjdaryCeinletthmlEntry
    ACCESS not-accessible
    STATUS mandatory
    DESCRIPTION
        ""
    ::= { fjdaryCeinletthml 2 }

fjdaryCeinletthmlEntry OBJECT-TYPE
    SYNTAX FjdaryCeinletthmlEntry
    ACCESS not-accessible
    STATUS mandatory
    DESCRIPTION
        ""
    INDEX { fjdaryCeinletthmlIndex }
    ::= { fjdaryCeinletthmlTable 1 }

FjdaryCeinletthmlEntry ::=
    SEQUENCE{
        fjdaryCeinletthmlIndex  INTEGER,
        fjdaryCeinletthmlItemId INTEGER,
        fjdaryCeinletthmlStatus FjdaryComponentStatus
    }

fjdaryCeinletthmlIndex OBJECT-TYPE
    SYNTAX INTEGER
    ACCESS read-only
    STATUS mandatory
    DESCRIPTION
        "The value of this object uniquely identifies this fjdaryCeinletthml
         entry."
    ::= { fjdaryCeinletthmlEntry 1 }

fjdaryCeinletthmlItemId OBJECT-TYPE
    SYNTAX INTEGER
    ACCESS read-only
    STATUS mandatory
    DESCRIPTION
        "The value of this object indicates the identification number of this
         CE inlet thermal sensor."
    ::= { fjdaryCeinletthmlEntry 2 }

fjdaryCeinletthmlStatus OBJECT-TYPE
    SYNTAX FjdaryComponentStatus
    ACCESS read-only
    STATUS mandatory
    DESCRIPTION
        "The value of this object indicates the state of this CE inlet thermal
         sensor."
    ::= { fjdaryCeinletthmlEntry 3 }

-------------------------------------------------------------------------------
--   fjdaryCethermal                                                         --
-------------------------------------------------------------------------------
fjdaryCethermalCount OBJECT-TYPE
    SYNTAX INTEGER
    ACCESS read-only
    STATUS mandatory
    DESCRIPTION
        "The number of CE thermal sensor's informations (regardless of their
         current state) present on this system."
    ::= { fjdaryCethermal 1 }

fjdaryCethermalTable OBJECT-TYPE
    SYNTAX SEQUENCE OF FjdaryCethermalEntry
    ACCESS not-accessible
    STATUS mandatory
    DESCRIPTION
        ""
    ::= { fjdaryCethermal 2 }

fjdaryCethermalEntry OBJECT-TYPE
    SYNTAX FjdaryCethermalEntry
    ACCESS not-accessible
    STATUS mandatory
    DESCRIPTION
        ""
    INDEX { fjdaryCethermalIndex }
    ::= { fjdaryCethermalTable 1 }

FjdaryCethermalEntry ::=
    SEQUENCE{
        fjdaryCethermalIndex  INTEGER,
        fjdaryCethermalItemId INTEGER,
        fjdaryCethermalStatus FjdaryComponentStatus
    }

fjdaryCethermalIndex OBJECT-TYPE
    SYNTAX INTEGER
    ACCESS read-only
    STATUS mandatory
    DESCRIPTION
        "The value of this object uniquely identifies this fjdaryCethermal
         entry."
    ::= { fjdaryCethermalEntry 1 }

fjdaryCethermalItemId OBJECT-TYPE
    SYNTAX INTEGER
    ACCESS read-only
    STATUS mandatory
    DESCRIPTION
        "The value of this object indicates the identification number of this
         CE thermal sensor."
    ::= { fjdaryCethermalEntry 2 }

fjdaryCethermalStatus OBJECT-TYPE
    SYNTAX FjdaryComponentStatus
    ACCESS read-only
    STATUS mandatory
    DESCRIPTION
        "The value of this object indicates the state of this CE thermal
         sensor."
    ::= { fjdaryCethermalEntry 3 }

-------------------------------------------------------------------------------
--   fjdaryCpsu                                                              --
-------------------------------------------------------------------------------
fjdaryCpsuCount OBJECT-TYPE
    SYNTAX INTEGER
    ACCESS read-only
    STATUS mandatory
    DESCRIPTION
        "The number of CPSU(CE power supply unit)'s informations (regardless of
         their current state) present on this system."
    ::= { fjdaryCpsu 1 }

fjdaryCpsuTable OBJECT-TYPE
    SYNTAX SEQUENCE OF FjdaryCpsuEntry
    ACCESS not-accessible
    STATUS mandatory
    DESCRIPTION
        ""
    ::= { fjdaryCpsu 2 }

fjdaryCpsuEntry OBJECT-TYPE
    SYNTAX FjdaryCpsuEntry
    ACCESS not-accessible
    STATUS mandatory
    DESCRIPTION
        ""
    INDEX { fjdaryCpsuIndex }
    ::= { fjdaryCpsuTable 1 }

FjdaryCpsuEntry ::=
    SEQUENCE{
        fjdaryCpsuIndex  INTEGER,
        fjdaryCpsuItemId INTEGER,
        fjdaryCpsuStatus FjdaryComponentStatus
    }

fjdaryCpsuIndex OBJECT-TYPE
    SYNTAX INTEGER
    ACCESS read-only
    STATUS mandatory
    DESCRIPTION
        "The value of this object uniquely identifies this fjdaryCpsu entry."
    ::= { fjdaryCpsuEntry 1 }

fjdaryCpsuItemId OBJECT-TYPE
    SYNTAX INTEGER
    ACCESS read-only
    STATUS mandatory
    DESCRIPTION
        "The value of this object indicates the identification number of this
         CPSU."
    ::= { fjdaryCpsuEntry 2 }

fjdaryCpsuStatus OBJECT-TYPE
    SYNTAX FjdaryComponentStatus
    ACCESS read-only
    STATUS mandatory
    DESCRIPTION
        "The value of this object indicates the state of this CPSU."
    ::= { fjdaryCpsuEntry 3 }

-------------------------------------------------------------------------------
--   fjdarySccb                                                              --
-------------------------------------------------------------------------------
fjdarySccbCount OBJECT-TYPE
    SYNTAX INTEGER
    ACCESS read-only
    STATUS mandatory
    DESCRIPTION
        "The number of SCCB's informations (regardless of their current state)
         present on this system."
    ::= { fjdarySccb 1 }

fjdarySccbTable OBJECT-TYPE
    SYNTAX SEQUENCE OF FjdarySccbEntry
    ACCESS not-accessible
    STATUS mandatory
    DESCRIPTION
        ""
    ::= { fjdarySccb 2 }

fjdarySccbEntry OBJECT-TYPE
    SYNTAX FjdarySccbEntry
    ACCESS not-accessible
    STATUS mandatory
    DESCRIPTION
        ""
    INDEX { fjdarySccbIndex }
    ::= { fjdarySccbTable 1 }

FjdarySccbEntry ::=
    SEQUENCE{
        fjdarySccbIndex  INTEGER,
        fjdarySccbItemId INTEGER,
        fjdarySccbStatus FjdaryComponentStatus
    }

fjdarySccbIndex OBJECT-TYPE
    SYNTAX INTEGER
    ACCESS read-only
    STATUS mandatory
    DESCRIPTION
        "The value of this object uniquely identifies this fjdarySccb entry."
    ::= { fjdarySccbEntry 1 }

fjdarySccbItemId OBJECT-TYPE
    SYNTAX INTEGER
    ACCESS read-only
    STATUS mandatory
    DESCRIPTION
        "The value of this object indicates the identification number of this
         SCCB."
    ::= { fjdarySccbEntry 2 }

fjdarySccbStatus OBJECT-TYPE
    SYNTAX FjdaryComponentStatus
    ACCESS read-only
    STATUS mandatory
    DESCRIPTION
        "The value of this object indicates the state of this SCCB."
    ::= { fjdarySccbEntry 3 }

-------------------------------------------------------------------------------
--   fjdaryDe                                                                --
-------------------------------------------------------------------------------
fjdaryDeCount OBJECT-TYPE
    SYNTAX INTEGER
    ACCESS read-only
    STATUS mandatory
    DESCRIPTION
        "The number of DE(device enclosure)'s informations (regardless of their
         current state) present on this system."
    ::= { fjdaryDe 1 }

fjdaryDeTable OBJECT-TYPE
    SYNTAX SEQUENCE OF FjdaryDeEntry
    ACCESS not-accessible
    STATUS mandatory
    DESCRIPTION
        ""
    ::= { fjdaryDe 2 }

fjdaryDeEntry OBJECT-TYPE
    SYNTAX FjdaryDeEntry
    ACCESS not-accessible
    STATUS mandatory
    DESCRIPTION
        ""
    INDEX { fjdaryDeIndex }
    ::= { fjdaryDeTable 1 }

FjdaryDeEntry ::=
    SEQUENCE{
        fjdaryDeIndex  INTEGER,
        fjdaryDeItemId INTEGER,
        fjdaryDeStatus FjdaryComponentStatus,
        fjdaryDeId     INTEGER,
        fjdaryDeType   INTEGER
    }

fjdaryDeIndex OBJECT-TYPE
    SYNTAX INTEGER
    ACCESS read-only
    STATUS mandatory
    DESCRIPTION
        "The value of this object uniquely identifies this fjdaryDe entry."
    ::= { fjdaryDeEntry 1 }

fjdaryDeItemId OBJECT-TYPE
    SYNTAX INTEGER
    ACCESS read-only
    STATUS mandatory
    DESCRIPTION
        "The value of this object indicates the identification number of this
         DE."
    ::= { fjdaryDeEntry 2 }

fjdaryDeStatus OBJECT-TYPE
    SYNTAX FjdaryComponentStatus
    ACCESS read-only
    STATUS mandatory
    DESCRIPTION
        "The value of this object indicates the state of this DE."
    ::= { fjdaryDeEntry 3 }

fjdaryDeId OBJECT-TYPE
    SYNTAX INTEGER
    ACCESS read-only
    STATUS mandatory
    DESCRIPTION
        "The value of this object indicates the identification of this DE."
    ::= { fjdaryDeEntry 4 }

fjdaryDeType OBJECT-TYPE
    SYNTAX INTEGER
    ACCESS read-only
    STATUS mandatory
    DESCRIPTION
        "The value of this object indicates the type of this DE."
    ::= { fjdaryDeEntry 5 }

-------------------------------------------------------------------------------
--   fjdaryPbc                                                               --
-------------------------------------------------------------------------------
fjdaryPbcCount OBJECT-TYPE
    SYNTAX INTEGER
    ACCESS read-only
    STATUS mandatory
    DESCRIPTION
        "The number of PBC(port bypass circuit)'s informations (regardless of
         their current state) present on this system."
    ::= { fjdaryPbc 1 }

fjdaryPbcTable OBJECT-TYPE
    SYNTAX SEQUENCE OF FjdaryPbcEntry
    ACCESS not-accessible
    STATUS mandatory
    DESCRIPTION
        ""
    ::= { fjdaryPbc 2 }

fjdaryPbcEntry OBJECT-TYPE
    SYNTAX FjdaryPbcEntry
    ACCESS not-accessible
    STATUS mandatory
    DESCRIPTION
        ""
    INDEX { fjdaryPbcIndex }
    ::= { fjdaryPbcTable 1 }

FjdaryPbcEntry ::=
    SEQUENCE{
        fjdaryPbcIndex     INTEGER,
        fjdaryPbcItemId    INTEGER,
        fjdaryPbcStatus    FjdaryComponentStatus,
        fjdaryPbcType      INTEGER,
        fjdaryPbcFirmTable OCTET STRING,
        fjdaryPbcDeiStatus INTEGER,
        fjdaryPbcFcStatus0 INTEGER,
        fjdaryPbcFcStatus1 INTEGER
    }

fjdaryPbcIndex OBJECT-TYPE
    SYNTAX INTEGER
    ACCESS read-only
    STATUS mandatory
    DESCRIPTION
        "The value of this object uniquely identifies this fjdaryPbc entry."
    ::= { fjdaryPbcEntry 1 }

fjdaryPbcItemId OBJECT-TYPE
    SYNTAX INTEGER
    ACCESS read-only
    STATUS mandatory
    DESCRIPTION
        "The value of this object indicates the identification number of this
         PBC."
    ::= { fjdaryPbcEntry 2 }

fjdaryPbcStatus OBJECT-TYPE
    SYNTAX FjdaryComponentStatus
    ACCESS read-only
    STATUS mandatory
    DESCRIPTION
        "The value of this object indicates the state of this PBC."
    ::= { fjdaryPbcEntry 3 }

fjdaryPbcType OBJECT-TYPE
    SYNTAX INTEGER
    ACCESS read-only
    STATUS mandatory
    DESCRIPTION
        "The value of this object indicates the type of this PBC."
    ::= { fjdaryPbcEntry 4 }

fjdaryPbcFirmTable OBJECT-TYPE
    SYNTAX OCTET STRING
    ACCESS read-only
    STATUS mandatory
    DESCRIPTION
        "The value of this object indicates the firmware information of this
         PBC."
    ::= { fjdaryPbcEntry 5 }

fjdaryPbcDeiStatus OBJECT-TYPE
    SYNTAX INTEGER
    ACCESS read-only
    STATUS mandatory
    DESCRIPTION
        "The value of this object indicates the DEI cable state of this PBC."
    ::= { fjdaryPbcEntry 6 }

fjdaryPbcFcStatus0 OBJECT-TYPE
    SYNTAX INTEGER
    ACCESS read-only
    STATUS mandatory
    DESCRIPTION
        "The value of this object indicates the FC cable state of this PBC."
    ::= { fjdaryPbcEntry 7 }

fjdaryPbcFcStatus1 OBJECT-TYPE
    SYNTAX INTEGER
    ACCESS read-only
    STATUS mandatory
    DESCRIPTION
        "The value of this object indicates the FC cable state of this PBC."
    ::= { fjdaryPbcEntry 8 }

-------------------------------------------------------------------------------
--   fjdaryDpsu                                                              --
-------------------------------------------------------------------------------
fjdaryDpsuCount OBJECT-TYPE
    SYNTAX INTEGER
    ACCESS read-only
    STATUS mandatory
    DESCRIPTION
        "The number of DPSU(DE power supply unit)'s informations (regardless of
         their current state) present on this system."
    ::= { fjdaryDpsu 1 }

fjdaryDpsuTable OBJECT-TYPE
    SYNTAX SEQUENCE OF FjdaryDpsuEntry
    ACCESS not-accessible
    STATUS mandatory
    DESCRIPTION
        ""
    ::= { fjdaryDpsu 2 }

fjdaryDpsuEntry OBJECT-TYPE
    SYNTAX FjdaryDpsuEntry
    ACCESS not-accessible
    STATUS mandatory
    DESCRIPTION
        ""
    INDEX { fjdaryDpsuIndex }
    ::= { fjdaryDpsuTable 1 }

FjdaryDpsuEntry ::=
    SEQUENCE{
        fjdaryDpsuIndex  INTEGER,
        fjdaryDpsuItemId INTEGER,
        fjdaryDpsuStatus FjdaryComponentStatus
    }

fjdaryDpsuIndex OBJECT-TYPE
    SYNTAX INTEGER
    ACCESS read-only
    STATUS mandatory
    DESCRIPTION
        "The value of this object uniquely identifies this fjdaryDpsu entry."
    ::= { fjdaryDpsuEntry 1 }

fjdaryDpsuItemId OBJECT-TYPE
    SYNTAX INTEGER
    ACCESS read-only
    STATUS mandatory
    DESCRIPTION
        "The value of this object indicates the identification number of this
         DPSU."
    ::= { fjdaryDpsuEntry 2 }

fjdaryDpsuStatus OBJECT-TYPE
    SYNTAX FjdaryComponentStatus
    ACCESS read-only
    STATUS mandatory
    DESCRIPTION
        "The value of this object indicates the state of this DPSU."
    ::= { fjdaryDpsuEntry 3 }

-------------------------------------------------------------------------------
--   fjdaryDefan                                                             --
-------------------------------------------------------------------------------
fjdaryDefanCount OBJECT-TYPE
    SYNTAX INTEGER
    ACCESS read-only
    STATUS mandatory
    DESCRIPTION
        "The number of DE FAN's informations (regardless of their current
         state) present on this system."
    ::= { fjdaryDefan 1 }

fjdaryDefanTable OBJECT-TYPE
    SYNTAX SEQUENCE OF FjdaryDefanEntry
    ACCESS not-accessible
    STATUS mandatory
    DESCRIPTION
        ""
    ::= { fjdaryDefan 2 }

fjdaryDefanEntry OBJECT-TYPE
    SYNTAX FjdaryDefanEntry
    ACCESS not-accessible
    STATUS mandatory
    DESCRIPTION
        ""
    INDEX { fjdaryDefanIndex }
    ::= { fjdaryDefanTable 1 }

FjdaryDefanEntry ::=
    SEQUENCE{
        fjdaryDefanIndex  INTEGER,
        fjdaryDefanItemId INTEGER,
        fjdaryDefanStatus FjdaryComponentStatus
    }

fjdaryDefanIndex OBJECT-TYPE
    SYNTAX INTEGER
    ACCESS read-only
    STATUS mandatory
    DESCRIPTION
        "The value of this object uniquely identifies this fjdaryDefan entry."
    ::= { fjdaryDefanEntry 1 }

fjdaryDefanItemId OBJECT-TYPE
    SYNTAX INTEGER
    ACCESS read-only
    STATUS mandatory
    DESCRIPTION
        "The value of this object indicates the identification number of this
         DE FAN."
    ::= { fjdaryDefanEntry 2 }

fjdaryDefanStatus OBJECT-TYPE
    SYNTAX FjdaryComponentStatus
    ACCESS read-only
    STATUS mandatory
    DESCRIPTION
        "The value of this object indicates the state of this DE FAN."
    ::= { fjdaryDefanEntry 3 }

-------------------------------------------------------------------------------
--   fjdaryDeinletthml                                                       --
-------------------------------------------------------------------------------
fjdaryDeinletthmlCount OBJECT-TYPE
    SYNTAX INTEGER
    ACCESS read-only
    STATUS mandatory
    DESCRIPTION
        "The number of DE inlet thermal sensor's informations (regardless of
         their current state) present on this system."
    ::= { fjdaryDeinletthml 1 }

fjdaryDeinletthmlTable OBJECT-TYPE
    SYNTAX SEQUENCE OF FjdaryDeinletthmlEntry
    ACCESS not-accessible
    STATUS mandatory
    DESCRIPTION
        ""
    ::= { fjdaryDeinletthml 2 }

fjdaryDeinletthmlEntry OBJECT-TYPE
    SYNTAX FjdaryDeinletthmlEntry
    ACCESS not-accessible
    STATUS mandatory
    DESCRIPTION
        ""
    INDEX { fjdaryDeinletthmlIndex }
    ::= { fjdaryDeinletthmlTable 1 }

FjdaryDeinletthmlEntry ::=
    SEQUENCE{
        fjdaryDeinletthmlIndex  INTEGER,
        fjdaryDeinletthmlItemId INTEGER,
        fjdaryDeinletthmlStatus FjdaryComponentStatus
    }

fjdaryDeinletthmlIndex OBJECT-TYPE
    SYNTAX INTEGER
    ACCESS read-only
    STATUS mandatory
    DESCRIPTION
        "The value of this object uniquely identifies this fjdaryDeinletthml
         entry."
    ::= { fjdaryDeinletthmlEntry 1 }

fjdaryDeinletthmlItemId OBJECT-TYPE
    SYNTAX INTEGER
    ACCESS read-only
    STATUS mandatory
    DESCRIPTION
        "The value of this object indicates the identification number of this
         DE inlet thermal sensor."
    ::= { fjdaryDeinletthmlEntry 2 }

fjdaryDeinletthmlStatus OBJECT-TYPE
    SYNTAX FjdaryComponentStatus
    ACCESS read-only
    STATUS mandatory
    DESCRIPTION
        "The value of this object indicates the state of this DE inlet thermal
         sensor."
    ::= { fjdaryDeinletthmlEntry 3 }

-------------------------------------------------------------------------------
--   fjdaryDethermal                                                         --
-------------------------------------------------------------------------------
fjdaryDethermalCount OBJECT-TYPE
    SYNTAX INTEGER
    ACCESS read-only
    STATUS mandatory
    DESCRIPTION
        "The number of DE thermal sensor's informations (regardless of their
         current state) present on this system."
    ::= { fjdaryDethermal 1 }

fjdaryDethermalTable OBJECT-TYPE
    SYNTAX SEQUENCE OF FjdaryDethermalEntry
    ACCESS not-accessible
    STATUS mandatory
    DESCRIPTION
        ""
    ::= { fjdaryDethermal 2 }

fjdaryDethermalEntry OBJECT-TYPE
    SYNTAX FjdaryDethermalEntry
    ACCESS not-accessible
    STATUS mandatory
    DESCRIPTION
        ""
    INDEX { fjdaryDethermalIndex }
    ::= { fjdaryDethermalTable 1 }

FjdaryDethermalEntry ::=
    SEQUENCE{
        fjdaryDethermalIndex  INTEGER,
        fjdaryDethermalItemId INTEGER,
        fjdaryDethermalStatus FjdaryComponentStatus
    }

fjdaryDethermalIndex OBJECT-TYPE
    SYNTAX INTEGER
    ACCESS read-only
    STATUS mandatory
    DESCRIPTION
        "The value of this object uniquely identifies this fjdaryDethermal
         entry."
    ::= { fjdaryDethermalEntry 1 }

fjdaryDethermalItemId OBJECT-TYPE
    SYNTAX INTEGER
    ACCESS read-only
    STATUS mandatory
    DESCRIPTION
        "The value of this object indicates the identification number of this
         DE thermal sensor."
    ::= { fjdaryDethermalEntry 2 }

fjdaryDethermalStatus OBJECT-TYPE
    SYNTAX FjdaryComponentStatus
    ACCESS read-only
    STATUS mandatory
    DESCRIPTION
        "The value of this object indicates the state of this DE thermal
         sensor."
    ::= { fjdaryDethermalEntry 3 }

-------------------------------------------------------------------------------
--   fjdaryDisk                                                              --
-------------------------------------------------------------------------------
fjdaryDiskCount OBJECT-TYPE
    SYNTAX INTEGER
    ACCESS read-only
    STATUS mandatory
    DESCRIPTION
        "The number of DISK's informations (regardless of their current state)
         present on this system."
    ::= { fjdaryDisk 1 }

fjdaryDiskTable OBJECT-TYPE
    SYNTAX SEQUENCE OF FjdaryDiskEntry
    ACCESS not-accessible
    STATUS mandatory
    DESCRIPTION
        ""
    ::= { fjdaryDisk 2 }

fjdaryDiskEntry OBJECT-TYPE
    SYNTAX FjdaryDiskEntry
    ACCESS not-accessible
    STATUS mandatory
    DESCRIPTION
        ""
    INDEX { fjdaryDiskIndex }
    ::= { fjdaryDiskTable 1 }

FjdaryDiskEntry ::=
    SEQUENCE{
        fjdaryDiskIndex     INTEGER,
        fjdaryDiskItemId    INTEGER,
        fjdaryDiskStatus    INTEGER,
        fjdaryDiskPlun      INTEGER,
        fjdaryDiskPurpose   INTEGER,
        fjdaryDiskType      INTEGER,
        fjdaryDiskWwn       OCTET STRING,
        fjdaryDiskVenderId  OCTET STRING,
        fjdaryDiskProductId OCTET STRING,
        fjdaryDiskRevision  OCTET STRING
    }

fjdaryDiskIndex OBJECT-TYPE
    SYNTAX INTEGER
    ACCESS read-only
    STATUS mandatory
    DESCRIPTION
        "The value of this object uniquely identifies this fjdaryDisk entry."
    ::= { fjdaryDiskEntry 1 }

fjdaryDiskItemId OBJECT-TYPE
    SYNTAX INTEGER
    ACCESS read-only
    STATUS mandatory
    DESCRIPTION
        "The value of this object indicates the identification number of this
         DISK."
    ::= { fjdaryDiskEntry 2 }

fjdaryDiskStatus OBJECT-TYPE
    SYNTAX INTEGER{
        available(1),
        broken(2),
        notavailable(3),
        notsupported(4),
        present(5),
        readying(6),
        recovering(7),
        partbroken(64),
        spare(65),
        formatting(66),
        unformatted(67),
        notexist(68),
        copying(69)
    }
    ACCESS read-only
    STATUS mandatory
    DESCRIPTION
        "The value of this object indicates the state of this DISK.

         available    : Normal state
         broken       : Abnormal state
                        (The data can not be guaranteed)
         notavailable : Not available state
                        (Because the RAID group is not set)
         notsupported : Unsupported error state
         present      : Undefined volume set state
         readying     : Data readying state
         recovering   : Data recovering state
         partbroken   : Abnormal state
         spare        : Using spare disk state
         formatting   : Data formatting state
         unformatted  : Unformatted state
         notexist     : Not exist
         copying      : Data copying state"
    ::= { fjdaryDiskEntry 3 }

fjdaryDiskPlun OBJECT-TYPE
    SYNTAX INTEGER
    ACCESS read-only
    STATUS mandatory
    DESCRIPTION
        "The value of this object indicates the PLUN of this DISK."
    ::= { fjdaryDiskEntry 4 }

fjdaryDiskPurpose OBJECT-TYPE
    SYNTAX INTEGER
    ACCESS read-only
    STATUS mandatory
    DESCRIPTION
        "The value of this object indicates the purpose of this DISK."
    ::= { fjdaryDiskEntry 5 }

fjdaryDiskType OBJECT-TYPE
    SYNTAX INTEGER
    ACCESS read-only
    STATUS mandatory
    DESCRIPTION
        "The value of this object indicates the type of this DISK."
    ::= { fjdaryDiskEntry 6 }

fjdaryDiskWwn OBJECT-TYPE
    SYNTAX OCTET STRING
    ACCESS read-only
    STATUS mandatory
    DESCRIPTION
        "The value of this object indicates the world wide name of this DISK."
    ::= { fjdaryDiskEntry 7 }

fjdaryDiskVenderId OBJECT-TYPE
    SYNTAX OCTET STRING
    ACCESS read-only
    STATUS mandatory
    DESCRIPTION
        "The value of this object indicates the vender of this DISK."
    ::= { fjdaryDiskEntry 8 }

fjdaryDiskProductId OBJECT-TYPE
    SYNTAX OCTET STRING
    ACCESS read-only
    STATUS mandatory
    DESCRIPTION
        "The value of this object indicates the product of this DISK."
    ::= { fjdaryDiskEntry 9 }

fjdaryDiskRevision OBJECT-TYPE
    SYNTAX OCTET STRING
    ACCESS read-only
    STATUS mandatory
    DESCRIPTION
        "The value of this object indicates the revision of this DISK."
    ::= { fjdaryDiskEntry 10 }

-------------------------------------------------------------------------------
--   fjdaryLanport                                                           --
-------------------------------------------------------------------------------
fjdaryLanportCount OBJECT-TYPE
    SYNTAX INTEGER
    ACCESS read-only
    STATUS mandatory
    DESCRIPTION
        "The number of LAN port's informations (regardless of theier current
         state) present on this system."
    ::= { fjdaryLanport 1 }

fjdaryLanportTable OBJECT-TYPE
    SYNTAX SEQUENCE OF FjdaryLanportEntry
    ACCESS not-accessible
    STATUS mandatory
    DESCRIPTION
        ""
    ::= { fjdaryLanport 2 }

fjdaryLanportEntry OBJECT-TYPE
    SYNTAX FjdaryLanportEntry
    ACCESS not-accessible
    STATUS mandatory
    DESCRIPTION
        ""
    INDEX { fjdaryLanportIndex }
    ::= { fjdaryLanportTable 1 }

FjdaryLanportEntry ::=
    SEQUENCE{
        fjdaryLanportIndex   INTEGER,
        fjdaryLanportStatus0 INTEGER,
        fjdaryLanportStatus1 INTEGER,
        fjdaryLanportStatus2 INTEGER
    }

fjdaryLanportIndex OBJECT-TYPE
    SYNTAX INTEGER
    ACCESS read-only
    STATUS mandatory
    DESCRIPTION
        "The value of this object uniquely identifies this fjdaryLanport
         entry."
    ::= { fjdaryLanportEntry 1 }

fjdaryLanportStatus0 OBJECT-TYPE
    SYNTAX INTEGER{
        linkup(1),
        undefined(4),
        linkdown(6),
        unknown(7)
    }
    ACCESS read-only
    STATUS mandatory
    DESCRIPTION
        "The value of this object indicates the MNT port state.

         linkup      : Link up state
         undefined   : Undefined state
         linkdown    : Link down state
         unknown     : Unknown state"
    ::= { fjdaryLanportEntry 2 }

fjdaryLanportStatus1 OBJECT-TYPE
    SYNTAX INTEGER{
        linkup(1),
        undefined(4),
        linkdown(6),
        unknown(7)
    }
    ACCESS read-only
    STATUS mandatory
    DESCRIPTION
        "The value of this object indicates the RMT port state.

         linkup      : Link up state
         undefined   : Undefined state
         linkdown    : Link down state
         unknown     : Unknown state"
    ::= { fjdaryLanportEntry 3 }

fjdaryLanportStatus2 OBJECT-TYPE
    SYNTAX INTEGER{
        linkup(1),
        undefined(4),
        linkdown(6),
        unknown(7)
    }
    ACCESS read-only
    STATUS mandatory
    DESCRIPTION
        "The value of this object indicates the FST port state.

         linkup      : Link up state
         undefined   : Undefined state
         linkdown    : Link down state
         unknown     : Unknown state"
    ::= { fjdaryLanportEntry 4 }

--***************************************************************************--
--   Logical Configuration                                                   --
--***************************************************************************--
-------------------------------------------------------------------------------
--   fjdaryCaPort                                                            --
-------------------------------------------------------------------------------
fjdaryCaPortCount OBJECT-TYPE
    SYNTAX INTEGER
    ACCESS read-only
    STATUS mandatory
    DESCRIPTION
        "The number of CA port's informations (regardless of their current
         state) present on this system."
    ::= { fjdaryCaPort 1 }

fjdaryCaPortTable OBJECT-TYPE
    SYNTAX SEQUENCE OF FjdaryCaPortEntry
    ACCESS not-accessible
    STATUS mandatory
    DESCRIPTION
        ""
    ::= { fjdaryCaPort 2 }

fjdaryCaPortEntry OBJECT-TYPE
    SYNTAX FjdaryCaPortEntry
    ACCESS not-accessible
    STATUS mandatory
    DESCRIPTION
        ""
    INDEX { fjdaryCaPortIndex }
    ::= { fjdaryCaPortTable 1 }

FjdaryCaPortEntry ::=
    SEQUENCE{
        fjdaryCaPortIndex           INTEGER,
        fjdaryCaPortPortInfo        OCTET STRING,
        fjdaryCaPortiscsiInfo       OCTET STRING,
        fjdaryCaPortiscsiName       OCTET STRING,
        fjdaryCaPortiscsiAliasName  OCTET STRING,
        fjdaryCaPortiscsiIpAddress  IpAddress,
        fjdaryCaPortiscsiSubnetMask IpAddress,
        fjdaryCaPortiscsiIsnsServer IpAddress,
        fjdaryCaPortCuImage         OCTET STRING
    }

fjdaryCaPortIndex OBJECT-TYPE
    SYNTAX INTEGER
    ACCESS read-only
    STATUS mandatory
    DESCRIPTION
        "The value of this object uniquely identifies this fjdaryCaPort entry."
    ::= { fjdaryCaPortEntry 1 }

fjdaryCaPortPortInfo OBJECT-TYPE
    SYNTAX OCTET STRING
    ACCESS read-only
    STATUS mandatory
    DESCRIPTION
        "The value of this object indicates the port informatiom of this CA
         port.
                  byte 0       byte 1       byte 2       byte 3
              +------------+------------+------------+------------+
          0x00| Reserved                | Factor     | Port Number|
              +------------+------------+------------+------------+
          0x04| Map Number | Security   | Host       | Method     |
              |            |  Mode      |  Connection|            |
              +------------+------------+------------+------------+
          0x08| LoopID     | Rate       | Class      | SFP Type   |
              +------------+------------+------------+------------+
          0x0c| RA Mode    | XSP        | RA Group ID| CM CPU MID |
              |            |  Connection|            |            |
              +------------+------------+------------+------------+
          0x10| FC Frame Size           | MTU Size                |
              +------------+------------+------------+------------+
          0x14| Reserved                                          |
              +------------+------------+------------+------------+
          0x18| WWN (Port Name)                                   |
              +                                                   +
          0x1c|                                                   |
              +------------+------------+------------+------------+"
    ::= { fjdaryCaPortEntry 2 }

fjdaryCaPortiscsiInfo OBJECT-TYPE
    SYNTAX OCTET STRING
    ACCESS read-only
    STATUS mandatory
    DESCRIPTION
        "The value of this object indicates an iscsi informatiom table of this
         CA port.
                  byte 0      byte 1      byte 2      byte 3
              +-----------+-----------+-----------+-----------+
          0x00| Reserved                                      |
              +-----------+-----------+-----------+-----------+
          0x04| Reserved              | iSCSI Flag            |
              +-----------+-----------+-----------+-----------+
          0x08| Reserved              | Name Valid| Reserved  |
              +-----------+-----------+-----------+-----------+
          0x0c| Reserved                                      |
              +-----------+-----------+-----------+-----------+"
    ::= { fjdaryCaPortEntry 3 }

fjdaryCaPortiscsiName OBJECT-TYPE
    SYNTAX OCTET STRING
    ACCESS read-only
    STATUS mandatory
    DESCRIPTION
        "The value of this object indicates an iscsi name of this CA port."
    ::= { fjdaryCaPortEntry 4 }

fjdaryCaPortiscsiAliasName OBJECT-TYPE
    SYNTAX OCTET STRING
    ACCESS read-only
    STATUS mandatory
    DESCRIPTION
        "The value of this object indicates an iscsi alias name of this CA
         port."
    ::= { fjdaryCaPortEntry 5 }

fjdaryCaPortiscsiIpAddress OBJECT-TYPE
    SYNTAX IpAddress
    ACCESS read-only
    STATUS mandatory
    DESCRIPTION
        "The value of this object indicates an iscsi ip address of this CA
         port."
    ::= { fjdaryCaPortEntry 6 }

fjdaryCaPortiscsiSubnetMask OBJECT-TYPE
    SYNTAX IpAddress
    ACCESS read-only
    STATUS mandatory
    DESCRIPTION
        "The value of this object indicates an iscsi subnet mask of this CA
         port."
    ::= { fjdaryCaPortEntry 7 }

fjdaryCaPortiscsiIsnsServer OBJECT-TYPE
    SYNTAX IpAddress
    ACCESS read-only
    STATUS mandatory
    DESCRIPTION
        "The value of this object indicates an isns server ip address of this
         CA port."
    ::= { fjdaryCaPortEntry 8 }

fjdaryCaPortCuImage OBJECT-TYPE
    SYNTAX OCTET STRING
    ACCESS read-only
    STATUS mandatory
    DESCRIPTION
        "The value of this object indicates a cu image informatiom table of
         this CA port.
                  byte 0      byte 1      byte 2      byte 3
              +-----------+-----------+-----------+-----------+
          0x00| LCUN 00   | LCUN 01   | LCUN 02   | LCUN 03   |
              +-----------+-----------+-----------+-----------+
          0x04| LCUN 04   | LCUN 05   | LCUN 06   | LCUN 07   |
              +-----------+-----------+-----------+-----------+
          0x08| LCUN 08   | LCUN 09   | LCUN 0A   | LCUN 0B   |
              +-----------+-----------+-----------+-----------+
          0x0c| LCUN 0C   | LCUN 0D   | LCUN 0E   | LCUN 0F   |
              +-----------+-----------+-----------+-----------+"
    ::= { fjdaryCaPortEntry 9 }

-------------------------------------------------------------------------------
--   fjdaryOlu                                                               --
-------------------------------------------------------------------------------
fjdaryOluCount OBJECT-TYPE
    SYNTAX INTEGER
    ACCESS read-only
    STATUS mandatory
    DESCRIPTION
        "The number of OLU's informations entry (regardless of their current
         state) present on this system."
    ::= { fjdaryOlu 1 }

fjdaryOluTable OBJECT-TYPE
    SYNTAX SEQUENCE OF FjdaryOluEntry
    ACCESS not-accessible
    STATUS mandatory
    DESCRIPTION
        ""
    ::= { fjdaryOlu 2 }

fjdaryOluEntry OBJECT-TYPE
    SYNTAX FjdaryOluEntry
    ACCESS not-accessible
    STATUS mandatory
    DESCRIPTION
        ""
    INDEX { fjdaryOluIndex }
    ::= { fjdaryOluTable 1 }

FjdaryOluEntry ::=
    SEQUENCE{
        fjdaryOluIndex     INTEGER,
        fjdaryOluInfoTable OCTET STRING
    }

fjdaryOluIndex OBJECT-TYPE
    SYNTAX INTEGER
    ACCESS read-only
    STATUS mandatory
    DESCRIPTION
        "The value of this object uniquely identifies this fjdaryOlu entry."
    ::= { fjdaryOluEntry 1 }

fjdaryOluInfoTable OBJECT-TYPE
    SYNTAX OCTET STRING
    ACCESS read-only
    STATUS mandatory
    DESCRIPTION
        "The value of this object indicates the OLU information of this system.
                  byte 0       byte 1       byte 2       byte 3
              +------------+------------+------------+------------+
          0x00| OLU#index*4 information (48 bytes)                |
              +------------+------------+------------+------------+
          0x30| OLU#index*4+1 information (48 bytes)              |
              +------------+------------+------------+------------+
          0x60| OLU#index*4+2 information (48 bytes)              |
              +------------+------------+------------+------------+
          0x90| OLU#index*4+3 information (48 bytes)              |
              +------------+------------+------------+------------+
         OLU informateion:
                  byte 0       byte 1       byte 2       byte 3
              +------------+------------+------------+------------+
          0x00| OLUN                    | Status                  |
              +------------+------------+------------+------------+
          0x04| SLU count  | Reserved                             |
              +------------+------------+------------+------------+
          0x08| SLUN 00                 | SLUN 01                 |
              +------------+------------+------------+------------+
              ~                                                   ~
              +------------+------------+------------+------------+
          0x24| SLUN 0E                 | SLUN 0F                 |
              +------------+------------+------------+------------+
          0x28| Reserved                                          |
              +------------+------------+------------+------------+
          0x2c| Reserved                                          |
              +------------+------------+------------+------------+"
    ::= { fjdaryOluEntry 2 }

-------------------------------------------------------------------------------
--   fjdaryMlu                                                               --
-------------------------------------------------------------------------------
fjdaryMluCount OBJECT-TYPE
    SYNTAX INTEGER
    ACCESS read-only
    STATUS mandatory
    DESCRIPTION
        "The number of MLU's informations entry (regardless of their current
         state) present on this system."
    ::= { fjdaryMlu 1 }

fjdaryMluTable OBJECT-TYPE
    SYNTAX SEQUENCE OF FjdaryMluEntry
    ACCESS not-accessible
    STATUS mandatory
    DESCRIPTION
        ""
    ::= { fjdaryMlu 2 }

fjdaryMluEntry OBJECT-TYPE
    SYNTAX FjdaryMluEntry
    ACCESS not-accessible
    STATUS mandatory
    DESCRIPTION
        ""
    INDEX { fjdaryMluIndex }
    ::= { fjdaryMluTable 1 }

FjdaryMluEntry ::=
    SEQUENCE{
        fjdaryMluIndex     INTEGER,
        fjdaryMluInfoTable OCTET STRING
    }

fjdaryMluIndex OBJECT-TYPE
    SYNTAX INTEGER
    ACCESS read-only
    STATUS mandatory
    DESCRIPTION
        "The value of this object uniquely identifies this fjdaryMlu entry."
    ::= { fjdaryMluEntry 1 }

fjdaryMluInfoTable OBJECT-TYPE
    SYNTAX OCTET STRING
    ACCESS read-only
    STATUS mandatory
    DESCRIPTION
        "The value of this object indicates the MLU information of this system.
                  byte 0       byte 1       byte 2       byte 3
              +------------+------------+------------+------------+
          0x00| MLU#index*16 information (16 bytes)               |
              +------------+------------+------------+------------+
          0x10| MLU#index*16+1 information (16 bytes)             |
              +------------+------------+------------+------------+
              ~                                                   ~
              +------------+------------+------------+------------+
          0xf0| MLU#index*16+15 information (16 bytes)            |
              +------------+------------+------------+------------+
         MLU information:
                  byte 0       byte 1       byte 2       byte 3
              +------------+------------+------------+------------+
          0x00| MLUN                    | Status                  |
              +------------+------------+------------+------------+
          0x04| Type Index | MLU Mode   | Reserved                |
              +------------+------------+------------+------------+
          0x08| SLUN                    | LCU No     | Reserved   |
              +------------+------------+------------+------------+
          0x0c| User Cylinder Count     | Reserved                |
              +------------+------------+------------+------------+"
    ::= { fjdaryMluEntry 2 }

-------------------------------------------------------------------------------
--   fjdarySlu                                                               --
-------------------------------------------------------------------------------
fjdarySluCount OBJECT-TYPE
    SYNTAX INTEGER
    ACCESS read-only
    STATUS mandatory
    DESCRIPTION
        "The number of SLU's informations entry (regardless of their current
         state) present on this system."
    ::= { fjdarySlu 1 }

fjdarySluTable OBJECT-TYPE
    SYNTAX SEQUENCE OF FjdarySluEntry
    ACCESS not-accessible
    STATUS mandatory
    DESCRIPTION
        ""
    ::= { fjdarySlu 2 }

fjdarySluEntry OBJECT-TYPE
    SYNTAX FjdarySluEntry
    ACCESS not-accessible
    STATUS mandatory
    DESCRIPTION
        ""
    INDEX { fjdarySluIndex }
    ::= { fjdarySluTable 1 }

FjdarySluEntry ::=
    SEQUENCE{
        fjdarySluIndex     INTEGER,
        fjdarySluInfoTable OCTET STRING
    }

fjdarySluIndex OBJECT-TYPE
    SYNTAX INTEGER
    ACCESS read-only
    STATUS mandatory
    DESCRIPTION
        "The value of this object uniquely identifies this fjdarySlu entry."
    ::= { fjdarySluEntry 1 }

fjdarySluInfoTable OBJECT-TYPE
    SYNTAX OCTET STRING
    ACCESS read-only
    STATUS mandatory
    DESCRIPTION
        "The value of this object indicates the SLU information of this system.
                  byte 0       byte 1       byte 2       byte 3
              +------------+------------+------------+------------+
          0x00| SLUN                    | Status                  |
              +------------+------------+------------+------------+
          0x04| LU Type    | Reserved                             |
              +------------+------------+------------+------------+
          0x08| RLUN                    | Temporary RLUN          |
              +------------+------------+------------+------------+
          0x0c| MLUN                    | OLUN                    |
              +------------+------------+------------+------------+
          0x10| Reserved (16 bytes)                               |
              ~                                                   ~
          0x1c|                                                   |
              +------------+------------+------------+------------+
          0x20| Start RLBA                                        |
              +                                                   +
          0x24|                                                   |
              +------------+------------+------------+------------+
          0x28| Temporary Start RLBA                              |
              +                                                   +
          0x2c|                                                   |
              +------------+------------+------------+------------+
          0x30| Start OLBA                                        |
              +                                                   +
          0x34|                                                   |
              +------------+------------+------------+------------+
          0x38| OLBA Count                                        |
              +                                                   +
          0x3c|                                                   |
              +------------+------------+------------+------------+
          0x40| SLBA Count                                        |
              +                                                   +
          0x44|                                                   |
              +------------+------------+------------+------------+
          0x48| Temporary SLBA Count                              |
              +                                                   +
          0x4c|                                                   |
              +------------+------------+------------+------------+
          0x50| Start SLBA for OLU                                |
              +                                                   +
          0x54|                                                   |
              +------------+------------+------------+------------+
          0x58| SLBA Count for OLU                                |
              +                                                   +
          0x5c|                                                   |
              +------------+------------+------------+------------+
          0x60| Virtual OLBA Count                                |
              +                                                   +
          0x64|                                                   |
              +------------+------------+------------+------------+
          0x68| Reserved (72 bytes)                               |
              ~                                                   ~
          0xac|                                                   |
              +------------+------------+------------+------------+"
    ::= { fjdarySluEntry 2 }

-------------------------------------------------------------------------------
--   fjdaryRlu                                                               --
-------------------------------------------------------------------------------
fjdaryRluCount OBJECT-TYPE
    SYNTAX INTEGER
    ACCESS read-only
    STATUS mandatory
    DESCRIPTION
        "The number of RLU's informations entry (regardless of their current
         state) present on this system."
    ::= { fjdaryRlu 1 }

fjdaryRluTable OBJECT-TYPE
    SYNTAX SEQUENCE OF FjdaryRluEntry
    ACCESS not-accessible
    STATUS mandatory
    DESCRIPTION
        ""
    ::= { fjdaryRlu 2 }

fjdaryRluEntry OBJECT-TYPE
    SYNTAX FjdaryRluEntry
    ACCESS not-accessible
    STATUS mandatory
    DESCRIPTION
        ""
    INDEX { fjdaryRluIndex }
    ::= { fjdaryRluTable 1 }

FjdaryRluEntry ::=
    SEQUENCE{
        fjdaryRluIndex      INTEGER,
        fjdaryRluInfoTable0 OCTET STRING,
        fjdaryRluInfoTable1 OCTET STRING,
        fjdaryRluInfoTable2 OCTET STRING
    }

fjdaryRluIndex OBJECT-TYPE
    SYNTAX INTEGER
    ACCESS read-only
    STATUS mandatory
    DESCRIPTION
        "The value of this object uniquely identifies this fjdaryRlu entry."
    ::= { fjdaryRluEntry 1 }

fjdaryRluInfoTable0 OBJECT-TYPE
    SYNTAX OCTET STRING
    ACCESS read-only
    STATUS mandatory
    DESCRIPTION
        "The value of this object indicates the RLU information #0 of this
         system.
                  byte 0       byte 1       byte 2       byte 3
              +------------+------------+------------+------------+
          0x00| RLUN                    | Status                  |
              +------------+------------+------------+------------+
          0x04| Def CM MID | Curr CM MID| Reserved                |
              +------------+------------+------------+------------+
          0x08| RAID Level | RLU Mode   | Blockade   | RLU Enable |
              +------------+------------+------------+------------+
          0x0c| Reserved                                          |
              +------------+------------+------------+------------+
          0x10| RLBA Count                                        |
              +                                                   +
          0x14|                                                   |
              +------------+------------+------------+------------+
          0x18| Stripe Depth                                      |
              +------------+------------+------------+------------+
          0x1c| Stripe Size                                       |
              +------------+------------+------------+------------+
          0x20| Expanded RLUN           | Temporary RLUN          |
              +------------+------------+------------+------------+
          0x24| Reserved (12 bytes)                               |
              ~                                                   ~
          0x2c|                                                   |
              +------------+------------+------------+------------+
          0x30| SLU Count  | Reserved                             |
              +------------+------------+------------+------------+"
    ::= { fjdaryRluEntry 2 }

fjdaryRluInfoTable1 OBJECT-TYPE
    SYNTAX OCTET STRING
    ACCESS read-only
    STATUS mandatory
    DESCRIPTION
        "The value of this object indicates the RLU information #1 of this
         system.
                  byte 0       byte 1       byte 2       byte 3
              +------------+------------+------------+------------+
          0x00| SLUN 00                 | SLUN 01                 |
              +------------+------------+------------+------------+
              ~                                                   ~
              +------------+------------+------------+------------+
          0xfc| SLUN 7E                 | SLUN 7F                 |
              +------------+------------+------------+------------+"
    ::= { fjdaryRluEntry 3 }

fjdaryRluInfoTable2 OBJECT-TYPE
    SYNTAX OCTET STRING
    ACCESS read-only
    STATUS mandatory
    DESCRIPTION
        "The value of this object indicates the RLU information #2 of this
         system.
                  byte 0       byte 1       byte 2       byte 3
              +------------+------------+------------+------------+
          0x00| M Disk cnt | Reserved                             |
              +------------+------------+------------+------------+
          0x04| DLUN 00                 | DLUN 01                 |
              +------------+------------+------------+------------+
              ~                                                   ~
              +------------+------------+------------+------------+
          0x20| DLUN 0E                 | DLUN 0F                 |
              +------------+------------+------------+------------+"
    ::= { fjdaryRluEntry 4 }

-------------------------------------------------------------------------------
--   fjdaryDlu                                                               --
-------------------------------------------------------------------------------
fjdaryDluCount OBJECT-TYPE
    SYNTAX INTEGER
    ACCESS read-only
    STATUS mandatory
    DESCRIPTION
        "The number of DLU's informations entry (regardless of their current
         state) present on this system."
    ::= { fjdaryDlu 1 }

fjdaryDluTable OBJECT-TYPE
    SYNTAX SEQUENCE OF FjdaryDluEntry
    ACCESS not-accessible
    STATUS mandatory
    DESCRIPTION
        ""
    ::= { fjdaryDlu 2 }

fjdaryDluEntry OBJECT-TYPE
    SYNTAX FjdaryDluEntry
    ACCESS not-accessible
    STATUS mandatory
    DESCRIPTION
        ""
    INDEX { fjdaryDluIndex }
    ::= { fjdaryDluTable 1 }

FjdaryDluEntry ::=
    SEQUENCE{
        fjdaryDluIndex     INTEGER,
        fjdaryDluInfoTable OCTET STRING
    }

fjdaryDluIndex OBJECT-TYPE
    SYNTAX INTEGER
    ACCESS read-only
    STATUS mandatory
    DESCRIPTION
        "The value of this object uniquely identifies this fjdaryDlu entry."
    ::= { fjdaryDluEntry 1 }

fjdaryDluInfoTable OBJECT-TYPE
    SYNTAX OCTET STRING
    ACCESS read-only
    STATUS mandatory
    DESCRIPTION
        "The value of this object indicates the DLU information of this system.
                  byte 0       byte 1       byte 2       byte 3
              +------------+------------+------------+------------+
          0x00| DLUN                    | Status                  |
              +------------+------------+------------+------------+
          0x04| RLUN                    | M Disk No  | Reserved   |
              +------------+------------+------------+------------+
          0x08| Start DLBA                                        |
              +                                                   +
          0x0c|                                                   |
              +------------+------------+------------+------------+
          0x10| Block Count                                       |
              +                                                   +
          0x14|                                                   |
              +------------+------------+------------+------------+
          0x18| Stripe Depth                                      |
              +------------+------------+------------+------------+
          0x1c| Stripe Size                                       |
              +------------+------------+------------+------------+
          0x20| M Disk cnt | Reserved                             |
              +------------+------------+------------+------------+
          0x24| Reserved                                          |
              +------------+------------+------------+------------+
          0x28| PLU in Use 00           | PLU in Use 01           |
              +------------+------------+------------+------------+
              ~                                                   ~
              +------------+------------+------------+------------+
          0x44| PLU in Use 0E           | PLU in Use 0F           |
              +------------+------------+------------+------------+
          0x48| Defined PLU 00          | Defined PLU 01          |
              +------------+------------+------------+------------+
              ~                                                   ~
              +------------+------------+------------+------------+
          0x64| Defined PLU 0E          | Defined PLU 0F          |
              +------------+------------+------------+------------+
          0x68| Reserved                                          |
              +                                                   +
          0x6c|                                                   |
              +------------+------------+------------+------------+"
    ::= { fjdaryDluEntry 2 }

-------------------------------------------------------------------------------
--   fjdaryOpenmap                                                           --
-------------------------------------------------------------------------------
fjdaryOpenmapCount OBJECT-TYPE
    SYNTAX INTEGER
    ACCESS read-only
    STATUS mandatory
    DESCRIPTION
        "The number of open volume mapping table's informations entry
         (regardless of their current state) present on this system."
    ::= { fjdaryOpenmap 1 }

fjdaryOpenmapTable OBJECT-TYPE
    SYNTAX SEQUENCE OF FjdaryOpenmapEntry
    ACCESS not-accessible
    STATUS mandatory
    DESCRIPTION
        ""
    ::= { fjdaryOpenmap 2 }

fjdaryOpenmapEntry OBJECT-TYPE
    SYNTAX FjdaryOpenmapEntry
    ACCESS not-accessible
    STATUS mandatory
    DESCRIPTION
        ""
    INDEX { fjdaryOpenmapIndex }
    ::= { fjdaryOpenmapTable 1 }

FjdaryOpenmapEntry ::=
    SEQUENCE{
        fjdaryOpenmapIndex     INTEGER,
        fjdaryOpenmapInfo      OCTET STRING,
        fjdaryOpenmapHostTable OCTET STRING
    }

fjdaryOpenmapIndex OBJECT-TYPE
    SYNTAX INTEGER
    ACCESS read-only
    STATUS mandatory
    DESCRIPTION
        "The value of this object uniquely identifies this fjdaryOpenmap
         entry."
    ::= { fjdaryOpenmapEntry 1 }

fjdaryOpenmapInfo OBJECT-TYPE
    SYNTAX OCTET STRING
    ACCESS read-only
    STATUS mandatory
    DESCRIPTION
        "The value of this object indicates the open volume mapping table
         information of this system.
                  byte 0       byte 1       byte 2       byte 3
              +------------+------------+------------+------------+
          0x00| MAP No     | Valid Cnt  | CA ModuleID| Port No    |
              +------------+------------+------------+------------+
          0x04| Default Affinity Group  | Reserved                |
              +------------+------------+------------+------------+
          0x08| Reserved                                          |
              +                                                   +
          0x0c|                                                   |
              +------------+------------+------------+------------+"
    ::= { fjdaryOpenmapEntry 2 }

fjdaryOpenmapHostTable OBJECT-TYPE
    SYNTAX OCTET STRING
    ACCESS read-only
    STATUS mandatory
    DESCRIPTION
        "The value of this object indicates the host affinity information of
         this system.
                  byte 0       byte 1       byte 2       byte 3
              +------------+------------+------------+------------+
          0x00| Host #00                | Affinity Group#00       |
              +------------+------------+------------+------------+
              ~                                                   ~
              +------------+------------+------------+------------+
          0xfc| Host #3F                | Affinity Group#3F       |
              +------------+------------+------------+------------+"
    ::= { fjdaryOpenmapEntry 3 }

-------------------------------------------------------------------------------
--   fjdaryLunolu                                                            --
-------------------------------------------------------------------------------
fjdaryLunoluCount OBJECT-TYPE
    SYNTAX INTEGER
    ACCESS read-only
    STATUS mandatory
    DESCRIPTION
        "The number of LUN-OLU mapping table's informations entry (regardless
         of their current state) present on this system."
    ::= { fjdaryLunolu 1 }

fjdaryLunoluTable OBJECT-TYPE
    SYNTAX SEQUENCE OF FjdaryLunoluEntry
    ACCESS not-accessible
    STATUS mandatory
    DESCRIPTION
        ""
    ::= { fjdaryLunolu 2 }

fjdaryLunoluEntry OBJECT-TYPE
    SYNTAX FjdaryLunoluEntry
    ACCESS not-accessible
    STATUS mandatory
    DESCRIPTION
        ""
    INDEX { fjdaryLunoluIndex }
    ::= { fjdaryLunoluTable 1 }

FjdaryLunoluEntry ::=
    SEQUENCE{
        fjdaryLunoluIndex  INTEGER,
        fjdaryLunoluInfo   OCTET STRING,
        fjdaryLunoluTable0 OCTET STRING,
        fjdaryLunoluTable1 OCTET STRING,
        fjdaryLunoluTable2 OCTET STRING,
        fjdaryLunoluTable3 OCTET STRING
    }

fjdaryLunoluIndex OBJECT-TYPE
    SYNTAX INTEGER
    ACCESS read-only
    STATUS mandatory
    DESCRIPTION
        "The value of this object uniquely identifies this fjdaryLunolu entry."
    ::= { fjdaryLunoluEntry 1 }

fjdaryLunoluInfo OBJECT-TYPE
    SYNTAX OCTET STRING
    ACCESS read-only
    STATUS mandatory
    DESCRIPTION
        "The value of this object indicates the LUN-OLU mapping table
         information of this system.
                  byte 0       byte 1       byte 2       byte 3
              +------------+------------+------------+------------+
          0x00| Affinity Group No       | Definition | Reserved   |
              +------------+------------+------------+------------+
          0x04| Affinity Group Name (16 bytes)                    |
              ~                                                   ~
          0x10|                                                   |
              +------------+------------+------------+------------+
          0x14| Prev Affinity Group No  | Next Affinity Group No  |
              +------------+------------+------------+------------+
          0x18| Host Response Table No  | Reserved                |
              +------------+------------+------------+------------+
          0x1c| Reserved                                          |
              +------------+------------+------------+------------+"
    ::= { fjdaryLunoluEntry 2 }

fjdaryLunoluTable0 OBJECT-TYPE
    SYNTAX OCTET STRING
    ACCESS read-only
    STATUS mandatory
    DESCRIPTION
        "The value of this object indicates the LUN-OLU mapping table
         information(LUN#0 to #127) of this system.
                  byte 0       byte 1       byte 2       byte 3
              +------------+------------+------------+------------+
          0x00| LUN#0-OLU#              | LUN#1-OLU#              |
              +------------+------------+------------+------------+
              ~                                                   ~
              +------------+------------+------------+------------+
          0xfc| LUN#126-OLU#            | LUN#127-OLU#            |
              +------------+------------+------------+------------+"
    ::= { fjdaryLunoluEntry 3 }

fjdaryLunoluTable1 OBJECT-TYPE
    SYNTAX OCTET STRING
    ACCESS read-only
    STATUS mandatory
    DESCRIPTION
        "The value of this object indicates the LUN-OLU mapping table
         information(LUN#128 to #255) of this system.
                  byte 0       byte 1       byte 2       byte 3
              +------------+------------+------------+------------+
          0x00| LUN#128-OLU#            | LUN#129-OLU#            |
              +------------+------------+------------+------------+
              ~                                                   ~
              +------------+------------+------------+------------+
          0xfc| LUN#254-OLU#            | LUN#255-OLU#            |
              +------------+------------+------------+------------+"
    ::= { fjdaryLunoluEntry 4 }

fjdaryLunoluTable2 OBJECT-TYPE
    SYNTAX OCTET STRING
    ACCESS read-only
    STATUS mandatory
    DESCRIPTION
        "The value of this object indicates the LUN-OLU mapping table
         information(LUN#256 to #383) of this system.
                  byte 0       byte 1       byte 2       byte 3
              +------------+------------+------------+------------+
          0x00| LUN#256-OLU#            | LUN#257-OLU#            |
              +------------+------------+------------+------------+
              ~                                                   ~
              +------------+------------+------------+------------+
          0xfc| LUN#382-OLU#            | LUN#383-OLU#            |
              +------------+------------+------------+------------+"
    ::= { fjdaryLunoluEntry 5 }

fjdaryLunoluTable3 OBJECT-TYPE
    SYNTAX OCTET STRING
    ACCESS read-only
    STATUS mandatory
    DESCRIPTION
        "The value of this object indicates the LUN-OLU mapping table
         information(LUN#384 to #511) of this system.
                  byte 0       byte 1       byte 2       byte 3
              +------------+------------+------------+------------+
          0x00| LUN#384-OLU#            | LUN#385-OLU#            |
              +------------+------------+------------+------------+
              ~                                                   ~
              +------------+------------+------------+------------+
          0xfc| LUN#510-OLU#            | LUN#511-OLU#            |
              +------------+------------+------------+------------+"
    ::= { fjdaryLunoluEntry 6 }

-------------------------------------------------------------------------------
--   fjdaryHostwwn                                                           --
-------------------------------------------------------------------------------
fjdaryHostwwnCount OBJECT-TYPE
    SYNTAX INTEGER
    ACCESS read-only
    STATUS mandatory
    DESCRIPTION
        "The number of host wwn table's informations entry (regardless of their
         current state) present on this system."
    ::= { fjdaryHostwwn 1 }

fjdaryHostwwnTable OBJECT-TYPE
    SYNTAX SEQUENCE OF FjdaryHostwwnEntry
    ACCESS not-accessible
    STATUS mandatory
    DESCRIPTION
        ""
    ::= { fjdaryHostwwn 2 }

fjdaryHostwwnEntry OBJECT-TYPE
    SYNTAX FjdaryHostwwnEntry
    ACCESS not-accessible
    STATUS mandatory
    DESCRIPTION
        ""
    INDEX { fjdaryHostwwnIndex }
    ::= { fjdaryHostwwnTable 1 }

FjdaryHostwwnEntry ::=
    SEQUENCE{
        fjdaryHostwwnIndex INTEGER,
        fjdaryHostwwnWWN   OCTET STRING
    }

fjdaryHostwwnIndex OBJECT-TYPE
    SYNTAX INTEGER
    ACCESS read-only
    STATUS mandatory
    DESCRIPTION
        "The value of this object uniquely identifies this fjdaryHostwwn
         entry."
    ::= { fjdaryHostwwnEntry 1 }

fjdaryHostwwnWWN OBJECT-TYPE
    SYNTAX OCTET STRING
    ACCESS read-only
    STATUS mandatory
    DESCRIPTION
        "The value of this object indicates the host wwn of this system.
                  byte 0       byte 1       byte 2       byte 3
              +------------+------------+------------+------------+
          0x00| Host WWN                                          |
              +                                                   +
          0x04|                                                   |
              +------------+------------+------------+------------+
          0x08| Host Response Table Num | Valid Flag | Reserved   |
              +------------+------------+------------+------------+
          0x0c| Reserved (20 bytes)                               |
              ~                                                   ~
          0x1c|                                                   |
              +------------+------------+------------+------------+"
    ::= { fjdaryHostwwnEntry 2 }

-------------------------------------------------------------------------------
--   fjdaryResetpath                                                         --
-------------------------------------------------------------------------------
fjdaryResetpathCount OBJECT-TYPE
    SYNTAX INTEGER
    ACCESS read-only
    STATUS mandatory
    DESCRIPTION
        "The number of reset path group table's informations entry (regardless
         of their current state) present on this system."
    ::= { fjdaryResetpath 1 }

fjdaryResetpathTable OBJECT-TYPE
    SYNTAX SEQUENCE OF FjdaryResetpathEntry
    ACCESS not-accessible
    STATUS mandatory
    DESCRIPTION
        ""
    ::= { fjdaryResetpath 2 }

fjdaryResetpathEntry OBJECT-TYPE
    SYNTAX FjdaryResetpathEntry
    ACCESS not-accessible
    STATUS mandatory
    DESCRIPTION
        ""
    INDEX { fjdaryResetpathIndex }
    ::= { fjdaryResetpathTable 1 }

FjdaryResetpathEntry ::=
    SEQUENCE{
        fjdaryResetpathIndex INTEGER,
        fjdaryResetpathGroup OCTET STRING
    }

fjdaryResetpathIndex OBJECT-TYPE
    SYNTAX INTEGER
    ACCESS read-only
    STATUS mandatory
    DESCRIPTION
        "The value of this object uniquely identifies this fjdaryResetpath
         entry."
    ::= { fjdaryResetpathEntry 1 }

fjdaryResetpathGroup OBJECT-TYPE
    SYNTAX OCTET STRING
    ACCESS read-only
    STATUS  mandatory
    DESCRIPTION
        "The value of this object indicates the reset path group table
         information of this system."
    ::= { fjdaryResetpathEntry 2 }

-------------------------------------------------------------------------------
--   fjdaryLcu                                                               --
-------------------------------------------------------------------------------
fjdaryLcuCount OBJECT-TYPE
    SYNTAX INTEGER
    ACCESS read-only
    STATUS mandatory
    DESCRIPTION
        "The number of LCU information table's entry (regardless of their
         current state) present on this system."
    ::= { fjdaryLcu 1 }

fjdaryLcuTable OBJECT-TYPE
    SYNTAX SEQUENCE OF FjdaryLcuEntry
    ACCESS not-accessible
    STATUS mandatory
    DESCRIPTION
        ""
    ::= { fjdaryLcu 2 }

fjdaryLcuEntry OBJECT-TYPE
    SYNTAX FjdaryLcuEntry
    ACCESS not-accessible
    STATUS mandatory
    DESCRIPTION
        ""
    INDEX { fjdaryLcuIndex }
    ::= { fjdaryLcuTable 1 }

FjdaryLcuEntry ::=
    SEQUENCE{
        fjdaryLcuIndex     INTEGER,
        fjdaryLcuInfoTable OCTET STRING
    }

fjdaryLcuIndex OBJECT-TYPE
    SYNTAX INTEGER
    ACCESS read-only
    STATUS mandatory
    DESCRIPTION
        "The value of this object uniquely identifies this fjdaryLcu entry."
    ::= { fjdaryLcuEntry 1 }

fjdaryLcuInfoTable OBJECT-TYPE
    SYNTAX OCTET STRING
    ACCESS read-only
    STATUS mandatory
    DESCRIPTION
        "The value of this object indicates the LCU information table of this
         system.
                  byte 0       byte 1       byte 2       byte 3
              +------------+------------+------------+------------+
          0x00| LCU No     | definition | LCU Mode   | Cache Mode |
              +------------+------------+------------+------------+
          0x04| Remote Flag| Reserved   | SSID                    |
              +------------+------------+------------+------------+
          0x08| Reserved                                          |
              +                                                   +
          0x0c|                                                   |
              +------------+------------+------------+------------+"
    ::= { fjdaryLcuEntry 2 }

-------------------------------------------------------------------------------
--   fjdaryIoamlu                                                            --
-------------------------------------------------------------------------------
fjdaryIoamluCount OBJECT-TYPE
    SYNTAX INTEGER
    ACCESS read-only
    STATUS mandatory
    DESCRIPTION
        "The number of LCU-CA-IOA mapping information table's entry (regardless
         of their current state) present on this system."
    ::= { fjdaryIoamlu 1 }

fjdaryIoamluTable OBJECT-TYPE
    SYNTAX SEQUENCE OF FjdaryIoamluEntry
    ACCESS not-accessible
    STATUS mandatory
    DESCRIPTION
        ""
    ::= { fjdaryIoamlu 2 }

fjdaryIoamluEntry OBJECT-TYPE
    SYNTAX FjdaryIoamluEntry
    ACCESS not-accessible
    STATUS mandatory
    DESCRIPTION
        ""
    INDEX { fjdaryIoamluIndex }
    ::= { fjdaryIoamluTable 1 }

FjdaryIoamluEntry ::=
    SEQUENCE{
        fjdaryIoamluIndex INTEGER,
        fjdaryIoamluLCU0  OCTET STRING,
        fjdaryIoamluLCU1  OCTET STRING,
        fjdaryIoamluLCU2  OCTET STRING,
        fjdaryIoamluLCU3  OCTET STRING,
        fjdaryIoamluLCU4  OCTET STRING,
        fjdaryIoamluLCU5  OCTET STRING,
        fjdaryIoamluLCU6  OCTET STRING,
        fjdaryIoamluLCU7  OCTET STRING,
        fjdaryIoamluLCU8  OCTET STRING,
        fjdaryIoamluLCU9  OCTET STRING,
        fjdaryIoamluLCU10 OCTET STRING,
        fjdaryIoamluLCU11 OCTET STRING,
        fjdaryIoamluLCU12 OCTET STRING,
        fjdaryIoamluLCU13 OCTET STRING,
        fjdaryIoamluLCU14 OCTET STRING,
        fjdaryIoamluLCU15 OCTET STRING,
        fjdaryIoamluLCU16 OCTET STRING,
        fjdaryIoamluLCU17 OCTET STRING,
        fjdaryIoamluLCU18 OCTET STRING,
        fjdaryIoamluLCU19 OCTET STRING,
        fjdaryIoamluLCU20 OCTET STRING,
        fjdaryIoamluLCU21 OCTET STRING,
        fjdaryIoamluLCU22 OCTET STRING,
        fjdaryIoamluLCU23 OCTET STRING,
        fjdaryIoamluLCU24 OCTET STRING,
        fjdaryIoamluLCU25 OCTET STRING,
        fjdaryIoamluLCU26 OCTET STRING,
        fjdaryIoamluLCU27 OCTET STRING,
        fjdaryIoamluLCU28 OCTET STRING,
        fjdaryIoamluLCU29 OCTET STRING,
        fjdaryIoamluLCU30 OCTET STRING,
        fjdaryIoamluLCU31 OCTET STRING,
        fjdaryIoamluLCU32 OCTET STRING,
        fjdaryIoamluLCU33 OCTET STRING,
        fjdaryIoamluLCU34 OCTET STRING,
        fjdaryIoamluLCU35 OCTET STRING,
        fjdaryIoamluLCU36 OCTET STRING,
        fjdaryIoamluLCU37 OCTET STRING,
        fjdaryIoamluLCU38 OCTET STRING,
        fjdaryIoamluLCU39 OCTET STRING,
        fjdaryIoamluLCU40 OCTET STRING,
        fjdaryIoamluLCU41 OCTET STRING,
        fjdaryIoamluLCU42 OCTET STRING,
        fjdaryIoamluLCU43 OCTET STRING,
        fjdaryIoamluLCU44 OCTET STRING,
        fjdaryIoamluLCU45 OCTET STRING,
        fjdaryIoamluLCU46 OCTET STRING,
        fjdaryIoamluLCU47 OCTET STRING,
        fjdaryIoamluLCU48 OCTET STRING,
        fjdaryIoamluLCU49 OCTET STRING,
        fjdaryIoamluLCU50 OCTET STRING,
        fjdaryIoamluLCU51 OCTET STRING,
        fjdaryIoamluLCU52 OCTET STRING,
        fjdaryIoamluLCU53 OCTET STRING,
        fjdaryIoamluLCU54 OCTET STRING,
        fjdaryIoamluLCU55 OCTET STRING,
        fjdaryIoamluLCU56 OCTET STRING,
        fjdaryIoamluLCU57 OCTET STRING,
        fjdaryIoamluLCU58 OCTET STRING,
        fjdaryIoamluLCU59 OCTET STRING,
        fjdaryIoamluLCU60 OCTET STRING,
        fjdaryIoamluLCU61 OCTET STRING,
        fjdaryIoamluLCU62 OCTET STRING,
        fjdaryIoamluLCU63 OCTET STRING
    }

fjdaryIoamluIndex OBJECT-TYPE
    SYNTAX INTEGER
    ACCESS read-only
    STATUS mandatory
    DESCRIPTION
        "The value of this object uniquely identifies this fjdaryIoamlu entry."
    ::= { fjdaryIoamluEntry 1 }

fjdaryIoamluLCU0 OBJECT-TYPE
    SYNTAX OCTET STRING
    ACCESS read-only
    STATUS mandatory
    DESCRIPTION
        "The value of this object indicates the LCU-CA-IOA mapping information
         table of this system.
         LCU#0 IOA#0-#127 MLU mapping table
                  byte 0       byte 1       byte 2       byte 3
              +------------+------------+------------+------------+
          0x00| IOA#0-MLU#              | IOA#1-MLU#              |
              +------------+------------+------------+------------+
              ~                                                   ~
              +------------+------------+------------+------------+
          0xfc| IOA#126-MLU#            | IOA#127-MLU#            |
              +------------+------------+------------+------------+"
    ::= { fjdaryIoamluEntry 2 }

fjdaryIoamluLCU1 OBJECT-TYPE
    SYNTAX OCTET STRING
    ACCESS read-only
    STATUS mandatory
    DESCRIPTION
        "The value of this object indicates the LCU-CA-IOA mapping information
         table of this system.
         LCU#0 IOA#128-#255 MLU mapping table
                  byte 0       byte 1       byte 2       byte 3
              +------------+------------+------------+------------+
          0x00| IOA#128-MLU#            | IOA#129-MLU#            |
              +------------+------------+------------+------------+
              ~                                                   ~
              +------------+------------+------------+------------+
          0xfc| IOA#254-MLU#            | IOA#255-MLU#            |
              +------------+------------+------------+------------+"
    ::= { fjdaryIoamluEntry 3 }

fjdaryIoamluLCU2 OBJECT-TYPE
    SYNTAX OCTET STRING
    ACCESS read-only
    STATUS mandatory
    DESCRIPTION
        "The value of this object indicates the LCU-CA-IOA mapping information
         table of this system.
         LCU#1 IOA#0-#127 MLU mapping table
                  byte 0       byte 1       byte 2       byte 3
              +------------+------------+------------+------------+
          0x00| IOA#0-MLU#              | IOA#1-MLU#              |
              +------------+------------+------------+------------+
              ~                                                   ~
              +------------+------------+------------+------------+
          0xfc| IOA#126-MLU#            | IOA#127-MLU#            |
              +------------+------------+------------+------------+"
    ::= { fjdaryIoamluEntry 4 }

fjdaryIoamluLCU3 OBJECT-TYPE
    SYNTAX OCTET STRING
    ACCESS read-only
    STATUS mandatory
    DESCRIPTION
        "The value of this object indicates the LCU-CA-IOA mapping information
         table of this system.
         LCU#1 IOA#128-#255 MLU mapping table
                  byte 0       byte 1       byte 2       byte 3
              +------------+------------+------------+------------+
          0x00| IOA#128-MLU#            | IOA#129-MLU#            |
              +------------+------------+------------+------------+
              ~                                                   ~
              +------------+------------+------------+------------+
          0xfc| IOA#254-MLU#            | IOA#255-MLU#            |
              +------------+------------+------------+------------+"
    ::= { fjdaryIoamluEntry 5 }

fjdaryIoamluLCU4 OBJECT-TYPE
    SYNTAX OCTET STRING
    ACCESS read-only
    STATUS mandatory
    DESCRIPTION
        "The value of this object indicates the LCU-CA-IOA mapping information
         table of this system.
         LCU#2 IOA#0-#127 MLU mapping table
                  byte 0       byte 1       byte 2       byte 3
              +------------+------------+------------+------------+
          0x00| IOA#0-MLU#              | IOA#1-MLU#              |
              +------------+------------+------------+------------+
              ~                                                   ~
              +------------+------------+------------+------------+
          0xfc| IOA#126-MLU#            | IOA#127-MLU#            |
              +------------+------------+------------+------------+"
    ::= { fjdaryIoamluEntry 6 }

fjdaryIoamluLCU5 OBJECT-TYPE
    SYNTAX OCTET STRING
    ACCESS read-only
    STATUS mandatory
    DESCRIPTION
        "The value of this object indicates the LCU-CA-IOA mapping information
         table of this system.
         LCU#2 IOA#128-#255 MLU mapping table
                  byte 0       byte 1       byte 2       byte 3
              +------------+------------+------------+------------+
          0x00| IOA#128-MLU#            | IOA#129-MLU#            |
              +------------+------------+------------+------------+
              ~                                                   ~
              +------------+------------+------------+------------+
          0xfc| IOA#254-MLU#            | IOA#255-MLU#            |
              +------------+------------+------------+------------+"
    ::= { fjdaryIoamluEntry 7 }

fjdaryIoamluLCU6 OBJECT-TYPE
    SYNTAX OCTET STRING
    ACCESS read-only
    STATUS mandatory
    DESCRIPTION
        "The value of this object indicates the LCU-CA-IOA mapping information
         table of this system.
         LCU#3 IOA#0-#127 MLU mapping table
                  byte 0       byte 1       byte 2       byte 3
              +------------+------------+------------+------------+
          0x00| IOA#0-MLU#              | IOA#1-MLU#              |
              +------------+------------+------------+------------+
              ~                                                   ~
              +------------+------------+------------+------------+
          0xfc| IOA#126-MLU#            | IOA#127-MLU#            |
              +------------+------------+------------+------------+"
    ::= { fjdaryIoamluEntry 8 }

fjdaryIoamluLCU7 OBJECT-TYPE
    SYNTAX OCTET STRING
    ACCESS read-only
    STATUS mandatory
    DESCRIPTION
        "The value of this object indicates the LCU-CA-IOA mapping information
         table of this system.
         LCU#3 IOA#128-#255 MLU mapping table
                  byte 0       byte 1       byte 2       byte 3
              +------------+------------+------------+------------+
          0x00| IOA#128-MLU#            | IOA#129-MLU#            |
              +------------+------------+------------+------------+
              ~                                                   ~
              +------------+------------+------------+------------+
          0xfc| IOA#254-MLU#            | IOA#255-MLU#            |
              +------------+------------+------------+------------+"
    ::= { fjdaryIoamluEntry 9 }

fjdaryIoamluLCU8 OBJECT-TYPE
    SYNTAX OCTET STRING
    ACCESS read-only
    STATUS mandatory
    DESCRIPTION
        "The value of this object indicates the LCU-CA-IOA mapping information
         table of this system.
         LCU#4 IOA#0-#127 MLU mapping table
                  byte 0       byte 1       byte 2       byte 3
              +------------+------------+------------+------------+
          0x00| IOA#0-MLU#              | IOA#1-MLU#              |
              +------------+------------+------------+------------+
              ~                                                   ~
              +------------+------------+------------+------------+
          0xfc| IOA#126-MLU#            | IOA#127-MLU#            |
              +------------+------------+------------+------------+"
    ::= { fjdaryIoamluEntry 10 }

fjdaryIoamluLCU9 OBJECT-TYPE
    SYNTAX OCTET STRING
    ACCESS read-only
    STATUS mandatory
    DESCRIPTION
        "The value of this object indicates the LCU-CA-IOA mapping information
         table of this system.
         LCU#4 IOA#128-#255 MLU mapping table
                  byte 0       byte 1       byte 2       byte 3
              +------------+------------+------------+------------+
          0x00| IOA#128-MLU#            | IOA#129-MLU#            |
              +------------+------------+------------+------------+
              ~                                                   ~
              +------------+------------+------------+------------+
          0xfc| IOA#254-MLU#            | IOA#255-MLU#            |
              +------------+------------+------------+------------+"
    ::= { fjdaryIoamluEntry 11 }

fjdaryIoamluLCU10 OBJECT-TYPE
    SYNTAX OCTET STRING
    ACCESS read-only
    STATUS mandatory
    DESCRIPTION
        "The value of this object indicates the LCU-CA-IOA mapping information
         table of this system.
         LCU#5 IOA#0-#127 MLU mapping table
                  byte 0       byte 1       byte 2       byte 3
              +------------+------------+------------+------------+
          0x00| IOA#0-MLU#              | IOA#1-MLU#              |
              +------------+------------+------------+------------+
              ~                                                   ~
              +------------+------------+------------+------------+
          0xfc| IOA#126-MLU#            | IOA#127-MLU#            |
              +------------+------------+------------+------------+"
    ::= { fjdaryIoamluEntry 12 }

fjdaryIoamluLCU11 OBJECT-TYPE
    SYNTAX OCTET STRING
    ACCESS read-only
    STATUS mandatory
    DESCRIPTION
        "The value of this object indicates the LCU-CA-IOA mapping information
         table of this system.
         LCU#5 IOA#128-#255 MLU mapping table
                  byte 0       byte 1       byte 2       byte 3
              +------------+------------+------------+------------+
          0x00| IOA#128-MLU#            | IOA#129-MLU#            |
              +------------+------------+------------+------------+
              ~                                                   ~
              +------------+------------+------------+------------+
          0xfc| IOA#254-MLU#            | IOA#255-MLU#            |
              +------------+------------+------------+------------+"
    ::= { fjdaryIoamluEntry 13 }

fjdaryIoamluLCU12 OBJECT-TYPE
    SYNTAX OCTET STRING
    ACCESS read-only
    STATUS mandatory
    DESCRIPTION
        "The value of this object indicates the LCU-CA-IOA mapping information
         table of this system.
         LCU#6 IOA#0-#127 MLU mapping table
                  byte 0       byte 1       byte 2       byte 3
              +------------+------------+------------+------------+
          0x00| IOA#0-MLU#              | IOA#1-MLU#              |
              +------------+------------+------------+------------+
              ~                                                   ~
              +------------+------------+------------+------------+
          0xfc| IOA#126-MLU#            | IOA#127-MLU#            |
              +------------+------------+------------+------------+"
    ::= { fjdaryIoamluEntry 14 }

fjdaryIoamluLCU13 OBJECT-TYPE
    SYNTAX OCTET STRING
    ACCESS read-only
    STATUS mandatory
    DESCRIPTION
        "The value of this object indicates the LCU-CA-IOA mapping information
         table of this system.
         LCU#6 IOA#128-#255 MLU mapping table
                  byte 0       byte 1       byte 2       byte 3
              +------------+------------+------------+------------+
          0x00| IOA#128-MLU#            | IOA#129-MLU#            |
              +------------+------------+------------+------------+
              ~                                                   ~
              +------------+------------+------------+------------+
          0xfc| IOA#254-MLU#            | IOA#255-MLU#            |
              +------------+------------+------------+------------+"
    ::= { fjdaryIoamluEntry 15 }

fjdaryIoamluLCU14 OBJECT-TYPE
    SYNTAX OCTET STRING
    ACCESS read-only
    STATUS mandatory
    DESCRIPTION
        "The value of this object indicates the LCU-CA-IOA mapping information
         table of this system.
         LCU#7 IOA#0-#127 MLU mapping table
                  byte 0       byte 1       byte 2       byte 3
              +------------+------------+------------+------------+
          0x00| IOA#0-MLU#              | IOA#1-MLU#              |
              +------------+------------+------------+------------+
              ~                                                   ~
              +------------+------------+------------+------------+
          0xfc| IOA#126-MLU#            | IOA#127-MLU#            |
              +------------+------------+------------+------------+"
    ::= { fjdaryIoamluEntry 16 }

fjdaryIoamluLCU15 OBJECT-TYPE
    SYNTAX OCTET STRING
    ACCESS read-only
    STATUS mandatory
    DESCRIPTION
        "The value of this object indicates the LCU-CA-IOA mapping information
         table of this system.
         LCU#7 IOA#128-#255 MLU mapping table
                  byte 0       byte 1       byte 2       byte 3
              +------------+------------+------------+------------+
          0x00| IOA#128-MLU#            | IOA#129-MLU#            |
              +------------+------------+------------+------------+
              ~                                                   ~
              +------------+------------+------------+------------+
          0xfc| IOA#254-MLU#            | IOA#255-MLU#            |
              +------------+------------+------------+------------+"
    ::= { fjdaryIoamluEntry 17 }

fjdaryIoamluLCU16 OBJECT-TYPE
    SYNTAX OCTET STRING
    ACCESS read-only
    STATUS mandatory
    DESCRIPTION
        "The value of this object indicates the LCU-CA-IOA mapping information
         table of this system.
         LCU#8 IOA#0-#127 MLU mapping table
                  byte 0       byte 1       byte 2       byte 3
              +------------+------------+------------+------------+
          0x00| IOA#0-MLU#              | IOA#1-MLU#              |
              +------------+------------+------------+------------+
              ~                                                   ~
              +------------+------------+------------+------------+
          0xfc| IOA#126-MLU#            | IOA#127-MLU#            |
              +------------+------------+------------+------------+"
    ::= { fjdaryIoamluEntry 18 }

fjdaryIoamluLCU17 OBJECT-TYPE
    SYNTAX OCTET STRING
    ACCESS read-only
    STATUS mandatory
    DESCRIPTION
        "The value of this object indicates the LCU-CA-IOA mapping information
         table of this system.
         LCU#8 IOA#128-#255 MLU mapping table
                  byte 0       byte 1       byte 2       byte 3
              +------------+------------+------------+------------+
          0x00| IOA#128-MLU#            | IOA#129-MLU#            |
              +------------+------------+------------+------------+
              ~                                                   ~
              +------------+------------+------------+------------+
          0xfc| IOA#254-MLU#            | IOA#255-MLU#            |
              +------------+------------+------------+------------+"
    ::= { fjdaryIoamluEntry 19 }

fjdaryIoamluLCU18 OBJECT-TYPE
    SYNTAX OCTET STRING
    ACCESS read-only
    STATUS mandatory
    DESCRIPTION
        "The value of this object indicates the LCU-CA-IOA mapping information
         table of this system.
         LCU#9 IOA#0-#127 MLU mapping table
                  byte 0       byte 1       byte 2       byte 3
              +------------+------------+------------+------------+
          0x00| IOA#0-MLU#              | IOA#1-MLU#              |
              +------------+------------+------------+------------+
              ~                                                   ~
              +------------+------------+------------+------------+
          0xfc| IOA#126-MLU#            | IOA#127-MLU#            |
              +------------+------------+------------+------------+"
    ::= { fjdaryIoamluEntry 20 }

fjdaryIoamluLCU19 OBJECT-TYPE
    SYNTAX OCTET STRING
    ACCESS read-only
    STATUS mandatory
    DESCRIPTION
        "The value of this object indicates the LCU-CA-IOA mapping information
         table of this system.
         LCU#9 IOA#128-#255 MLU mapping table
                  byte 0       byte 1       byte 2       byte 3
              +------------+------------+------------+------------+
          0x00| IOA#128-MLU#            | IOA#129-MLU#            |
              +------------+------------+------------+------------+
              ~                                                   ~
              +------------+------------+------------+------------+
          0xfc| IOA#254-MLU#            | IOA#255-MLU#            |
              +------------+------------+------------+------------+"
    ::= { fjdaryIoamluEntry 21 }

fjdaryIoamluLCU20 OBJECT-TYPE
    SYNTAX OCTET STRING
    ACCESS read-only
    STATUS mandatory
    DESCRIPTION
        "The value of this object indicates the LCU-CA-IOA mapping information
         table of this system.
         LCU#10 IOA#0-#127 MLU mapping table
                  byte 0       byte 1       byte 2       byte 3
              +------------+------------+------------+------------+
          0x00| IOA#0-MLU#              | IOA#1-MLU#              |
              +------------+------------+------------+------------+
              ~                                                   ~
              +------------+------------+------------+------------+
          0xfc| IOA#126-MLU#            | IOA#127-MLU#            |
              +------------+------------+------------+------------+"
    ::= { fjdaryIoamluEntry 22 }

fjdaryIoamluLCU21 OBJECT-TYPE
    SYNTAX OCTET STRING
    ACCESS read-only
    STATUS mandatory
    DESCRIPTION
        "The value of this object indicates the LCU-CA-IOA mapping information
         table of this system.
         LCU#10 IOA#128-#255 MLU mapping table
                  byte 0       byte 1       byte 2       byte 3
              +------------+------------+------------+------------+
          0x00| IOA#128-MLU#            | IOA#129-MLU#            |
              +------------+------------+------------+------------+
              ~                                                   ~
              +------------+------------+------------+------------+
          0xfc| IOA#254-MLU#            | IOA#255-MLU#            |
              +------------+------------+------------+------------+"
    ::= { fjdaryIoamluEntry 23 }

fjdaryIoamluLCU22 OBJECT-TYPE
    SYNTAX OCTET STRING
    ACCESS read-only
    STATUS mandatory
    DESCRIPTION
        "The value of this object indicates the LCU-CA-IOA mapping information
         table of this system.
         LCU#11 IOA#0-#127 MLU mapping table
                  byte 0       byte 1       byte 2       byte 3
              +------------+------------+------------+------------+
          0x00| IOA#0-MLU#              | IOA#1-MLU#              |
              +------------+------------+------------+------------+
              ~                                                   ~
              +------------+------------+------------+------------+
          0xfc| IOA#126-MLU#            | IOA#127-MLU#            |
              +------------+------------+------------+------------+"
    ::= { fjdaryIoamluEntry 24 }

fjdaryIoamluLCU23 OBJECT-TYPE
    SYNTAX OCTET STRING
    ACCESS read-only
    STATUS mandatory
    DESCRIPTION
        "The value of this object indicates the LCU-CA-IOA mapping information
         table of this system.
         LCU#11 IOA#128-#255 MLU mapping table
                  byte 0       byte 1       byte 2       byte 3
              +------------+------------+------------+------------+
          0x00| IOA#128-MLU#            | IOA#129-MLU#            |
              +------------+------------+------------+------------+
              ~                                                   ~
              +------------+------------+------------+------------+
          0xfc| IOA#254-MLU#            | IOA#255-MLU#            |
              +------------+------------+------------+------------+"
    ::= { fjdaryIoamluEntry 25 }

fjdaryIoamluLCU24 OBJECT-TYPE
    SYNTAX OCTET STRING
    ACCESS read-only
    STATUS mandatory
    DESCRIPTION
        "The value of this object indicates the LCU-CA-IOA mapping information
         table of this system.
         LCU#12 IOA#0-#127 MLU mapping table
                  byte 0       byte 1       byte 2       byte 3
              +------------+------------+------------+------------+
          0x00| IOA#0-MLU#              | IOA#1-MLU#              |
              +------------+------------+------------+------------+
              ~                                                   ~
              +------------+------------+------------+------------+
          0xfc| IOA#126-MLU#            | IOA#127-MLU#            |
              +------------+------------+------------+------------+"
    ::= { fjdaryIoamluEntry 26 }

fjdaryIoamluLCU25 OBJECT-TYPE
    SYNTAX OCTET STRING
    ACCESS read-only
    STATUS mandatory
    DESCRIPTION
        "The value of this object indicates the LCU-CA-IOA mapping information
         table of this system.
         LCU#12 IOA#128-#255 MLU mapping table
                  byte 0       byte 1       byte 2       byte 3
              +------------+------------+------------+------------+
          0x00| IOA#128-MLU#            | IOA#129-MLU#            |
              +------------+------------+------------+------------+
              ~                                                   ~
              +------------+------------+------------+------------+
          0xfc| IOA#254-MLU#            | IOA#255-MLU#            |
              +------------+------------+------------+------------+"
    ::= { fjdaryIoamluEntry 27 }

fjdaryIoamluLCU26 OBJECT-TYPE
    SYNTAX OCTET STRING
    ACCESS read-only
    STATUS mandatory
    DESCRIPTION
        "The value of this object indicates the LCU-CA-IOA mapping information
         table of this system.
         LCU#13 IOA#0-#127 MLU mapping table
                  byte 0       byte 1       byte 2       byte 3
              +------------+------------+------------+------------+
          0x00| IOA#0-MLU#              | IOA#1-MLU#              |
              +------------+------------+------------+------------+
              ~                                                   ~
              +------------+------------+------------+------------+
          0xfc| IOA#126-MLU#            | IOA#127-MLU#            |
              +------------+------------+------------+------------+"
    ::= { fjdaryIoamluEntry 28 }

fjdaryIoamluLCU27 OBJECT-TYPE
    SYNTAX OCTET STRING
    ACCESS read-only
    STATUS mandatory
    DESCRIPTION
        "The value of this object indicates the LCU-CA-IOA mapping information
         table of this system.
         LCU#13 IOA#128-#255 MLU mapping table
                  byte 0       byte 1       byte 2       byte 3
              +------------+------------+------------+------------+
          0x00| IOA#128-MLU#            | IOA#129-MLU#            |
              +------------+------------+------------+------------+
              ~                                                   ~
              +------------+------------+------------+------------+
          0xfc| IOA#254-MLU#            | IOA#255-MLU#            |
              +------------+------------+------------+------------+"
    ::= { fjdaryIoamluEntry 29 }

fjdaryIoamluLCU28 OBJECT-TYPE
    SYNTAX OCTET STRING
    ACCESS read-only
    STATUS mandatory
    DESCRIPTION
        "The value of this object indicates the LCU-CA-IOA mapping information
         table of this system.
         LCU#14 IOA#0-#127 MLU mapping table
                  byte 0       byte 1       byte 2       byte 3
              +------------+------------+------------+------------+
          0x00| IOA#0-MLU#              | IOA#1-MLU#              |
              +------------+------------+------------+------------+
              ~                                                   ~
              +------------+------------+------------+------------+
          0xfc| IOA#126-MLU#            | IOA#127-MLU#            |
              +------------+------------+------------+------------+"
    ::= { fjdaryIoamluEntry 30 }

fjdaryIoamluLCU29 OBJECT-TYPE
    SYNTAX OCTET STRING
    ACCESS read-only
    STATUS mandatory
    DESCRIPTION
        "The value of this object indicates the LCU-CA-IOA mapping information
         table of this system.
         LCU#14 IOA#128-#255 MLU mapping table
                  byte 0       byte 1       byte 2       byte 3
              +------------+------------+------------+------------+
          0x00| IOA#128-MLU#            | IOA#129-MLU#            |
              +------------+------------+------------+------------+
              ~                                                   ~
              +------------+------------+------------+------------+
          0xfc| IOA#254-MLU#            | IOA#255-MLU#            |
              +------------+------------+------------+------------+"
    ::= { fjdaryIoamluEntry 31 }

fjdaryIoamluLCU30 OBJECT-TYPE
    SYNTAX OCTET STRING
    ACCESS read-only
    STATUS mandatory
    DESCRIPTION
        "The value of this object indicates the LCU-CA-IOA mapping information
         table of this system.
         LCU#15 IOA#0-#127 MLU mapping table
                  byte 0       byte 1       byte 2       byte 3
              +------------+------------+------------+------------+
          0x00| IOA#0-MLU#              | IOA#1-MLU#              |
              +------------+------------+------------+------------+
              ~                                                   ~
              +------------+------------+------------+------------+
          0xfc| IOA#126-MLU#            | IOA#127-MLU#            |
              +------------+------------+------------+------------+"
    ::= { fjdaryIoamluEntry 32 }

fjdaryIoamluLCU31 OBJECT-TYPE
    SYNTAX OCTET STRING
    ACCESS read-only
    STATUS mandatory
    DESCRIPTION
        "The value of this object indicates the LCU-CA-IOA mapping information
         table of this system.
         LCU#15 IOA#128-#255 MLU mapping table
                  byte 0       byte 1       byte 2       byte 3
              +------------+------------+------------+------------+
          0x00| IOA#128-MLU#            | IOA#129-MLU#            |
              +------------+------------+------------+------------+
              ~                                                   ~
              +------------+------------+------------+------------+
          0xfc| IOA#254-MLU#            | IOA#255-MLU#            |
              +------------+------------+------------+------------+"
    ::= { fjdaryIoamluEntry 33 }

fjdaryIoamluLCU32 OBJECT-TYPE
    SYNTAX OCTET STRING
    ACCESS read-only
    STATUS mandatory
    DESCRIPTION
        "The value of this object indicates the LCU-CA-IOA mapping information
         table of this system.
         LCU#16 IOA#0-#127 MLU mapping table
                  byte 0       byte 1       byte 2       byte 3
              +------------+------------+------------+------------+
          0x00| IOA#0-MLU#              | IOA#1-MLU#              |
              +------------+------------+------------+------------+
              ~                                                   ~
              +------------+------------+------------+------------+
          0xfc| IOA#126-MLU#            | IOA#127-MLU#            |
              +------------+------------+------------+------------+"
    ::= { fjdaryIoamluEntry 34 }

fjdaryIoamluLCU33 OBJECT-TYPE
    SYNTAX OCTET STRING
    ACCESS read-only
    STATUS mandatory
    DESCRIPTION
        "The value of this object indicates the LCU-CA-IOA mapping information
         table of this system.
         LCU#16 IOA#128-#255 MLU mapping table
                  byte 0       byte 1       byte 2       byte 3
              +------------+------------+------------+------------+
          0x00| IOA#128-MLU#            | IOA#129-MLU#            |
              +------------+------------+------------+------------+
              ~                                                   ~
              +------------+------------+------------+------------+
          0xfc| IOA#254-MLU#            | IOA#255-MLU#            |
              +------------+------------+------------+------------+"
    ::= { fjdaryIoamluEntry 35 }

fjdaryIoamluLCU34 OBJECT-TYPE
    SYNTAX OCTET STRING
    ACCESS read-only
    STATUS mandatory
    DESCRIPTION
        "The value of this object indicates the LCU-CA-IOA mapping information
         table of this system.
         LCU#17 IOA#0-#127 MLU mapping table
                  byte 0       byte 1       byte 2       byte 3
              +------------+------------+------------+------------+
          0x00| IOA#0-MLU#              | IOA#1-MLU#              |
              +------------+------------+------------+------------+
              ~                                                   ~
              +------------+------------+------------+------------+
          0xfc| IOA#126-MLU#            | IOA#127-MLU#            |
              +------------+------------+------------+------------+"
    ::= { fjdaryIoamluEntry 36 }

fjdaryIoamluLCU35 OBJECT-TYPE
    SYNTAX OCTET STRING
    ACCESS read-only
    STATUS mandatory
    DESCRIPTION
        "The value of this object indicates the LCU-CA-IOA mapping information
         table of this system.
         LCU#17 IOA#128-#255 MLU mapping table
                  byte 0       byte 1       byte 2       byte 3
              +------------+------------+------------+------------+
          0x00| IOA#128-MLU#            | IOA#129-MLU#            |
              +------------+------------+------------+------------+
              ~                                                   ~
              +------------+------------+------------+------------+
          0xfc| IOA#254-MLU#            | IOA#255-MLU#            |
              +------------+------------+------------+------------+"
    ::= { fjdaryIoamluEntry 37 }

fjdaryIoamluLCU36 OBJECT-TYPE
    SYNTAX OCTET STRING
    ACCESS read-only
    STATUS mandatory
    DESCRIPTION
        "The value of this object indicates the LCU-CA-IOA mapping information
         table of this system.
         LCU#18 IOA#0-#127 MLU mapping table
                  byte 0       byte 1       byte 2       byte 3
              +------------+------------+------------+------------+
          0x00| IOA#0-MLU#              | IOA#1-MLU#              |
              +------------+------------+------------+------------+
              ~                                                   ~
              +------------+------------+------------+------------+
          0xfc| IOA#126-MLU#            | IOA#127-MLU#            |
              +------------+------------+------------+------------+"
    ::= { fjdaryIoamluEntry 38 }

fjdaryIoamluLCU37 OBJECT-TYPE
    SYNTAX OCTET STRING
    ACCESS read-only
    STATUS mandatory
    DESCRIPTION
        "The value of this object indicates the LCU-CA-IOA mapping information
         table of this system.
         LCU#18 IOA#128-#255 MLU mapping table
                  byte 0       byte 1       byte 2       byte 3
              +------------+------------+------------+------------+
          0x00| IOA#128-MLU#            | IOA#129-MLU#            |
              +------------+------------+------------+------------+
              ~                                                   ~
              +------------+------------+------------+------------+
          0xfc| IOA#254-MLU#            | IOA#255-MLU#            |
              +------------+------------+------------+------------+"
    ::= { fjdaryIoamluEntry 39 }

fjdaryIoamluLCU38 OBJECT-TYPE
    SYNTAX OCTET STRING
    ACCESS read-only
    STATUS mandatory
    DESCRIPTION
        "The value of this object indicates the LCU-CA-IOA mapping information
         table of this system.
         LCU#19 IOA#0-#127 MLU mapping table
                  byte 0       byte 1       byte 2       byte 3
              +------------+------------+------------+------------+
          0x00| IOA#0-MLU#              | IOA#1-MLU#              |
              +------------+------------+------------+------------+
              ~                                                   ~
              +------------+------------+------------+------------+
          0xfc| IOA#126-MLU#            | IOA#127-MLU#            |
              +------------+------------+------------+------------+"
    ::= { fjdaryIoamluEntry 40 }

fjdaryIoamluLCU39 OBJECT-TYPE
    SYNTAX OCTET STRING
    ACCESS read-only
    STATUS mandatory
    DESCRIPTION
        "The value of this object indicates the LCU-CA-IOA mapping information
         table of this system.
         LCU#19 IOA#128-#255 MLU mapping table
                  byte 0       byte 1       byte 2       byte 3
              +------------+------------+------------+------------+
          0x00| IOA#128-MLU#            | IOA#129-MLU#            |
              +------------+------------+------------+------------+
              ~                                                   ~
              +------------+------------+------------+------------+
          0xfc| IOA#254-MLU#            | IOA#255-MLU#            |
              +------------+------------+------------+------------+"
    ::= { fjdaryIoamluEntry 41 }

fjdaryIoamluLCU40 OBJECT-TYPE
    SYNTAX OCTET STRING
    ACCESS read-only
    STATUS mandatory
    DESCRIPTION
        "The value of this object indicates the LCU-CA-IOA mapping information
         table of this system.
         LCU#20 IOA#0-#127 MLU mapping table
                  byte 0       byte 1       byte 2       byte 3
              +------------+------------+------------+------------+
          0x00| IOA#0-MLU#              | IOA#1-MLU#              |
              +------------+------------+------------+------------+
              ~                                                   ~
              +------------+------------+------------+------------+
          0xfc| IOA#126-MLU#            | IOA#127-MLU#            |
              +------------+------------+------------+------------+"
    ::= { fjdaryIoamluEntry 42 }

fjdaryIoamluLCU41 OBJECT-TYPE
    SYNTAX OCTET STRING
    ACCESS read-only
    STATUS mandatory
    DESCRIPTION
        "The value of this object indicates the LCU-CA-IOA mapping information
         table of this system.
         LCU#20 IOA#128-#255 MLU mapping table
                  byte 0       byte 1       byte 2       byte 3
              +------------+------------+------------+------------+
          0x00| IOA#128-MLU#            | IOA#129-MLU#            |
              +------------+------------+------------+------------+
              ~                                                   ~
              +------------+------------+------------+------------+
          0xfc| IOA#254-MLU#            | IOA#255-MLU#            |
              +------------+------------+------------+------------+"
    ::= { fjdaryIoamluEntry 43 }

fjdaryIoamluLCU42 OBJECT-TYPE
    SYNTAX OCTET STRING
    ACCESS read-only
    STATUS mandatory
    DESCRIPTION
        "The value of this object indicates the LCU-CA-IOA mapping information
         table of this system.
         LCU#21 IOA#0-#127 MLU mapping table
                  byte 0       byte 1       byte 2       byte 3
              +------------+------------+------------+------------+
          0x00| IOA#0-MLU#              | IOA#1-MLU#              |
              +------------+------------+------------+------------+
              ~                                                   ~
              +------------+------------+------------+------------+
          0xfc| IOA#126-MLU#            | IOA#127-MLU#            |
              +------------+------------+------------+------------+"
    ::= { fjdaryIoamluEntry 44 }

fjdaryIoamluLCU43 OBJECT-TYPE
    SYNTAX OCTET STRING
    ACCESS read-only
    STATUS mandatory
    DESCRIPTION
        "The value of this object indicates the LCU-CA-IOA mapping information
         table of this system.
         LCU#21 IOA#128-#255 MLU mapping table
                  byte 0       byte 1       byte 2       byte 3
              +------------+------------+------------+------------+
          0x00| IOA#128-MLU#            | IOA#129-MLU#            |
              +------------+------------+------------+------------+
              ~                                                   ~
              +------------+------------+------------+------------+
          0xfc| IOA#254-MLU#            | IOA#255-MLU#            |
              +------------+------------+------------+------------+"
    ::= { fjdaryIoamluEntry 45 }

fjdaryIoamluLCU44 OBJECT-TYPE
    SYNTAX OCTET STRING
    ACCESS read-only
    STATUS mandatory
    DESCRIPTION
        "The value of this object indicates the LCU-CA-IOA mapping information
         table of this system.
         LCU#22 IOA#0-#127 MLU mapping table
                  byte 0       byte 1       byte 2       byte 3
              +------------+------------+------------+------------+
          0x00| IOA#0-MLU#              | IOA#1-MLU#              |
              +------------+------------+------------+------------+
              ~                                                   ~
              +------------+------------+------------+------------+
          0xfc| IOA#126-MLU#            | IOA#127-MLU#            |
              +------------+------------+------------+------------+"
    ::= { fjdaryIoamluEntry 46 }

fjdaryIoamluLCU45 OBJECT-TYPE
    SYNTAX OCTET STRING
    ACCESS read-only
    STATUS mandatory
    DESCRIPTION
        "The value of this object indicates the LCU-CA-IOA mapping information
         table of this system.
         LCU#22 IOA#128-#255 MLU mapping table
                  byte 0       byte 1       byte 2       byte 3
              +------------+------------+------------+------------+
          0x00| IOA#128-MLU#            | IOA#129-MLU#            |
              +------------+------------+------------+------------+
              ~                                                   ~
              +------------+------------+------------+------------+
          0xfc| IOA#254-MLU#            | IOA#255-MLU#            |
              +------------+------------+------------+------------+"
    ::= { fjdaryIoamluEntry 47 }

fjdaryIoamluLCU46 OBJECT-TYPE
    SYNTAX OCTET STRING
    ACCESS read-only
    STATUS mandatory
    DESCRIPTION
        "The value of this object indicates the LCU-CA-IOA mapping information
         table of this system.
         LCU#23 IOA#0-#127 MLU mapping table
                  byte 0       byte 1       byte 2       byte 3
              +------------+------------+------------+------------+
          0x00| IOA#0-MLU#              | IOA#1-MLU#              |
              +------------+------------+------------+------------+
              ~                                                   ~
              +------------+------------+------------+------------+
          0xfc| IOA#126-MLU#            | IOA#127-MLU#            |
              +------------+------------+------------+------------+"
    ::= { fjdaryIoamluEntry 48 }

fjdaryIoamluLCU47 OBJECT-TYPE
    SYNTAX OCTET STRING
    ACCESS read-only
    STATUS mandatory
    DESCRIPTION
        "The value of this object indicates the LCU-CA-IOA mapping information
         table of this system.
         LCU#23 IOA#128-#255 MLU mapping table
                  byte 0       byte 1       byte 2       byte 3
              +------------+------------+------------+------------+
          0x00| IOA#128-MLU#            | IOA#129-MLU#            |
              +------------+------------+------------+------------+
              ~                                                   ~
              +------------+------------+------------+------------+
          0xfc| IOA#254-MLU#            | IOA#255-MLU#            |
              +------------+------------+------------+------------+"
    ::= { fjdaryIoamluEntry 49 }

fjdaryIoamluLCU48 OBJECT-TYPE
    SYNTAX OCTET STRING
    ACCESS read-only
    STATUS mandatory
    DESCRIPTION
        "The value of this object indicates the LCU-CA-IOA mapping information
         table of this system.
         LCU#24 IOA#0-#127 MLU mapping table
                  byte 0       byte 1       byte 2       byte 3
              +------------+------------+------------+------------+
          0x00| IOA#0-MLU#              | IOA#1-MLU#              |
              +------------+------------+------------+------------+
              ~                                                   ~
              +------------+------------+------------+------------+
          0xfc| IOA#126-MLU#            | IOA#127-MLU#            |
              +------------+------------+------------+------------+"
    ::= { fjdaryIoamluEntry 50 }

fjdaryIoamluLCU49 OBJECT-TYPE
    SYNTAX OCTET STRING
    ACCESS read-only
    STATUS mandatory
    DESCRIPTION
        "The value of this object indicates the LCU-CA-IOA mapping information
         table of this system.
         LCU#24 IOA#128-#255 MLU mapping table
                  byte 0       byte 1       byte 2       byte 3
              +------------+------------+------------+------------+
          0x00| IOA#128-MLU#            | IOA#129-MLU#            |
              +------------+------------+------------+------------+
              ~                                                   ~
              +------------+------------+------------+------------+
          0xfc| IOA#254-MLU#            | IOA#255-MLU#            |
              +------------+------------+------------+------------+"
    ::= { fjdaryIoamluEntry 51 }

fjdaryIoamluLCU50 OBJECT-TYPE
    SYNTAX OCTET STRING
    ACCESS read-only
    STATUS mandatory
    DESCRIPTION
        "The value of this object indicates the LCU-CA-IOA mapping information
         table of this system.
         LCU#25 IOA#0-#127 MLU mapping table
                  byte 0       byte 1       byte 2       byte 3
              +------------+------------+------------+------------+
          0x00| IOA#0-MLU#              | IOA#1-MLU#              |
              +------------+------------+------------+------------+
              ~                                                   ~
              +------------+------------+------------+------------+
          0xfc| IOA#126-MLU#            | IOA#127-MLU#            |
              +------------+------------+------------+------------+"
    ::= { fjdaryIoamluEntry 52 }

fjdaryIoamluLCU51 OBJECT-TYPE
    SYNTAX OCTET STRING
    ACCESS read-only
    STATUS mandatory
    DESCRIPTION
        "The value of this object indicates the LCU-CA-IOA mapping information
         table of this system.
         LCU#25 IOA#128-#255 MLU mapping table
                  byte 0       byte 1       byte 2       byte 3
              +------------+------------+------------+------------+
          0x00| IOA#128-MLU#            | IOA#129-MLU#            |
              +------------+------------+------------+------------+
              ~                                                   ~
              +------------+------------+------------+------------+
          0xfc| IOA#254-MLU#            | IOA#255-MLU#            |
              +------------+------------+------------+------------+"
    ::= { fjdaryIoamluEntry 53 }

fjdaryIoamluLCU52 OBJECT-TYPE
    SYNTAX OCTET STRING
    ACCESS read-only
    STATUS mandatory
    DESCRIPTION
        "The value of this object indicates the LCU-CA-IOA mapping information
         table of this system.
         LCU#26 IOA#0-#127 MLU mapping table
                  byte 0       byte 1       byte 2       byte 3
              +------------+------------+------------+------------+
          0x00| IOA#0-MLU#              | IOA#1-MLU#              |
              +------------+------------+------------+------------+
              ~                                                   ~
              +------------+------------+------------+------------+
          0xfc| IOA#126-MLU#            | IOA#127-MLU#            |
              +------------+------------+------------+------------+"
    ::= { fjdaryIoamluEntry 54 }

fjdaryIoamluLCU53 OBJECT-TYPE
    SYNTAX OCTET STRING
    ACCESS read-only
    STATUS mandatory
    DESCRIPTION
        "The value of this object indicates the LCU-CA-IOA mapping information
         table of this system.
         LCU#26 IOA#128-#255 MLU mapping table
                  byte 0       byte 1       byte 2       byte 3
              +------------+------------+------------+------------+
          0x00| IOA#128-MLU#            | IOA#129-MLU#            |
              +------------+------------+------------+------------+
              ~                                                   ~
              +------------+------------+------------+------------+
          0xfc| IOA#254-MLU#            | IOA#255-MLU#            |
              +------------+------------+------------+------------+"
    ::= { fjdaryIoamluEntry 55 }

fjdaryIoamluLCU54 OBJECT-TYPE
    SYNTAX OCTET STRING
    ACCESS read-only
    STATUS mandatory
    DESCRIPTION
        "The value of this object indicates the LCU-CA-IOA mapping information
         table of this system.
         LCU#27 IOA#0-#127 MLU mapping table
                  byte 0       byte 1       byte 2       byte 3
              +------------+------------+------------+------------+
          0x00| IOA#0-MLU#              | IOA#1-MLU#              |
              +------------+------------+------------+------------+
              ~                                                   ~
              +------------+------------+------------+------------+
          0xfc| IOA#126-MLU#            | IOA#127-MLU#            |
              +------------+------------+------------+------------+"
    ::= { fjdaryIoamluEntry 56 }

fjdaryIoamluLCU55 OBJECT-TYPE
    SYNTAX OCTET STRING
    ACCESS read-only
    STATUS mandatory
    DESCRIPTION
        "The value of this object indicates the LCU-CA-IOA mapping information
         table of this system.
         LCU#27 IOA#128-#255 MLU mapping table
                  byte 0       byte 1       byte 2       byte 3
              +------------+------------+------------+------------+
          0x00| IOA#128-MLU#            | IOA#129-MLU#            |
              +------------+------------+------------+------------+
              ~                                                   ~
              +------------+------------+------------+------------+
          0xfc| IOA#254-MLU#            | IOA#255-MLU#            |
              +------------+------------+------------+------------+"
    ::= { fjdaryIoamluEntry 57 }

fjdaryIoamluLCU56 OBJECT-TYPE
    SYNTAX OCTET STRING
    ACCESS read-only
    STATUS mandatory
    DESCRIPTION
        "The value of this object indicates the LCU-CA-IOA mapping information
         table of this system.
         LCU#28 IOA#0-#127 MLU mapping table
                  byte 0       byte 1       byte 2       byte 3
              +------------+------------+------------+------------+
          0x00| IOA#0-MLU#              | IOA#1-MLU#              |
              +------------+------------+------------+------------+
              ~                                                   ~
              +------------+------------+------------+------------+
          0xfc| IOA#126-MLU#            | IOA#127-MLU#            |
              +------------+------------+------------+------------+"
    ::= { fjdaryIoamluEntry 58 }

fjdaryIoamluLCU57 OBJECT-TYPE
    SYNTAX OCTET STRING
    ACCESS read-only
    STATUS mandatory
    DESCRIPTION
        "The value of this object indicates the LCU-CA-IOA mapping information
         table of this system.
         LCU#28 IOA#128-#255 MLU mapping table
                  byte 0       byte 1       byte 2       byte 3
              +------------+------------+------------+------------+
          0x00| IOA#128-MLU#            | IOA#129-MLU#            |
              +------------+------------+------------+------------+
              ~                                                   ~
              +------------+------------+------------+------------+
          0xfc| IOA#254-MLU#            | IOA#255-MLU#            |
              +------------+------------+------------+------------+"
    ::= { fjdaryIoamluEntry 59 }

fjdaryIoamluLCU58 OBJECT-TYPE
    SYNTAX OCTET STRING
    ACCESS read-only
    STATUS mandatory
    DESCRIPTION
        "The value of this object indicates the LCU-CA-IOA mapping information
         table of this system.
         LCU#29 IOA#0-#127 MLU mapping table
                  byte 0       byte 1       byte 2       byte 3
              +------------+------------+------------+------------+
          0x00| IOA#0-MLU#              | IOA#1-MLU#              |
              +------------+------------+------------+------------+
              ~                                                   ~
              +------------+------------+------------+------------+
          0xfc| IOA#126-MLU#            | IOA#127-MLU#            |
              +------------+------------+------------+------------+"
    ::= { fjdaryIoamluEntry 60 }

fjdaryIoamluLCU59 OBJECT-TYPE
    SYNTAX OCTET STRING
    ACCESS read-only
    STATUS mandatory
    DESCRIPTION
        "The value of this object indicates the LCU-CA-IOA mapping information
         table of this system.
         LCU#29 IOA#128-#255 MLU mapping table
                  byte 0       byte 1       byte 2       byte 3
              +------------+------------+------------+------------+
          0x00| IOA#128-MLU#            | IOA#129-MLU#            |
              +------------+------------+------------+------------+
              ~                                                   ~
              +------------+------------+------------+------------+
          0xfc| IOA#254-MLU#            | IOA#255-MLU#            |
              +------------+------------+------------+------------+"
    ::= { fjdaryIoamluEntry 61 }

fjdaryIoamluLCU60 OBJECT-TYPE
    SYNTAX OCTET STRING
    ACCESS read-only
    STATUS mandatory
    DESCRIPTION
        "The value of this object indicates the LCU-CA-IOA mapping information
         table of this system.
         LCU#30 IOA#0-#127 MLU mapping table
                  byte 0       byte 1       byte 2       byte 3
              +------------+------------+------------+------------+
          0x00| IOA#0-MLU#              | IOA#1-MLU#              |
              +------------+------------+------------+------------+
              ~                                                   ~
              +------------+------------+------------+------------+
          0xfc| IOA#126-MLU#            | IOA#127-MLU#            |
              +------------+------------+------------+------------+"
    ::= { fjdaryIoamluEntry 62 }

fjdaryIoamluLCU61 OBJECT-TYPE
    SYNTAX OCTET STRING
    ACCESS read-only
    STATUS mandatory
    DESCRIPTION
        "The value of this object indicates the LCU-CA-IOA mapping information
         table of this system.
         LCU#30 IOA#128-#255 MLU mapping table
                  byte 0       byte 1       byte 2       byte 3
              +------------+------------+------------+------------+
          0x00| IOA#128-MLU#            | IOA#129-MLU#            |
              +------------+------------+------------+------------+
              ~                                                   ~
              +------------+------------+------------+------------+
          0xfc| IOA#254-MLU#            | IOA#255-MLU#            |
              +------------+------------+------------+------------+"
    ::= { fjdaryIoamluEntry 63 }

fjdaryIoamluLCU62 OBJECT-TYPE
    SYNTAX OCTET STRING
    ACCESS read-only
    STATUS mandatory
    DESCRIPTION
        "The value of this object indicates the LCU-CA-IOA mapping information
         table of this system.
         LCU#31 IOA#0-#127 MLU mapping table
                  byte 0       byte 1       byte 2       byte 3
              +------------+------------+------------+------------+
          0x00| IOA#0-MLU#              | IOA#1-MLU#              |
              +------------+------------+------------+------------+
              ~                                                   ~
              +------------+------------+------------+------------+
          0xfc| IOA#126-MLU#            | IOA#127-MLU#            |
              +------------+------------+------------+------------+"
    ::= { fjdaryIoamluEntry 64 }

fjdaryIoamluLCU63 OBJECT-TYPE
    SYNTAX OCTET STRING
    ACCESS read-only
    STATUS mandatory
    DESCRIPTION
        "The value of this object indicates the LCU-CA-IOA mapping information
         table of this system.
         LCU#31 IOA#128-#255 MLU mapping table
                  byte 0       byte 1       byte 2       byte 3
              +------------+------------+------------+------------+
          0x00| IOA#128-MLU#            | IOA#129-MLU#            |
              +------------+------------+------------+------------+
              ~                                                   ~
              +------------+------------+------------+------------+
          0xfc| IOA#254-MLU#            | IOA#255-MLU#            |
              +------------+------------+------------+------------+"
    ::= { fjdaryIoamluEntry 65 }

-------------------------------------------------------------------------------
--   fjdaryHostiscsi                                                         --
-------------------------------------------------------------------------------
fjdaryHostiscsiCount OBJECT-TYPE
    SYNTAX INTEGER
    ACCESS read-only
    STATUS mandatory
    DESCRIPTION
        "The number of host iscsi configuration table entries."
    ::= { fjdaryHostiscsi 1 }

fjdaryHostiscsiTable OBJECT-TYPE
    SYNTAX SEQUENCE OF FjdaryHostiscsiEntry
    ACCESS not-accessible
    STATUS mandatory
    DESCRIPTION
        ""
    ::= { fjdaryHostiscsi 2 }

fjdaryHostiscsiEntry OBJECT-TYPE
    SYNTAX FjdaryHostiscsiEntry
    ACCESS not-accessible
    STATUS mandatory
    DESCRIPTION
        ""
    INDEX { fjdaryHostiscsiIndex }
    ::= { fjdaryHostiscsiTable 1 }

FjdaryHostiscsiEntry ::=
    SEQUENCE{
        fjdaryHostiscsiIndex     INTEGER,
        fjdaryHostiscsiDefine    OCTET STRING,
        fjdaryHostiscsiName      OCTET STRING,
        fjdaryHostiscsiAliasName OCTET STRING,
        fjdaryHostiscsiIpAddress IpAddress
    }

fjdaryHostiscsiIndex OBJECT-TYPE
    SYNTAX INTEGER
    ACCESS read-only
    STATUS mandatory
    DESCRIPTION
        "The value of this object uniquely identifies this fjdaryHostiscsi
         entry. This value ranges are from 0 to the value of
         fjdaryHostiscsiCount-1."
    ::= { fjdaryHostiscsiEntry 1 }

fjdaryHostiscsiDefine OBJECT-TYPE
    SYNTAX OCTET STRING
    ACCESS read-only
    STATUS mandatory
    DESCRIPTION
        "This object shows hostiscsi.
                  byte 0      byte 1      byte 2      byte 3
              +-----------+-----------+-----------+-----------+
          0x00| Reserved (12 bytes)                           |
              ~                                               ~
          0x08|                                               |
              +-----------+-----------+-----------+-----------+
          0x0c| Host Response Table No| Valid Flag| Reserved  |
              +-----------+-----------+-----------+-----------+
          0x10| Reserved (16 bytes)                           |
              ~                                               ~
          0x1c|                                               |
              +-----------+-----------+-----------+-----------+"
    ::= { fjdaryHostiscsiEntry 2 }

fjdaryHostiscsiName OBJECT-TYPE
    SYNTAX OCTET STRING
    ACCESS read-only
    STATUS mandatory
    DESCRIPTION
        "The value of this object shows iscsi name of a host."
    ::= { fjdaryHostiscsiEntry 3 }

fjdaryHostiscsiAliasName OBJECT-TYPE
    SYNTAX OCTET STRING
    ACCESS read-only
    STATUS mandatory
    DESCRIPTION
        "The value of this object shows alias name of a host."
    ::= { fjdaryHostiscsiEntry 4 }

fjdaryHostiscsiIpAddress OBJECT-TYPE
    SYNTAX IpAddress
    ACCESS read-only
    STATUS mandatory
    DESCRIPTION
        "The value of this object shows ip address of a host."
    ::= { fjdaryHostiscsiEntry 5 }

-------------------------------------------------------------------------------
--   fjdaryHostResponse                                                      --
-------------------------------------------------------------------------------
fjdaryHostResponseCount OBJECT-TYPE
    SYNTAX INTEGER
    ACCESS read-only
    STATUS mandatory
    DESCRIPTION
        "The number of host response informations entry (regardless of their
         current state) present on this system."
    ::= { fjdaryHostResponse 1 }

fjdaryHostResponseTable OBJECT-TYPE
    SYNTAX SEQUENCE OF FjdaryHostResponseEntry
    ACCESS not-accessible
    STATUS mandatory
    DESCRIPTION
        ""
    ::= { fjdaryHostResponse 2 }

fjdaryHostResponseEntry OBJECT-TYPE
    SYNTAX FjdaryHostResponseEntry
    ACCESS not-accessible
    STATUS mandatory
    DESCRIPTION
        ""
    INDEX { fjdaryHostResponseIndex }
    ::= { fjdaryHostResponseTable 1 }

FjdaryHostResponseEntry ::=
    SEQUENCE{
        fjdaryHostResponseIndex     INTEGER,
        fjdaryHostResponseInfoTable OCTET STRING
    }

fjdaryHostResponseIndex OBJECT-TYPE
    SYNTAX INTEGER
    ACCESS read-only
    STATUS mandatory
    DESCRIPTION
        "The value of this object uniquely identifies this fjdaryHostResponse
         entry."
    ::= { fjdaryHostResponseEntry 1 }

fjdaryHostResponseInfoTable OBJECT-TYPE
    SYNTAX OCTET STRING
    ACCESS read-only
    STATUS mandatory
    DESCRIPTION
        "The value of this object indicates the host response information of
         this system.
                  byte 0       byte 1       byte 2       byte 3
              +------------+------------+------------+------------+
          0x00| Table No                | Valid Flag | Reserved   |
              +------------+------------+------------+------------+
          0x04| Host Response Name (16 bytes)                     |
              ~                                                   ~
          0x10|                                                   |
              +------------+------------+------------+------------+
          0x14| Reserved                                          |
              +------------+------------+------------+------------+
          0x18| SCC Mode   |Host Cmd T.O| Sense Ctrl              |
              +------------+------------+------------+------------+
          0x1c| Ope Mode   | Reserved                             |
              +------------+------------+------------+------------+
          0x20| Status Ctrl| Reserved                             |
              +------------+------------+------------+------------+
          0x24| Reserved (24 bytes)                               |
              ~                                                   ~
          0x3c|                                                   |
              +------------+------------+------------+------------+
          0x40|Inquiry Mode|Inquiry Type|Inquiry Ver.| Reserved   |
              +------------+------------+------------+------------+
          0x44| Reserved                                          |
              +------------+------------+------------+------------+
          0x48| Entry Sense| Entry Sense| Entry Sense| Entry Sense|
              |  Key#0     |  Code#0    |  SubCode#0 |  ConvBit#0 |
              +------------+------------+------------+------------+
          0x4c| ReportSense| ReportSense| ReportSense| ReportSense|
              |  Key#0     |  Code#0    |  SubCode#0 |  ConvBit#0 |
              +------------+------------+------------+------------+
              ~                                                   ~
              +------------+------------+------------+------------+
          0x80| Entry Sense| Entry Sense| Entry Sense| Entry Sense|
              |  Key#7     |  Code#7    |  SubCode#7 |  ConvBit#7 |
              +------------+------------+------------+------------+
          0x84| ReportSense| ReportSense| ReportSense| ReportSense|
              |  Key#7     |  Code#7    |  SubCode#7 |  ConvBit#7 |
              +------------+------------+------------+------------+
          0x88| Reserved                                          |
              +                                                   +
          0x8c|                                                   |
              +------------+------------+------------+------------+"
    ::= { fjdaryHostResponseEntry 2 }

--***************************************************************************--
--   Firmware                                                                --
--***************************************************************************--
fjdaryFirmTotal OBJECT-TYPE
    SYNTAX OCTET STRING
    ACCESS read-only
    STATUS mandatory
    DESCRIPTION
        "The value of this object indicates the total firmware information.
                  byte 0       byte 1       byte 2       byte 3
              +------------+------------+------------+------------+
          0x00| Firmware Virsion        | Firmware Level          |
              +------------+------------+------------+------------+
          0x04| Firmware Suffix                                   |
              +------------+------------+------------+------------+"
    ::= { fjdaryFirm 1 }

--***************************************************************************--
--   Performance Information                                                 --
--***************************************************************************--
fjdaryPfheadInf OBJECT-TYPE
    SYNTAX OCTET STRING
    ACCESS read-only
    STATUS mandatory
    DESCRIPTION
        "Header that stores performance information.
                  byte 0       byte 1       byte 2       byte 3
              +------------+------------+------------+------------+
          0x00| Model Info | Reserved   | Version    | Level      |
              +------------+------------+------------+------------+
          0x04| Interval Time                                     |
              +------------+------------+------------+------------+
          0x08| Update Time                                       |
              +------------+------------+------------+------------+
          0x0c| Status     | Reserved                             |
              +------------+------------+------------+------------+
          0x10| Reserved (16 bytes)                               |
              ~                                                   ~
          0x1c|                                                   |
              +------------+------------+------------+------------+"
    ::= { fjdaryPfhead 1 }

-------------------------------------------------------------------------------
--   fjdaryPfopca                                                            --
-------------------------------------------------------------------------------
fjdaryPfopcaCount OBJECT-TYPE
    SYNTAX INTEGER
    ACCESS read-only
    STATUS mandatory
    DESCRIPTION
        "The number of OPEN-CA performance data table's entry on this system."
    ::= { fjdaryPfopca 1 }

fjdaryPfopcaTable OBJECT-TYPE
    SYNTAX SEQUENCE OF FjdaryPfopcaEntry
    ACCESS not-accessible
    STATUS mandatory
    DESCRIPTION
        ""
    ::= { fjdaryPfopca 2 }

fjdaryPfopcaEntry OBJECT-TYPE
    SYNTAX FjdaryPfopcaEntry
    ACCESS not-accessible
    STATUS mandatory
    DESCRIPTION
        ""
    INDEX { fjdaryPfopcaIndex }
    ::= { fjdaryPfopcaTable 1 }

FjdaryPfopcaEntry ::=
    SEQUENCE{
        fjdaryPfopcaIndex INTEGER,
        fjdaryPfopcaInfo0 OCTET STRING,
        fjdaryPfopcaInfo1 OCTET STRING
    }

fjdaryPfopcaIndex OBJECT-TYPE
    SYNTAX INTEGER
    ACCESS read-only
    STATUS mandatory
    DESCRIPTION
        "The value of this object uniquely identifies this fjdaryPfopca entry."
    ::= { fjdaryPfopcaEntry 1 }

fjdaryPfopcaInfo0 OBJECT-TYPE
    SYNTAX OCTET STRING
    ACCESS read-only
    STATUS mandatory
    DESCRIPTION
        "The value of this object indicates the OPEN-CA Info#0-#1 performance
         data.
                  byte 0       byte 1       byte 2       byte 3
              +------------+------------+------------+------------+
          0x00| OPEN-CA Info#0 (128 bytes)                        |
              +------------+------------+------------+------------+
          0x80| OPEN-CA Info#1 (128 bytes)                        |
              +------------+------------+------------+------------+
         OPEN-CA Info:
                  byte 0       byte 1       byte 2       byte 3
              +------------+------------+------------+------------+
          0x00| OPEN-CA ISP Info#0 (64 bytes)                     |
              +------------+------------+------------+------------+
          0x40| OPEN-CA ISP Info#1 (64 bytes)                     |
              +------------+------------+------------+------------+
         OPEN-CA ISP Info:
                  byte 0       byte 1       byte 2       byte 3
              +------------+------------+------------+------------+
          0x00| OPEN-CA Port Info#0 (32 bytes)                    |
              +------------+------------+------------+------------+
          0x20| OPEN-CA Port Info#1 (32 bytes)                    |
              +------------+------------+------------+------------+
         OPEN-CA Port Info:
                  byte 0       byte 1       byte 2       byte 3
              +------------+------------+------------+------------+
          0x00| Read Command Count                                |
              +------------+------------+------------+------------+
          0x04| Write Command Count                               |
              +------------+------------+------------+------------+
          0x08| Read Block Count                                  |
              +------------+------------+------------+------------+
          0x0c| Write Block Count                                 |
              +------------+------------+------------+------------+
          0x10| Reserved (16 bytes)                               |
              ~                                                   ~
          0x1c|                                                   |
              +------------+------------+------------+------------+
         OPEN-CA Port Info (RA Mode):
                  byte 0       byte 1       byte 2       byte 3
              +------------+------------+------------+------------+
          0x00| Initiator Command Count                           |
              +------------+------------+------------+------------+
          0x04| Target Command Count                              |
              +------------+------------+------------+------------+
          0x08| Initiator Block Count                             |
              +------------+------------+------------+------------+
          0x0c| Target Block Count                                |
              +------------+------------+------------+------------+
          0x10| Reserved (16 bytes)                               |
              ~                                                   ~
          0x1c|                                                   |
              +------------+------------+------------+------------+"
    ::= { fjdaryPfopcaEntry 2 }

fjdaryPfopcaInfo1 OBJECT-TYPE
    SYNTAX OCTET STRING
    ACCESS read-only
    STATUS mandatory
    DESCRIPTION
        "The value of this object indicates the OPEN-CA Info#2-#3 performance
         data.
                  byte 0       byte 1       byte 2       byte 3
              +------------+------------+------------+------------+
          0x00| OPEN-CA Info#2 (128 bytes)                        |
              +------------+------------+------------+------------+
          0x80| OPEN-CA Info#3 (128 bytes)                        |
              +------------+------------+------------+------------+"
    ::= { fjdaryPfopcaEntry 3 }

-------------------------------------------------------------------------------
--   fjdaryPfocca                                                            --
-------------------------------------------------------------------------------
fjdaryPfoccaCount OBJECT-TYPE
    SYNTAX INTEGER
    ACCESS read-only
    STATUS mandatory
    DESCRIPTION
        "The number of OCLINK-CA performance data table's entry on this
         system."
    ::= { fjdaryPfocca 1 }

fjdaryPfoccaTable OBJECT-TYPE
    SYNTAX SEQUENCE OF FjdaryPfoccaEntry
    ACCESS not-accessible
    STATUS mandatory
    DESCRIPTION
        ""
    ::= { fjdaryPfocca 2 }

fjdaryPfoccaEntry OBJECT-TYPE
    SYNTAX FjdaryPfoccaEntry
    ACCESS not-accessible
    STATUS mandatory
    DESCRIPTION
        ""
    INDEX { fjdaryPfoccaIndex }
    ::= { fjdaryPfoccaTable 1 }

FjdaryPfoccaEntry ::=
    SEQUENCE{
        fjdaryPfoccaIndex INTEGER,
        fjdaryPfoccaInfo  OCTET STRING
    }

fjdaryPfoccaIndex OBJECT-TYPE
    SYNTAX INTEGER
    ACCESS read-only
    STATUS mandatory
    DESCRIPTION
        "The value of this object uniquely identifies this fjdaryPfocca entry."
    ::= { fjdaryPfoccaEntry 1 }

fjdaryPfoccaInfo OBJECT-TYPE
    SYNTAX OCTET STRING
    ACCESS read-only
    STATUS mandatory
    DESCRIPTION
        "The value of this object indicates the OCLINK-CA performance data.
                  byte 0       byte 1       byte 2       byte 3
              +------------+------------+------------+------------+
          0x00| Total CPU Time                                    |
              +------------+------------+------------+------------+
          0x04| Idle CPU Time                                     |
              +------------+------------+------------+------------+
          0x08| Reserved                                          |
              +                                                   +
          0x0c|                                                   |
              +------------+------------+------------+------------+
          0x10| Initial Selection Count                           |
              +------------+------------+------------+------------+
          0x14| Reconnection Count by CM                          |
              +------------+------------+------------+------------+
          0x18| Reconnection Count by I/O                         |
              +------------+------------+------------+------------+
          0x1c| Reconnection Count by Async                       |
              +------------+------------+------------+------------+
          0x20| Cancel Reconnection Count by CM                   |
              +------------+------------+------------+------------+
          0x24| Cancel Reconnection Count by CA                   |
              +------------+------------+------------+------------+
          0x28| Host Connect Time                                 |
              +------------+------------+------------+------------+
          0x2c| CM Connect Time                                   |
              +------------+------------+------------+------------+
          0x30| Host Read Byte Count                              |
              +                                                   +
          0x34|                                                   |
              +------------+------------+------------+------------+
          0x38| CM Read Byte Count                                |
              +                                                   +
          0x3c|                                                   |
              +------------+------------+------------+------------+
          0x40| Host Write Byte Count                             |
              +                                                   +
          0x44|                                                   |
              +------------+------------+------------+------------+
          0x48| CM Write Byte Count                               |
              +                                                   +
          0x4c|                                                   |
              +------------+------------+------------+------------+"
    ::= { fjdaryPfoccaEntry 2 }

-------------------------------------------------------------------------------
--   fjdaryPfflca                                                            --
-------------------------------------------------------------------------------
fjdaryPfflcaCount OBJECT-TYPE
    SYNTAX INTEGER
    ACCESS read-only
    STATUS mandatory
    DESCRIPTION
        "The number of FCLINK-CA performance data table's entry on this
         system."
    ::= { fjdaryPfflca 1 }

fjdaryPfflcaTable OBJECT-TYPE
    SYNTAX SEQUENCE OF FjdaryPfflcaEntry
    ACCESS not-accessible
    STATUS mandatory
    DESCRIPTION
        ""
    ::= { fjdaryPfflca 2 }

fjdaryPfflcaEntry OBJECT-TYPE
    SYNTAX FjdaryPfflcaEntry
    ACCESS not-accessible
    STATUS mandatory
    DESCRIPTION
        ""
    INDEX { fjdaryPfflcaIndex }
    ::= { fjdaryPfflcaTable 1 }

FjdaryPfflcaEntry ::=
    SEQUENCE{
        fjdaryPfflcaIndex INTEGER,
        fjdaryPfflcaInfo  OCTET STRING
    }

fjdaryPfflcaIndex OBJECT-TYPE
    SYNTAX INTEGER
    ACCESS read-only
    STATUS mandatory
    DESCRIPTION
        "The value of this object uniquely identifies this fjdaryPfflca entry."
    ::= { fjdaryPfflcaEntry 1 }

fjdaryPfflcaInfo OBJECT-TYPE
    SYNTAX OCTET STRING
    ACCESS read-only
    STATUS mandatory
    DESCRIPTION
        "The value of this object indicates the FCLINK-CA Info performance
         data.
                  byte 0       byte 1       byte 2       byte 3
              +------------+------------+------------+------------+
          0x00| FCLINK-CA Port Info#0 (64 bytes)                  |
              +------------+------------+------------+------------+
          0x40| FCLINK-CA Port Info#1 (64 bytes)                  |
              +------------+------------+------------+------------+
         FCLINK-CA Port Info:
                  byte 0       byte 1       byte 2       byte 3
              +------------+------------+------------+------------+
          0x00| Total CPU Time                                    |
              +------------+------------+------------+------------+
          0x04| Idle CPU Time                                     |
              +------------+------------+------------+------------+
          0x08| Reserved                                          |
              +                                                   +
          0x0c|                                                   |
              +------------+------------+------------+------------+
          0x10| Initial Selection Count                           |
              +------------+------------+------------+------------+
          0x14| Reconnection Count by I/O                         |
              +------------+------------+------------+------------+
          0x18| Reconnection Count by Async                       |
              +------------+------------+------------+------------+
          0x1c| Reserved                                          |
              +------------+------------+------------+------------+
          0x20| Host Read Byte Count                              |
              +                                                   +
          0x24|                                                   |
              +------------+------------+------------+------------+
          0x28| CM Read Byte Count                                |
              +                                                   +
          0x2c|                                                   |
              +------------+------------+------------+------------+
          0x30| Host Write Byte Count                             |
              +                                                   +
          0x34|                                                   |
              +------------+------------+------------+------------+
          0x38| CM Write Byte Count                               |
              +                                                   +
          0x3c|                                                   |
              +------------+------------+------------+------------+"
    ::= { fjdaryPfflcaEntry 2 }

-------------------------------------------------------------------------------
--   fjdaryPfdi                                                              --
-------------------------------------------------------------------------------
fjdaryPfdiCount OBJECT-TYPE
    SYNTAX INTEGER
    ACCESS read-only
    STATUS mandatory
    DESCRIPTION
        "The number of DI(drive interface) performance data table's entry on
         this system."
    ::= { fjdaryPfdi 1 }

fjdaryPfdiTable OBJECT-TYPE
    SYNTAX SEQUENCE OF FjdaryPfdiEntry
    ACCESS not-accessible
    STATUS mandatory
    DESCRIPTION
        ""
    ::= { fjdaryPfdi 2 }

fjdaryPfdiEntry OBJECT-TYPE
    SYNTAX FjdaryPfdiEntry
    ACCESS not-accessible
    STATUS mandatory
    DESCRIPTION
        ""
    INDEX { fjdaryPfdiIndex }
    ::= { fjdaryPfdiTable 1 }

FjdaryPfdiEntry ::=
    SEQUENCE{
        fjdaryPfdiIndex INTEGER,
        fjdaryPfdiInfo  OCTET STRING
    }

fjdaryPfdiIndex OBJECT-TYPE
    SYNTAX INTEGER
    ACCESS read-only
    STATUS mandatory
    DESCRIPTION
        "The value of this object uniquely identifies this fjdaryPfdi entry."
    ::= { fjdaryPfdiEntry 1 }

fjdaryPfdiInfo OBJECT-TYPE
    SYNTAX OCTET STRING
    ACCESS read-only
    STATUS mandatory
    DESCRIPTION
        "The value of this object indicates the DI performance data.
                  byte 0       byte 1       byte 2       byte 3
              +------------+------------+------------+------------+
          0x00| DI Port Info#0 (16 bytes)                         |
              +------------+------------+------------+------------+
          0x10| DI Port Info#1 (16 bytes)                         |
              +------------+------------+------------+------------+
              ~                                                   ~
              +------------+------------+------------+------------+
          0x70| DI Port Info#7 (16 bytes)                         |
              +------------+------------+------------+------------+
         DI Port Info:
                  byte 0       byte 1       byte 2       byte 3
              +------------+------------+------------+------------+
          0x00| Read Command Count                                |
              +------------+------------+------------+------------+
          0x04| Write Command Count                               |
              +------------+------------+------------+------------+
          0x08| Read Block Count                                  |
              +------------+------------+------------+------------+
          0x0c| Write Block Count                                 |
              +------------+------------+------------+------------+"
    ::= { fjdaryPfdiEntry 2 }

-------------------------------------------------------------------------------
--   fjdaryPfbrt                                                             --
-------------------------------------------------------------------------------
fjdaryPfbrtCount OBJECT-TYPE
    SYNTAX INTEGER
    ACCESS read-only
    STATUS mandatory
    DESCRIPTION
        "The number of BRT performance data table's entry on this system."
    ::= { fjdaryPfbrt 1 }

fjdaryPfbrtTable OBJECT-TYPE
    SYNTAX SEQUENCE OF FjdaryPfbrtEntry
    ACCESS not-accessible
    STATUS mandatory
    DESCRIPTION
        ""
    ::= { fjdaryPfbrt 2 }

fjdaryPfbrtEntry OBJECT-TYPE
    SYNTAX FjdaryPfbrtEntry
    ACCESS not-accessible
    STATUS mandatory
    DESCRIPTION
        ""
    INDEX { fjdaryPfbrtIndex }
    ::= { fjdaryPfbrtTable 1 }

FjdaryPfbrtEntry ::=
    SEQUENCE{
        fjdaryPfbrtIndex INTEGER,
        fjdaryPfbrtInfo0 OCTET STRING,
        fjdaryPfbrtInfo1 OCTET STRING,
        fjdaryPfbrtInfo2 OCTET STRING,
        fjdaryPfbrtInfo3 OCTET STRING
    }

fjdaryPfbrtIndex OBJECT-TYPE
    SYNTAX INTEGER
    ACCESS read-only
    STATUS mandatory
    DESCRIPTION
        "The value of this object uniquely identifies this fjdaryPfbrt entry."
    ::= { fjdaryPfbrtEntry 1 }

fjdaryPfbrtInfo0 OBJECT-TYPE
    SYNTAX OCTET STRING
    ACCESS read-only
    STATUS mandatory
    DESCRIPTION
        "The value of this object indicates the BRT Info#0-#15 performance
         data.
                  byte 0       byte 1       byte 2       byte 3
              +------------+------------+------------+------------+
          0x00| BRT Port Info#0 (16 bytes)                        |
              +------------+------------+------------+------------+
          0x10| BRT Port Info#1 (16 bytes)                        |
              +------------+------------+------------+------------+
              ~                                                   ~
              +------------+------------+------------+------------+
          0xf0| BRT Port Info#15 (16 bytes)                       |
              +------------+------------+------------+------------+
         BRT Port Info:
                  byte 0       byte 1       byte 2       byte 3
              +------------+------------+------------+------------+
          0x00| Read Command Count                                |
              +------------+------------+------------+------------+
          0x04| Write Command Count                               |
              +------------+------------+------------+------------+
          0x08| Read Block Count                                  |
              +------------+------------+------------+------------+
          0x0c| Write Block Count                                 |
              +------------+------------+------------+------------+"
    ::= { fjdaryPfbrtEntry 2 }

fjdaryPfbrtInfo1 OBJECT-TYPE
    SYNTAX OCTET STRING
    ACCESS read-only
    STATUS mandatory
    DESCRIPTION
        "The value of this object indicates the BRT Info#16-#31 performance
         data.
                  byte 0       byte 1       byte 2       byte 3
              +------------+------------+------------+------------+
          0x00| BRT Port Info#16 (16 bytes)                       |
              +------------+------------+------------+------------+
          0x10| BRT Port Info#17 (16 bytes)                       |
              +------------+------------+------------+------------+
              ~                                                   ~
              +------------+------------+------------+------------+
          0xf0| BRT Port Info#31 (16 bytes)                       |
              +------------+------------+------------+------------+"
    ::= { fjdaryPfbrtEntry 3 }

fjdaryPfbrtInfo2 OBJECT-TYPE
    SYNTAX OCTET STRING
    ACCESS read-only
    STATUS mandatory
    DESCRIPTION
        "The value of this object indicates the BRT Info#32-#47 performance
         data.
                  byte 0       byte 1       byte 2       byte 3
              +------------+------------+------------+------------+
          0x00| BRT Port Info#32 (16 bytes)                       |
              +------------+------------+------------+------------+
          0x10| BRT Port Info#33 (16 bytes)                       |
              +------------+------------+------------+------------+
              ~                                                   ~
              +------------+------------+------------+------------+
          0xf0| BRT Port Info#47 (16 bytes)                       |
              +------------+------------+------------+------------+"
    ::= { fjdaryPfbrtEntry 4 }

fjdaryPfbrtInfo3 OBJECT-TYPE
    SYNTAX OCTET STRING
    ACCESS read-only
    STATUS mandatory
    DESCRIPTION
        "The value of this object indicates the BRT Info#48-#63 performance
         data.
                  byte 0       byte 1       byte 2       byte 3
              +------------+------------+------------+------------+
          0x00| BRT Port Info#48 (16 bytes)                       |
              +------------+------------+------------+------------+
          0x10| BRT Port Info#49 (16 bytes)                       |
              +------------+------------+------------+------------+
              ~                                                   ~
              +------------+------------+------------+------------+
          0xf0| BRT Port Info#63 (16 bytes)                       |
              +------------+------------+------------+------------+"
    ::= { fjdaryPfbrtEntry 5 }

-------------------------------------------------------------------------------
--   fjdaryPfdisk                                                            --
-------------------------------------------------------------------------------
fjdaryPfdiskCount OBJECT-TYPE
    SYNTAX INTEGER
    ACCESS read-only
    STATUS mandatory
    DESCRIPTION
        "The number of DISK performance data table's entry on this system."
    ::= { fjdaryPfdisk 1 }

fjdaryPfdiskTable OBJECT-TYPE
    SYNTAX SEQUENCE OF FjdaryPfdiskEntry
    ACCESS not-accessible
    STATUS mandatory
    DESCRIPTION
        ""
    ::= { fjdaryPfdisk 2 }

fjdaryPfdiskEntry OBJECT-TYPE
    SYNTAX FjdaryPfdiskEntry
    ACCESS not-accessible
    STATUS mandatory
    DESCRIPTION
        ""
    INDEX { fjdaryPfdiskIndex }
    ::= { fjdaryPfdiskTable 1 }

FjdaryPfdiskEntry ::=
    SEQUENCE{
        fjdaryPfdiskIndex INTEGER,
        fjdaryPfdiskInfo  OCTET STRING
    }

fjdaryPfdiskIndex OBJECT-TYPE
    SYNTAX INTEGER
    ACCESS read-only
    STATUS mandatory
    DESCRIPTION
        "The value of this object uniquely identifies this fjdaryPfdisk entry."
    ::= { fjdaryPfdiskEntry 1 }

fjdaryPfdiskInfo OBJECT-TYPE
    SYNTAX OCTET STRING
    ACCESS read-only
    STATUS mandatory
    DESCRIPTION
        "The value of this object indicates the DISK performance data.
                  byte 0       byte 1       byte 2       byte 3
              +------------+------------+------------+------------+
          0x00| DISK Info#index*8 (32 bytes)                      |
              +------------+------------+------------+------------+
          0x20| DISK Info#index*8+1 (32 bytes)                    |
              +------------+------------+------------+------------+
              ~                                                   ~
              +------------+------------+------------+------------+
          0xe0| DISK Info#index*8+7 (32 bytes)                    |
              +------------+------------+------------+------------+
         DISK Info:
                  byte 0       byte 1       byte 2       byte 3
              +------------+------------+------------+------------+
          0x00| PLU                     | Reserved   | Busy Rate  |
              +------------+------------+------------+------------+
          0x04| Xfer Rate                                         |
              +------------+------------+------------+------------+
          0x08| Busy Time                                         |
              +                                                   +
          0x0c|                                                   |
              +------------+------------+------------+------------+
          0x10| Read Command Count                                |
              +------------+------------+------------+------------+
          0x14| Write Command Count                               |
              +------------+------------+------------+------------+
          0x18| Read Block Count                                  |
              +------------+------------+------------+------------+
          0x1c| Write Block Count                                 |
              +------------+------------+------------+------------+"
    ::= { fjdaryPfdiskEntry 2 }

-------------------------------------------------------------------------------
--   fjdaryPfdisktime                                                        --
-------------------------------------------------------------------------------
fjdaryPfdisktimeCount OBJECT-TYPE
    SYNTAX INTEGER
    ACCESS read-only
    STATUS mandatory
    DESCRIPTION
        "The number of DISK time performance data table's entry on this
         system."
    ::= { fjdaryPfdisktime 1 }

fjdaryPfdisktimeTable OBJECT-TYPE
    SYNTAX SEQUENCE OF FjdaryPfdisktimeEntry
    ACCESS not-accessible
    STATUS mandatory
    DESCRIPTION
        ""
    ::= { fjdaryPfdisktime 2 }

fjdaryPfdisktimeEntry OBJECT-TYPE
    SYNTAX FjdaryPfdisktimeEntry
    ACCESS not-accessible
    STATUS mandatory
    DESCRIPTION
        ""
    INDEX { fjdaryPfdisktimeIndex }
    ::= { fjdaryPfdisktimeTable 1 }

FjdaryPfdisktimeEntry ::=
    SEQUENCE{
        fjdaryPfdisktimeIndex INTEGER,
        fjdaryPfdisktimeInfo  OCTET STRING
    }

fjdaryPfdisktimeIndex OBJECT-TYPE
    SYNTAX INTEGER
    ACCESS read-only
    STATUS mandatory
    DESCRIPTION
        "The value of this object uniquely identifies this fjdaryPfdisktime
         entry."
    ::= { fjdaryPfdisktimeEntry 1 }

fjdaryPfdisktimeInfo OBJECT-TYPE
    SYNTAX OCTET STRING
    ACCESS read-only
    STATUS mandatory
    DESCRIPTION
        "The value of this object indicates the DISK time performance data.
                  byte 0       byte 1       byte 2       byte 3
              +------------+------------+------------+------------+
          0x00| Busy Time#index*15 (8 bytes)                      |
              +------------+------------+------------+------------+
          0x08| Busy Time#index*15+1 (8 bytes)                    |
              +------------+------------+------------+------------+
              ~                                                   ~
              +------------+------------+------------+------------+
          0x70| Busy Time#index*15+14 (8 bytes)                   |
              +------------+------------+------------+------------+"
    ::= { fjdaryPfdisktimeEntry 2 }

-------------------------------------------------------------------------------
--   fjdaryPfcm                                                              --
-------------------------------------------------------------------------------
fjdaryPfcmCount OBJECT-TYPE
    SYNTAX INTEGER
    ACCESS read-only
    STATUS mandatory
    DESCRIPTION
        "The number of CM performance data table's entry on this system."
    ::= { fjdaryPfcm 1 }

fjdaryPfcmTable OBJECT-TYPE
    SYNTAX SEQUENCE OF FjdaryPfcmEntry
    ACCESS not-accessible
    STATUS mandatory
    DESCRIPTION
        ""
    ::= { fjdaryPfcm 2 }

fjdaryPfcmEntry OBJECT-TYPE
    SYNTAX FjdaryPfcmEntry
    ACCESS not-accessible
    STATUS mandatory
    DESCRIPTION
        ""
    INDEX { fjdaryPfcmIndex }
    ::= { fjdaryPfcmTable 1 }

FjdaryPfcmEntry ::=
    SEQUENCE{
        fjdaryPfcmIndex INTEGER,
        fjdaryPfcmInfo  OCTET STRING
    }

fjdaryPfcmIndex OBJECT-TYPE
    SYNTAX INTEGER
    ACCESS read-only
    STATUS mandatory
    DESCRIPTION
        "The value of this object uniquely identifies this fjdaryPfcm entry."
    ::= { fjdaryPfcmEntry 1 }

fjdaryPfcmInfo OBJECT-TYPE
    SYNTAX OCTET STRING
    ACCESS read-only
    STATUS mandatory
    DESCRIPTION
        "The value of this object indicates the CM performance data.
                  byte 0       byte 1       byte 2       byte 3
              +------------+------------+------------+------------+
          0x00| Total CPU Time                                    |
              +------------+------------+------------+------------+
          0x04| Idle CPU Time                                     |
              +------------+------------+------------+------------+
          0x08| Total SUB CPU Time                                |
              +------------+------------+------------+------------+
          0x0c| Idle SUB CPU Time                                 |
              +------------+------------+------------+------------+"
    ::= { fjdaryPfcmEntry 2 }

-------------------------------------------------------------------------------
--   fjdaryPfcacheolu                                                        --
-------------------------------------------------------------------------------
fjdaryPfcacheoluCount OBJECT-TYPE
    SYNTAX INTEGER
    ACCESS read-only
    STATUS mandatory
    DESCRIPTION
        "The number of OLU performance data gathered in cache layer table's
         entry on this system."
    ::= { fjdaryPfcacheolu 1 }

fjdaryPfcacheoluTable OBJECT-TYPE
    SYNTAX SEQUENCE OF FjdaryPfcacheoluEntry
    ACCESS not-accessible
    STATUS mandatory
    DESCRIPTION
        ""
    ::= { fjdaryPfcacheolu 2 }

fjdaryPfcacheoluEntry OBJECT-TYPE
    SYNTAX FjdaryPfcacheoluEntry
    ACCESS not-accessible
    STATUS mandatory
    DESCRIPTION
        ""
    INDEX { fjdaryPfcacheoluIndex }
    ::= { fjdaryPfcacheoluTable 1 }

FjdaryPfcacheoluEntry ::=
    SEQUENCE{
        fjdaryPfcacheoluIndex INTEGER,
        fjdaryPfcacheoluInfo  OCTET STRING
    }

fjdaryPfcacheoluIndex OBJECT-TYPE
    SYNTAX INTEGER
    ACCESS read-only
    STATUS mandatory
    DESCRIPTION
        "The value of this object uniquely identifies this fjdaryPfcacheolu
         entry."
    ::= { fjdaryPfcacheoluEntry 1 }

fjdaryPfcacheoluInfo OBJECT-TYPE
    SYNTAX OCTET STRING
    ACCESS read-only
    STATUS mandatory
    DESCRIPTION
        "The value of this object indicates the OLU performance data gathered
         in cache layer.
                  byte 0       byte 1       byte 2       byte 3
              +------------+------------+------------+------------+
          0x00| CACHE OLU#index*4 Info (48 bytes)                 |
              +------------+------------+------------+------------+
          0x30| CACHE OLU#index*4+1 Info (48 bytes)               |
              +------------+------------+------------+------------+
          0x60| CACHE OLU#index*4+2 Info (48 bytes)               |
              +------------+------------+------------+------------+
          0x90| CACHE OLU#index*4+3 Info (48 bytes)               |
              +------------+------------+------------+------------+
         CACHE OLU information:
                  byte 0       byte 1       byte 2       byte 3
              +------------+------------+------------+------------+
          0x00| Read Command Count                                |
              +------------+------------+------------+------------+
          0x04| Write Command Count                               |
              +------------+------------+------------+------------+
          0x08| Read Hit Count                                    |
              +------------+------------+------------+------------+
          0x0c| Write Hit Count                                   |
              +------------+------------+------------+------------+
          0x10| Pre-fetch Read Hit Count                          |
              +------------+------------+------------+------------+
          0x14| Read Block Count                                  |
              +------------+------------+------------+------------+
          0x18| Write Block Count                                 |
              +------------+------------+------------+------------+
          0x1c| Staging Count                                     |
              +------------+------------+------------+------------+
          0x20| Writeback Count                                   |
              +------------+------------+------------+------------+
          0x24| Read Miss Staging Count                           |
              +------------+------------+------------+------------+
          0x28| Sequential Read Count                             |
              +------------+------------+------------+------------+
          0x2c| Sequential Write Count                            |
              +------------+------------+------------+------------+"
    ::= { fjdaryPfcacheoluEntry 2 }

-------------------------------------------------------------------------------
--   fjdaryPfrscolu                                                          --
-------------------------------------------------------------------------------
fjdaryPfrscoluCount OBJECT-TYPE
    SYNTAX INTEGER
    ACCESS read-only
    STATUS mandatory
    DESCRIPTION
        "The number of OLU performance data gathered in resource layer table's
         entry on this system."
    ::= { fjdaryPfrscolu 1 }

fjdaryPfrscoluTable OBJECT-TYPE
    SYNTAX SEQUENCE OF FjdaryPfrscoluEntry
    ACCESS not-accessible
    STATUS mandatory
    DESCRIPTION
        ""
    ::= { fjdaryPfrscolu 2 }

fjdaryPfrscoluEntry OBJECT-TYPE
    SYNTAX FjdaryPfrscoluEntry
    ACCESS not-accessible
    STATUS mandatory
    DESCRIPTION
        ""
    INDEX { fjdaryPfrscoluIndex }
    ::= { fjdaryPfrscoluTable 1 }

FjdaryPfrscoluEntry ::=
    SEQUENCE{
        fjdaryPfrscoluIndex INTEGER,
        fjdaryPfrscoluInfo  OCTET STRING
    }

fjdaryPfrscoluIndex OBJECT-TYPE
    SYNTAX INTEGER
    ACCESS read-only
    STATUS mandatory
    DESCRIPTION
        "The value of this object uniquely identifies this fjdaryPfrscolu
         entry."
    ::= { fjdaryPfrscoluEntry 1 }

fjdaryPfrscoluInfo OBJECT-TYPE
    SYNTAX OCTET STRING
    ACCESS read-only
    STATUS mandatory
    DESCRIPTION
        "The value of this object indicates the OLU performance data gathered
         in resource layer.
                  byte 0       byte 1       byte 2       byte 3
              +------------+------------+------------+------------+
          0x00| RSC OLU#index*16 Info (16 bytes)                  |
              +------------+------------+------------+------------+
          0x10| RSC OLU#index*16+1 Info (16 bytes)                |
              +------------+------------+------------+------------+
              ~                                                   
              +------------+------------+------------+------------+
          0xf0| RSC OLU#index*16+15 Info (16 bytes)               |
              +------------+------------+------------+------------+
         RSC OLU information:
                  byte 0       byte 1       byte 2       byte 3
              +------------+------------+------------+------------+
          0x00| Read Response Time                                |
              +------------+------------+------------+------------+
          0x04| Write Response Time                               |
              +------------+------------+------------+------------+
          0x08| Extent Busy Count                                 |
              +------------+------------+------------+------------+
          0x0c| Reserved                                          |
              +------------+------------+------------+------------+"
    ::= { fjdaryPfrscoluEntry 2 }

-------------------------------------------------------------------------------
--   fjdaryPfrscrlu                                                          --
-------------------------------------------------------------------------------
fjdaryPfrscrluCount OBJECT-TYPE
    SYNTAX INTEGER
    ACCESS read-only
    STATUS mandatory
    DESCRIPTION
        "The number of RLU performance data gathered in resource layer table's
         entry on this system."
    ::= { fjdaryPfrscrlu 1 }

fjdaryPfrscrluTable OBJECT-TYPE
    SYNTAX SEQUENCE OF FjdaryPfrscrluEntry
    ACCESS not-accessible
    STATUS mandatory
    DESCRIPTION
        ""
    ::= { fjdaryPfrscrlu 2 }

fjdaryPfrscrluEntry OBJECT-TYPE
    SYNTAX FjdaryPfrscrluEntry
    ACCESS not-accessible
    STATUS mandatory
    DESCRIPTION
        ""
    INDEX { fjdaryPfrscrluIndex }
    ::= { fjdaryPfrscrluTable 1 }

FjdaryPfrscrluEntry ::=
    SEQUENCE{
        fjdaryPfrscrluIndex INTEGER,
        fjdaryPfrscrluInfo  OCTET STRING
    }

fjdaryPfrscrluIndex OBJECT-TYPE
    SYNTAX INTEGER
    ACCESS read-only
    STATUS mandatory
    DESCRIPTION
        "The value of this object uniquely identifies this fjdaryPfrscrlu
         entry."
    ::= { fjdaryPfrscrluEntry 1 }

fjdaryPfrscrluInfo OBJECT-TYPE
    SYNTAX OCTET STRING
    ACCESS read-only
    STATUS mandatory
    DESCRIPTION
        "The value of this object indicates the RLU performance data gathered
         in resource layer.
                  byte 0       byte 1       byte 2       byte 3
              +------------+------------+------------+------------+
          0x00| RSC RLU#index*16 Info (16 bytes)                  |
              +------------+------------+------------+------------+
          0x10| RSC RLU#index*16+1 Info (16 bytes)                |
              +------------+------------+------------+------------+
              ~                                                   
              +------------+------------+------------+------------+
          0xf0| RSC RLU#index*16+15 Info (16 bytes)               |
              +------------+------------+------------+------------+
         RSC RLU information:
                  byte 0       byte 1       byte 2       byte 3
              +------------+------------+------------+------------+
          0x00| CPU Cross Access Count                            |
              +------------+------------+------------+------------+
          0x04| Straight Access Count                             |
              +------------+------------+------------+------------+
          0x08| Cross Access Count                                |
              +------------+------------+------------+------------+
          0x0c| Reserved                                          |
              +------------+------------+------------+------------+"
    ::= { fjdaryPfrscrluEntry 2 }

-------------------------------------------------------------------------------
--   fjdaryPfcopycm                                                          --
-------------------------------------------------------------------------------
fjdaryPfcopycmCount OBJECT-TYPE
    SYNTAX INTEGER
    ACCESS read-only
    STATUS mandatory
    DESCRIPTION
        "The number of CM performance data gathered in copy layer table's entry
         on this system."
    ::= { fjdaryPfcopycm 1 }

fjdaryPfcopycmTable OBJECT-TYPE
    SYNTAX SEQUENCE OF FjdaryPfcopycmEntry
    ACCESS not-accessible
    STATUS mandatory
    DESCRIPTION
        ""
    ::= { fjdaryPfcopycm 2 }

fjdaryPfcopycmEntry OBJECT-TYPE
    SYNTAX FjdaryPfcopycmEntry
    ACCESS not-accessible
    STATUS mandatory
    DESCRIPTION
        ""
    INDEX { fjdaryPfcopycmIndex }
    ::= { fjdaryPfcopycmTable 1 }

FjdaryPfcopycmEntry ::=
    SEQUENCE{
        fjdaryPfcopycmIndex INTEGER,
        fjdaryPfcopycmInfo  OCTET STRING
    }

fjdaryPfcopycmIndex OBJECT-TYPE
    SYNTAX INTEGER
    ACCESS read-only
    STATUS mandatory
    DESCRIPTION
        "The value of this object uniquely identifies this fjdaryPfcopycm
         entry."
    ::= { fjdaryPfcopycmEntry 1 }

fjdaryPfcopycmInfo OBJECT-TYPE
    SYNTAX OCTET STRING
    ACCESS read-only
    STATUS mandatory
    DESCRIPTION
        "The value of this object indicates the CM performance data gathered in
         copy layer.
                  byte 0       byte 1       byte 2       byte 3
              +------------+------------+------------+------------+
          0x00| Copy Remain Count                                 |
              +                                                   +
          0x04|                                                   |
              +------------+------------+------------+------------+
          0x08| Reserved                                          |
              +                                                   +
          0x0c|                                                   |
              +------------+------------+------------+------------+"
    ::= { fjdaryPfcopycmEntry 2 }

-------------------------------------------------------------------------------
--   fjdaryPfcopyslu                                                         --
-------------------------------------------------------------------------------
fjdaryPfcopysluCount OBJECT-TYPE
    SYNTAX INTEGER
    ACCESS read-only
    STATUS mandatory
    DESCRIPTION
        "The number of SLU performance data gathered in copy layer table's
         entry on this system."
    ::= { fjdaryPfcopyslu 1 }

fjdaryPfcopysluTable OBJECT-TYPE
    SYNTAX SEQUENCE OF FjdaryPfcopysluEntry
    ACCESS not-accessible
    STATUS mandatory
    DESCRIPTION
        ""
    ::= { fjdaryPfcopyslu 2 }

fjdaryPfcopysluEntry OBJECT-TYPE
    SYNTAX FjdaryPfcopysluEntry
    ACCESS not-accessible
    STATUS mandatory
    DESCRIPTION
        ""
    INDEX { fjdaryPfcopysluIndex }
    ::= { fjdaryPfcopysluTable 1 }

FjdaryPfcopysluEntry ::=
    SEQUENCE{
        fjdaryPfcopysluIndex INTEGER,
        fjdaryPfcopysluInfo  OCTET STRING
    }

fjdaryPfcopysluIndex OBJECT-TYPE
    SYNTAX INTEGER
    ACCESS read-only
    STATUS mandatory
    DESCRIPTION
        "The value of this object uniquely identifies this fjdaryPfcopyslu
         entry."
    ::= { fjdaryPfcopysluEntry 1 }

fjdaryPfcopysluInfo OBJECT-TYPE
    SYNTAX OCTET STRING
    ACCESS read-only
    STATUS mandatory
    DESCRIPTION
        "The value of this object indicates the SLU performance data gathered
         in copy layer.
                  byte 0       byte 1       byte 2       byte 3
              +------------+------------+------------+------------+
          0x00| COPY SLU#index*4 Info (64 bytes)                  |
              +------------+------------+------------+------------+
          0x40| COPY SLU#index*4+1 Info (64 bytes)                |
              +------------+------------+------------+------------+
          0x80| COPY SLU#index*4+2 Info (64 bytes)                |
              +------------+------------+------------+------------+
          0xc0| COPY SLU#index*4+3 Info (64 bytes)                |
              +------------+------------+------------+------------+
         COPY SLU information:
                  byte 0       byte 1       byte 2       byte 3
              +------------+------------+------------+------------+
          0x00| EC Source Copy Block Count                        |
              +------------+------------+------------+------------+
          0x04| EC Destination Copy Block Count                   |
              +------------+------------+------------+------------+
          0x08| OPC Source Copy Block Count                       |
              +------------+------------+------------+------------+
          0x0c| OPC Destination Copy Block Count                  |
              +------------+------------+------------+------------+
          0x10| REC Source Copy Block Count                       |
              +------------+------------+------------+------------+
          0x14| REC Destination Copy Block Count                  |
              +------------+------------+------------+------------+
          0x18| Reserved                                          |
              +                                                   +
          0x1c|                                                   |
              +------------+------------+------------+------------+
          0x20| EC Source Copy Area Write Count                   |
              +------------+------------+------------+------------+
          0x24| OPC Source Un-copy Area Write Count               |
              +------------+------------+------------+------------+
          0x28| REC Source Copy Area Write Count                  |
              +------------+------------+------------+------------+
          0x2c| Busy I/O Count                                    |
              +------------+------------+------------+------------+
          0x30| I/O Limit Busy Count                              |
              +------------+------------+------------+------------+
          0x34| Extent Busy Count                                 |
              +------------+------------+------------+------------+
          0x38| Cache Busy Count                                  |
              +------------+------------+------------+------------+
          0x3c| Other Busy Count                                  |
              +------------+------------+------------+------------+"
    ::= { fjdaryPfcopysluEntry 2 }

-------------------------------------------------------------------------------
--   fjdaryPfcacheslu                                                        --
-------------------------------------------------------------------------------
fjdaryPfcachesluCount OBJECT-TYPE
    SYNTAX INTEGER
    ACCESS read-only
    STATUS mandatory
    DESCRIPTION
        "The number of SLU performance data gathered in cache layer table's
         entry on this system."
    ::= { fjdaryPfcacheslu 1 }

fjdaryPfcachesluTable OBJECT-TYPE
    SYNTAX SEQUENCE OF FjdaryPfcachesluEntry
    ACCESS not-accessible
    STATUS mandatory
    DESCRIPTION
        ""
    ::= { fjdaryPfcacheslu 2 }

fjdaryPfcachesluEntry OBJECT-TYPE
    SYNTAX FjdaryPfcachesluEntry
    ACCESS not-accessible
    STATUS mandatory
    DESCRIPTION
        ""
    INDEX { fjdaryPfcachesluIndex }
    ::= { fjdaryPfcachesluTable 1 }

FjdaryPfcachesluEntry ::=
    SEQUENCE{
        fjdaryPfcachesluIndex INTEGER,
        fjdaryPfcachesluInfo  OCTET STRING
    }

fjdaryPfcachesluIndex OBJECT-TYPE
    SYNTAX INTEGER
    ACCESS read-only
    STATUS mandatory
    DESCRIPTION
        "The value of this object uniquely identifies this fjdaryPfcacheslu
         entry."
    ::= { fjdaryPfcachesluEntry 1 }

fjdaryPfcachesluInfo OBJECT-TYPE
    SYNTAX OCTET STRING
    ACCESS read-only
    STATUS mandatory
    DESCRIPTION
        "The value of this object indicates the SLU performance data gathered
         in cache layer.
                  byte 0       byte 1       byte 2       byte 3
              +------------+------------+------------+------------+
          0x00| CACHE SLU#index*4 Info (48 bytes)                 |
              +------------+------------+------------+------------+
          0x30| CACHE SLU#index*4+1 Info (48 bytes)               |
              +------------+------------+------------+------------+
          0x60| CACHE SLU#index*4+2 Info (48 bytes)               |
              +------------+------------+------------+------------+
          0x90| CACHE SLU#index*4+3 Info (48 bytes)               |
              +------------+------------+------------+------------+
         CACHE SLU information:
                  byte 0       byte 1       byte 2       byte 3
              +------------+------------+------------+------------+
          0x00| Read Command Count                                |
              +------------+------------+------------+------------+
          0x04| Write Command Count                               |
              +------------+------------+------------+------------+
          0x08| Read Hit Count                                    |
              +------------+------------+------------+------------+
          0x0c| Write Hit Count                                   |
              +------------+------------+------------+------------+
          0x10| Pre-fetch Read Hit Count                          |
              +------------+------------+------------+------------+
          0x14| Read Block Count                                  |
              +------------+------------+------------+------------+
          0x18| Write Block Count                                 |
              +------------+------------+------------+------------+
          0x1c| Staging Count                                     |
              +------------+------------+------------+------------+
          0x20| Writeback Count                                   |
              +------------+------------+------------+------------+
          0x24| Read Miss Staging Count                           |
              +------------+------------+------------+------------+
          0x28| Sequential Read Count                             |
              +------------+------------+------------+------------+
          0x2c| Sequential Write Count                            |
              +------------+------------+------------+------------+"
    ::= { fjdaryPfcachesluEntry 2 }

-------------------------------------------------------------------------------
--   fjdaryPfrscslu                                                          --
-------------------------------------------------------------------------------
fjdaryPfrscsluCount OBJECT-TYPE
    SYNTAX INTEGER
    ACCESS read-only
    STATUS mandatory
    DESCRIPTION
        "The number of SLU performance data gathered in resource layer table's
         entry on this system."
    ::= { fjdaryPfrscslu 1 }

fjdaryPfrscsluTable OBJECT-TYPE
    SYNTAX SEQUENCE OF FjdaryPfrscsluEntry
    ACCESS not-accessible
    STATUS mandatory
    DESCRIPTION
        ""
    ::= { fjdaryPfrscslu 2 }

fjdaryPfrscsluEntry OBJECT-TYPE
    SYNTAX FjdaryPfrscsluEntry
    ACCESS not-accessible
    STATUS mandatory
    DESCRIPTION
        ""
    INDEX { fjdaryPfrscsluIndex }
    ::= { fjdaryPfrscsluTable 1 }

FjdaryPfrscsluEntry ::=
    SEQUENCE{
        fjdaryPfrscsluIndex INTEGER,
        fjdaryPfrscsluInfo  OCTET STRING
    }

fjdaryPfrscsluIndex OBJECT-TYPE
    SYNTAX INTEGER
    ACCESS read-only
    STATUS mandatory
    DESCRIPTION
        "The value of this object uniquely identifies this fjdaryPfrscslu
         entry."
    ::= { fjdaryPfrscsluEntry 1 }

fjdaryPfrscsluInfo OBJECT-TYPE
    SYNTAX OCTET STRING
    ACCESS read-only
    STATUS mandatory
    DESCRIPTION
        "The value of this object indicates the SLU performance data gathered
         in resource layer.
                  byte 0       byte 1       byte 2       byte 3
              +------------+------------+------------+------------+
          0x00| RSC SLU#index*32 Info (8 bytes)                   |
              +------------+------------+------------+------------+
          0x08| RSC SLU#index*32+1 Info (8 bytes)                 |
              +------------+------------+------------+------------+
              ~                                                   
              +------------+------------+------------+------------+
          0xf8| RSC SLU#index*32+31 Info (8 bytes)                |
              +------------+------------+------------+------------+
         RSC SLU information:
                  byte 0       byte 1       byte 2       byte 3
              +------------+------------+------------+------------+
          0x00| Read Response Time                                |
              +------------+------------+------------+------------+
          0x04| Write Response Time                               |
              +------------+------------+------------+------------+"
    ::= { fjdaryPfrscsluEntry 2 }

-------------------------------------------------------------------------------
--   fjdaryPfcachecopyslu                                                    --
-------------------------------------------------------------------------------
fjdaryPfcachecopysluCount OBJECT-TYPE
    SYNTAX INTEGER
    ACCESS read-only
    STATUS mandatory
    DESCRIPTION
        "The number of SLU performance data gathered in cache and copy layer
         table's entry on this system."
    ::= { fjdaryPfcachecopyslu 1 }

fjdaryPfcachecopysluTable OBJECT-TYPE
    SYNTAX SEQUENCE OF FjdaryPfcachecopysluEntry
    ACCESS not-accessible
    STATUS mandatory
    DESCRIPTION
        ""
    ::= { fjdaryPfcachecopyslu 2 }

fjdaryPfcachecopysluEntry OBJECT-TYPE
    SYNTAX FjdaryPfcachecopysluEntry
    ACCESS not-accessible
    STATUS mandatory
    DESCRIPTION
        ""
    INDEX { fjdaryPfcachecopysluIndex }
    ::= { fjdaryPfcachecopysluTable 1 }

FjdaryPfcachecopysluEntry ::=
    SEQUENCE{
        fjdaryPfcachecopysluIndex INTEGER,
        fjdaryPfcachecopysluInfo  OCTET STRING
    }

fjdaryPfcachecopysluIndex OBJECT-TYPE
    SYNTAX INTEGER
    ACCESS read-only
    STATUS mandatory
    DESCRIPTION
        "The value of this object uniquely identifies this fjdaryPfcachecopyslu
         entry."
    ::= { fjdaryPfcachecopysluEntry 1 }

fjdaryPfcachecopysluInfo OBJECT-TYPE
    SYNTAX OCTET STRING
    ACCESS read-only
    STATUS mandatory
    DESCRIPTION
        "The value of this object indicates the SLU performance data gathered
         in cache and copy layer.
                  byte 0       byte 1       byte 2       byte 3
              +------------+------------+------------+------------+
          0x00| CACHE COPY SLU#index*4 Info (48 bytes)            |
              +------------+------------+------------+------------+
          0x30| CACHE COPY SLU#index*4+1 Info (48 bytes)          |
              +------------+------------+------------+------------+
          0x60| CACHE COPY SLU#index*4+2 Info (48 bytes)          |
              +------------+------------+------------+------------+
          0x90| CACHE COPY SLU#index*4+3 Info (48 bytes)          |
              +------------+------------+------------+------------+
         CACHE COPY SLU information:
                  byte 0       byte 1       byte 2       byte 3
              +------------+------------+------------+------------+
          0x00| Read Command Count                                |
              +------------+------------+------------+------------+
          0x04| Write Command Count                               |
              +------------+------------+------------+------------+
          0x08| Read Hit Count                                    |
              +------------+------------+------------+------------+
          0x0c| Write Hit Count                                   |
              +------------+------------+------------+------------+
          0x10| Pre-fetch Read Hit Count                          |
              +------------+------------+------------+------------+
          0x14| Read Block Count                                  |
              +------------+------------+------------+------------+
          0x18| Write Block Count                                 |
              +------------+------------+------------+------------+
          0x1c| Staging Count                                     |
              +------------+------------+------------+------------+
          0x20| Write back Count                                  |
              +------------+------------+------------+------------+
          0x24| Read Miss Staging Count                           |
              +------------+------------+------------+------------+
          0x28| Sequential Read Count                             |
              +------------+------------+------------+------------+
          0x2c| Sequential Write Count                            |
              +------------+------------+------------+------------+"
    ::= { fjdaryPfcachecopysluEntry 2 }

-------------------------------------------------------------------------------
--   fjdaryPfcachesdvslu                                                    --
-------------------------------------------------------------------------------
fjdaryPfcachesdvsluCount OBJECT-TYPE
    SYNTAX INTEGER
    ACCESS read-only
    STATUS mandatory
    DESCRIPTION
        "The number of SLU performance data gathered in cache and sdv layer
         table's entry on this system."
    ::= { fjdaryPfcachesdvslu 1 }

fjdaryPfcachesdvsluTable OBJECT-TYPE
    SYNTAX SEQUENCE OF FjdaryPfcachesdvsluEntry
    ACCESS not-accessible
    STATUS mandatory
    DESCRIPTION
        ""
    ::= { fjdaryPfcachesdvslu 2 }

fjdaryPfcachesdvsluEntry OBJECT-TYPE
    SYNTAX FjdaryPfcachesdvsluEntry
    ACCESS not-accessible
    STATUS mandatory
    DESCRIPTION
        ""
    INDEX { fjdaryPfcachesdvsluIndex }
    ::= { fjdaryPfcachesdvsluTable 1 }

FjdaryPfcachesdvsluEntry ::=
    SEQUENCE{
        fjdaryPfcachesdvsluIndex INTEGER,
        fjdaryPfcachesdvsluInfo  OCTET STRING
    }

fjdaryPfcachesdvsluIndex OBJECT-TYPE
    SYNTAX INTEGER
    ACCESS read-only
    STATUS mandatory
    DESCRIPTION
        "The value of this object uniquely identifies this fjdaryPfcachesdvslu
         entry."
    ::= { fjdaryPfcachesdvsluEntry 1 }

fjdaryPfcachesdvsluInfo OBJECT-TYPE
    SYNTAX OCTET STRING
    ACCESS read-only
    STATUS mandatory
    DESCRIPTION
        "The value of this object indicates the SLU performance data gathered
         in cache and sdv layer.
                  byte 0       byte 1       byte 2       byte 3
              +------------+------------+------------+------------+
          0x00| CACHE SDV SLU#index*4 Info (64 bytes)             |
              +------------+------------+------------+------------+
          0x40| CACHE SDV SLU#index*4+1 Info (64 bytes)           |
              +------------+------------+------------+------------+
          0x80| CACHE SDV SLU#index*4+2 Info (64 bytes)           |
              +------------+------------+------------+------------+
          0xc0| CACHE SDV SLU#index*4+3 Info (64 bytes)           |
              +------------+------------+------------+------------+
         CACHE SDV SLU information:
                  byte 0       byte 1       byte 2       byte 3
              +------------+------------+------------+------------+
          0x00| Read Command Count                                |
              +------------+------------+------------+------------+
          0x04| Write Command Count                               |
              +------------+------------+------------+------------+
          0x08| Read Hit Count                                    |
              +------------+------------+------------+------------+
          0x0c| Write Hit Count                                   |
              +------------+------------+------------+------------+
          0x10| Pre-fetch Read Hit Count                          |
              +------------+------------+------------+------------+
          0x14| Read Block Count                                  |
              +------------+------------+------------+------------+
          0x18| Write Block Count                                 |
              +------------+------------+------------+------------+
          0x1c| Staging Count                                     |
              +------------+------------+------------+------------+
          0x20| Write back Count                                  |
              +------------+------------+------------+------------+
          0x24| Read Miss Staging Count                           |
              +------------+------------+------------+------------+
          0x28| Sequential Read Count                             |
              +------------+------------+------------+------------+
          0x2c| Sequential Write Count                            |
              +------------+------------+------------+------------+
          0x30| Pre-fetch Staging Count                           |
              +------------+------------+------------+------------+
          0x34| Pre-fetch Staging Purge Count                     |
              +------------+------------+------------+------------+
          0x38| Reserved                                          |
              +                                                   +
          0x3c|                                                   |
              +------------+------------+------------+------------+"
    ::= { fjdaryPfcachesdvsluEntry 2 }

-------------------------------------------------------------------------------
--   fjdaryPfcachecopyolu                                                    --
-------------------------------------------------------------------------------
fjdaryPfcachecopyoluCount OBJECT-TYPE
    SYNTAX INTEGER
    ACCESS read-only
    STATUS mandatory
    DESCRIPTION
        "The number of OLU performance data gathered in cache and copy layer
         table's entry on this system."
    ::= { fjdaryPfcachecopyolu 1 }

fjdaryPfcachecopyoluTable OBJECT-TYPE
    SYNTAX SEQUENCE OF FjdaryPfcachecopyoluEntry
    ACCESS not-accessible
    STATUS mandatory
    DESCRIPTION
        ""
    ::= { fjdaryPfcachecopyolu 2 }

fjdaryPfcachecopyoluEntry OBJECT-TYPE
    SYNTAX FjdaryPfcachecopyoluEntry
    ACCESS not-accessible
    STATUS mandatory
    DESCRIPTION
        ""
    INDEX { fjdaryPfcachecopyoluIndex }
    ::= { fjdaryPfcachecopyoluTable 1 }

FjdaryPfcachecopyoluEntry ::=
    SEQUENCE{
        fjdaryPfcachecopyoluIndex INTEGER,
        fjdaryPfcachecopyoluInfo  OCTET STRING
    }

fjdaryPfcachecopyoluIndex OBJECT-TYPE
    SYNTAX INTEGER
    ACCESS read-only
    STATUS mandatory
    DESCRIPTION
        "The value of this object uniquely identifies this fjdaryPfcachecopyolu
         entry."
    ::= { fjdaryPfcachecopyoluEntry 1 }

fjdaryPfcachecopyoluInfo OBJECT-TYPE
    SYNTAX OCTET STRING
    ACCESS read-only
    STATUS mandatory
    DESCRIPTION
        "The value of this object indicates the OLU performance data gathered
         in cache and copy layer.
                  byte 0       byte 1       byte 2       byte 3
              +------------+------------+------------+------------+
          0x00| CACHE COPY OLU#index*4 Info (48 bytes)            |
              +------------+------------+------------+------------+
          0x30| CACHE COPY OLU#index*4+1 Info (48 bytes)          |
              +------------+------------+------------+------------+
          0x60| CACHE COPY OLU#index*4+2 Info (48 bytes)          |
              +------------+------------+------------+------------+
          0x90| CACHE COPY OLU#index*4+3 Info (48 bytes)          |
              +------------+------------+------------+------------+
         CACHE COPY OLU information:
                  byte 0       byte 1       byte 2       byte 3
              +------------+------------+------------+------------+
          0x00| Read Command Count                                |
              +------------+------------+------------+------------+
          0x04| Write Command Count                               |
              +------------+------------+------------+------------+
          0x08| Read Hit Count                                    |
              +------------+------------+------------+------------+
          0x0c| Write Hit Count                                   |
              +------------+------------+------------+------------+
          0x10| Pre-fetch Read Hit Count                          |
              +------------+------------+------------+------------+
          0x14| Read Block Count                                  |
              +------------+------------+------------+------------+
          0x18| Write Block Count                                 |
              +------------+------------+------------+------------+
          0x1c| Staging Count                                     |
              +------------+------------+------------+------------+
          0x20| Write back Count                                  |
              +------------+------------+------------+------------+
          0x24| Read Miss Staging Count                           |
              +------------+------------+------------+------------+
          0x28| Sequential Read Count                             |
              +------------+------------+------------+------------+
          0x2c| Sequential Write Count                            |
              +------------+------------+------------+------------+"
    ::= { fjdaryPfcachecopyoluEntry 2 }

-------------------------------------------------------------------------------
--   fjdaryPfcachecommonolu                                                  --
-------------------------------------------------------------------------------
fjdaryPfcachecommonoluCount OBJECT-TYPE
    SYNTAX INTEGER
    ACCESS read-only
    STATUS mandatory
    DESCRIPTION
        "The number of OLU performance data gathered in cache layer table's
         entry on this system."
    ::= { fjdaryPfcachecommonolu 1 }

fjdaryPfcachecommonoluTable OBJECT-TYPE
    SYNTAX SEQUENCE OF FjdaryPfcachecommonoluEntry
    ACCESS not-accessible
    STATUS mandatory
    DESCRIPTION
        ""
    ::= { fjdaryPfcachecommonolu 2 }

fjdaryPfcachecommonoluEntry OBJECT-TYPE
    SYNTAX FjdaryPfcachecommonoluEntry
    ACCESS not-accessible
    STATUS mandatory
    DESCRIPTION
        ""
    INDEX { fjdaryPfcachecommonoluIndex }
    ::= { fjdaryPfcachecommonoluTable 1 }

FjdaryPfcachecommonoluEntry ::=
    SEQUENCE{
        fjdaryPfcachecommonoluIndex INTEGER,
        fjdaryPfcachecommonoluInfo  OCTET STRING
    }

fjdaryPfcachecommonoluIndex OBJECT-TYPE
    SYNTAX INTEGER
    ACCESS read-only
    STATUS mandatory
    DESCRIPTION
        "The value of this object uniquely identifies this
         fjdaryPfcachecommonolu entry."
    ::= { fjdaryPfcachecommonoluEntry 1 }

fjdaryPfcachecommonoluInfo OBJECT-TYPE
    SYNTAX OCTET STRING
    ACCESS read-only
    STATUS mandatory
    DESCRIPTION
        "The value of this object indicates the SLU performance data gathered
         in cache layer.
                  byte 0       byte 1       byte 2       byte 3
              +------------+------------+------------+------------+
          0x00| CACHE COMMON OLU#index*16 Info (16 bytes)         |
              +------------+------------+------------+------------+
          0x10| CACHE COMMON OLU#index*16+1 Info (16 bytes)       |
              +------------+------------+------------+------------+
              ~                                                   
              +------------+------------+------------+------------+
          0xf0| CACHE COMMON OLU#index*16+15 Info (16 bytes)      |
              +------------+------------+------------+------------+
         CACHE COMMON OLU information:
                  byte 0       byte 1       byte 2       byte 3
              +------------+------------+------------+------------+
          0x00| Pre-fetch Staging Count                           |
              +------------+------------+------------+------------+
          0x04| Pre-fetch Staging Purge Count                     |
              +------------+------------+------------+------------+
          0x08| Reserved                                          |
              +                                                   +
          0x0c|                                                   |
              +------------+------------+------------+------------+"
    ::= { fjdaryPfcachecommonoluEntry 2 }

-------------------------------------------------------------------------------
--   fjdaryPfcachecommonslu                                                  --
-------------------------------------------------------------------------------
fjdaryPfcachecommonsluCount OBJECT-TYPE
    SYNTAX INTEGER
    ACCESS read-only
    STATUS mandatory
    DESCRIPTION
        "The number of SLU performance data gathered in cache layer table's
         entry on this system."
    ::= { fjdaryPfcachecommonslu 1 }

fjdaryPfcachecommonsluTable OBJECT-TYPE
    SYNTAX SEQUENCE OF FjdaryPfcachecommonsluEntry
    ACCESS not-accessible
    STATUS mandatory
    DESCRIPTION
        ""
    ::= { fjdaryPfcachecommonslu 2 }

fjdaryPfcachecommonsluEntry OBJECT-TYPE
    SYNTAX FjdaryPfcachecommonsluEntry
    ACCESS not-accessible
    STATUS mandatory
    DESCRIPTION
        ""
    INDEX { fjdaryPfcachecommonsluIndex }
    ::= { fjdaryPfcachecommonsluTable 1 }

FjdaryPfcachecommonsluEntry ::=
    SEQUENCE{
        fjdaryPfcachecommonsluIndex INTEGER,
        fjdaryPfcachecommonsluInfo  OCTET STRING
    }

fjdaryPfcachecommonsluIndex OBJECT-TYPE
    SYNTAX INTEGER
    ACCESS read-only
    STATUS mandatory
    DESCRIPTION
        "The value of this object uniquely identifies this
         fjdaryPfcachecommonslu entry."
    ::= { fjdaryPfcachecommonsluEntry 1 }

fjdaryPfcachecommonsluInfo OBJECT-TYPE
    SYNTAX OCTET STRING
    ACCESS read-only
    STATUS mandatory
    DESCRIPTION
        "The value of this object indicates the SLU performance data gathered
         in cache layer.
                  byte 0       byte 1       byte 2       byte 3
              +------------+------------+------------+------------+
          0x00| CACHE COMMON SLU#index*16 Info (16 bytes)         |
              +------------+------------+------------+------------+
          0x10| CACHE COMMON SLU#index*16+1 Info (16 bytes)       |
              +------------+------------+------------+------------+
              ~                                                   
              +------------+------------+------------+------------+
          0xf0| CACHE COMMON SLU#index*16+15 Info (16 bytes)      |
              +------------+------------+------------+------------+
         CACHE COMMON SLU information:
                  byte 0       byte 1       byte 2       byte 3
              +------------+------------+------------+------------+
          0x00| Pre-fetch Staging Count                           |
              +------------+------------+------------+------------+
          0x04| Pre-fetch Staging Purge Count                     |
              +------------+------------+------------+------------+
          0x08| Reserved                                          |
              +                                                   +
          0x0c|                                                   |
              +------------+------------+------------+------------+"
    ::= { fjdaryPfcachecommonsluEntry 2 }

--***************************************************************************--
--   Trap Definitions                                                        --
--***************************************************************************--
fjdarye50ConfigChange TRAP-TYPE
    ENTERPRISE aplNetFjdarye50
    VARIABLES{
        fjdarySspMachineId,
        fjdaryTrapMessage
    }
    DESCRIPTION
        "A configChange trap signifies that the sending protocol entity
         recognizes the change in configuration information."
        --#TYPE "Configuration changed"
        --#SUMMARY "Configuration changed event from %s, message: %s"
        --#ARGUMENTS {0,1}
        --#SEVERITY INFORMATIONAL
        --#TIMEINDEX 6
    ::= 0

fjdarye50FirmChange TRAP-TYPE
    ENTERPRISE aplNetFjdarye50
    VARIABLES{
        fjdarySspMachineId,
        fjdaryTrapMessage
    }
    DESCRIPTION
        "A firmChange trap signifies that the exchange of the firmware was
         executed."
        --#TYPE "Firmware changed"
        --#SUMMARY "Firmware changed event from %s, message: %s"
        --#ARGUMENTS {0,1}
        --#SEVERITY INFORMATIONAL
        --#TIMEINDEX 6
    ::= 1

fjdarye50ItemFault TRAP-TYPE
    ENTERPRISE aplNetFjdarye50
    VARIABLES{
        fjdaryTrapItemId,
        fjdarySspMachineId,
        fjdaryTrapMessage
    }
    DESCRIPTION
        "A itemFault trap signifies that device was failed."
        --#TYPE "Item fault"
        --#SUMMARY "Item fault event from %s, id: %x, message: %s"
        --#ARGUMENTS {1,0,2}
        --#SEVERITY CRITICAL
        --#TIMEINDEX 6
    ::= 2

fjdarye50BatteryExpiration TRAP-TYPE
    ENTERPRISE aplNetFjdarye50
    VARIABLES{
        fjdaryTrapItemId,
        fjdarySspMachineId,
        fjdaryTrapMessage
    }
    DESCRIPTION
        "A batteryExpiration trap signifies that the exchange time of the
         battery comes."
        --#TYPE "Battery expiration"
        --#SUMMARY "Battery expiration event from %s, id: %x, message: %s"
        --#ARGUMENTS {1,0,2}
        --#SEVERITY CRITICAL
        --#TIMEINDEX 6
    ::= 3

fjdarye50RebuildNotStart TRAP-TYPE
    ENTERPRISE aplNetFjdarye50
    VARIABLES{
        fjdarySspMachineId,
        fjdaryTrapMessage
    }
    DESCRIPTION
        "A rebuildNotStart trap signifies that not to be able to begin to
         execute the rebuild because there is no spare disk."
        --#TYPE "Rebuild not started"
        --#SUMMARY "Rebuild not started event from %s, message: %s"
        --#ARGUMENTS {0,1}
        --#SEVERITY CRITICAL
        --#TIMEINDEX 6
    ::= 4

fjdarye50ItemWarning TRAP-TYPE
    ENTERPRISE aplNetFjdarye50
    VARIABLES{
        fjdaryTrapItemId,
        fjdarySspMachineId,
        fjdaryTrapMessage,
        fjdaryTrapWarningInfo
    }
    DESCRIPTION
        "A itemWarning trap signifies that device was warning."
        --#TYPE "Item warning"
        --#SUMMARY "Item warning event from %s, id: %x[%x], message: %s"
        --#ARGUMENTS {1,0,3,2}
        --#SEVERITY CRITICAL
        --#TIMEINDEX 6
    ::= 5

fjdarye50SensorStatusChange TRAP-TYPE
    ENTERPRISE aplNetFjdarye50
    VARIABLES{
        fjdaryTrapItemId,
        fjdarySspMachineId,
        fjdaryTrapSensorInfo,
        fjdaryTrapMessage
    }
    DESCRIPTION
        "A sensorStatusChange trap signifies that environment sensor status
         changes."
        --#TYPE "Sensor status changed"
        --#SUMMARY "Sensor status changed event from %s, id: %x[%x], message: %s"
        --#ARGUMENTS {1,0,2,3}
        --#SEVERITY CRITICAL
        --#TIMEINDEX 6
    ::= 6

fjdarye50MaintenanceRequired TRAP-TYPE
    ENTERPRISE aplNetFjdarye50
    VARIABLES{
        fjdarySspMachineId,
        fjdaryTrapMaintenanceInfo,
        fjdaryTrapMessage
    }
    DESCRIPTION
        "A maintenanceRequired trap signifies that maintenance information."
        --#TYPE "Maintenance required"
        --#SUMMARY "Maintenance required event from %s, id: %x, message: %s"
        --#ARGUMENTS {0,1,2}
        --#SEVERITY CRITICAL
        --#TIMEINDEX 6
    ::= 7

END
