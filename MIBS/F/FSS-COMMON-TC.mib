--=============================================================================
-- Copyright (c) 2016 Fujitsu Network Communications, Inc. All Rights Reserved.
--=============================================================================

FSS-COMMON-TC DEFINITIONS ::= BEGIN

IMPORTS
    MODULE-IDENTITY, Integer32, Unsigned32
        FROM SNMPv2-SMI
    TEXTUAL-CONVENTION
        FROM SNMPv2-TC
    fssCommon
        FROM FSS-COMMON-SMI
    DisplayString
        FROM SNMPv2-TC
    ;

fcTc MODULE-IDENTITY
    LAST-UPDATED "201601200000Z"
    ORGANIZATION 
        "Fujitsu Network Communications, Inc."
    CONTACT-INFO 
        "Fujitsu Technical Assistance Center (FTAC),        
         1-800-USE-FTAC (1-800-873-3822)"
    DESCRIPTION 
        "This MIB module contains common textual conventions (TC)
         used throughout the Fujitsu Network Communications, Inc. 
         enterprise MIB.  It contains only those generic 
         TCs potentially used in more than one MIB module."
    REVISION      "201601200000Z" 
    DESCRIPTION
            "Initial version for release."
    ::= { fssCommon 1 } -- See FSS-COMMON-SMI.mib

--=====================================================================--
-- Textual Conventions                                                 --
--=====================================================================--

FCSeverity ::= TEXTUAL-CONVENTION
    STATUS      current
    DESCRIPTION
        "The severity of the standing condition."
    SYNTAX      INTEGER{
        other         (9999),  -- Other
        na            (0),     -- Not Applicable 
        critical      (1),     -- Critical
        major         (2),     -- Major
        minor         (3),     -- Minor
        not-alarmed   (4),     -- Not Alarmed
        not-reported  (5),     -- Not Reported
        warning       (6),     -- Warning 
        indeterminate (7)      -- Indeterminate
    }

FCCondEffect ::= TEXTUAL-CONVENTION
    STATUS      current
    DESCRIPTION
        "The effect of the condition."
    SYNTAX      INTEGER{
        other   (9999),      -- Other
        na      (0),         -- Not Applicable 
        cl      (1),         -- Cleared
        sc      (2),         -- Standing Condition
        tc      (3)          -- Transient Condition
    }

FCServEffect ::= TEXTUAL-CONVENTION
    STATUS      current
    DESCRIPTION
        "The effect on service caused by a standing condition."
    SYNTAX      INTEGER{
        other   (9999),      -- Other
        na      (0),         -- Not Applicable 
        sa      (1),         -- Service Affecting
        nsa     (2)          -- Non-Service Affecting
    }

FCLocation ::= TEXTUAL-CONVENTION
    STATUS      current
    DESCRIPTION
        "The location of the condition."
    SYNTAX      INTEGER{
        other (9999),     -- Other
        na    (0),        -- Not Applicable 
        nend  (1),        -- Near End
        fend  (2)         -- Far End
    }

FCDirection ::= TEXTUAL-CONVENTION
    STATUS      current
    DESCRIPTION
        "The direction of the condition."
    SYNTAX      INTEGER{
        other    (9999),  -- Other
        na       (0),     -- Not Applicable 
        receive  (1),     -- Receive
        transmit (2)      -- Transmit
    }

FCTimePeriod ::= TEXTUAL-CONVENTION
    STATUS      current
    DESCRIPTION
        "Indicates the time period for which the raised threshold 
         crossing alert is associated with."
    SYNTAX      INTEGER{
        other    (9999),  -- Other
        na       (0),     -- Not Applicable 
        min-15   (1),     -- 15 Minute
        hr-24    (2),     -- 24 Hour (1 Day)
        week-1   (3),     -- 1 Week
        month-1  (4)      -- 1 Month
    }


FCTrapType ::= TEXTUAL-CONVENTION
    STATUS      current
    DESCRIPTION
        "Indicates the type of notification that was generated.
         For every type of Trap emitted, there should be a corresponding
         Trap type defined."
    SYNTAX      INTEGER{
        other         (9999),   -- Other
        na            (0),      -- Not Applicable 
        cond          (1),      -- Condition
        tca           (2),      -- Threshold Crossing Alert
        dbchg         (3)       -- Database Change Notification
    }

FCObjectName ::= TEXTUAL-CONVENTION
    STATUS      current
    DESCRIPTION
        "The name of the object generating the trap."
    SYNTAX      DisplayString (SIZE(1..80))

FCCondType ::= TEXTUAL-CONVENTION
    STATUS      current
    DESCRIPTION
        "The possible alarms/events that are supported by fcCondTrap. 
         A value of prod-specific or qual-xxx, indicates that 
         the condition type will be further qualified by the
         product specific condition qualifier object."
    SYNTAX      INTEGER {
        prod-specific                           (0),        -- Project Specific Condition (see Condition Qualifier)

-- EQPT Alarms
        equipmentFault                          (1),        -- EQUIPMENT - Fault
        equipmentRemoved                        (2),        -- EQUIPMENT - Removed
        equipmentMismatchAttributes             (3),        -- EQUIPMENT - Mismatch
        equipmentWarmup                         (4),        -- EQUIPMENT - Warmup
        equipmentLedOn                          (5),        -- EQUIPMENT - Equipment Common Visual LED Activated
        administrativeDown                      (6),        -- GENERAL - Adminstrative State Down
        administrativeTesting                   (7),        -- GENERAL - Adminstrative State Testing
        overTemperatureEquipment                (8),        -- EQUIPMENT - EQPT Temp Over Operating Spec
        incompatibleSffHardware                 (9),        -- EQUIPMENT - Incompatible Hardware 
        configurationStandBy                    (10),       -- EQUIPMENT - Configuration Standby
        shelfProvisioningMode                   (11),       -- EQUIPMENT - Shelf Provisioning Mode
        equipmentInterConnectFailure            (12),       -- EQUIPMENT - Interconnection Failure
        equipmentMiscabledConnection            (13),       -- EQUIPMENT - Miscabled COnnection
        fanCoolingFail                          (14),       -- EQUIPMENT - Fan Cooling Failure
        equipmentCurrExceededFeed               (15),       -- EQUIPMENT - Current Exceeded on Feed
        interConnectFailureBladePiu             (16),       -- EQUIPMENT - Interconnection Failure Blade PIU
        lampTest                                (17),       -- EQUIPMENT - Lamp Test
        otdrScanInProgress                      (18),       -- EQUIPMENT - OTDR Scan In Progress

-- Common Alarms - Database
        databaseCorruption                      (100),
        databaseLockedSoftwareUpgradeInProgress (101),
        databaseLockedDbRestoreInProgress       (102),
        databaseLockedSysInitInProgress         (103),
        databaseLockedDbAlarmPresent            (104),
        databaseLockedIlfViolation              (105),
        databaseLockedShelfProvModePresent      (106),
        databaseVersionMismatch                 (107),
        databaseSystemSignatureMismatch         (108),

-- Common - SWDL Alarms
        softwareVersionMismatch                 (200),
        softwareStageInProgress                 (201), 

-- Common - FWDL Alarms
        firmwareVersionMismatch                 (300),
        firmwareInitInProgress                  (301),
        firmwareBackwardCompatibleLimited       (302),
        firmwareBackwardCompatibleAll           (303),
      --firmwareActivation                      (304),
        firmwareDownloadOrActivationFailure     (305),
        incompatibleFirmware                    (306),
        incompatibleHardware                    (307),
        noFirmware                              (308),

-- Common - SWKEYS Alarms
        ilfViolation                            (350),
        ilfViolationCritical                    (351),
        ilfViolationMajor                       (352),

-- Common - System Alarms
        softwareReset                           (400),

-- Common - NTP Alarms
        sysNtpNotSynchronized                   (450),
        interConnectFailure                     (451),
        sysNameChanged                          (452),

-- Common - HTTPS Alarms
        certificateNotInstalled                 (470),

-- Common - GCC Alarms
        generalCommunicationChannel0Failure     (500),

-- Power Module Alarms
        powerProblem                            (600),
        powerProblemA                           (601),
        powerProblemB                           (602),

-- Facility Alarms
        opticalPowerReceive                     (1001),
        opticalPowerTransmit                    (1002),
        lossOfSignal                            (1003),
        lossOfFrame                             (1004),
        lossOfMultiframe                        (1005),
        backwardDefectIndication                (1006),
        forwardDefectIndication                 (1007),
        signalDegrade                           (1008),
        trailTraceMismatch                      (1009),
        backwardIncomingAlignmentError          (1010),
        incomingAlignmentError                  (1011),
        alarmIndicationSignal                   (1012),
        openConnectionIndication                (1013),
        locked                                  (1014),
        lossofTandemConnection                  (1015),
        payloadMismatch                         (1016),
        clientSignalFailDefect                  (1017),
        multiplexStructureIdentifierMismatch    (1018),
        lossOfOmfIndication                     (1019),
        lossOfFrameAndLossOfMultiframe          (1020),
        cnOutOfRange                            (1021),
        cnLossOfSynchronization                 (1022),
        highBER                                 (1023),
        localFault                              (1024),
        remoteFault                             (1025),
        lossOfAlignment                         (1026),
        lossOfSynchronization                   (1027),
        lossOfFECAlignment                      (1028),
        remoteLANFault                          (1029),
        lanTransmitLocalFault                   (1030),
        lanTransmitRemoteFault                  (1031),
        lanTransmitOff                          (1032),
        facilityLoopbackActive                  (1033),
        facilityLoopback2Active                 (1034),
        terminalLoopbackActive                  (1035),
        facilityTestsignalActive                (1036),
        terminalTestsignalActive                (1037),
        linkDown                                (1038),
        powerOutOfSpecification                 (1039),
        powerOutOfSpecificationHigh             (1040),
        powerOutOfSpecificationHighL1           (1041),
        powerOutOfSpecificationHighL2           (1042),
        powerOutOfSpecificationHighL3           (1043),
        powerOutOfSpecificationHighL4           (1044),
        powerOutOfSpecificationLow              (1045),
        powerOutOfSpecificationLowL1            (1046),
        powerOutOfSpecificationLowL2            (1047),
        powerOutOfSpecificationLowL3            (1048),
        powerOutOfSpecificationLowL4            (1049),
        fanFilterShouldBeReplaced               (1050),
        fanFilterShouldBeCleaned                (1051),
        equipmentOverTemperature                (1052),
        portLossOfLight                         (1053),
        thresholdCrossingAlertSpanlossVariationTooLow        (1054),
        thresholdCrossingAlertSpanlossVariationTooHigh       (1055),
        thresholdCrossingAlertOscOpticalReceivePowerTooHigh  (1056),
        thresholdCrossingAlertOscOpticalReceivePowerTooLow   (1057),
        thresholdCrossingAlertOscOpticalTransmitPowerTooHigh (1058),
        thresholdCrossingAlertOscOpticalTransmitPowerTooLow  (1059),
        thresholdCrossingAlertOpticalReceivePowerTooHigh     (1060),
        thresholdCrossingAlertOpticalReceivePowerTooLow      (1061),
        thresholdCrossingAlertOpticalTransmitPowerTooHigh    (1062),
        thresholdCrossingAlertOpticalTransmitPowerTooLow     (1063),
        postBlockAutoLaserShutdown              (1064),
        postBlockAutoPowerReduction             (1065),
        postBlockManualLaserShutdown            (1066),
        preBlockSpanAdjustmentInProgress        (1067),
        postBlockSpanAdjustmentInProgress       (1068),
        payloadMissingIndication                (1069),
        manualOverrideActive                    (1070),
        unequippedIndication                    (1071),
        reflectionTooHigh                       (1072),
        oscPowerOutOfSpecificationHigh          (1073),
        oscPowerOutOfSpecificationLow           (1074),
        oscControlFailure                       (1075),
        modeMismatch                            (1076),
        omsPowerOutOfSpecificationHigh          (1077),
        omsPowerOutOfSpecificationLow           (1078),
        otsSpanlossPowerOutOfSpecificationHigh  (1079),
        otsSpanlossPowerOutOfSpecificationLow   (1080),
        autoPowerReduction                      (1081),
        postBlockAutoShutoffDisabled            (1082),
        totalpowerOutOfSpecificationHigh        (1083),
        totalpowerOutOfSpecificationLow         (1084),

-- DIP Alarms
        dipSessionActive                        (1500),

-- PPP Alarms
        pPPFailure                              (1600),

-- LLDP Alarms
       lldpFail                                 (1700)
    }

FCTcCondType ::= TEXTUAL-CONVENTION
    STATUS  current
    DESCRIPTION
        "The possible transient conditions that are supported by fcTcTrap." 
    SYNTAX  INTEGER {
        prod-specific            (0),        -- Project Specific TC (see TC Qualifier)

-- Protection Events
        manualSwitch                            (10001),
        workingSwitchProtection                 (10002),
        workingSwitchProtectionManual           (10003),
        workingSwitchProtectionForced           (10004),
        workingSwitchWorking                    (10005),

-- Database Activation Events
        databaseActivation                      (10100),
        databaseActivationFailure               (10101),
        databaseActivationReversion             (10102),


-- Firmware Activation Events
        firmwareActivation                      (10200),
        firmwareActivationComplete              (10201),
        firmwareActivationFailure               (10202),

-- SWDL
    -- Software Activation Events
        softwareActivation                      (10300),
        softwareActivationComplete              (10301),
        softwareActivationFailure               (10302),
        softwareReversion                       (10303),
    -- Cancel Validation Timer events
        cancelValidationTimerInProgress         (10304),
        cancelValidationTimerComplete           (10305),
        cancelValidationTimerFailed             (10306),
        uBootFailOver                           (10307),
        softwareFailOver                        (10308),

-- Date & Time Events
        daylightSavingTimeAdjustment            (10400),
        dateTimeModified                        (10401),

-- NTP Events
        sysNtpSynchronized                      (10500),
        sysNtpSwitchOver                        (10501),

-- System Restart Events
        systemRestartCold                       (10600),
        systemRestartWarm                       (10601),
        systemRestartDbInitialization           (10602),
        systemRestartShfprov                    (10603),

-- Copy File Events
        copyFileInProgress                      (10700),
        copyFileComplete                        (10701),
        copyFileFailure                         (10702),
        copyFileFailureTransfer                 (10703),
        copyFileFailureMd5check                 (10704),
        copyFileFailureVerification             (10705),

-- Equipment Status Events
        equipmentPlugin                         (10800),
        equipmentPlugout                        (10801),

-- Entity Oper Status Change Events
        entityOperStatusChangeToUp              (10900),
        entityOperStatusChangeToDown            (10901),
        entityOperStatusChangeToTesting         (10902),
        entityOperStatusChangeToUnknown         (10903),
        entityOperStatusChangeToDormant         (10904),
        entityOperStatusChangeToNotPresent      (10905),
        entityOperStatusChangeToLowerLayerDown  (10906),

-- Auto/Force Logoff Events
        autoLogoffAssociationCancellation       (11000),
        autoLogoffSessionTimeout                (11001),
        autoLogoffCableDisconnect               (11002),
        autoLogoffPasswordChanged               (11003),
        forcedLogoff                            (11004),

-- IP Events
        ipNotReachable                          (11100),
        ipReachable                             (11101),
        ipPingRequestTimedOut                   (11102),

-- Protocol Events
        lldpNbrInfoChanged                      (11200),

-- OTDR Events
        otdrScanComplete                        (11300),
        otdrScanFailure                         (11301)

    }
               
FCTcaCondType ::= TEXTUAL-CONVENTION
    STATUS  current
    DESCRIPTION
        "The possible threshold crossing alerts that are supported by fcTcaTrap." 
    SYNTAX  INTEGER {
        prod-specific            (0),        -- Project Specific TCA (see TCA Qualifier)

-- Port TCA
        tCAOpticalReceivePowerTooLow            (1),
        tCAOpticalReceivePowerTooHigh           (2),
        tCAOpticalTransmitPowerTooLow           (3),
        tCAOpticalTransmitPowerTooHigh          (4),
        tCALaserBiasCurrentTooHigh              (5),
        -- Port Lane 1 TCA
        tCAOpticalReceivePowerLane1TooLow       (6),
        tCAOpticalReceivePowerLane1TooHigh      (7),
        tCAOpticalTransmitPowerLane1TooLow      (8),
        tCAOpticalTransmitPowerLane1TooHigh     (9),
        tCALaserBiasCurrentLane1TooHigh         (10),
        -- Port Lane 2 TCA
        tCAOpticalReceivePowerLane2TooLow       (11),
        tCAOpticalReceivePowerLane2TooHigh      (12),
        tCAOpticalTransmitPowerLane2TooLow      (13),
        tCAOpticalTransmitPowerLane2TooHigh     (14),
        tCALaserBiasCurrentLane2TooHigh         (15),
        -- Port Lane 3 TCA
        tCAOpticalReceivePowerLane3TooLow       (16),
        tCAOpticalReceivePowerLane3TooHigh      (17),
        tCAOpticalTransmitPowerLane3TooLow      (18),
        tCAOpticalTransmitPowerLane3TooHigh     (19),
        tCALaserBiasCurrentLane3TooHigh         (20),
        -- Port Lane 4 TCA
        tCAOpticalReceivePowerLane4TooLow       (21),
        tCAOpticalReceivePowerLane4TooHigh      (22),
        tCAOpticalTransmitPowerLane4TooLow      (23),
        tCAOpticalTransmitPowerLane4TooHigh     (24),
        tCALaserBiasCurrentLane4TooHigh         (25),

        tCATotalOpticalReceivePowerTooLow       (26),
        tCATotalOpticalReceivePowerTooHigh      (27),
        -- L0 specific Port TCA
        tCASpanlossVariationTooLow              (28),
        tCASpanlossVariationTooHigh             (29),
        tCAOpticalReceivePowerOscTooLow         (30),
        tCAOpticalReceivePowerOscTooHigh        (31),
        tCAOpticalTransmitPowerOscTooLow        (32),
        tCAOpticalTransmitPowerOscTooHigh       (33),


-- Facility TCA
        tCAFECCorrectedCodewords                (201),      
        tCAFECUncorrectedCodewords              (202),
        tCAFECCorrectedSymbols                  (203),
        tCACodingViolations                     (204),
        tCAErroredSeconds                       (205),
        tCASeverelyErroredSeconds               (206),
        tCAFECUncorrectedBlocks                 (207),
        tCAFECCorrectedBits                     (208),
        tCASDFECCorrectedBits                   (209),
        tCABackgroundBlockErrors                (210),
        tCADelayMeasurement                     (211),
        tCAUnavailableSeconds                   (212),
        tCAErroredBlocks                        (213)
    }

FCStdObjectIndex ::= TEXTUAL-CONVENTION
    STATUS      current
    DESCRIPTION
        "A sequencial index."
    SYNTAX      Unsigned32 (1..4294967295)

FCStdTypeIndex ::= TEXTUAL-CONVENTION
    STATUS      current
    DESCRIPTION
        "A sequencial subindex."
    SYNTAX      Unsigned32 (1..4294967295) 

FCTrapHistIndex ::= TEXTUAL-CONVENTION
    STATUS      current
    DESCRIPTION
        "A sequencial Trap index."
    SYNTAX      Unsigned32 (1..4294967295)

FCMonType ::= TEXTUAL-CONVENTION
    STATUS  current
    DESCRIPTION
        "The possible Mon Types Supported."
    SYNTAX  INTEGER {
        prod-specific            (0)        -- Project Specific TCA (see TCA Qualifier)
    }

END
