FIBERMUX-MIB

-- Title:	FIBERMUX MIB
-- Date:	September 24, 1990


	DEFINITIONS ::= BEGIN

	IMPORTS
		enterprises, NetworkAddress, IpAddress,
		Counter, Gauge, TimeTicks
		FROM RFC1065-SMI
		OBJECT-TYPE FROM RFC-1212;

	fibermux	OBJECT IDENTIFIER ::=	{ enterprises 120 }
	fmxProducts	OBJECT IDENTIFIER ::=	{ fibermux 1 }
	fmxCrossbow	OBJECT IDENTIFIER ::=	{ fmxProducts 1 }
	fmxVariables	OBJECT IDENTIFIER ::=	{ fibermux 2 }
	fmxHubs 	OBJECT IDENTIFIER ::=	{ fmxVariables 1 }
	fmxSystemGrp	OBJECT IDENTIFIER ::=	{ fmxHubs 1 }
	fmxCrossbowGrp	OBJECT IDENTIFIER ::=	{ fmxHubs 2 }


	fmxHubHwVer	OBJECT-TYPE
		SYNTAX	OCTET STRING
		ACCESS	read-only
		STATUS	mandatory
DESCRIPTION ""
		::= { fmxSystemGrp 1 }

	fmxHubFwVer	OBJECT-TYPE
		SYNTAX	OCTET STRING
		ACCESS	read-only
		STATUS	mandatory
DESCRIPTION ""
		::= { fmxSystemGrp 2 }

	fmxHubAddress	OBJECT-TYPE
		SYNTAX	OCTET STRING
		ACCESS	read-only
		STATUS	mandatory
DESCRIPTION ""
		::= { fmxSystemGrp 3 }

	fmxHubDate	OBJECT-TYPE
		SYNTAX	OBJECT IDENTIFIER
		ACCESS	read-write
		STATUS	mandatory
DESCRIPTION ""
		::= { fmxSystemGrp 4 }

	fmxHubElapsetick OBJECT-TYPE
		SYNTAX	TimeTicks
		ACCESS	read-only
		STATUS	mandatory
DESCRIPTION ""
		::= { fmxSystemGrp 5 }

	fmxHubSamplingRate OBJECT-TYPE
		SYNTAX	Gauge
		ACCESS	read-write
		STATUS	mandatory
DESCRIPTION ""
		::= { fmxSystemGrp 6 }

	fmxHubPeakTraffic OBJECT-TYPE
		SYNTAX	Gauge
		ACCESS	read-only
		STATUS	mandatory
DESCRIPTION ""
		::= { fmxSystemGrp 7 }

	fmxHubAverageTraffic OBJECT-TYPE
		SYNTAX	Gauge
		ACCESS	read-only
		STATUS	mandatory
DESCRIPTION ""
		::= { fmxSystemGrp 8 }

	fmxHubCurrentTraffic OBJECT-TYPE
		SYNTAX	Gauge
		ACCESS	read-only
		STATUS	mandatory
DESCRIPTION ""
		::= { fmxSystemGrp 9 }

	fmxHubTotalFrameRx OBJECT-TYPE
		SYNTAX	Counter
		ACCESS	read-only
		STATUS	mandatory
DESCRIPTION ""
		::= { fmxSystemGrp 10 }

	fmxHubAverageByte OBJECT-TYPE
		SYNTAX	Gauge
		ACCESS	read-only
		STATUS	mandatory
DESCRIPTION ""
		::= { fmxSystemGrp 11 }

	fmxHubCRCErrors OBJECT-TYPE
		SYNTAX	Counter
		ACCESS	read-only
		STATUS	mandatory
DESCRIPTION ""
		::= { fmxSystemGrp 12 }

	fmxHubAlignErrors OBJECT-TYPE
		SYNTAX	Counter
		ACCESS	read-only
		STATUS	mandatory
DESCRIPTION ""
		::= { fmxSystemGrp 13 }

	fmxHubMissedErrors OBJECT-TYPE
		SYNTAX	Counter
		ACCESS	read-only
		STATUS	mandatory
DESCRIPTION ""
		::= { fmxSystemGrp 14 }

	fmxHubStatus OBJECT-TYPE
		SYNTAX	INTEGER {
			pwrAB-bad(0),
			pwrB-OK(1),
			pwrA-OK(2),
			pwrAB-OK(3)
		}
		ACCESS	read-only
		STATUS	mandatory
DESCRIPTION ""
		::= { fmxSystemGrp 15 }

	fmxHubClear	OBJECT-TYPE
		SYNTAX	INTEGER {
			on(1)
		}
		ACCESS	write-only
		STATUS	mandatory
DESCRIPTION ""
		::= { fmxSystemGrp 16 }

	fmxCbCardTable OBJECT-TYPE
		SYNTAX	SEQUENCE OF FmxCbCardEntry
		ACCESS	read-write
		STATUS	mandatory
DESCRIPTION ""
		::= { fmxCrossbowGrp 1 }

	fmxCbCardEntry OBJECT-TYPE
		SYNTAX	FmxCbCardEntry
		ACCESS	read-write
		STATUS	mandatory
DESCRIPTION ""
		::= { fmxCbCardTable 1 }

	FmxCbCardEntry ::= SEQUENCE {
		fmxCbCIndex
			INTEGER,
		fmxCbCType
			INTEGER,
		fmxCbCReset
			INTEGER,
		fmxCbCEnable
			INTEGER,
		fmxCbCFIFOError
			INTEGER,
		fmxCbCJabberError
			INTEGER,
		fmxCbCLockup
			INTEGER,
		fmxCbCTraffic
			INTEGER,
		fmxCbCTimeslot
			INTEGER,
		fmxCbCAddress
			INTEGER
	}

	fmxCbCIndex	OBJECT-TYPE
		SYNTAX	INTEGER
		ACCESS	read-only
		STATUS	mandatory
DESCRIPTION ""
		::= { fmxCbCardEntry 1 }

	fmxCbCType	OBJECT-TYPE
		SYNTAX	INTEGER
		ACCESS	read-only
		STATUS	mandatory
DESCRIPTION ""
		::= { fmxCbCardEntry 2 }

	fmxCbCReset	OBJECT-TYPE
		SYNTAX	INTEGER {
			on(1)
		}
		ACCESS	write-only
		STATUS	mandatory
DESCRIPTION ""
		::= { fmxCbCardEntry 3 }

	fmxCbCEnable OBJECT-TYPE
		SYNTAX	INTEGER {
			off(0),
			on(1)
		}
		ACCESS	read-write
		STATUS	mandatory
DESCRIPTION ""
		::= { fmxCbCardEntry 4 }

	fmxCbCFIFOError OBJECT-TYPE
		SYNTAX	INTEGER {
			off(0),
			on(1)
		}
		ACCESS	read-only
		STATUS	mandatory
DESCRIPTION ""
		::= { fmxCbCardEntry 5 }

	fmxCbCJabberError OBJECT-TYPE
		SYNTAX	INTEGER {
			off(0),
			on(1)
		}
		ACCESS	read-only
		STATUS	mandatory
DESCRIPTION ""
		::= { fmxCbCardEntry 6 }

	fmxCbCLockup OBJECT-TYPE
		SYNTAX	INTEGER {
			off(0),
			on(1)
		}
		ACCESS	read-only
		STATUS	mandatory
DESCRIPTION ""
		::= { fmxCbCardEntry 7 }

	fmxCbCTraffic OBJECT-TYPE
		SYNTAX	INTEGER {
			off(0),
			on(1)
		}
		ACCESS	read-only
		STATUS	mandatory
DESCRIPTION ""
		::= { fmxCbCardEntry 8 }

	fmxCbCTimeslot OBJECT-TYPE
		SYNTAX	INTEGER
		ACCESS	read-write
		STATUS	mandatory
DESCRIPTION ""
		::= { fmxCbCardEntry 9 }

	fmxCbCAddress OBJECT-TYPE
		SYNTAX	INTEGER
		ACCESS	read-only
		STATUS	mandatory
DESCRIPTION ""
		::= { fmxCbCardEntry 10 }

	fmxCbCPortTable OBJECT-TYPE
		SYNTAX	SEQUENCE OF FmxCbCPortEntry
		ACCESS	read-write
		STATUS	mandatory
DESCRIPTION ""
		::= { fmxCrossbowGrp 2 }

	fmxCbCPortEntry OBJECT-TYPE
		SYNTAX	FmxCbCPortEntry
		ACCESS	read-write
		STATUS	mandatory
DESCRIPTION ""
		::= { fmxCbCPortTable 1 }

	FmxCbCPortEntry ::= SEQUENCE {
		fmxCbCPIndex
			INTEGER,
		fmxCbCPIntegrity
			INTEGER,
		fmxCbCPJabberError
			INTEGER,
		fmxCbCPEnable
			INTEGER,
		fmxCbCPRedundCtrl
			INTEGER,
		fmxCbCPRedundPrimary
			INTEGER,
		fmxCbCPRedundActive
			INTEGER,
		fmxCbCPRedundPort
			INTEGER,
		fmxCbCPRedundCard
			INTEGER,
		fmxCbCPRedundErrors
			Counter,
		fmxCbCPRedundErrorLimit
			Gauge
	}

	fmxCbCPIndex OBJECT-TYPE
		SYNTAX	INTEGER
		ACCESS	read-only
		STATUS	mandatory
DESCRIPTION ""
		::= { fmxCbCPortEntry 1 }

	fmxCbCPEnable OBJECT-TYPE
		SYNTAX	INTEGER {
			off(0),
			on(1)
		}
		ACCESS	read-write
		STATUS	mandatory
DESCRIPTION ""
		::= { fmxCbCPortEntry 2 }

	fmxCbCPIntegrity OBJECT-TYPE
		SYNTAX	INTEGER {
			off(0),
			on(1)
		}
		ACCESS	read-only
		STATUS	mandatory
DESCRIPTION ""
		::= { fmxCbCPortEntry 3 }

	fmxCbCPJabberError OBJECT-TYPE
		SYNTAX	INTEGER {
			off(0),
			on(1)
		}
		ACCESS	read-only
		STATUS	mandatory
DESCRIPTION ""
		::= { fmxCbCPortEntry 4 }

	fmxCbCPRedundCtrl OBJECT-TYPE
		SYNTAX	INTEGER {
			off(0),
			on(1)
		}
		ACCESS	read-write
		STATUS	mandatory
DESCRIPTION ""
		::= { fmxCbCPortEntry 5 }

	fmxCbCPRedundPrimary OBJECT-TYPE
		SYNTAX	INTEGER {
			off(0),
			on(1)
		}
		ACCESS	read-write
		STATUS	mandatory
DESCRIPTION ""
		::= { fmxCbCPortEntry 6 }

	fmxCbCPRedundActive OBJECT-TYPE
		SYNTAX	INTEGER {
			off(0),
			on(1)
		}
		ACCESS	read-only
		STATUS	mandatory
DESCRIPTION ""
		::= { fmxCbCPortEntry 7 }

	fmxCbCPRedundPort OBJECT-TYPE
		SYNTAX	INTEGER
		ACCESS	read-write
		STATUS	mandatory
DESCRIPTION ""
		::= { fmxCbCPortEntry 8 }

	fmxCbCPRedundCard OBJECT-TYPE
		SYNTAX	INTEGER
		ACCESS	read-write
		STATUS	mandatory
DESCRIPTION ""
		::= { fmxCbCPortEntry 9 }

	fmxCbCPRedundErrors OBJECT-TYPE
		SYNTAX	Counter
		ACCESS	read-only
		STATUS	mandatory
DESCRIPTION ""
		::= { fmxCbCPortEntry 10 }

	fmxCbCPRedundErrorLimit OBJECT-TYPE
		SYNTAX	Gauge
		ACCESS	read-write
		STATUS	mandatory
DESCRIPTION ""
		::= { fmxCbCPortEntry 11 }

	END
