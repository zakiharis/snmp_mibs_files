F3-L3-MIB DEFINITIONS ::= BEGIN

IMPORTS
    MODULE-IDENTITY, OBJECT-TYPE, Integer32, Unsigned32, IpAddress, Counter64
             FROM SNMPv2-SMI
    MODULE-COMPLIANCE, OBJECT-GROUP
             FROM SNMPv2-CONF
    DateAndTime, DisplayString, TruthValue, RowStatus, StorageType, 
    MacAddress, VariablePointer, TEXTUAL-CONVENTION
             FROM SNMPv2-TC
    Ipv6Address
             FROM IPV6-TC
    InterfaceIndex, ifIndex
             FROM IF-MIB
    PhysicalIndex
             FROM ENTITY-MIB
    fsp150cm
             FROM  ADVA-MIB 
    AdminState, OperationalState, SecondaryState, VlanId, VlanPriority,
    F3DisplayString, IpVersion, TrafficDirection, 
    CmPmIntervalType, CmPmBinAction, PerfCounter64
             FROM  CM-COMMON-MIB
    CmDhcpRole, DHCPHostNameType, DHCPCIDType,IpEntryType
             FROM  CM-IP-MIB
    neIndex, shelfIndex, slotIndex
             FROM CM-ENTITY-MIB
    PolicerAlgorithmType, PolicerColorMode
             FROM CM-FACILITY-MIB;

f3L3MIB MODULE-IDENTITY
    LAST-UPDATED    "201409120000Z"
    ORGANIZATION    "ADVA Optical Networking"
    CONTACT-INFO
            "        Jack Chen
                     ADVA Optical Networking, Inc.
                Tel: +86755 86217400-8205
             E-mail: jchen@advaoptical.com
             Postal: 
             "
    DESCRIPTION
            "This module defines the L3 MIB definitions used by 
             the F3 (FSP150CM/CC) product lines.
             Copyright (C) ADVA Optical Networking."
    REVISION        "201409120000Z"
    DESCRIPTION
        "Notes from release 201409120000Z" 
    ::= {fsp150cm 37}    

-- 
-- OID definitions
-- 
f3L3Objects        OBJECT IDENTIFIER ::= {f3L3MIB 1}
f3L3Performance    OBJECT IDENTIFIER ::= {f3L3MIB 2}
f3L3Notifications  OBJECT IDENTIFIER ::= {f3L3MIB 3}
f3L3Conformance    OBJECT IDENTIFIER ::= {f3L3MIB 4}

--
-- Textual Conventions
--
VrfAction ::= TEXTUAL-CONVENTION
    STATUS       current
    DESCRIPTION
        "Describes the action on Vrf."
    SYNTAX       INTEGER {
                   notApplicable (0),
                   ping (1),
                   fluchARPCache(2),
                   traceRoute(3),
                   retrieveEffectiveRoutes(4)
                 }

IfIpAddressSourceType ::= TEXTUAL-CONVENTION
    STATUS       current
    DESCRIPTION
        "Describes the Ip Interface adress source type."
    SYNTAX       INTEGER {
                   dhcp (1),
                   static(2)
                 }

DhcpRelayInterfaceSide ::= TEXTUAL-CONVENTION
    STATUS       current
    DESCRIPTION
        "Describes the DHCP relay interface side."
    SYNTAX       INTEGER {
                   client (1),
                   server(2)
                 }

L3AclRuleOperation ::= TEXTUAL-CONVENTION
    STATUS       current
    DESCRIPTION
        "Describes the acl rule operation."
    SYNTAX       INTEGER {
                   notApplicable (0),
                   accept (1),
                   deny (2)
                 }

AclRuleL2Side ::= TEXTUAL-CONVENTION
    STATUS       current
    DESCRIPTION
        "Describes the acl rule l2 side."
    SYNTAX       INTEGER {
                   access(1),
                   network(2)
                 }

TrafficIpRouteStatus ::= TEXTUAL-CONVENTION
    STATUS       current
    DESCRIPTION
        "Describes the traffci ipv4 route status."
    SYNTAX       INTEGER {
                   active(1),
                   nexthopUnresovled(2),
                   interfaceOutage(3),
                   noResources(4),
                   standby(5)
                 }

RouteFlags ::= TEXTUAL-CONVENTION
    STATUS       current
    DESCRIPTION
        "Describes the traffci ipv4 route flags."
    SYNTAX       BITS {
                   dDynamic(0),
                   gUseGW(1),
                   hFullMask(2),
                   mModifiedByIcmp(3),
                   oOutage(4),
                   uNormal(5)
                 }

AffectiveArpActionType ::= TEXTUAL-CONVENTION
    STATUS       current
    DESCRIPTION
        "Describes the retrieve effective arp action."
    SYNTAX       INTEGER {
                   notApplicable (0),
                   retrieveAffectiveArp (1)
                 }


--
--  Mac Sec Table
--
f3DhcpRelayAgentTable  OBJECT-TYPE
    SYNTAX      SEQUENCE OF F3DhcpRelayAgentEntry
    MAX-ACCESS  not-accessible
    STATUS      current
    DESCRIPTION
            "A list of entries for the Dhcp Relay Agent."
    ::= { f3L3Objects 1 }

f3DhcpRelayAgentEntry  OBJECT-TYPE
    SYNTAX      F3DhcpRelayAgentEntry
    MAX-ACCESS  not-accessible
    STATUS      current
    DESCRIPTION
            "A conceptual row in the f3DhcpRelayAgentTable."
    INDEX { neIndex, f3DhcpRelayAgentIndex }
    ::= { f3DhcpRelayAgentTable 1 }

F3DhcpRelayAgentEntry ::= SEQUENCE {
    f3DhcpRelayAgentIndex                               Integer32,
    f3DhcpRelayAgentAlias                               F3DisplayString,
    f3DhcpRelayAgentAdminState                          AdminState,
    f3DhcpRelayAgentSecondaryState                      SecondaryState,
    f3DhcpRelayAgentOperationalState                    OperationalState,
    f3DhcpRelayAgentIpVersion                           IpVersion,
    f3DhcpRelayAgentServerIpAddress                     IpAddress,
    f3DhcpRelayAgentOp82SubOp9ControlEnabled            TruthValue,
    f3DhcpRelayAgentOp82SubOp9Value                     DisplayString,
    f3DhcpRelayAgentStorageType                         StorageType,
    f3DhcpRelayAgentRowStatus                           RowStatus
}

f3DhcpRelayAgentIndex OBJECT-TYPE
    SYNTAX      Integer32
    MAX-ACCESS  not-accessible
    STATUS      current
    DESCRIPTION
           "The index of the DHCP relay agent entry."
    ::= { f3DhcpRelayAgentEntry 1 }

f3DhcpRelayAgentAlias OBJECT-TYPE
    SYNTAX      F3DisplayString (SIZE (0..256))
    MAX-ACCESS  read-write
    STATUS      current
    DESCRIPTION
           "The DHCP relay agent alias."
    ::= { f3DhcpRelayAgentEntry 2 }

f3DhcpRelayAgentAdminState OBJECT-TYPE
    SYNTAX      AdminState
    MAX-ACCESS  read-write
    STATUS      current
    DESCRIPTION
           "The admin state of this DCHP relay agent."
    ::= { f3DhcpRelayAgentEntry 3 }

f3DhcpRelayAgentSecondaryState OBJECT-TYPE
    SYNTAX      SecondaryState
    MAX-ACCESS  read-only
    STATUS      current
    DESCRIPTION
           "The secondary state of this DCHP relay agent."
    ::= { f3DhcpRelayAgentEntry 4 }

f3DhcpRelayAgentOperationalState OBJECT-TYPE
    SYNTAX      OperationalState
    MAX-ACCESS  read-only
    STATUS      current
    DESCRIPTION
           "The operational state of this DCHP relay agent."
    ::= { f3DhcpRelayAgentEntry 5 }

f3DhcpRelayAgentIpVersion OBJECT-TYPE
    SYNTAX      IpVersion
    MAX-ACCESS  read-write
    STATUS      current
    DESCRIPTION
           "The Ip version of this DCHP relay agent."
    ::= { f3DhcpRelayAgentEntry 6 }

f3DhcpRelayAgentServerIpAddress OBJECT-TYPE
    SYNTAX      IpAddress
    MAX-ACCESS  read-write
    STATUS      current
    DESCRIPTION
           "The Ipv4 address of this DCHP relay agent."
    ::= { f3DhcpRelayAgentEntry 7 }

f3DhcpRelayAgentOp82SubOp9ControlEnabled OBJECT-TYPE
    SYNTAX      TruthValue
    MAX-ACCESS  read-write
    STATUS      current
    DESCRIPTION
           "This object describes the suboption9 of the option82 whether enabled."
    ::= { f3DhcpRelayAgentEntry 8 }

f3DhcpRelayAgentOp82SubOp9Value OBJECT-TYPE
    SYNTAX      DisplayString (SIZE (0..255))
    MAX-ACCESS  read-write
    STATUS      current
    DESCRIPTION
           "This object describes the vendor string if the suboption9 enabled."
    ::= { f3DhcpRelayAgentEntry 9 }

f3DhcpRelayAgentStorageType OBJECT-TYPE
    SYNTAX     StorageType
    MAX-ACCESS read-create
    STATUS     current
    DESCRIPTION
            "The type of storage configured for this entry."
    ::= { f3DhcpRelayAgentEntry 10 }

f3DhcpRelayAgentRowStatus OBJECT-TYPE
    SYNTAX      RowStatus
    MAX-ACCESS  read-create
    STATUS      current
    DESCRIPTION
            "The status of this row.
            An entry MUST NOT exist in the active state unless all
            objects in the entry have an appropriate value, as described
            in the description clause for each writable object.

            The values of f3DhcpRelayAgentRowStatus supported are
            createAndGo(4) and destroy(6).  All mandatory attributes
            must be specified in a single SNMP SET request with
            f3DhcpRelayAgentRowStatus value as createAndGo(4).
            Upon successful row creation, this variable has a
            value of active(1).

            The f3DhcpRelayAgentRowStatus object may be modified if
            the associated instance of this object is equal to active(1)."
    ::= { f3DhcpRelayAgentEntry 11 }

--
--  VRF User Table
--
f3VrfTable  OBJECT-TYPE
    SYNTAX      SEQUENCE OF F3VrfEntry
    MAX-ACCESS  not-accessible
    STATUS      current
    DESCRIPTION
            "A list of entries for the VRF user."
    ::= { f3L3Objects 2 }

f3VrfEntry  OBJECT-TYPE
    SYNTAX      F3VrfEntry
    MAX-ACCESS  not-accessible
    STATUS      current
    DESCRIPTION
            "A conceptual row in the f3VrfTable."
    INDEX { neIndex, f3VrfIndex }
    ::= { f3VrfTable 1 }

F3VrfEntry ::= SEQUENCE {
    f3VrfIndex                               Integer32,
    f3VrfAlias                               F3DisplayString,
    f3VrfAdminState                          AdminState,
    f3VrfSecondaryState                      SecondaryState,
    f3VrfOperationalState                    OperationalState,
    f3VrfAccIsolationControlEnabled          TruthValue,
    f3VrfPingIpv4Destination                 IpAddress,
    f3VrfTraceRouteIpv4Destination           IpAddress,
    f3VrfAction                              VrfAction,
    f3VrfPingResult                          F3DisplayString,
    f3VrfTraceRouteResult                    F3DisplayString,
    f3VrfStorageType                         StorageType,
    f3VrfRowStatus                           RowStatus,
    f3VrfDhcpRoutesControl                   TruthValue
}

f3VrfIndex OBJECT-TYPE
    SYNTAX      Integer32
    MAX-ACCESS  not-accessible
    STATUS      current
    DESCRIPTION
           "The vrf number."
    ::= { f3VrfEntry 1 }

f3VrfAlias OBJECT-TYPE
    SYNTAX      F3DisplayString (SIZE (0..256))
    MAX-ACCESS  read-write
    STATUS      current
    DESCRIPTION
           "This object describes the vrf alias."
    ::= { f3VrfEntry 2 }

f3VrfAdminState OBJECT-TYPE
    SYNTAX      AdminState
    MAX-ACCESS  read-write
    STATUS      current
    DESCRIPTION
           "This object describes the vrf admin state."
    ::= { f3VrfEntry 3 }

f3VrfSecondaryState OBJECT-TYPE
    SYNTAX      SecondaryState
    MAX-ACCESS  read-only
    STATUS      current
    DESCRIPTION
           "This object describes the vrf secondary state."
    ::= { f3VrfEntry 4 }

f3VrfOperationalState OBJECT-TYPE
    SYNTAX      OperationalState
    MAX-ACCESS  read-only
    STATUS      current
    DESCRIPTION
           "This object describes the vrf operational state."
    ::= { f3VrfEntry 5 }

f3VrfAccIsolationControlEnabled OBJECT-TYPE
    SYNTAX      OperationalState
    MAX-ACCESS  read-write
    STATUS      current
    DESCRIPTION
           "This object is used to control traffic between L3 flowpoint
           on Acc port."
    ::= { f3VrfEntry 6 }

f3VrfPingIpv4Destination OBJECT-TYPE
    SYNTAX      IpAddress
    MAX-ACCESS  read-write
    STATUS      current
    DESCRIPTION
           "This object allows user to specify the IP Address to which
 	          ICMP Ping will be initiated."
    ::= { f3VrfEntry 7 }

f3VrfTraceRouteIpv4Destination OBJECT-TYPE
    SYNTAX      IpAddress
    MAX-ACCESS  read-write
    STATUS      current
    DESCRIPTION
           "This object allows user to specify the IP Address to which
          	Trace Route will be initiated."
    ::= { f3VrfEntry 8 }

f3VrfAction OBJECT-TYPE
    SYNTAX      VrfAction
    MAX-ACCESS  read-write
    STATUS      current
    DESCRIPTION
           "The Vrf action, includes fluch ARP cache, ping, trace route."
    ::= { f3VrfEntry 9 }

f3VrfPingResult OBJECT-TYPE
    SYNTAX      F3DisplayString
    MAX-ACCESS  read-only
    STATUS      current
    DESCRIPTION
           "The Ping action result."
    ::= { f3VrfEntry 10 }

f3VrfTraceRouteResult OBJECT-TYPE
    SYNTAX      F3DisplayString
    MAX-ACCESS  read-only
    STATUS      current
    DESCRIPTION
           "The trace route action result."
    ::= { f3VrfEntry 11 }

f3VrfStorageType OBJECT-TYPE
    SYNTAX     StorageType
    MAX-ACCESS read-create
    STATUS     current
    DESCRIPTION
            "The type of storage configured for this entry."
    ::= { f3VrfEntry 12 }

f3VrfRowStatus OBJECT-TYPE
    SYNTAX      RowStatus
    MAX-ACCESS  read-create
    STATUS      current
    DESCRIPTION
            "The status of this row.
            An entry MUST NOT exist in the active state unless all
            objects in the entry have an appropriate value, as described
            in the description clause for each writable object.

            The values of f3VrfRowStatus supported are
            createAndGo(4) and destroy(6).  All mandatory attributes
            must be specified in a single SNMP SET request with
            f3VrfRowStatus value as createAndGo(4).
            Upon successful row creation, this variable has a
            value of active(1).

            The f3VrfRowStatus object may be modified if
            the associated instance of this object is equal to active(1)."
    ::= { f3VrfEntry 13 }

f3VrfDhcpRoutesControl OBJECT-TYPE
    SYNTAX      TruthValue
    MAX-ACCESS  read-write
    STATUS      current
    DESCRIPTION
           "This object is used to control dynamic routes creation based on DHCP relay agent operation.
           if it is disabled, the vrf should not use host ip addresses assigned by means of DHCP relay agent
           for the dynamic routes creation."
    ::= { f3VrfEntry 14 }

--
--  L3 flowpoint Table
--
f3L3FlowPointTable  OBJECT-TYPE
    SYNTAX      SEQUENCE OF F3L3FlowPointEntry
    MAX-ACCESS  not-accessible
    STATUS      current
    DESCRIPTION
            "A list of entries for the L3 flowpoint."
    ::= { f3L3Objects 3 }

f3L3FlowPointEntry  OBJECT-TYPE
    SYNTAX      F3L3FlowPointEntry
    MAX-ACCESS  not-accessible
    STATUS      current
    DESCRIPTION
            "A conceptual row in the f3L3FlowPointTable."
    INDEX { neIndex, shelfIndex, slotIndex, f3L3FlowPointPortTypeIndex, f3L3FlowPointPortIndex, f3L3FlowPointIndex }
    ::= { f3L3FlowPointTable 1 }

F3L3FlowPointEntry ::= SEQUENCE {
    f3L3FlowPointPortTypeIndex                       Integer32,
    f3L3FlowPointPortIndex                           Integer32,
    f3L3FlowPointIndex                               Integer32,
    f3L3FlowPointAlias                               F3DisplayString,
    f3L3FlowPointAdminState                          AdminState,
    f3L3FlowPointSecondaryState                      SecondaryState,
    f3L3FlowPointOperationalState                    OperationalState,
    f3L3FlowPointMultiCOSEnabled                     TruthValue,
    f3L3FlowPointCOS                                 Integer32,
    f3L3FlowPointUntaggedMemberShipEnabled           TruthValue,
    f3L3FlowPointOuterTagMemberShipEnabled           TruthValue,
    f3L3FlowPointOuterTagMemberShipVlanId            VlanId,
    f3L3FlowPointInnerTagMemberShipEnabled           TruthValue,
    f3L3FlowPointInnerTagMemberShipVlanId            VlanId,
    f3L3FlowPointFragmentedPktsFwdEnabled            TruthValue,
    f3L3FlowPointHCosMgmtEnabled                     TruthValue,
    f3L3FlowPointHCosGuaranteedBwHi                  Unsigned32,
    f3L3FlowPointHCosGuaranteedBwLo                  Unsigned32,
    f3L3FlowPointHCosMaximumBwHi                     Unsigned32,
    f3L3FlowPointHCosMaximumBwLo                     Unsigned32,
    f3L3FlowPointPolicingEnabled                     TruthValue,
    f3L3FlowPointStorageType                         StorageType,
    f3L3FlowPointRowStatus                           RowStatus
}

f3L3FlowPointPortTypeIndex OBJECT-TYPE
    SYNTAX      Integer32
    MAX-ACCESS  not-accessible
    STATUS      current
    DESCRIPTION
           "It specifies the port type, value 1 means net port, value 2 means acc port."
    ::= { f3L3FlowPointEntry 1 }

f3L3FlowPointPortIndex OBJECT-TYPE
    SYNTAX      Integer32
    MAX-ACCESS  not-accessible
    STATUS      current
    DESCRIPTION
           "The port number value."
    ::= { f3L3FlowPointEntry 2 }

f3L3FlowPointIndex OBJECT-TYPE
    SYNTAX      Integer32
    MAX-ACCESS  not-accessible
    STATUS      current
    DESCRIPTION
           "The L3 flow point number."
    ::= { f3L3FlowPointEntry 3 }

f3L3FlowPointAlias OBJECT-TYPE
    SYNTAX      F3DisplayString (SIZE (0..256))
    MAX-ACCESS  read-write
    STATUS      current
    DESCRIPTION
           "This object describes the L3 flow point alias."
    ::= { f3L3FlowPointEntry 4 }

f3L3FlowPointAdminState OBJECT-TYPE
    SYNTAX      AdminState
    MAX-ACCESS  read-write
    STATUS      current
    DESCRIPTION
           "This object describes the L3 flow point admin state."
    ::= { f3L3FlowPointEntry 5 }

f3L3FlowPointSecondaryState OBJECT-TYPE
    SYNTAX      SecondaryState
    MAX-ACCESS  read-only
    STATUS      current
    DESCRIPTION
           "This object describes the L3 flow point secondary state."
    ::= { f3L3FlowPointEntry 6 }

f3L3FlowPointOperationalState OBJECT-TYPE
    SYNTAX      OperationalState
    MAX-ACCESS  read-only
    STATUS      current
    DESCRIPTION
           "This object describes the L3 flow point operational state."
    ::= { f3L3FlowPointEntry 7 }

f3L3FlowPointMultiCOSEnabled OBJECT-TYPE
    SYNTAX      TruthValue
    MAX-ACCESS  read-write
    STATUS      current
    DESCRIPTION
           "Control to enable or disable per-COS BWPs on a FlowPoint.
            ENABLED:per-COS BWPs (CIR, EIR, CBS, EBS, CM, CF) are applied as a policing 
                     function for all ingress frames of this flowpoint.
            DISABLED:per-Flow BWP (CIR, EIR, CBS, EBS, CM, CF) is applied as a policing 
                     function for all ingress frames of this flowpoint.
            User must independently enable each COS BWP when ENABLED."
    ::= { f3L3FlowPointEntry 8 }

f3L3FlowPointCOS OBJECT-TYPE
    SYNTAX      Integer32
    MAX-ACCESS  read-write
    STATUS      current
    DESCRIPTION
           "Identifies the internal COS applied to all ingress frames of the flowpoint."
    ::= { f3L3FlowPointEntry 9 }

f3L3FlowPointUntaggedMemberShipEnabled OBJECT-TYPE
    SYNTAX      TruthValue
    MAX-ACCESS  read-write
    STATUS      current
    DESCRIPTION
           "This attribute controls untagged frames membership for the Flowpoint.
            ENABLED: Ingress untagged frame matches Flowpoint membership.
            DISABLED: Ingress untagged frame does not match Flowpoint membership."
    ::= { f3L3FlowPointEntry 10 }

f3L3FlowPointOuterTagMemberShipEnabled OBJECT-TYPE
    SYNTAX      TruthValue
    MAX-ACCESS  read-write
    STATUS      current
    DESCRIPTION
           "This attribute controls outer tag membership for the Flowpoint whether enabled."
    ::= { f3L3FlowPointEntry 11 }

f3L3FlowPointOuterTagMemberShipVlanId OBJECT-TYPE
    SYNTAX      VlanId
    MAX-ACCESS  read-write
    STATUS      current
    DESCRIPTION
           "This attribute controls outer tag VlanId membership for the Flowpoint."
    ::= { f3L3FlowPointEntry 12 }

f3L3FlowPointInnerTagMemberShipEnabled OBJECT-TYPE
    SYNTAX      TruthValue
    MAX-ACCESS  read-write
    STATUS      current
    DESCRIPTION
           "This attribute controls inner tag membership for the Flowpoint whether enabled."
    ::= { f3L3FlowPointEntry 13 }

f3L3FlowPointInnerTagMemberShipVlanId OBJECT-TYPE
    SYNTAX      VlanId
    MAX-ACCESS  read-write
    STATUS      current
    DESCRIPTION
           "This attribute controls inner tag VlanId membership for the Flowpoint."
    ::= { f3L3FlowPointEntry 14 }

f3L3FlowPointFragmentedPktsFwdEnabled OBJECT-TYPE
    SYNTAX      TruthValue
    MAX-ACCESS  read-write
    STATUS      current
    DESCRIPTION
           "This attribute specifies whether received IP Packets with More Fragments
            flag should be forwarded by the FlowPoint."
    ::= { f3L3FlowPointEntry 15 }

f3L3FlowPointHCosMgmtEnabled OBJECT-TYPE
    SYNTAX      TruthValue
    MAX-ACCESS  read-write
    STATUS      current
    DESCRIPTION
           "This attribute specifies whether the Hierarchical COS shaping enabled for this flow point."
    ::= { f3L3FlowPointEntry 16 }

f3L3FlowPointHCosGuaranteedBwHi OBJECT-TYPE
    SYNTAX      Unsigned32
    MAX-ACCESS  read-write
    STATUS      current
    DESCRIPTION
           "This attribute specifies the Hierarchical COS guarranteed bandwidth 
           high 32 bits for this flow point."
    ::= { f3L3FlowPointEntry 17 }

f3L3FlowPointHCosGuaranteedBwLo OBJECT-TYPE
    SYNTAX      Unsigned32
    MAX-ACCESS  read-write
    STATUS      current
    DESCRIPTION
           "This attribute specifies the Hierarchical COS guarranteed bandwidth 
           low 32 bits for this flow point."
    ::= { f3L3FlowPointEntry 18 }

f3L3FlowPointHCosMaximumBwHi OBJECT-TYPE
    SYNTAX      Unsigned32
    MAX-ACCESS  read-write
    STATUS      current
    DESCRIPTION
           "This attribute specifies the Hierarchical COS maximum bandwidth 
           high 32 bits for this flow point."
    ::= { f3L3FlowPointEntry 19 }

f3L3FlowPointHCosMaximumBwLo OBJECT-TYPE
    SYNTAX      Unsigned32
    MAX-ACCESS  read-write
    STATUS      current
    DESCRIPTION
           "This attribute specifies the Hierarchical COS maximum bandwidth 
           low 32 bits for this flow point."
    ::= { f3L3FlowPointEntry 20 }

f3L3FlowPointPolicingEnabled OBJECT-TYPE
    SYNTAX      TruthValue
    MAX-ACCESS  read-write
    STATUS      current
    DESCRIPTION
           "This attribute allows enable or disable policers of the flow point."
    ::= { f3L3FlowPointEntry 21 }

f3L3FlowPointStorageType OBJECT-TYPE
    SYNTAX     StorageType
    MAX-ACCESS read-create
    STATUS     current
    DESCRIPTION
            "The type of storage configured for this entry."
    ::= { f3L3FlowPointEntry 22 }

f3L3FlowPointRowStatus OBJECT-TYPE
    SYNTAX      RowStatus
    MAX-ACCESS  read-create
    STATUS      current
    DESCRIPTION
            "The status of this row.
            An entry MUST NOT exist in the active state unless all
            objects in the entry have an appropriate value, as described
            in the description clause for each writable object.

            The values of f3L3FlowPointRowStatus supported are
            createAndGo(4) and destroy(6).  All mandatory attributes
            must be specified in a single SNMP SET request with
            f3L3FlowPointRowStatus value as createAndGo(4).
            Upon successful row creation, this variable has a
            value of active(1).

            The f3L3FlowPointRowStatus object may be modified if
            the associated instance of this object is equal to active(1)."
    ::= { f3L3FlowPointEntry 23 }

--
--  L3 ACL Rule Table
--
f3L3AclRuleTable  OBJECT-TYPE
    SYNTAX      SEQUENCE OF F3L3AclRuleEntry
    MAX-ACCESS  not-accessible
    STATUS      current
    DESCRIPTION
            "A list of entries for the L3 ACL rule."
    ::= { f3L3Objects 4 }

f3L3AclRuleEntry  OBJECT-TYPE
    SYNTAX      F3L3AclRuleEntry
    MAX-ACCESS  not-accessible
    STATUS      current
    DESCRIPTION
            "A conceptual row in the f3L3AclRuleTable."
    INDEX { neIndex, shelfIndex, slotIndex,
            f3L3FlowPointPortIndex, f3L3AclRuleParentIndex, f3L3AclRuleIndex }
    ::= { f3L3AclRuleTable 1 }

F3L3AclRuleEntry ::= SEQUENCE {
    f3L3AclRuleParentIndex                               Integer32,
    f3L3AclRuleIndex                                     Integer32,
    f3L3AclRuleAlias                                     F3DisplayString,
    f3L3AclRuleSrcIpv4AddressControl                     TruthValue,
    f3L3AclRuleDynamicSrcIpControl                       TruthValue,
    f3L3AclRuleSrcIpv4AddressLowLimit                    IpAddress,
    f3L3AclRuleDstIpv4AddressControl                     TruthValue,
    f3L3AclRuleDstIpv4AddressLowLimit                    IpAddress,
    f3L3AclRuleIpv4PriorityControl                       TruthValue,
    f3L3AclRuleIpv4PriorityLowLimit                      Integer32,
    f3L3AclRuleProtocolControl                           TruthValue,
    f3L3AclRuleProtocolNumber                            Integer32,
    f3L3AclRuleSrcPortControl                            TruthValue,
    f3L3AclRuleSrcPortLowLimit                           Integer32,
    f3L3AclRuleSrcPortHighLimit                          Integer32,
    f3L3AclRuleDstPortControl                            TruthValue,
    f3L3AclRuleDstPortLowLimit                           Integer32,
    f3L3AclRuleDstPortHighLimit                          Integer32,
    f3L3AclRulePriority                                  Integer32,
    f3L3AclRuleCOS                                       Integer32,
    f3L3AclRuleOperation                                 L3AclRuleOperation,
    f3L3AclRuleSummary                                   F3DisplayString,
    f3L3AclRuleCosOverrideControl                        TruthValue,
    f3L3AclRuleSrcMacAddressControl                      TruthValue,
    f3L3AclRuleDynamicSrcMacAddressControl               TruthValue,
    f3L3AclRuleSrcMacAddress                             MacAddress,
    f3L3AclRuleSrcMacAddressMask                         MacAddress,
    f3L3AclRuleDstMacAddressControl                      TruthValue,
    f3L3AclRuleDstMacAddress                             MacAddress,
    f3L3AclRuleDstMacAddressMask                         MacAddress,
    f3L3AclRuleOuterVlanVIDControl                       TruthValue,
    f3L3AclRuleOuterVlanVIDLowLimit                      VlanId,
    f3L3AclRuleOuterVlanVIDHighLimit                     VlanId,
    f3L3AclRuleInnerVlanVIDControl                       TruthValue,
    f3L3AclRuleInnerVlanVIDLowLimit                      VlanId,
    f3L3AclRuleInnerVlanVIDHighLimit                     VlanId,
    f3L3AclRuleOuterVlanPcpControl                       TruthValue,
    f3L3AclRuleOuterVlanPcpLowLimit                      VlanPriority,
    f3L3AclRuleOuterVlanPcpHighLimit                     VlanPriority,
    f3L3AclRuleInnerVlanPcpControl                       TruthValue,
    f3L3AclRuleInnerVlanPcpLowLimit                      VlanPriority,
    f3L3AclRuleInnerVlanPcpHighLimit                     VlanPriority,
    f3L3AclRuleOuterVlanDeiControl                       TruthValue,
    f3L3AclRuleOuterVlanDei                              Unsigned32,
    f3L3AclRuleEtherTypeControl                          TruthValue,
    f3L3AclRuleEtherType                                 Integer32,
    f3L3AclRuleTcpFlagsControl                           TruthValue,
    f3L3AclRuleTcpFlags                                  Integer32,
    f3L3AclRuleSrcIpv4AddressHighLimit                   IpAddress,
    f3L3AclRuleDstIpv4AddressHighLimit                   IpAddress,
    f3L3AclRuleIpv4PriorityHighLimit                     Integer32,
    f3L3AclRuleStorageType                               StorageType,
    f3L3AclRuleRowStatus                                 RowStatus,
    f3L3AclRuleAdminState                                AdminState
}

f3L3AclRuleParentIndex OBJECT-TYPE
    SYNTAX      Integer32
    MAX-ACCESS  not-accessible
    STATUS      current
    DESCRIPTION
           "The ACL rule parent number, it could be flow index or L3 flow point index."
    ::= { f3L3AclRuleEntry 1 }

f3L3AclRuleIndex OBJECT-TYPE
    SYNTAX      Integer32
    MAX-ACCESS  not-accessible
    STATUS      current
    DESCRIPTION
           "The ACL rule number."
    ::= { f3L3AclRuleEntry 2 }

f3L3AclRuleAlias OBJECT-TYPE
    SYNTAX      F3DisplayString (SIZE (0..256))
    MAX-ACCESS  read-write
    STATUS      current
    DESCRIPTION
           "The ACL rule alias."
    ::= { f3L3AclRuleEntry 3 }

f3L3AclRuleSrcIpv4AddressControl OBJECT-TYPE
    SYNTAX      TruthValue
    MAX-ACCESS  read-write
    STATUS      current
    DESCRIPTION
           "The ACL rule source IPv4 Adress control whether enabled."
    ::= { f3L3AclRuleEntry 4 }

f3L3AclRuleDynamicSrcIpControl OBJECT-TYPE
    SYNTAX      TruthValue
    MAX-ACCESS  read-write
    STATUS      current
    DESCRIPTION
           "The ACL rule dynamic source IPv4 Adress control whether enabled."
    ::= { f3L3AclRuleEntry 5 }

f3L3AclRuleSrcIpv4AddressLowLimit OBJECT-TYPE
    SYNTAX      IpAddress
    MAX-ACCESS  read-write
    STATUS      current
    DESCRIPTION
           "The ACL rule source IPv4 Adress low limit."
    ::= { f3L3AclRuleEntry 6 }

f3L3AclRuleDstIpv4AddressControl OBJECT-TYPE
    SYNTAX      TruthValue
    MAX-ACCESS  read-write
    STATUS      current
    DESCRIPTION
           "The ACL rule Destination IPv4 Adress control whether enabled."
    ::= { f3L3AclRuleEntry 7 }

f3L3AclRuleDstIpv4AddressLowLimit OBJECT-TYPE
    SYNTAX      IpAddress
    MAX-ACCESS  read-write
    STATUS      current
    DESCRIPTION
           "The ACL rule Destination IPv4 Adress low limit."
    ::= { f3L3AclRuleEntry 8 }

f3L3AclRuleIpv4PriorityControl OBJECT-TYPE
    SYNTAX      TruthValue
    MAX-ACCESS  read-write
    STATUS      current
    DESCRIPTION
           "The ACL rule IPv4 Priority control whether enabled."
    ::= { f3L3AclRuleEntry 9 }

f3L3AclRuleIpv4PriorityLowLimit OBJECT-TYPE
    SYNTAX      Integer32
    MAX-ACCESS  read-write
    STATUS      current
    DESCRIPTION
           "The ACL rule IPv4 priority low limit."
    ::= { f3L3AclRuleEntry 10 }

f3L3AclRuleProtocolControl OBJECT-TYPE
    SYNTAX      TruthValue
    MAX-ACCESS  read-write
    STATUS      current
    DESCRIPTION
           "The ACL rule protocol control whether enabled."
    ::= { f3L3AclRuleEntry 11 }

f3L3AclRuleProtocolNumber OBJECT-TYPE
    SYNTAX      Integer32
    MAX-ACCESS  read-write
    STATUS      current
    DESCRIPTION
           "The ACL rule protocol number."
    ::= { f3L3AclRuleEntry 12 }

f3L3AclRuleSrcPortControl OBJECT-TYPE
    SYNTAX      TruthValue
    MAX-ACCESS  read-write
    STATUS      current
    DESCRIPTION
           "The ACL rule source port whether enabled."
    ::= { f3L3AclRuleEntry 13 }

f3L3AclRuleSrcPortLowLimit OBJECT-TYPE
    SYNTAX      Integer32
    MAX-ACCESS  read-write
    STATUS      current
    DESCRIPTION
           "The ACL rule source port low limit."
    ::= { f3L3AclRuleEntry 14 }

f3L3AclRuleSrcPortHighLimit OBJECT-TYPE
    SYNTAX      Integer32
    MAX-ACCESS  read-write
    STATUS      current
    DESCRIPTION
           "The ACL rule source port low limit."
    ::= { f3L3AclRuleEntry 15 }

f3L3AclRuleDstPortControl OBJECT-TYPE
    SYNTAX      TruthValue
    MAX-ACCESS  read-write
    STATUS      current
    DESCRIPTION
           "The ACL rule destination port whether enabled."
    ::= { f3L3AclRuleEntry 16 }

f3L3AclRuleDstPortLowLimit OBJECT-TYPE
    SYNTAX      Integer32
    MAX-ACCESS  read-write
    STATUS      current
    DESCRIPTION
           "The ACL rule destination port low limit."
    ::= { f3L3AclRuleEntry 17 }

f3L3AclRuleDstPortHighLimit OBJECT-TYPE
    SYNTAX      Integer32
    MAX-ACCESS  read-write
    STATUS      current
    DESCRIPTION
           "The ACL rule destination port low limit."
    ::= { f3L3AclRuleEntry 18 }

f3L3AclRulePriority OBJECT-TYPE
    SYNTAX      Integer32
    MAX-ACCESS  read-write
    STATUS      current
    DESCRIPTION
           "The ACL rule priority."
    ::= { f3L3AclRuleEntry 19 }

f3L3AclRuleCOS OBJECT-TYPE
    SYNTAX      Integer32
    MAX-ACCESS  read-write
    STATUS      current
    DESCRIPTION
           "The ACL rule class of service."
    ::= { f3L3AclRuleEntry 20 }

f3L3AclRuleOperation OBJECT-TYPE
    SYNTAX      L3AclRuleOperation
    MAX-ACCESS  read-write
    STATUS      current
    DESCRIPTION
           "The ACL rule action."
    ::= { f3L3AclRuleEntry 21 }

f3L3AclRuleSummary OBJECT-TYPE
    SYNTAX      F3DisplayString
    MAX-ACCESS  read-only
    STATUS      current
    DESCRIPTION
           "The ACL rule summary."
    ::= { f3L3AclRuleEntry 22 }

f3L3AclRuleCosOverrideControl OBJECT-TYPE
    SYNTAX      TruthValue
    MAX-ACCESS  read-write
    STATUS      current
    DESCRIPTION
           "The ACL rule COS Override control."
    ::= { f3L3AclRuleEntry 23 }

f3L3AclRuleSrcMacAddressControl OBJECT-TYPE
    SYNTAX      TruthValue
    MAX-ACCESS  read-write
    STATUS      current
    DESCRIPTION
           "The ACL rule Source MAC address control."
    ::= { f3L3AclRuleEntry 24 }

f3L3AclRuleDynamicSrcMacAddressControl OBJECT-TYPE
    SYNTAX      TruthValue
    MAX-ACCESS  read-write
    STATUS      current
    DESCRIPTION
           "The ACL rule dynamic Source MAC address control."
    ::= { f3L3AclRuleEntry 25 }

f3L3AclRuleSrcMacAddress OBJECT-TYPE
    SYNTAX      MacAddress
    MAX-ACCESS  read-write
    STATUS      current
    DESCRIPTION
           "The ACL rule dynamic Source MAC address."
    ::= { f3L3AclRuleEntry 26 }

f3L3AclRuleSrcMacAddressMask OBJECT-TYPE
    SYNTAX      MacAddress
    MAX-ACCESS  read-write
    STATUS      current
    DESCRIPTION
           "The ACL rule dynamic Source MAC address mask."
    ::= { f3L3AclRuleEntry 27 }

f3L3AclRuleDstMacAddressControl OBJECT-TYPE
    SYNTAX      TruthValue
    MAX-ACCESS  read-write
    STATUS      current
    DESCRIPTION
           "The ACL rule dynamic Destination MAC address control."
    ::= { f3L3AclRuleEntry 28 }

f3L3AclRuleDstMacAddress OBJECT-TYPE
    SYNTAX      MacAddress
    MAX-ACCESS  read-write
    STATUS      current
    DESCRIPTION
           "The ACL rule dynamic Destination MAC address."
    ::= { f3L3AclRuleEntry 29 }

f3L3AclRuleDstMacAddressMask OBJECT-TYPE
    SYNTAX      MacAddress
    MAX-ACCESS  read-write
    STATUS      current
    DESCRIPTION
           "The ACL rule dynamic Destination MAC address mask."
    ::= { f3L3AclRuleEntry 30 }

f3L3AclRuleOuterVlanVIDControl OBJECT-TYPE
    SYNTAX      TruthValue
    MAX-ACCESS  read-write
    STATUS      current
    DESCRIPTION
           "The ACL rule outer VID control."
    ::= { f3L3AclRuleEntry 31 }

f3L3AclRuleOuterVlanVIDLowLimit OBJECT-TYPE
    SYNTAX      VlanId
    MAX-ACCESS  read-write
    STATUS      current
    DESCRIPTION
           "The ACL rule outer Vlan ID low limit."
    ::= { f3L3AclRuleEntry 32 }

f3L3AclRuleOuterVlanVIDHighLimit OBJECT-TYPE
    SYNTAX      VlanId
    MAX-ACCESS  read-write
    STATUS      current
    DESCRIPTION
           "The ACL rule outer Vlan ID high limit."
    ::= { f3L3AclRuleEntry 33 }

f3L3AclRuleInnerVlanVIDControl OBJECT-TYPE
    SYNTAX      TruthValue
    MAX-ACCESS  read-write
    STATUS      current
    DESCRIPTION
           "The ACL rule inner VID control."
    ::= { f3L3AclRuleEntry 34 }

f3L3AclRuleInnerVlanVIDLowLimit OBJECT-TYPE
    SYNTAX      VlanId
    MAX-ACCESS  read-write
    STATUS      current
    DESCRIPTION
           "The ACL rule inner Vlan ID low limit."
    ::= { f3L3AclRuleEntry 35 }

f3L3AclRuleInnerVlanVIDHighLimit OBJECT-TYPE
    SYNTAX      VlanId
    MAX-ACCESS  read-write
    STATUS      current
    DESCRIPTION
           "The ACL rule Inner Vlan ID high limit."
    ::= { f3L3AclRuleEntry 36 }

f3L3AclRuleOuterVlanPcpControl OBJECT-TYPE
    SYNTAX      TruthValue
    MAX-ACCESS  read-write
    STATUS      current
    DESCRIPTION
           "The ACL rule outer vlan PCP control."
    ::= { f3L3AclRuleEntry 37 }

f3L3AclRuleOuterVlanPcpLowLimit OBJECT-TYPE
    SYNTAX      VlanPriority
    MAX-ACCESS  read-write
    STATUS      current
    DESCRIPTION
           "The ACL rule outer vlan PCP priority low limit."
    ::= { f3L3AclRuleEntry 38 }

f3L3AclRuleOuterVlanPcpHighLimit OBJECT-TYPE
    SYNTAX      VlanPriority
    MAX-ACCESS  read-write
    STATUS      current
    DESCRIPTION
           "The ACL rule outer vlan PCP priority high limit."
    ::= { f3L3AclRuleEntry 39 }

f3L3AclRuleInnerVlanPcpControl OBJECT-TYPE
    SYNTAX      TruthValue
    MAX-ACCESS  read-write
    STATUS      current
    DESCRIPTION
           "The ACL rule inner vlan PCP control."
    ::= { f3L3AclRuleEntry 40 }

f3L3AclRuleInnerVlanPcpLowLimit OBJECT-TYPE
    SYNTAX      VlanPriority
    MAX-ACCESS  read-write
    STATUS      current
    DESCRIPTION
           "The ACL rule inner vlan PCP priority low limit."
    ::= { f3L3AclRuleEntry 41 }

f3L3AclRuleInnerVlanPcpHighLimit OBJECT-TYPE
    SYNTAX      VlanPriority
    MAX-ACCESS  read-write
    STATUS      current
    DESCRIPTION
           "The ACL rule inner vlan PCP priority high limit."
    ::= { f3L3AclRuleEntry 42 }

f3L3AclRuleOuterVlanDeiControl OBJECT-TYPE
    SYNTAX      TruthValue
    MAX-ACCESS  read-write
    STATUS      current
    DESCRIPTION
           "The ACL rule outer vlan DEI control."
    ::= { f3L3AclRuleEntry 43 }

f3L3AclRuleOuterVlanDei OBJECT-TYPE
    SYNTAX      Unsigned32 (0..1)
    MAX-ACCESS  read-write
    STATUS      current
    DESCRIPTION
           "The ACL rule outer vlan DEI."
    ::= { f3L3AclRuleEntry 44 }

f3L3AclRuleEtherTypeControl OBJECT-TYPE
    SYNTAX      TruthValue
    MAX-ACCESS  read-write
    STATUS      current
    DESCRIPTION
           "The ACL rule outer vlan ether type control."
    ::= { f3L3AclRuleEntry 45 }

f3L3AclRuleEtherType OBJECT-TYPE
    SYNTAX      Integer32
    MAX-ACCESS  read-write
    STATUS      current
    DESCRIPTION
           "The ACL rule outer vlan ether type."
    ::= { f3L3AclRuleEntry 46 }

f3L3AclRuleTcpFlagsControl OBJECT-TYPE
    SYNTAX      TruthValue
    MAX-ACCESS  read-write
    STATUS      current
    DESCRIPTION
           "The ACL rule outer vlan TCP flags control."
    ::= { f3L3AclRuleEntry 47 }

f3L3AclRuleTcpFlags OBJECT-TYPE
    SYNTAX      Integer32
    MAX-ACCESS  read-write
    STATUS      current
    DESCRIPTION
           "The ACL rule outer vlan TCP flags."
    ::= { f3L3AclRuleEntry 48 }

f3L3AclRuleSrcIpv4AddressHighLimit OBJECT-TYPE
    SYNTAX      IpAddress
    MAX-ACCESS  read-write
    STATUS      current
    DESCRIPTION
           "The ACL rule source ipv4 adress high limit."
    ::= { f3L3AclRuleEntry 49 }

f3L3AclRuleDstIpv4AddressHighLimit OBJECT-TYPE
    SYNTAX      IpAddress
    MAX-ACCESS  read-write
    STATUS      current
    DESCRIPTION
           "The ACL rule destination ipv4 adress high limit."
    ::= { f3L3AclRuleEntry 50 }

f3L3AclRuleIpv4PriorityHighLimit OBJECT-TYPE
    SYNTAX      Integer32
    MAX-ACCESS  read-write
    STATUS      current
    DESCRIPTION
           "The ACL rule ipv4 priority high limit."
    ::= { f3L3AclRuleEntry 51 }

f3L3AclRuleStorageType OBJECT-TYPE
    SYNTAX      StorageType
    MAX-ACCESS  read-create
    STATUS      current
    DESCRIPTION
           "The type of storage configured for this entry."
    ::= { f3L3AclRuleEntry 52 }

f3L3AclRuleRowStatus OBJECT-TYPE
    SYNTAX      RowStatus
    MAX-ACCESS  read-create
    STATUS      current
    DESCRIPTION
           "The status of this row.
          	An entry MUST NOT exist in the active state unless all
          	objects in the entry have an appropriate value, as described
          	in the description clause for each writable object.
 	
          	The values of f3L3AclRuleRowStatus supported are
          	createAndGo(4) and destroy(6).  All mandatory attributes
          	must be specified in a single SNMP SET request with
          	f3L3AclRuleRowStatus value as createAndGo(4).
          	Upon successful row creation, this object has a
          	value of active(1).
 	
          	The f3L3AclRuleRowStatus object may be modified if
          	the associated instance of this object is equal to active(1)."
    ::= { f3L3AclRuleEntry 53 }

f3L3AclRuleAdminState  OBJECT-TYPE
    SYNTAX      AdminState
    MAX-ACCESS  read-write
    STATUS      current
    DESCRIPTION
           "This object allows user configure the Acl Rule in in-service or management state."
    ::= { f3L3AclRuleEntry 54 }

--
--  L2 A2N ACL Rule Table
--
f3L2A2NAclRuleTable  OBJECT-TYPE
    SYNTAX      SEQUENCE OF F3L2A2NAclRuleEntry
    MAX-ACCESS  not-accessible
    STATUS      current
    DESCRIPTION
            "A list of entries for the L2A2N ACL rule."
    ::= { f3L3Objects 5 }

f3L2A2NAclRuleEntry  OBJECT-TYPE
    SYNTAX      F3L2A2NAclRuleEntry
    MAX-ACCESS  not-accessible
    STATUS      current
    DESCRIPTION
            "A conceptual row in the f3L2A2NAclRuleTable."
    INDEX { neIndex, shelfIndex, slotIndex,
            f3L3FlowPointPortIndex, f3L2A2NAclRuleParentIndex, f3L2A2NAclRuleIndex }
    ::= { f3L2A2NAclRuleTable 1 }

F3L2A2NAclRuleEntry ::= SEQUENCE {
    f3L2A2NAclRuleParentIndex                               Integer32,
    f3L2A2NAclRuleIndex                                     Integer32,
    f3L2A2NAclRuleAlias                                     F3DisplayString,
    f3L2A2NAclRuleSrcIpv4AddressControl                     TruthValue,
    f3L2A2NAclRuleDynamicSrcIpControl                       TruthValue,
    f3L2A2NAclRuleSrcIpv4AddressLowLimit                    IpAddress,
    f3L2A2NAclRuleDstIpv4AddressControl                     TruthValue,
    f3L2A2NAclRuleDstIpv4AddressLowLimit                    IpAddress,
    f3L2A2NAclRuleIpv4PriorityControl                       TruthValue,
    f3L2A2NAclRuleIpv4PriorityLowLimit                      Integer32,
    f3L2A2NAclRuleProtocolControl                           TruthValue,
    f3L2A2NAclRuleProtocolNumber                            Integer32,
    f3L2A2NAclRuleSrcPortControl                            TruthValue,
    f3L2A2NAclRuleSrcPortLowLimit                           Integer32,
    f3L2A2NAclRuleSrcPortHighLimit                          Integer32,
    f3L2A2NAclRuleDstPortControl                            TruthValue,
    f3L2A2NAclRuleDstPortLowLimit                           Integer32,
    f3L2A2NAclRuleDstPortHighLimit                          Integer32,
    f3L2A2NAclRulePriority                                  Integer32,
    f3L2A2NAclRuleCOS                                       Integer32,
    f3L2A2NAclRuleOperation                                 L3AclRuleOperation,
    f3L2A2NAclRuleSummary                                   F3DisplayString,
    f3L2A2NAclRuleCosOverrideControl                        TruthValue,
    f3L2A2NAclRuleSrcMacAddressControl                      TruthValue,
    f3L2A2NAclRuleDynamicSrcMacAddressControl               TruthValue,
    f3L2A2NAclRuleSrcMacAddress                             MacAddress,
    f3L2A2NAclRuleSrcMacAddressMask                         MacAddress,
    f3L2A2NAclRuleDstMacAddressControl                      TruthValue,
    f3L2A2NAclRuleDstMacAddress                             MacAddress,
    f3L2A2NAclRuleDstMacAddressMask                         MacAddress,
    f3L2A2NAclRuleOuterVlanVIDControl                       TruthValue,
    f3L2A2NAclRuleOuterVlanVIDLowLimit                      VlanId,
    f3L2A2NAclRuleOuterVlanVIDHighLimit                     VlanId,
    f3L2A2NAclRuleInnerVlanVIDControl                       TruthValue,
    f3L2A2NAclRuleInnerVlanVIDLowLimit                      VlanId,
    f3L2A2NAclRuleInnerVlanVIDHighLimit                     VlanId,
    f3L2A2NAclRuleOuterVlanPcpControl                       TruthValue,
    f3L2A2NAclRuleOuterVlanPcpLowLimit                      VlanPriority,
    f3L2A2NAclRuleOuterVlanPcpHighLimit                     VlanPriority,
    f3L2A2NAclRuleInnerVlanPcpControl                       TruthValue,
    f3L2A2NAclRuleInnerVlanPcpLowLimit                      VlanPriority,
    f3L2A2NAclRuleInnerVlanPcpHighLimit                     VlanPriority,
    f3L2A2NAclRuleOuterVlanDeiControl                       TruthValue,
    f3L2A2NAclRuleOuterVlanDei                              Unsigned32,
    f3L2A2NAclRuleEtherTypeControl                          TruthValue,
    f3L2A2NAclRuleEtherType                                 Integer32,
    f3L2A2NAclRuleTcpFlagsControl                           TruthValue,
    f3L2A2NAclRuleTcpFlags                                  Integer32,
    f3L2A2NAclRuleSrcIpv4AddressHighLimit                   IpAddress,
    f3L2A2NAclRuleDstIpv4AddressHighLimit                   IpAddress,
    f3L2A2NAclRuleIpv4PriorityHighLimit                     Integer32,
    f3L2A2NAclRuleStorageType                               StorageType,
    f3L2A2NAclRuleRowStatus                                 RowStatus,
    f3L2A2NAclRuleAdminState                                AdminState
}

f3L2A2NAclRuleParentIndex OBJECT-TYPE
    SYNTAX      Integer32
    MAX-ACCESS  not-accessible
    STATUS      current
    DESCRIPTION
           "The ACL rule parent number, it could be flow index"
    ::= { f3L2A2NAclRuleEntry 1 }

f3L2A2NAclRuleIndex OBJECT-TYPE
    SYNTAX      Integer32
    MAX-ACCESS  not-accessible
    STATUS      current
    DESCRIPTION
           "The ACL rule number."
    ::= { f3L2A2NAclRuleEntry 2 }

f3L2A2NAclRuleAlias OBJECT-TYPE
    SYNTAX      F3DisplayString (SIZE (0..256))
    MAX-ACCESS  read-write
    STATUS      current
    DESCRIPTION
           "The ACL rule alias."
    ::= { f3L2A2NAclRuleEntry 3 }

f3L2A2NAclRuleSrcIpv4AddressControl OBJECT-TYPE
    SYNTAX      TruthValue
    MAX-ACCESS  read-write
    STATUS      current
    DESCRIPTION
           "The ACL rule source IPv4 Adress control whether enabled."
    ::= { f3L2A2NAclRuleEntry 4 }

f3L2A2NAclRuleDynamicSrcIpControl OBJECT-TYPE
    SYNTAX      TruthValue
    MAX-ACCESS  read-write
    STATUS      current
    DESCRIPTION
           "The ACL rule dynamic source IPv4 Adress control whether enabled."
    ::= { f3L2A2NAclRuleEntry 5 }

f3L2A2NAclRuleSrcIpv4AddressLowLimit OBJECT-TYPE
    SYNTAX      IpAddress
    MAX-ACCESS  read-write
    STATUS      current
    DESCRIPTION
           "The ACL rule source IPv4 Adress low limit."
    ::= { f3L2A2NAclRuleEntry 6 }

f3L2A2NAclRuleDstIpv4AddressControl OBJECT-TYPE
    SYNTAX      TruthValue
    MAX-ACCESS  read-write
    STATUS      current
    DESCRIPTION
           "The ACL rule Destination IPv4 Adress control whether enabled."
    ::= { f3L2A2NAclRuleEntry 7 }

f3L2A2NAclRuleDstIpv4AddressLowLimit OBJECT-TYPE
    SYNTAX      IpAddress
    MAX-ACCESS  read-write
    STATUS      current
    DESCRIPTION
           "The ACL rule Destination IPv4 Adress low limit."
    ::= { f3L2A2NAclRuleEntry 8 }

f3L2A2NAclRuleIpv4PriorityControl OBJECT-TYPE
    SYNTAX      TruthValue
    MAX-ACCESS  read-write
    STATUS      current
    DESCRIPTION
           "The ACL rule IPv4 Priority control whether enabled."
    ::= { f3L2A2NAclRuleEntry 9 }

f3L2A2NAclRuleIpv4PriorityLowLimit OBJECT-TYPE
    SYNTAX      Integer32
    MAX-ACCESS  read-write
    STATUS      current
    DESCRIPTION
           "The ACL rule IPv4 priority low limit."
    ::= { f3L2A2NAclRuleEntry 10 }

f3L2A2NAclRuleProtocolControl OBJECT-TYPE
    SYNTAX      TruthValue
    MAX-ACCESS  read-write
    STATUS      current
    DESCRIPTION
           "The ACL rule protocol control whether enabled."
    ::= { f3L2A2NAclRuleEntry 11 }

f3L2A2NAclRuleProtocolNumber OBJECT-TYPE
    SYNTAX      Integer32
    MAX-ACCESS  read-write
    STATUS      current
    DESCRIPTION
           "The ACL rule protocol number."
    ::= { f3L2A2NAclRuleEntry 12 }

f3L2A2NAclRuleSrcPortControl OBJECT-TYPE
    SYNTAX      TruthValue
    MAX-ACCESS  read-write
    STATUS      current
    DESCRIPTION
           "The ACL rule source port whether enabled."
    ::= { f3L2A2NAclRuleEntry 13 }

f3L2A2NAclRuleSrcPortLowLimit OBJECT-TYPE
    SYNTAX      Integer32
    MAX-ACCESS  read-write
    STATUS      current
    DESCRIPTION
           "The ACL rule source port low limit."
    ::= { f3L2A2NAclRuleEntry 14 }

f3L2A2NAclRuleSrcPortHighLimit OBJECT-TYPE
    SYNTAX      Integer32
    MAX-ACCESS  read-write
    STATUS      current
    DESCRIPTION
           "The ACL rule source port low limit."
    ::= { f3L2A2NAclRuleEntry 15 }

f3L2A2NAclRuleDstPortControl OBJECT-TYPE
    SYNTAX      TruthValue
    MAX-ACCESS  read-write
    STATUS      current
    DESCRIPTION
           "The ACL rule destination port whether enabled."
    ::= { f3L2A2NAclRuleEntry 16 }

f3L2A2NAclRuleDstPortLowLimit OBJECT-TYPE
    SYNTAX      Integer32
    MAX-ACCESS  read-write
    STATUS      current
    DESCRIPTION
           "The ACL rule destination port low limit."
    ::= { f3L2A2NAclRuleEntry 17 }

f3L2A2NAclRuleDstPortHighLimit OBJECT-TYPE
    SYNTAX      Integer32
    MAX-ACCESS  read-write
    STATUS      current
    DESCRIPTION
           "The ACL rule destination port low limit."
    ::= { f3L2A2NAclRuleEntry 18 }

f3L2A2NAclRulePriority OBJECT-TYPE
    SYNTAX      Integer32
    MAX-ACCESS  read-write
    STATUS      current
    DESCRIPTION
           "The ACL rule priority."
    ::= { f3L2A2NAclRuleEntry 19 }

f3L2A2NAclRuleCOS OBJECT-TYPE
    SYNTAX      Integer32
    MAX-ACCESS  read-write
    STATUS      current
    DESCRIPTION
           "The ACL rule class of service."
    ::= { f3L2A2NAclRuleEntry 20 }

f3L2A2NAclRuleOperation OBJECT-TYPE
    SYNTAX      L3AclRuleOperation
    MAX-ACCESS  read-write
    STATUS      current
    DESCRIPTION
           "The ACL rule action."
    ::= { f3L2A2NAclRuleEntry 21 }

f3L2A2NAclRuleSummary OBJECT-TYPE
    SYNTAX      F3DisplayString
    MAX-ACCESS  read-only
    STATUS      current
    DESCRIPTION
           "The ACL rule summary."
    ::= { f3L2A2NAclRuleEntry 22 }

f3L2A2NAclRuleCosOverrideControl OBJECT-TYPE
    SYNTAX      TruthValue
    MAX-ACCESS  read-write
    STATUS      current
    DESCRIPTION
           "The ACL rule COS Override control."
    ::= { f3L2A2NAclRuleEntry 23 }

f3L2A2NAclRuleSrcMacAddressControl OBJECT-TYPE
    SYNTAX      TruthValue
    MAX-ACCESS  read-write
    STATUS      current
    DESCRIPTION
           "The ACL rule Source MAC address control."
    ::= { f3L2A2NAclRuleEntry 24 }

f3L2A2NAclRuleDynamicSrcMacAddressControl OBJECT-TYPE
    SYNTAX      TruthValue
    MAX-ACCESS  read-write
    STATUS      current
    DESCRIPTION
           "The ACL rule dynamic Source MAC address control."
    ::= { f3L2A2NAclRuleEntry 25 }

f3L2A2NAclRuleSrcMacAddress OBJECT-TYPE
    SYNTAX      MacAddress
    MAX-ACCESS  read-write
    STATUS      current
    DESCRIPTION
           "The ACL rule dynamic Source MAC address."
    ::= { f3L2A2NAclRuleEntry 26 }

f3L2A2NAclRuleSrcMacAddressMask OBJECT-TYPE
    SYNTAX      MacAddress
    MAX-ACCESS  read-write
    STATUS      current
    DESCRIPTION
           "The ACL rule dynamic Source MAC address mask."
    ::= { f3L2A2NAclRuleEntry 27 }

f3L2A2NAclRuleDstMacAddressControl OBJECT-TYPE
    SYNTAX      TruthValue
    MAX-ACCESS  read-write
    STATUS      current
    DESCRIPTION
           "The ACL rule dynamic Destination MAC address control."
    ::= { f3L2A2NAclRuleEntry 28 }

f3L2A2NAclRuleDstMacAddress OBJECT-TYPE
    SYNTAX      MacAddress
    MAX-ACCESS  read-write
    STATUS      current
    DESCRIPTION
           "The ACL rule dynamic Destination MAC address."
    ::= { f3L2A2NAclRuleEntry 29 }

f3L2A2NAclRuleDstMacAddressMask OBJECT-TYPE
    SYNTAX      MacAddress
    MAX-ACCESS  read-write
    STATUS      current
    DESCRIPTION
           "The ACL rule dynamic Destination MAC address mask."
    ::= { f3L2A2NAclRuleEntry 30 }

f3L2A2NAclRuleOuterVlanVIDControl OBJECT-TYPE
    SYNTAX      TruthValue
    MAX-ACCESS  read-write
    STATUS      current
    DESCRIPTION
           "The ACL rule outer VID control."
    ::= { f3L2A2NAclRuleEntry 31 }

f3L2A2NAclRuleOuterVlanVIDLowLimit OBJECT-TYPE
    SYNTAX      VlanId
    MAX-ACCESS  read-write
    STATUS      current
    DESCRIPTION
           "The ACL rule outer Vlan ID low limit."
    ::= { f3L2A2NAclRuleEntry 32 }

f3L2A2NAclRuleOuterVlanVIDHighLimit OBJECT-TYPE
    SYNTAX      VlanId
    MAX-ACCESS  read-write
    STATUS      current
    DESCRIPTION
           "The ACL rule outer Vlan ID high limit."
    ::= { f3L2A2NAclRuleEntry 33 }

f3L2A2NAclRuleInnerVlanVIDControl OBJECT-TYPE
    SYNTAX      TruthValue
    MAX-ACCESS  read-write
    STATUS      current
    DESCRIPTION
           "The ACL rule inner VID control."
    ::= { f3L2A2NAclRuleEntry 34 }

f3L2A2NAclRuleInnerVlanVIDLowLimit OBJECT-TYPE
    SYNTAX      VlanId
    MAX-ACCESS  read-write
    STATUS      current
    DESCRIPTION
           "The ACL rule inner Vlan ID low limit."
    ::= { f3L2A2NAclRuleEntry 35 }

f3L2A2NAclRuleInnerVlanVIDHighLimit OBJECT-TYPE
    SYNTAX      VlanId
    MAX-ACCESS  read-write
    STATUS      current
    DESCRIPTION
           "The ACL rule Inner Vlan ID high limit."
    ::= { f3L2A2NAclRuleEntry 36 }

f3L2A2NAclRuleOuterVlanPcpControl OBJECT-TYPE
    SYNTAX      TruthValue
    MAX-ACCESS  read-write
    STATUS      current
    DESCRIPTION
           "The ACL rule outer vlan PCP control."
    ::= { f3L2A2NAclRuleEntry 37 }

f3L2A2NAclRuleOuterVlanPcpLowLimit OBJECT-TYPE
    SYNTAX      VlanPriority
    MAX-ACCESS  read-write
    STATUS      current
    DESCRIPTION
           "The ACL rule outer vlan PCP priority low limit."
    ::= { f3L2A2NAclRuleEntry 38 }

f3L2A2NAclRuleOuterVlanPcpHighLimit OBJECT-TYPE
    SYNTAX      VlanPriority
    MAX-ACCESS  read-write
    STATUS      current
    DESCRIPTION
           "The ACL rule outer vlan PCP priority high limit."
    ::= { f3L2A2NAclRuleEntry 39 }

f3L2A2NAclRuleInnerVlanPcpControl OBJECT-TYPE
    SYNTAX      TruthValue
    MAX-ACCESS  read-write
    STATUS      current
    DESCRIPTION
           "The ACL rule inner vlan PCP control."
    ::= { f3L2A2NAclRuleEntry 40 }

f3L2A2NAclRuleInnerVlanPcpLowLimit OBJECT-TYPE
    SYNTAX      VlanPriority
    MAX-ACCESS  read-write
    STATUS      current
    DESCRIPTION
           "The ACL rule inner vlan PCP priority low limit."
    ::= { f3L2A2NAclRuleEntry 41 }

f3L2A2NAclRuleInnerVlanPcpHighLimit OBJECT-TYPE
    SYNTAX      VlanPriority
    MAX-ACCESS  read-write
    STATUS      current
    DESCRIPTION
           "The ACL rule inner vlan PCP priority high limit."
    ::= { f3L2A2NAclRuleEntry 42 }

f3L2A2NAclRuleOuterVlanDeiControl OBJECT-TYPE
    SYNTAX      TruthValue
    MAX-ACCESS  read-write
    STATUS      current
    DESCRIPTION
           "The ACL rule outer vlan DEI control."
    ::= { f3L2A2NAclRuleEntry 43 }

f3L2A2NAclRuleOuterVlanDei OBJECT-TYPE
    SYNTAX      Unsigned32 (0..1)
    MAX-ACCESS  read-write
    STATUS      current
    DESCRIPTION
           "The ACL rule outer vlan DEI."
    ::= { f3L2A2NAclRuleEntry 44 }

f3L2A2NAclRuleEtherTypeControl OBJECT-TYPE
    SYNTAX      TruthValue
    MAX-ACCESS  read-write
    STATUS      current
    DESCRIPTION
           "The ACL rule outer vlan ether type control."
    ::= { f3L2A2NAclRuleEntry 45 }

f3L2A2NAclRuleEtherType OBJECT-TYPE
    SYNTAX      Integer32
    MAX-ACCESS  read-write
    STATUS      current
    DESCRIPTION
           "The ACL rule outer vlan ether type."
    ::= { f3L2A2NAclRuleEntry 46 }

f3L2A2NAclRuleTcpFlagsControl OBJECT-TYPE
    SYNTAX      TruthValue
    MAX-ACCESS  read-write
    STATUS      current
    DESCRIPTION
           "The ACL rule outer vlan TCP flags control."
    ::= { f3L2A2NAclRuleEntry 47 }

f3L2A2NAclRuleTcpFlags OBJECT-TYPE
    SYNTAX      Integer32
    MAX-ACCESS  read-write
    STATUS      current
    DESCRIPTION
           "The ACL rule outer vlan TCP flags."
    ::= { f3L2A2NAclRuleEntry 48 }

f3L2A2NAclRuleSrcIpv4AddressHighLimit OBJECT-TYPE
    SYNTAX      IpAddress
    MAX-ACCESS  read-write
    STATUS      current
    DESCRIPTION
           "The ACL rule source ipv4 adress high limit."
    ::= { f3L2A2NAclRuleEntry 49 }

f3L2A2NAclRuleDstIpv4AddressHighLimit OBJECT-TYPE
    SYNTAX      IpAddress
    MAX-ACCESS  read-write
    STATUS      current
    DESCRIPTION
           "The ACL rule destination ipv4 adress high limit."
    ::= { f3L2A2NAclRuleEntry 50 }

f3L2A2NAclRuleIpv4PriorityHighLimit OBJECT-TYPE
    SYNTAX      Integer32
    MAX-ACCESS  read-write
    STATUS      current
    DESCRIPTION
           "The ACL rule ipv4 priority high limit."
    ::= { f3L2A2NAclRuleEntry 51 }

f3L2A2NAclRuleStorageType OBJECT-TYPE
    SYNTAX      StorageType
    MAX-ACCESS  read-create
    STATUS      current
    DESCRIPTION
           "The type of storage configured for this entry."
    ::= { f3L2A2NAclRuleEntry 52 }

f3L2A2NAclRuleRowStatus OBJECT-TYPE
    SYNTAX      RowStatus
    MAX-ACCESS  read-create
    STATUS      current
    DESCRIPTION
           "The status of this row.
          	An entry MUST NOT exist in the active state unless all
          	objects in the entry have an appropriate value, as described
          	in the description clause for each writable object.
 	
          	The values of f3L2A2NAclRuleRowStatus supported are
          	createAndGo(4) and destroy(6).  All mandatory attributes
          	must be specified in a single SNMP SET request with
          	f3L2A2NAclRuleRowStatus value as createAndGo(4).
          	Upon successful row creation, this object has a
          	value of active(1).
 	
          	The f3L2A2NAclRuleRowStatus object may be modified if
          	the associated instance of this object is equal to active(1)."
    ::= { f3L2A2NAclRuleEntry 53 }

f3L2A2NAclRuleAdminState OBJECT-TYPE
    SYNTAX      AdminState
    MAX-ACCESS  read-write
    STATUS      current
    DESCRIPTION
           "This object allows user configure the Acl Rule in-service or management state."
    ::= { f3L2A2NAclRuleEntry 54 }

--
--  L2 N2A ACL Rule Table
--
f3L2N2AAclRuleTable  OBJECT-TYPE
    SYNTAX      SEQUENCE OF F3L2N2AAclRuleEntry
    MAX-ACCESS  not-accessible
    STATUS      current
    DESCRIPTION
            "A list of entries for the L2N2A ACL rule."
    ::= { f3L3Objects 6 }

f3L2N2AAclRuleEntry  OBJECT-TYPE
    SYNTAX      F3L2N2AAclRuleEntry
    MAX-ACCESS  not-accessible
    STATUS      current
    DESCRIPTION
            "A conceptual row in the f3L2N2AAclRuleTable."
    INDEX { neIndex, shelfIndex, slotIndex,
            f3L3FlowPointPortIndex, f3L2N2AAclRuleParentIndex, f3L2N2AAclRuleIndex }
    ::= { f3L2N2AAclRuleTable 1 }

F3L2N2AAclRuleEntry ::= SEQUENCE {
    f3L2N2AAclRuleParentIndex                               Integer32,
    f3L2N2AAclRuleIndex                                     Integer32,
    f3L2N2AAclRuleAlias                                     F3DisplayString,
    f3L2N2AAclRuleSrcIpv4AddressControl                     TruthValue,
    f3L2N2AAclRuleDynamicSrcIpControl                       TruthValue,
    f3L2N2AAclRuleSrcIpv4AddressLowLimit                    IpAddress,
    f3L2N2AAclRuleDstIpv4AddressControl                     TruthValue,
    f3L2N2AAclRuleDstIpv4AddressLowLimit                    IpAddress,
    f3L2N2AAclRuleIpv4PriorityControl                       TruthValue,
    f3L2N2AAclRuleIpv4PriorityLowLimit                      Integer32,
    f3L2N2AAclRuleProtocolControl                           TruthValue,
    f3L2N2AAclRuleProtocolNumber                            Integer32,
    f3L2N2AAclRuleSrcPortControl                            TruthValue,
    f3L2N2AAclRuleSrcPortLowLimit                           Integer32,
    f3L2N2AAclRuleSrcPortHighLimit                          Integer32,
    f3L2N2AAclRuleDstPortControl                            TruthValue,
    f3L2N2AAclRuleDstPortLowLimit                           Integer32,
    f3L2N2AAclRuleDstPortHighLimit                          Integer32,
    f3L2N2AAclRulePriority                                  Integer32,
    f3L2N2AAclRuleCOS                                       Integer32,
    f3L2N2AAclRuleOperation                                 L3AclRuleOperation,
    f3L2N2AAclRuleSummary                                   F3DisplayString,
    f3L2N2AAclRuleCosOverrideControl                        TruthValue,
    f3L2N2AAclRuleSrcMacAddressControl                      TruthValue,
    f3L2N2AAclRuleDynamicSrcMacAddressControl               TruthValue,
    f3L2N2AAclRuleSrcMacAddress                             MacAddress,
    f3L2N2AAclRuleSrcMacAddressMask                         MacAddress,
    f3L2N2AAclRuleDstMacAddressControl                      TruthValue,
    f3L2N2AAclRuleDstMacAddress                             MacAddress,
    f3L2N2AAclRuleDstMacAddressMask                         MacAddress,
    f3L2N2AAclRuleOuterVlanVIDControl                       TruthValue,
    f3L2N2AAclRuleOuterVlanVIDLowLimit                      VlanId,
    f3L2N2AAclRuleOuterVlanVIDHighLimit                     VlanId,
    f3L2N2AAclRuleInnerVlanVIDControl                       TruthValue,
    f3L2N2AAclRuleInnerVlanVIDLowLimit                      VlanId,
    f3L2N2AAclRuleInnerVlanVIDHighLimit                     VlanId,
    f3L2N2AAclRuleOuterVlanPcpControl                       TruthValue,
    f3L2N2AAclRuleOuterVlanPcpLowLimit                      VlanPriority,
    f3L2N2AAclRuleOuterVlanPcpHighLimit                     VlanPriority,
    f3L2N2AAclRuleInnerVlanPcpControl                       TruthValue,
    f3L2N2AAclRuleInnerVlanPcpLowLimit                      VlanPriority,
    f3L2N2AAclRuleInnerVlanPcpHighLimit                     VlanPriority,
    f3L2N2AAclRuleOuterVlanDeiControl                       TruthValue,
    f3L2N2AAclRuleOuterVlanDei                              Unsigned32,
    f3L2N2AAclRuleEtherTypeControl                          TruthValue,
    f3L2N2AAclRuleEtherType                                 Integer32,
    f3L2N2AAclRuleTcpFlagsControl                           TruthValue,
    f3L2N2AAclRuleTcpFlags                                  Integer32,
    f3L2N2AAclRuleSrcIpv4AddressHighLimit                   IpAddress,
    f3L2N2AAclRuleDstIpv4AddressHighLimit                   IpAddress,
    f3L2N2AAclRuleIpv4PriorityHighLimit                     Integer32,
    f3L2N2AAclRuleStorageType                               StorageType,
    f3L2N2AAclRuleRowStatus                                 RowStatus,
    f3L2N2AAclRuleAdminState                                AdminState
}

f3L2N2AAclRuleParentIndex OBJECT-TYPE
    SYNTAX      Integer32
    MAX-ACCESS  not-accessible
    STATUS      current
    DESCRIPTION
           "The ACL rule parent number, it could be flow index"
    ::= { f3L2N2AAclRuleEntry 1 }

f3L2N2AAclRuleIndex OBJECT-TYPE
    SYNTAX      Integer32
    MAX-ACCESS  not-accessible
    STATUS      current
    DESCRIPTION
           "The ACL rule number."
    ::= { f3L2N2AAclRuleEntry 2 }

f3L2N2AAclRuleAlias OBJECT-TYPE
    SYNTAX      F3DisplayString (SIZE (0..256))
    MAX-ACCESS  read-write
    STATUS      current
    DESCRIPTION
           "The ACL rule alias."
    ::= { f3L2N2AAclRuleEntry 3 }

f3L2N2AAclRuleSrcIpv4AddressControl OBJECT-TYPE
    SYNTAX      TruthValue
    MAX-ACCESS  read-write
    STATUS      current
    DESCRIPTION
           "The ACL rule source IPv4 Adress control whether enabled."
    ::= { f3L2N2AAclRuleEntry 4 }

f3L2N2AAclRuleDynamicSrcIpControl OBJECT-TYPE
    SYNTAX      TruthValue
    MAX-ACCESS  read-write
    STATUS      current
    DESCRIPTION
           "The ACL rule dynamic source IPv4 Adress control whether enabled."
    ::= { f3L2N2AAclRuleEntry 5 }

f3L2N2AAclRuleSrcIpv4AddressLowLimit OBJECT-TYPE
    SYNTAX      IpAddress
    MAX-ACCESS  read-write
    STATUS      current
    DESCRIPTION
           "The ACL rule source IPv4 Adress low limit."
    ::= { f3L2N2AAclRuleEntry 6 }

f3L2N2AAclRuleDstIpv4AddressControl OBJECT-TYPE
    SYNTAX      TruthValue
    MAX-ACCESS  read-write
    STATUS      current
    DESCRIPTION
           "The ACL rule Destination IPv4 Adress control whether enabled."
    ::= { f3L2N2AAclRuleEntry 7 }

f3L2N2AAclRuleDstIpv4AddressLowLimit OBJECT-TYPE
    SYNTAX      IpAddress
    MAX-ACCESS  read-write
    STATUS      current
    DESCRIPTION
           "The ACL rule Destination IPv4 Adress low limit."
    ::= { f3L2N2AAclRuleEntry 8 }

f3L2N2AAclRuleIpv4PriorityControl OBJECT-TYPE
    SYNTAX      TruthValue
    MAX-ACCESS  read-write
    STATUS      current
    DESCRIPTION
           "The ACL rule IPv4 Priority control whether enabled."
    ::= { f3L2N2AAclRuleEntry 9 }

f3L2N2AAclRuleIpv4PriorityLowLimit OBJECT-TYPE
    SYNTAX      Integer32
    MAX-ACCESS  read-write
    STATUS      current
    DESCRIPTION
           "The ACL rule IPv4 priority low limit."
    ::= { f3L2N2AAclRuleEntry 10 }

f3L2N2AAclRuleProtocolControl OBJECT-TYPE
    SYNTAX      TruthValue
    MAX-ACCESS  read-write
    STATUS      current
    DESCRIPTION
           "The ACL rule protocol control whether enabled."
    ::= { f3L2N2AAclRuleEntry 11 }

f3L2N2AAclRuleProtocolNumber OBJECT-TYPE
    SYNTAX      Integer32
    MAX-ACCESS  read-write
    STATUS      current
    DESCRIPTION
           "The ACL rule protocol number."
    ::= { f3L2N2AAclRuleEntry 12 }

f3L2N2AAclRuleSrcPortControl OBJECT-TYPE
    SYNTAX      TruthValue
    MAX-ACCESS  read-write
    STATUS      current
    DESCRIPTION
           "The ACL rule source port whether enabled."
    ::= { f3L2N2AAclRuleEntry 13 }

f3L2N2AAclRuleSrcPortLowLimit OBJECT-TYPE
    SYNTAX      Integer32
    MAX-ACCESS  read-write
    STATUS      current
    DESCRIPTION
           "The ACL rule source port low limit."
    ::= { f3L2N2AAclRuleEntry 14 }

f3L2N2AAclRuleSrcPortHighLimit OBJECT-TYPE
    SYNTAX      Integer32
    MAX-ACCESS  read-write
    STATUS      current
    DESCRIPTION
           "The ACL rule source port low limit."
    ::= { f3L2N2AAclRuleEntry 15 }

f3L2N2AAclRuleDstPortControl OBJECT-TYPE
    SYNTAX      TruthValue
    MAX-ACCESS  read-write
    STATUS      current
    DESCRIPTION
           "The ACL rule destination port whether enabled."
    ::= { f3L2N2AAclRuleEntry 16 }

f3L2N2AAclRuleDstPortLowLimit OBJECT-TYPE
    SYNTAX      Integer32
    MAX-ACCESS  read-write
    STATUS      current
    DESCRIPTION
           "The ACL rule destination port low limit."
    ::= { f3L2N2AAclRuleEntry 17 }

f3L2N2AAclRuleDstPortHighLimit OBJECT-TYPE
    SYNTAX      Integer32
    MAX-ACCESS  read-write
    STATUS      current
    DESCRIPTION
           "The ACL rule destination port low limit."
    ::= { f3L2N2AAclRuleEntry 18 }

f3L2N2AAclRulePriority OBJECT-TYPE
    SYNTAX      Integer32
    MAX-ACCESS  read-write
    STATUS      current
    DESCRIPTION
           "The ACL rule priority."
    ::= { f3L2N2AAclRuleEntry 19 }

f3L2N2AAclRuleCOS OBJECT-TYPE
    SYNTAX      Integer32
    MAX-ACCESS  read-write
    STATUS      current
    DESCRIPTION
           "The ACL rule class of service."
    ::= { f3L2N2AAclRuleEntry 20 }

f3L2N2AAclRuleOperation OBJECT-TYPE
    SYNTAX      L3AclRuleOperation
    MAX-ACCESS  read-write
    STATUS      current
    DESCRIPTION
           "The ACL rule action."
    ::= { f3L2N2AAclRuleEntry 21 }

f3L2N2AAclRuleSummary OBJECT-TYPE
    SYNTAX      F3DisplayString
    MAX-ACCESS  read-only
    STATUS      current
    DESCRIPTION
           "The ACL rule summary."
    ::= { f3L2N2AAclRuleEntry 22 }

f3L2N2AAclRuleCosOverrideControl OBJECT-TYPE
    SYNTAX      TruthValue
    MAX-ACCESS  read-write
    STATUS      current
    DESCRIPTION
           "The ACL rule COS Override control."
    ::= { f3L2N2AAclRuleEntry 23 }

f3L2N2AAclRuleSrcMacAddressControl OBJECT-TYPE
    SYNTAX      TruthValue
    MAX-ACCESS  read-write
    STATUS      current
    DESCRIPTION
           "The ACL rule Source MAC address control."
    ::= { f3L2N2AAclRuleEntry 24 }

f3L2N2AAclRuleDynamicSrcMacAddressControl OBJECT-TYPE
    SYNTAX      TruthValue
    MAX-ACCESS  read-write
    STATUS      current
    DESCRIPTION
           "The ACL rule dynamic Source MAC address control."
    ::= { f3L2N2AAclRuleEntry 25 }

f3L2N2AAclRuleSrcMacAddress OBJECT-TYPE
    SYNTAX      MacAddress
    MAX-ACCESS  read-write
    STATUS      current
    DESCRIPTION
           "The ACL rule dynamic Source MAC address."
    ::= { f3L2N2AAclRuleEntry 26 }

f3L2N2AAclRuleSrcMacAddressMask OBJECT-TYPE
    SYNTAX      MacAddress
    MAX-ACCESS  read-write
    STATUS      current
    DESCRIPTION
           "The ACL rule dynamic Source MAC address mask."
    ::= { f3L2N2AAclRuleEntry 27 }

f3L2N2AAclRuleDstMacAddressControl OBJECT-TYPE
    SYNTAX      TruthValue
    MAX-ACCESS  read-write
    STATUS      current
    DESCRIPTION
           "The ACL rule dynamic Destination MAC address control."
    ::= { f3L2N2AAclRuleEntry 28 }

f3L2N2AAclRuleDstMacAddress OBJECT-TYPE
    SYNTAX      MacAddress
    MAX-ACCESS  read-write
    STATUS      current
    DESCRIPTION
           "The ACL rule dynamic Destination MAC address."
    ::= { f3L2N2AAclRuleEntry 29 }

f3L2N2AAclRuleDstMacAddressMask OBJECT-TYPE
    SYNTAX      MacAddress
    MAX-ACCESS  read-write
    STATUS      current
    DESCRIPTION
           "The ACL rule dynamic Destination MAC address mask."
    ::= { f3L2N2AAclRuleEntry 30 }

f3L2N2AAclRuleOuterVlanVIDControl OBJECT-TYPE
    SYNTAX      TruthValue
    MAX-ACCESS  read-write
    STATUS      current
    DESCRIPTION
           "The ACL rule outer VID control."
    ::= { f3L2N2AAclRuleEntry 31 }

f3L2N2AAclRuleOuterVlanVIDLowLimit OBJECT-TYPE
    SYNTAX      VlanId
    MAX-ACCESS  read-write
    STATUS      current
    DESCRIPTION
           "The ACL rule outer Vlan ID low limit."
    ::= { f3L2N2AAclRuleEntry 32 }

f3L2N2AAclRuleOuterVlanVIDHighLimit OBJECT-TYPE
    SYNTAX      VlanId
    MAX-ACCESS  read-write
    STATUS      current
    DESCRIPTION
           "The ACL rule outer Vlan ID high limit."
    ::= { f3L2N2AAclRuleEntry 33 }

f3L2N2AAclRuleInnerVlanVIDControl OBJECT-TYPE
    SYNTAX      TruthValue
    MAX-ACCESS  read-write
    STATUS      current
    DESCRIPTION
           "The ACL rule inner VID control."
    ::= { f3L2N2AAclRuleEntry 34 }

f3L2N2AAclRuleInnerVlanVIDLowLimit OBJECT-TYPE
    SYNTAX      VlanId
    MAX-ACCESS  read-write
    STATUS      current
    DESCRIPTION
           "The ACL rule inner Vlan ID low limit."
    ::= { f3L2N2AAclRuleEntry 35 }

f3L2N2AAclRuleInnerVlanVIDHighLimit OBJECT-TYPE
    SYNTAX      VlanId
    MAX-ACCESS  read-write
    STATUS      current
    DESCRIPTION
           "The ACL rule Inner Vlan ID high limit."
    ::= { f3L2N2AAclRuleEntry 36 }

f3L2N2AAclRuleOuterVlanPcpControl OBJECT-TYPE
    SYNTAX      TruthValue
    MAX-ACCESS  read-write
    STATUS      current
    DESCRIPTION
           "The ACL rule outer vlan PCP control."
    ::= { f3L2N2AAclRuleEntry 37 }

f3L2N2AAclRuleOuterVlanPcpLowLimit OBJECT-TYPE
    SYNTAX      VlanPriority
    MAX-ACCESS  read-write
    STATUS      current
    DESCRIPTION
           "The ACL rule outer vlan PCP priority low limit."
    ::= { f3L2N2AAclRuleEntry 38 }

f3L2N2AAclRuleOuterVlanPcpHighLimit OBJECT-TYPE
    SYNTAX      VlanPriority
    MAX-ACCESS  read-write
    STATUS      current
    DESCRIPTION
           "The ACL rule outer vlan PCP priority high limit."
    ::= { f3L2N2AAclRuleEntry 39 }

f3L2N2AAclRuleInnerVlanPcpControl OBJECT-TYPE
    SYNTAX      TruthValue
    MAX-ACCESS  read-write
    STATUS      current
    DESCRIPTION
           "The ACL rule inner vlan PCP control."
    ::= { f3L2N2AAclRuleEntry 40 }

f3L2N2AAclRuleInnerVlanPcpLowLimit OBJECT-TYPE
    SYNTAX      VlanPriority
    MAX-ACCESS  read-write
    STATUS      current
    DESCRIPTION
           "The ACL rule inner vlan PCP priority low limit."
    ::= { f3L2N2AAclRuleEntry 41 }

f3L2N2AAclRuleInnerVlanPcpHighLimit OBJECT-TYPE
    SYNTAX      VlanPriority
    MAX-ACCESS  read-write
    STATUS      current
    DESCRIPTION
           "The ACL rule inner vlan PCP priority high limit."
    ::= { f3L2N2AAclRuleEntry 42 }

f3L2N2AAclRuleOuterVlanDeiControl OBJECT-TYPE
    SYNTAX      TruthValue
    MAX-ACCESS  read-write
    STATUS      current
    DESCRIPTION
           "The ACL rule outer vlan DEI control."
    ::= { f3L2N2AAclRuleEntry 43 }

f3L2N2AAclRuleOuterVlanDei OBJECT-TYPE
    SYNTAX      Unsigned32 (0..1)
    MAX-ACCESS  read-write
    STATUS      current
    DESCRIPTION
           "The ACL rule outer vlan DEI."
    ::= { f3L2N2AAclRuleEntry 44 }

f3L2N2AAclRuleEtherTypeControl OBJECT-TYPE
    SYNTAX      TruthValue
    MAX-ACCESS  read-write
    STATUS      current
    DESCRIPTION
           "The ACL rule outer vlan ether type control."
    ::= { f3L2N2AAclRuleEntry 45 }

f3L2N2AAclRuleEtherType OBJECT-TYPE
    SYNTAX      Integer32
    MAX-ACCESS  read-write
    STATUS      current
    DESCRIPTION
           "The ACL rule outer vlan ether type."
    ::= { f3L2N2AAclRuleEntry 46 }

f3L2N2AAclRuleTcpFlagsControl OBJECT-TYPE
    SYNTAX      TruthValue
    MAX-ACCESS  read-write
    STATUS      current
    DESCRIPTION
           "The ACL rule outer vlan TCP flags control."
    ::= { f3L2N2AAclRuleEntry 47 }

f3L2N2AAclRuleTcpFlags OBJECT-TYPE
    SYNTAX      Integer32
    MAX-ACCESS  read-write
    STATUS      current
    DESCRIPTION
           "The ACL rule outer vlan TCP flags."
    ::= { f3L2N2AAclRuleEntry 48 }

f3L2N2AAclRuleSrcIpv4AddressHighLimit OBJECT-TYPE
    SYNTAX      IpAddress
    MAX-ACCESS  read-write
    STATUS      current
    DESCRIPTION
           "The ACL rule source ipv4 adress high limit."
    ::= { f3L2N2AAclRuleEntry 49 }

f3L2N2AAclRuleDstIpv4AddressHighLimit OBJECT-TYPE
    SYNTAX      IpAddress
    MAX-ACCESS  read-write
    STATUS      current
    DESCRIPTION
           "The ACL rule destination ipv4 adress high limit."
    ::= { f3L2N2AAclRuleEntry 50 }

f3L2N2AAclRuleIpv4PriorityHighLimit OBJECT-TYPE
    SYNTAX      Integer32
    MAX-ACCESS  read-write
    STATUS      current
    DESCRIPTION
           "The ACL rule ipv4 priority high limit."
    ::= { f3L2N2AAclRuleEntry 51 }

f3L2N2AAclRuleStorageType OBJECT-TYPE
    SYNTAX      StorageType
    MAX-ACCESS  read-create
    STATUS      current
    DESCRIPTION
           "The type of storage configured for this entry."
    ::= { f3L2N2AAclRuleEntry 52 }

f3L2N2AAclRuleRowStatus OBJECT-TYPE
    SYNTAX      RowStatus
    MAX-ACCESS  read-create
    STATUS      current
    DESCRIPTION
           "The status of this row.
          	An entry MUST NOT exist in the active state unless all
          	objects in the entry have an appropriate value, as described
          	in the description clause for each writable object.
 	
          	The values of f3L2N2AAclRuleRowStatus supported are
          	createAndGo(4) and destroy(6).  All mandatory attributes
          	must be specified in a single SNMP SET request with
          	f3L2N2AAclRuleRowStatus value as createAndGo(4).
          	Upon successful row creation, this object has a
          	value of active(1).
 	
          	The f3L2N2AAclRuleRowStatus object may be modified if
          	the associated instance of this object is equal to active(1)."
    ::= { f3L2N2AAclRuleEntry 53 }

f3L2N2AAclRuleAdminState OBJECT-TYPE
    SYNTAX      AdminState
    MAX-ACCESS  read-write
    STATUS      current
    DESCRIPTION
           "This object allows user configure the Acl Rule in-service or management state."
    ::= { f3L2N2AAclRuleEntry 54 }

--
--L3 Policer
--
f3L3QosPolicerTable  OBJECT-TYPE
    SYNTAX      SEQUENCE OF F3L3QosPolicerEntry
    MAX-ACCESS  not-accessible
    STATUS      current
    DESCRIPTION
        "A list of entries corresponding to Ethernet Quality of Service 
         Policer for configuration purposes."
    ::= { f3L3Objects 7 }

f3L3QosPolicerEntry OBJECT-TYPE
    SYNTAX      F3L3QosPolicerEntry 
    MAX-ACCESS  not-accessible
    STATUS      current
    DESCRIPTION
         "A conceptual row in the f3L3QosPolicerTable. 
          These entries represent a Quality of Service Policer."
    INDEX { neIndex, shelfIndex, slotIndex, f3L3FlowPointPortTypeIndex, 
            f3L3FlowPointPortIndex, f3L3FlowPointIndex, f3L3QosPolicerIndex }
    ::= { f3L3QosPolicerTable 1 }

F3L3QosPolicerEntry ::= SEQUENCE {
    f3L3QosPolicerIndex                 Integer32,

    -- State Management params
    f3L3QosPolicerAdminState            AdminState,
    f3L3QosPolicerOperationalState      OperationalState,
    f3L3QosPolicerSecondaryState        SecondaryState,

    f3L3QosPolicerCIRLo                 Unsigned32,
    f3L3QosPolicerCIRHi                 Unsigned32,
    f3L3QosPolicerEIRLo                 Unsigned32,
    f3L3QosPolicerEIRHi                 Unsigned32,
    f3L3QosPolicerCBS                   Integer32,
    f3L3QosPolicerEBS                   Integer32,
    f3L3QosPolicerAlgorithm             PolicerAlgorithmType,
    f3L3QosPolicerColorMode             PolicerColorMode,
    f3L3QosPolicerCouplingFlag          TruthValue,
    f3L3QosPolicerStorageType           StorageType,
    f3L3QosPolicerRowStatus             RowStatus 
}

f3L3QosPolicerIndex OBJECT-TYPE
    SYNTAX      Integer32 (1..16)
    MAX-ACCESS  read-create
    STATUS      current
    DESCRIPTION
            "The Policer Index that represents the COS level.  This
             is applicable in case of a Multi COS flow. Index 1
             represents COS 0; Index 2 represents COS 1 and so on. 

             In release 5.6CC the range is extended to 1..16 to support duplicate
             N2A policers on a Flow. The duplicate policers are created under a Flow 
             if network interface of the Flow is ERP Group or Split Horizon Group. 
             In case of multi-cos Flow indices 1..8 represent policers of COS 0..7 
             going from Network 1 port; indices 9..16 represent policers for COS 0..7 
             going from Network 2 port.
             In case of single-cos Flow index 1 represents policer going from Network 1
             port; index 9 represents policer going from Network 2 port.
             "
    ::= { f3L3QosPolicerEntry 1 }

-- State Management params
f3L3QosPolicerAdminState OBJECT-TYPE
    SYNTAX      AdminState 
    MAX-ACCESS  read-write
    STATUS      current
    DESCRIPTION
            "This object represents the Administrative State of 
             the QOS Flow Policer." 
    ::= { f3L3QosPolicerEntry 2 }

f3L3QosPolicerOperationalState OBJECT-TYPE
    SYNTAX      OperationalState 
    MAX-ACCESS  read-only
    STATUS      current
    DESCRIPTION
            "This object represents the Operational State of the QOS Flow Policer." 
    ::= { f3L3QosPolicerEntry 3 }

f3L3QosPolicerSecondaryState OBJECT-TYPE
    SYNTAX      SecondaryState 
    MAX-ACCESS  read-only
    STATUS      current
    DESCRIPTION
            "This object represents the Secondary State of the QOS Flow Policer." 
    ::= { f3L3QosPolicerEntry 4 }

f3L3QosPolicerCIRLo OBJECT-TYPE
    SYNTAX     Unsigned32
    MAX-ACCESS read-create
    STATUS     current
    DESCRIPTION
         "This object allows specification of the Commited Information
          Rate(CIR) on Policer.  This represents the lower 32 bits of the
          CIR."
     ::= { f3L3QosPolicerEntry 5 }

f3L3QosPolicerCIRHi OBJECT-TYPE
    SYNTAX     Unsigned32
    MAX-ACCESS read-create
    STATUS     current
    DESCRIPTION
         "This object allows specification of the Commited Information
          Rate(CIR) on Policer.  This represents the upper 32 bits of the
          CIR."
     ::= { f3L3QosPolicerEntry 6 }

f3L3QosPolicerEIRLo OBJECT-TYPE
    SYNTAX     Unsigned32
    MAX-ACCESS read-create
    STATUS     current
    DESCRIPTION
         "This object allows specification of the Excess Information
          Rate(EIR) on the Policer.  This represents the lower 32 bits
          of the EIR."
     ::= { f3L3QosPolicerEntry 7 }

f3L3QosPolicerEIRHi OBJECT-TYPE
    SYNTAX     Unsigned32
    MAX-ACCESS read-create
    STATUS     current
    DESCRIPTION
         "This object allows specification of the Excess Information
          Rate(EIR) on the Policer.  This represents the upper 32 bits
          of the EIR."
     ::= { f3L3QosPolicerEntry 8 }

f3L3QosPolicerCBS OBJECT-TYPE
    SYNTAX     Integer32
    MAX-ACCESS read-create
    STATUS     current
    DESCRIPTION
         "This object allows specification of the Commited Burst Size
          (CBS) on Policer."
     ::= { f3L3QosPolicerEntry 9 }

f3L3QosPolicerEBS OBJECT-TYPE
    SYNTAX     Integer32
    MAX-ACCESS read-create
    STATUS     current
    DESCRIPTION
         "This object allows specification of the Excess Burst Size
          (EBS) on the Policer."
     ::= { f3L3QosPolicerEntry 10 }

f3L3QosPolicerAlgorithm OBJECT-TYPE
    SYNTAX      PolicerAlgorithmType 
    MAX-ACCESS  read-only
    STATUS      current
    DESCRIPTION
          "This object allows specification of Policer algorithm as
           'srTCM' (Single Rate Triple Color Marking) or 'trTCM' (Two Rate
           Triple Color Marking)."
    ::= { f3L3QosPolicerEntry 11 }

f3L3QosPolicerColorMode OBJECT-TYPE
    SYNTAX      PolicerColorMode 
    MAX-ACCESS  read-create
    STATUS      current
    DESCRIPTION
          "This object allows specification of Policer Color Mode as
           'color-aware' or 'color-blind'."
    ::= { f3L3QosPolicerEntry 12 }

f3L3QosPolicerCouplingFlag OBJECT-TYPE
    SYNTAX      TruthValue
    MAX-ACCESS  read-create
    STATUS      current
    DESCRIPTION
       "This object allows specification of Policer Coupling Flag.
        When coupling is enabled, tokens that would normally be 
        added to the C-bucket are passed to the E-bucket only once the CIR
        bucket has reached its CBS level. Therefore under this condition
        the E-bucket is being filled at the rate of CIR + EIR. 
        Normally the long term average of frames declared yellow is 
        bounded by the EIR. Coupling is a function to allow the 
        long term average of frames declared yellow to be bounded by 
        CIR + EIR. This allows a higher volume of yellow frames 
        to be delivered/received if the arrival of green marked frames 
        is low.  Tokens from the E-bucket do NOT get passed to the 
        C-bucket once the EBS level has been reached.
        Enabling coupling in combination with a provisioned EIR of 0 
        allows for a single rate three color marking (srTCM) algorithm 
        to be established.  In this situation the E-bucket is filled at the 
        CIR rate in the case the C-bucket is filled to its CBS level."
    ::= { f3L3QosPolicerEntry 13 }

f3L3QosPolicerStorageType OBJECT-TYPE
    SYNTAX     StorageType
    MAX-ACCESS read-create
    STATUS     current
    DESCRIPTION
            "The type of storage configured for this entry."
    ::= { f3L3QosPolicerEntry 14 }

f3L3QosPolicerRowStatus OBJECT-TYPE
    SYNTAX      RowStatus
    MAX-ACCESS  read-create
    STATUS      current
    DESCRIPTION
            "The status of this row.
            An entry MUST NOT exist in the active state unless all
            objects in the entry have an appropriate value, as described
            in the description clause for each writable object.

            The values of f3L3QosPolicerRowStatus supported are
            createAndGo(4) and destroy(6).  All mandatory attributes
            must be specified in a single SNMP SET request with
            f3L3QosPolicerRowStatus value as createAndGo(4).
            Upon successful row creation, this object has a
            value of active(1).

            The f3L3QosPolicerRowStatus object may be modified if
            the associated instance of this object is equal to active(1)."
    ::= { f3L3QosPolicerEntry 15 }

--
--  L3 Port Quality of Service Shaper 
--
f3L3QosShaperTable  OBJECT-TYPE
    SYNTAX      SEQUENCE OF F3L3QosShaperEntry
    MAX-ACCESS  not-accessible
    STATUS      current
    DESCRIPTION
            "A list of entries corresponding to Ethernet Access Port 
             Quality of Service Shaper for configuration purposes.
             These shapers can be managed when the Access Port is
             in evpl mode and are relevant for traffic in the
             network to access direction."
    ::= { f3L3Objects 8 }

f3L3QosShaperEntry OBJECT-TYPE
    SYNTAX      F3L3QosShaperEntry 
    MAX-ACCESS  not-accessible
    STATUS      current
    DESCRIPTION
            "A conceptual row in the f3L3QosShaperTable. 
             These entries represent a Quality of Service Shaper."
    INDEX { neIndex, shelfIndex, slotIndex, f3L3FlowPointPortTypeIndex, 
            f3L3FlowPointPortIndex, f3L3FlowPointIndex,  
            f3L3QosShaperIndex }
    ::= { f3L3QosShaperTable 1 }

F3L3QosShaperEntry ::= SEQUENCE {
    -- QOS Shaper Index/Id
    f3L3QosShaperIndex               Integer32,

    -- State Management params
    f3L3QosShaperAdminState          AdminState,
    f3L3QosShaperOperationalState    OperationalState,
    f3L3QosShaperSecondaryState      SecondaryState,

    -- QOS Shaper Properties
    f3L3QosShaperCIRLo               Unsigned32,
    f3L3QosShaperCIRHi               Unsigned32,
    f3L3QosShaperEIRLo               Unsigned32,
    f3L3QosShaperEIRHi               Unsigned32,
    f3L3QosShaperBufferSize          Unsigned32,
    f3L3QosShaperCOS                 Integer32,

    --wred threshold
    f3L3QosShaperWredGreenMinQueueThreshold       Unsigned32,
    f3L3QosShaperWredGreenMaxQueueThreshold       Unsigned32,
    f3L3QosShaperWredGreenDropProbability         Unsigned32,
    f3L3QosShaperWredYellowMinQueueThreshold      Unsigned32,
    f3L3QosShaperWredYellowMaxQueueThreshold      Unsigned32,
    f3L3QosShaperWredYellowDropProbability        Unsigned32,
    f3L3QosShaperStorageType                      StorageType,
    f3L3QosShaperRowStatus                        RowStatus
}

f3L3QosShaperIndex OBJECT-TYPE
    SYNTAX      Integer32 (1..8)
    MAX-ACCESS  read-create
    STATUS      current
    DESCRIPTION
            "The unique integer index value corresponding to a 
             Quality of Service Shaper."
    ::= { f3L3QosShaperEntry 1 }

-- State Management params
f3L3QosShaperAdminState OBJECT-TYPE
    SYNTAX      AdminState 
    MAX-ACCESS  read-write
    STATUS      current
    DESCRIPTION
            "This object represents the Administrative State of 
             the QOS Shaper." 
    ::= { f3L3QosShaperEntry 2 }

f3L3QosShaperOperationalState OBJECT-TYPE
    SYNTAX      OperationalState 
    MAX-ACCESS  read-only
    STATUS      current
    DESCRIPTION
            "This object represents the Operational State of the QOS Shaper." 
    ::= { f3L3QosShaperEntry 3 }

f3L3QosShaperSecondaryState OBJECT-TYPE
    SYNTAX      SecondaryState 
    MAX-ACCESS  read-only
    STATUS      current
    DESCRIPTION
            "This object represents the Secondary State of the QOS Shaper." 
    ::= { f3L3QosShaperEntry 4 }

f3L3QosShaperCIRLo OBJECT-TYPE
    SYNTAX     Unsigned32
    MAX-ACCESS read-create
    STATUS     current
    DESCRIPTION
         "This object represents the Commited Information
          Rate(CIR) (Lower 32 bits)of a Shaper."
     ::= { f3L3QosShaperEntry 5 }

f3L3QosShaperCIRHi OBJECT-TYPE
    SYNTAX     Unsigned32
    MAX-ACCESS read-create
    STATUS     current
    DESCRIPTION
         "This object represents the Commited Information
          Rate(CIR) (Higher 32 bits) of a Shaper."
     ::= { f3L3QosShaperEntry 6 }

f3L3QosShaperEIRLo OBJECT-TYPE
    SYNTAX     Unsigned32
    MAX-ACCESS read-create
    STATUS     current
    DESCRIPTION
         "This object represents the Excess Information
          Rate(EIR) (Higher 32 bits) on the Shaper."
     ::= { f3L3QosShaperEntry 7 }

f3L3QosShaperEIRHi OBJECT-TYPE
    SYNTAX     Unsigned32
    MAX-ACCESS read-create
    STATUS     current
    DESCRIPTION
         "This object represents the Excess Information
          Rate(EIR) (Higher 32 bits) on the Shaper."
     ::= { f3L3QosShaperEntry 8 }

f3L3QosShaperBufferSize OBJECT-TYPE
    SYNTAX     Unsigned32
    MAX-ACCESS read-create
    STATUS     current
    DESCRIPTION
         "This object represents the Buffer Size of the Shaper."
     ::= { f3L3QosShaperEntry 9 }

f3L3QosShaperCOS OBJECT-TYPE
    SYNTAX     Integer32 (0..7)
    MAX-ACCESS read-only
    STATUS     current
    DESCRIPTION
            "This object provides the COS (Class of Service)
             value for the QOS Shaper."
    ::= { f3L3QosShaperEntry 10 }

f3L3QosShaperWredGreenMinQueueThreshold OBJECT-TYPE
    SYNTAX     Unsigned32
    MAX-ACCESS read-create
    STATUS     current
    DESCRIPTION
         "This object represents the Wred green packet min queue threshold value."
     ::= { f3L3QosShaperEntry 11 }

f3L3QosShaperWredGreenMaxQueueThreshold OBJECT-TYPE
    SYNTAX     Unsigned32
    MAX-ACCESS read-create
    STATUS     current
    DESCRIPTION
         "This object represents the Wred green packet max queue threshold value."
     ::= { f3L3QosShaperEntry 12 }

f3L3QosShaperWredGreenDropProbability OBJECT-TYPE
    SYNTAX     Unsigned32
    MAX-ACCESS read-create
    STATUS     current
    DESCRIPTION
         "This object represents the Wred green packet drop probability."
     ::= { f3L3QosShaperEntry 13 }

f3L3QosShaperWredYellowMinQueueThreshold OBJECT-TYPE
    SYNTAX     Unsigned32
    MAX-ACCESS read-create
    STATUS     current
    DESCRIPTION
         "This object represents the Wred yellow packet min queue threshold value."
     ::= { f3L3QosShaperEntry 14 }

f3L3QosShaperWredYellowMaxQueueThreshold OBJECT-TYPE
    SYNTAX     Unsigned32
    MAX-ACCESS read-create
    STATUS     current
    DESCRIPTION
         "This object represents the Wred yellow packet max queue threshold value."
     ::= { f3L3QosShaperEntry 15 }

f3L3QosShaperWredYellowDropProbability OBJECT-TYPE
    SYNTAX     Unsigned32
    MAX-ACCESS read-create
    STATUS     current
    DESCRIPTION
         "This object represents the Wred yellow packet drop probability."
     ::= { f3L3QosShaperEntry 16 }

f3L3QosShaperStorageType OBJECT-TYPE
    SYNTAX     StorageType
    MAX-ACCESS read-create
    STATUS     current
    DESCRIPTION
            "The type of storage configured for this entry."
    ::= { f3L3QosShaperEntry 17 }

f3L3QosShaperRowStatus OBJECT-TYPE
    SYNTAX      RowStatus
    MAX-ACCESS  read-create
    STATUS      current
    DESCRIPTION
            "The status of this row.
            An entry MUST NOT exist in the active state unless all
            objects in the entry have an appropriate value, as described
            in the description clause for each writable object.

            The values of f3L3QosShaperRowStatus supported are
            createAndGo(4) and destroy(6).  All mandatory attributes
            must be specified in a single SNMP SET request with
            f3L3QosShaperRowStatus value as createAndGo(4).
            Upon successful row creation, this object has a
            value of active(1).

            The f3L3QosShaperRowStatus object may be modified if
            the associated instance of this object is equal to active(1)."
    ::= { f3L3QosShaperEntry 18 }
    
--
--  L3 traffic ip interface Table
--
f3L3TrafficIPInterfaceTable  OBJECT-TYPE
    SYNTAX      SEQUENCE OF F3L3TrafficIPInterfaceEntry
    MAX-ACCESS  not-accessible
    STATUS      current
    DESCRIPTION
            "A list of entries for the L3 Traffic IP Interface."
    ::= { f3L3Objects 9 }

f3L3TrafficIPInterfaceEntry  OBJECT-TYPE
    SYNTAX      F3L3TrafficIPInterfaceEntry
    MAX-ACCESS  not-accessible
    STATUS      current
    DESCRIPTION
            "A conceptual row in the f3L3TrafficIPInterfaceTable."
    INDEX { neIndex, shelfIndex, slotIndex,
            f3L3FlowPointPortIndex, f3L3FlowPointIndex, f3L3TrafficIPIfIndex }
    ::= { f3L3TrafficIPInterfaceTable 1 }

F3L3TrafficIPInterfaceEntry ::= SEQUENCE {
    f3L3TrafficIPIfIndex                               Integer32,
    f3L3TrafficIPIfName                                DisplayString,
    f3L3TrafficIPIfAdminState                          AdminState,
    f3L3TrafficIPIfSecondaryState                      SecondaryState,
    f3L3TrafficIPIfOperationalState                    OperationalState,
    f3L3TrafficIPIfProxyArpEnabled                     TruthValue,
    f3L3TrafficIPIfIpAddressSourceType                 IfIpAddressSourceType,
    f3L3TrafficIPIfMgmtUseEnable                       TruthValue,
    f3L3TrafficIPIfIpAddress                           IpAddress,
    f3L3TrafficIPIfMask                                IpAddress,

    f3L3TrafficIPIfDhcpRelayInterfaceSide              DhcpRelayInterfaceSide,
    f3L3TrafficIPIfDhcpRelayVendorClassiDOpt60         DisplayString,
    f3L3TrafficIPIfDhcpRelayVendorClassiDOpt60Control  TruthValue,
    f3L3TrafficIPIfDhcpRelayUserClassOpt77             DisplayString,
    f3L3TrafficIPIfDhcpRelayUserClassOpt77Control      TruthValue,
    f3L3TrafficIPIfDhcpRelayInfoOpt82Sub1              DisplayString,
    f3L3TrafficIPIfDhcpRelayInfoOpt82Sub1Enabled       TruthValue,
    f3L3TrafficIPIfDhcpRelayInfoOpt82Sub2              DisplayString,
    f3L3TrafficIPIfDhcpRelayInfoOpt82Sub2Enabled       TruthValue,

    f3L3TrafficIPIfDhcpEnabled                         TruthValue,
    f3L3TrafficIPIfDhcpRole                            CmDhcpRole,
    f3L3TrafficIPIfDhcpClientIdEnabled                 TruthValue,
    f3L3TrafficIPIfDhcpClientId                        DisplayString,
    f3L3TrafficIPIfDhcpClassIdEnabled                  TruthValue,
    f3L3TrafficIPIfDhcpHostNameEnabled                 TruthValue,
    f3L3TrafficIPIfDhcpHostName                        DisplayString,
    f3L3TrafficIPIfDhcpClientIdType                    DHCPCIDType,
    f3L3TrafficIPIfDhcpHostNameType                    DHCPHostNameType,
    f3L3TrafficIPIfStorageType                         StorageType,
    f3L3TrafficIPIfRowStatus                           RowStatus,

    f3L3TrafficIPIfAction                              AffectiveArpActionType
}

f3L3TrafficIPIfIndex OBJECT-TYPE
    SYNTAX      Integer32
    MAX-ACCESS  not-accessible
    STATUS      current
    DESCRIPTION
           "It specifies the traffic IP interface number."
    ::= { f3L3TrafficIPInterfaceEntry 1 }

f3L3TrafficIPIfName OBJECT-TYPE
    SYNTAX      DisplayString (SIZE (0..15))
    MAX-ACCESS  read-write
    STATUS      current
    DESCRIPTION
           "It specifies the traffic IP interface name."
    ::= { f3L3TrafficIPInterfaceEntry 2 }

f3L3TrafficIPIfAdminState OBJECT-TYPE
    SYNTAX      AdminState
    MAX-ACCESS  read-write
    STATUS      current
    DESCRIPTION
           "This object represents the Administrative State of the interface."
    ::= { f3L3TrafficIPInterfaceEntry 3 }

f3L3TrafficIPIfSecondaryState OBJECT-TYPE
    SYNTAX      SecondaryState
    MAX-ACCESS  read-only
    STATUS      current
    DESCRIPTION
           "This object represents the Secondary State of the interface."
    ::= { f3L3TrafficIPInterfaceEntry 4 }

f3L3TrafficIPIfOperationalState OBJECT-TYPE
    SYNTAX      OperationalState
    MAX-ACCESS  read-only
    STATUS      current
    DESCRIPTION
           "This object represents the Operational State of the interface."
    ::= { f3L3TrafficIPInterfaceEntry 5 }

f3L3TrafficIPIfProxyArpEnabled OBJECT-TYPE
    SYNTAX      TruthValue
    MAX-ACCESS  read-write
    STATUS      current
    DESCRIPTION
           "This attribute controls poxy ARP on this interface."
    ::= { f3L3TrafficIPInterfaceEntry 6 }

f3L3TrafficIPIfIpAddressSourceType OBJECT-TYPE
    SYNTAX      IfIpAddressSourceType
    MAX-ACCESS  read-write
    STATUS      current
    DESCRIPTION
           "This attribute represents the IP address source type."
    ::= { f3L3TrafficIPInterfaceEntry 7 }

f3L3TrafficIPIfMgmtUseEnable OBJECT-TYPE
    SYNTAX      TruthValue
    MAX-ACCESS  read-write
    STATUS      current
    DESCRIPTION
           "This attribute is used for controlling use of interface for management.
            If enabled the NE can be managed through this interface."
    ::= { f3L3TrafficIPInterfaceEntry 8 }

f3L3TrafficIPIfIpAddress OBJECT-TYPE
    SYNTAX      IpAddress
    MAX-ACCESS  read-write
    STATUS      current
    DESCRIPTION
           "IP Address of the interface."
    ::= { f3L3TrafficIPInterfaceEntry 9 }

f3L3TrafficIPIfMask OBJECT-TYPE
    SYNTAX      IpAddress
    MAX-ACCESS  read-write
    STATUS      current
    DESCRIPTION
           "IP Address mask of the interface."
    ::= { f3L3TrafficIPInterfaceEntry 10 }

f3L3TrafficIPIfDhcpRelayInterfaceSide OBJECT-TYPE
    SYNTAX      DhcpRelayInterfaceSide
    MAX-ACCESS  read-write
    STATUS      current
    DESCRIPTION
           "This object represents interface side."
    ::= { f3L3TrafficIPInterfaceEntry 11 }

f3L3TrafficIPIfDhcpRelayVendorClassiDOpt60 OBJECT-TYPE
    SYNTAX      DisplayString (SIZE (0..255))
    MAX-ACCESS  read-write
    STATUS      current
    DESCRIPTION
           "DHCP Option 60 value used for association of received
            DHCP message with Traffic IP Interface ."
    ::= { f3L3TrafficIPInterfaceEntry 12 }

f3L3TrafficIPIfDhcpRelayVendorClassiDOpt60Control OBJECT-TYPE
    SYNTAX      TruthValue
    MAX-ACCESS  read-write
    STATUS      current
    DESCRIPTION
           "This Attribute is used to control inspection of 
           DHCP option 60 presence in the DHCP messages received 
           on Client Side Traffic IP Interface."
    ::= { f3L3TrafficIPInterfaceEntry 13 }

f3L3TrafficIPIfDhcpRelayUserClassOpt77 OBJECT-TYPE
    SYNTAX      DisplayString (SIZE (0..255))
    MAX-ACCESS  read-write
    STATUS      current
    DESCRIPTION
           "DHCP Option 77 value used for association of received
            DHCP message with Traffic IP Interface ."
    ::= { f3L3TrafficIPInterfaceEntry 14 }

f3L3TrafficIPIfDhcpRelayUserClassOpt77Control OBJECT-TYPE
    SYNTAX      TruthValue
    MAX-ACCESS  read-write
    STATUS      current
    DESCRIPTION
           "This Attribute is used to control inspection of 
           DHCP option 77 presence in the DHCP messages received 
           on Client Side Traffic IP Interface."
    ::= { f3L3TrafficIPInterfaceEntry 15 }

f3L3TrafficIPIfDhcpRelayInfoOpt82Sub1 OBJECT-TYPE
    SYNTAX      DisplayString (SIZE (0..255))
    MAX-ACCESS  read-write
    STATUS      current
    DESCRIPTION
           "DHCP Option 82 sub option 1 value."
    ::= { f3L3TrafficIPInterfaceEntry 16 }

f3L3TrafficIPIfDhcpRelayInfoOpt82Sub1Enabled OBJECT-TYPE
    SYNTAX      TruthValue
    MAX-ACCESS  read-write
    STATUS      current
    DESCRIPTION
           "This Attribute is used to control inspection of 
           DHCP option 82 sub option 1 presence in the DHCP messages received 
           on Client Side Traffic IP Interface."
    ::= { f3L3TrafficIPInterfaceEntry 17 }

f3L3TrafficIPIfDhcpRelayInfoOpt82Sub2 OBJECT-TYPE
    SYNTAX      DisplayString (SIZE (0..255))
    MAX-ACCESS  read-write
    STATUS      current
    DESCRIPTION
           "DHCP Option 82 sub option 2 value."
    ::= { f3L3TrafficIPInterfaceEntry 18 }

f3L3TrafficIPIfDhcpRelayInfoOpt82Sub2Enabled OBJECT-TYPE
    SYNTAX      TruthValue
    MAX-ACCESS  read-write
    STATUS      current
    DESCRIPTION
           "This Attribute is used to control inspection of 
           DHCP option 82 sub option 2 presence in the DHCP messages received 
           on Client Side Traffic IP Interface."
    ::= { f3L3TrafficIPInterfaceEntry 19 }

f3L3TrafficIPIfDhcpEnabled OBJECT-TYPE
    SYNTAX      TruthValue
    MAX-ACCESS  read-only
    STATUS      current
    DESCRIPTION
           "Whether or not DHCP is enabled on this interface."
    ::= { f3L3TrafficIPInterfaceEntry 20 }

f3L3TrafficIPIfDhcpRole OBJECT-TYPE
    SYNTAX      CmDhcpRole
    MAX-ACCESS  read-only
    STATUS      current
    DESCRIPTION
           "Specify the DHCP role on this interface."
    ::= { f3L3TrafficIPInterfaceEntry 21 }

f3L3TrafficIPIfDhcpClientIdEnabled OBJECT-TYPE
    SYNTAX      TruthValue
    MAX-ACCESS  read-write
    STATUS      current
    DESCRIPTION
           "Whether or not DHCP client id enabled."
    ::= { f3L3TrafficIPInterfaceEntry 22 }

f3L3TrafficIPIfDhcpClientId OBJECT-TYPE
    SYNTAX      DisplayString
    MAX-ACCESS  read-write
    STATUS      current
    DESCRIPTION
           "Specify the DHCP Cliend ID value."
    ::= { f3L3TrafficIPInterfaceEntry 23 }

f3L3TrafficIPIfDhcpClassIdEnabled OBJECT-TYPE
    SYNTAX      TruthValue
    MAX-ACCESS  read-write
    STATUS      current
    DESCRIPTION
           "Whether or not DHCP class id enabled."
    ::= { f3L3TrafficIPInterfaceEntry 24 }

f3L3TrafficIPIfDhcpHostNameEnabled OBJECT-TYPE
    SYNTAX      TruthValue
    MAX-ACCESS  read-write
    STATUS      current
    DESCRIPTION
           "Whether or not DHCP host name enabled."
    ::= { f3L3TrafficIPInterfaceEntry 25 }

f3L3TrafficIPIfDhcpHostName OBJECT-TYPE
    SYNTAX      DisplayString
    MAX-ACCESS  read-write
    STATUS      current
    DESCRIPTION
           "DHCP host name value."
    ::= { f3L3TrafficIPInterfaceEntry 26 }

f3L3TrafficIPIfDhcpClientIdType OBJECT-TYPE
    SYNTAX      DHCPCIDType
    MAX-ACCESS  read-write
    STATUS      current
    DESCRIPTION
           "This object describe whether the dhcp cid type."
    ::= { f3L3TrafficIPInterfaceEntry 27 }

f3L3TrafficIPIfDhcpHostNameType OBJECT-TYPE
    SYNTAX      DHCPHostNameType
    MAX-ACCESS  read-write
    STATUS      current
    DESCRIPTION
           "This object describe whether the dhcp host name type."
    ::= { f3L3TrafficIPInterfaceEntry 28 }

f3L3TrafficIPIfStorageType OBJECT-TYPE
    SYNTAX      StorageType
    MAX-ACCESS  read-create
    STATUS      current
    DESCRIPTION
           "The type of storage configured for this entry."
    ::= { f3L3TrafficIPInterfaceEntry 29 }

f3L3TrafficIPIfRowStatus OBJECT-TYPE
    SYNTAX      RowStatus
    MAX-ACCESS  read-create
    STATUS      current
    DESCRIPTION
           "The status of this row.
          	An entry MUST NOT exist in the active state unless all
          	objects in the entry have an appropriate value, as described
          	in the description clause for each writable object.
 	
          	The values of f3L3TrafficIPIfRowStatus supported are
          	createAndGo(4) and destroy(6).  All mandatory attributes
          	must be specified in a single SNMP SET request with
          	f3L3TrafficIPIfRowStatus value as createAndGo(4).
          	Upon successful row creation, this object has a
          	value of active(1).
 	
          	The f3L3TrafficIPIfRowStatus object may be modified if
          	the associated instance of this object is equal to active(1)."
    ::= { f3L3TrafficIPInterfaceEntry 30 }

f3L3TrafficIPIfAction OBJECT-TYPE
    SYNTAX      AffectiveArpActionType
    MAX-ACCESS  read-write
    STATUS      current
    DESCRIPTION
           "This objects describes action set on this traffic ip interface."
    ::= { f3L3TrafficIPInterfaceEntry 31 }

--
--
--
f3DhcpRelayAgentTrafficIpIfMemberTable  OBJECT-TYPE
    SYNTAX      SEQUENCE OF F3DhcpRelayAgentTrafficIpIfMemberEntry
    MAX-ACCESS  not-accessible
    STATUS      current
    DESCRIPTION
            "A list of entries for the Dhcp Relay Agent Traffic Ip Interface member."
    ::= { f3L3Objects 10 }

f3DhcpRelayAgentTrafficIpIfMemberEntry  OBJECT-TYPE
    SYNTAX      F3DhcpRelayAgentTrafficIpIfMemberEntry
    MAX-ACCESS  not-accessible
    STATUS      current
    DESCRIPTION
            "A conceptual row in the f3DhcpRelayAgentTrafficIpIfMemberTable."
    INDEX { neIndex, f3DhcpRelayAgentIndex, f3DhcpRelayAgentTrafficIpIfMemberObject }
    ::= { f3DhcpRelayAgentTrafficIpIfMemberTable 1 }

F3DhcpRelayAgentTrafficIpIfMemberEntry ::= SEQUENCE {
    f3DhcpRelayAgentTrafficIpIfMemberObject             VariablePointer,
    f3DhcpRelayAgentTrafficIpIfMemberStorageType        StorageType,
    f3DhcpRelayAgentTrafficIpIfMemberRowStatus          RowStatus
}

f3DhcpRelayAgentTrafficIpIfMemberObject OBJECT-TYPE
    SYNTAX      VariablePointer
    MAX-ACCESS  not-accessible
    STATUS      current
    DESCRIPTION
           "This object describes the traffic ip interface."
    ::= { f3DhcpRelayAgentTrafficIpIfMemberEntry 1 }

f3DhcpRelayAgentTrafficIpIfMemberStorageType OBJECT-TYPE
    SYNTAX      StorageType
    MAX-ACCESS  read-create
    STATUS      current
    DESCRIPTION
           "The type of storage configured for this entry."
    ::= { f3DhcpRelayAgentTrafficIpIfMemberEntry 2 }

f3DhcpRelayAgentTrafficIpIfMemberRowStatus OBJECT-TYPE
    SYNTAX      RowStatus
    MAX-ACCESS  read-create
    STATUS      current
    DESCRIPTION
           "The status of this row.
          	An entry MUST NOT exist in the active state unless all
          	objects in the entry have an appropriate value, as described
          	in the description clause for each writable object.
 	
          	The values of f3DhcpRelayAgentTrafficIpIfMemberRowStatus supported are
          	createAndGo(4) and destroy(6).  All mandatory attributes
          	must be specified in a single SNMP SET request with
          	f3DhcpRelayAgentTrafficIpIfMemberRowStatus value as createAndGo(4).
          	Upon successful row creation, this object has a
          	value of active(1).
 	
          	The f3DhcpRelayAgentTrafficIpIfMemberRowStatus object may be modified if
          	the associated instance of this object is equal to active(1)."
    ::= { f3DhcpRelayAgentTrafficIpIfMemberEntry 3 }

---
---
---
f3VrfTrafficIpIfMemberTable  OBJECT-TYPE
    SYNTAX      SEQUENCE OF F3VrfTrafficIpIfMemberEntry
    MAX-ACCESS  not-accessible
    STATUS      current
    DESCRIPTION
            "A list of entries for the Vrf Traffic Ip Interface member."
    ::= { f3L3Objects 11 }

f3VrfTrafficIpIfMemberEntry  OBJECT-TYPE
    SYNTAX      F3VrfTrafficIpIfMemberEntry
    MAX-ACCESS  not-accessible
    STATUS      current
    DESCRIPTION
            "A conceptual row in the f3DhcpRelayAgentTrafficIpIfMemberTable."
    INDEX { neIndex, f3VrfIndex, f3VrfTrafficIpIfMemberObject }
    ::= { f3VrfTrafficIpIfMemberTable 1 }

F3VrfTrafficIpIfMemberEntry ::= SEQUENCE {
    f3VrfTrafficIpIfMemberObject             VariablePointer,
    f3VrfTrafficIpIfMemberStorageType        StorageType,
    f3VrfTrafficIpIfMemberRowStatus          RowStatus
}

f3VrfTrafficIpIfMemberObject OBJECT-TYPE
    SYNTAX      VariablePointer
    MAX-ACCESS  not-accessible
    STATUS      current
    DESCRIPTION
           "This object describes the traffic ip interface."
    ::= { f3VrfTrafficIpIfMemberEntry 1 }

f3VrfTrafficIpIfMemberStorageType OBJECT-TYPE
    SYNTAX      StorageType
    MAX-ACCESS  read-create
    STATUS      current
    DESCRIPTION
           "The type of storage configured for this entry."
    ::= { f3VrfTrafficIpIfMemberEntry 2 }

f3VrfTrafficIpIfMemberRowStatus OBJECT-TYPE
    SYNTAX      RowStatus
    MAX-ACCESS  read-create
    STATUS      current
    DESCRIPTION
           "The status of this row.
          	An entry MUST NOT exist in the active state unless all
          	objects in the entry have an appropriate value, as described
          	in the description clause for each writable object.
 	
          	The values of f3VrfTrafficIpIfMemberRowStatus supported are
          	createAndGo(4) and destroy(6).  All mandatory attributes
          	must be specified in a single SNMP SET request with
          	f3VrfTrafficIpIfMemberRowStatus value as createAndGo(4).
          	Upon successful row creation, this object has a
          	value of active(1).
 	
          	The f3VrfTrafficIpIfMemberRowStatus object may be modified if
          	the associated instance of this object is equal to active(1)."
    ::= { f3VrfTrafficIpIfMemberEntry 3 }

--
--  L3 taffic ipv4 route Table
--
f3L3TrafficIpv4RouteTable  OBJECT-TYPE
    SYNTAX      SEQUENCE OF F3L3TrafficIpv4RouteEntry
    MAX-ACCESS  not-accessible
    STATUS      current
    DESCRIPTION
            "A list of entries for the L3 Traffic Ipv4 route.
             Must set f3VrfAction as retrieveEffectiveRoutes(4) before get data from this table."
    ::= { f3L3Objects 12 }

f3L3TrafficIpv4RouteEntry  OBJECT-TYPE
    SYNTAX      F3L3TrafficIpv4RouteEntry
    MAX-ACCESS  not-accessible
    STATUS      current
    DESCRIPTION
            "A conceptual row in the f3L3TrafficIpv4RouteTable."
    INDEX { neIndex, f3VrfIndex, f3L3TrafficIpv4RouteDest, f3L3TrafficIpv4RouteMask, f3L3TrafficIpv4RouteNextHop, f3L3TrafficIpv4RouteInterface }
    ::= { f3L3TrafficIpv4RouteTable 1 }

F3L3TrafficIpv4RouteEntry ::= SEQUENCE {
    f3L3TrafficIpv4RouteDest                                IpAddress,
    f3L3TrafficIpv4RouteMask                                IpAddress,
    f3L3TrafficIpv4RouteNextHop                             IpAddress,
    f3L3TrafficIpv4RouteMetric                              Integer32,
    f3L3TrafficIpv4RouteInterface                           DisplayString,
    f3L3TrafficIpv4RouteAdvertise                           TruthValue,
    f3L3TrafficIpv4RouteStatus                              TrafficIpRouteStatus,
    f3L3TrafficIpv4RouteSourceForwardingEnable              TruthValue,
    f3L3TrafficIpv4RouteFlags                               RouteFlags,
    f3L3TrafficIpv4RouteStorageType                         StorageType,
    f3L3TrafficIpv4RouteRowStatus                           RowStatus,
    f3L3TrafficIpv4RouteType                                IpEntryType
}

f3L3TrafficIpv4RouteDest OBJECT-TYPE
    SYNTAX      IpAddress
    MAX-ACCESS  read-write
    STATUS      current
    DESCRIPTION
           "It specifies the traffic Ipv4 route destination."
    ::= { f3L3TrafficIpv4RouteEntry 1 }

f3L3TrafficIpv4RouteMask OBJECT-TYPE
    SYNTAX      IpAddress
    MAX-ACCESS  read-write
    STATUS      current
    DESCRIPTION
           "It specifies the traffic Ipv4 route mask."
    ::= { f3L3TrafficIpv4RouteEntry 2 }

f3L3TrafficIpv4RouteNextHop OBJECT-TYPE
    SYNTAX      IpAddress
    MAX-ACCESS  read-write
    STATUS      current
    DESCRIPTION
           "It specifies the traffic Ipv4 route next hop."
    ::= { f3L3TrafficIpv4RouteEntry 3 }

f3L3TrafficIpv4RouteMetric OBJECT-TYPE
    SYNTAX      Integer32
    MAX-ACCESS  read-write
    STATUS      current
    DESCRIPTION
           "It specifies the traffic Ipv4 route metric."
    ::= { f3L3TrafficIpv4RouteEntry 4 }

f3L3TrafficIpv4RouteInterface OBJECT-TYPE
    SYNTAX      DisplayString
    MAX-ACCESS  read-write
    STATUS      current
    DESCRIPTION
           "It specifies the traffic Ipv4 route interface."
    ::= { f3L3TrafficIpv4RouteEntry 5 }

f3L3TrafficIpv4RouteAdvertise OBJECT-TYPE
    SYNTAX      TruthValue
    MAX-ACCESS  read-write
    STATUS      current
    DESCRIPTION
           "It specifies the traffic Ipv4 route advertise."
    ::= { f3L3TrafficIpv4RouteEntry 6 }

f3L3TrafficIpv4RouteStatus OBJECT-TYPE
    SYNTAX      TrafficIpRouteStatus
    MAX-ACCESS  read-only
    STATUS      current
    DESCRIPTION
           "It specifies the traffic Ipv4 route status."
    ::= { f3L3TrafficIpv4RouteEntry 7 }

f3L3TrafficIpv4RouteSourceForwardingEnable OBJECT-TYPE
    SYNTAX      TruthValue
    MAX-ACCESS  read-write
    STATUS      current
    DESCRIPTION
           "It specifies the traffic Ipv4 route source forwarding whether enabled."
    ::= { f3L3TrafficIpv4RouteEntry 8 }

f3L3TrafficIpv4RouteFlags OBJECT-TYPE
    SYNTAX      RouteFlags
    MAX-ACCESS  read-only
    STATUS      current
    DESCRIPTION
           "It specifies the traffic Ipv4 route flags."
    ::= { f3L3TrafficIpv4RouteEntry 9 }

f3L3TrafficIpv4RouteStorageType OBJECT-TYPE
    SYNTAX      StorageType
    MAX-ACCESS  read-create
    STATUS      current
    DESCRIPTION
           "The type of storage configured for this entry."
    ::= { f3L3TrafficIpv4RouteEntry 10 }

f3L3TrafficIpv4RouteRowStatus OBJECT-TYPE
    SYNTAX      RowStatus
    MAX-ACCESS  read-create
    STATUS      current
    DESCRIPTION
           "The status of this row.
          	An entry MUST NOT exist in the active state unless all
          	objects in the entry have an appropriate value, as described
          	in the description clause for each writable object.
 	
          	The values of f3L3TrafficIpv4RouteRowStatus supported are
          	createAndGo(4) and destroy(6).  All mandatory attributes
          	must be specified in a single SNMP SET request with
          	f3L3TrafficIpv4RouteRowStatus value as createAndGo(4).
          	Upon successful row creation, this object has a
          	value of active(1).
 	
          	The f3L3TrafficIpv4RouteRowStatus object may be modified if
          	the associated instance of this object is equal to active(1)."
    ::= { f3L3TrafficIpv4RouteEntry 11 }

f3L3TrafficIpv4RouteType OBJECT-TYPE
    SYNTAX      IpEntryType
    MAX-ACCESS  read-only
    STATUS      current
    DESCRIPTION
           "It specifies the route is dynamic or static."
    ::= { f3L3TrafficIpv4RouteEntry 12 }

--
--  L3 Traffic Arp Table 
--
f3L3TrafficArpTable  OBJECT-TYPE
    SYNTAX      SEQUENCE OF F3L3TrafficArpEntry
    MAX-ACCESS  not-accessible
    STATUS      current
    DESCRIPTION
            "A list of Traffic ARP entries on the NIDs.
             Must set f3L3TrafficIPIfAction as retrieveAffectiveArp (1) before get data from this table."
    ::= { f3L3Objects 13 }

f3L3TrafficArpEntry OBJECT-TYPE
    SYNTAX      F3L3TrafficArpEntry 
    MAX-ACCESS  not-accessible
    STATUS      current
    DESCRIPTION
            "A conceptual row in the f3L3TrafficArpTable. Entries can
            be created/deleted in this table by management application action."
    INDEX { neIndex, shelfIndex, slotIndex,
            f3L3FlowPointPortIndex, f3L3FlowPointIndex, f3L3TrafficIPIfIndex, f3L3TrafficArpIPAddress }
    ::= { f3L3TrafficArpTable 1 }

F3L3TrafficArpEntry ::= SEQUENCE {
    f3L3TrafficArpIPAddress      IpAddress,
    f3L3TrafficArpMacAddress     MacAddress,
    f3L3TrafficArpInterface      DisplayString,
    f3L3TrafficArpEntryType      IpEntryType,
    f3L3TrafficArpStorageType    StorageType,
    f3L3TrafficArpRowStatus      RowStatus
}

f3L3TrafficArpIPAddress OBJECT-TYPE
    SYNTAX     IpAddress
    MAX-ACCESS not-accessible
    STATUS     current
    DESCRIPTION
         "This object allows configuration of the ARP Entry IP Address."
     ::= { f3L3TrafficArpEntry 1 }

f3L3TrafficArpMacAddress OBJECT-TYPE
    SYNTAX     MacAddress
    MAX-ACCESS read-create
    STATUS     current
    DESCRIPTION
         "This object allows management of the ARP Entry MAC Address."
     ::= { f3L3TrafficArpEntry 2 }

f3L3TrafficArpInterface OBJECT-TYPE
    SYNTAX     DisplayString
    MAX-ACCESS read-only
    STATUS     current
    DESCRIPTION
         "This object allows management of the ARP Entry Interface."
     ::= { f3L3TrafficArpEntry 3 }

f3L3TrafficArpEntryType OBJECT-TYPE
    SYNTAX     IpEntryType
    MAX-ACCESS read-write 
    STATUS     current
    DESCRIPTION
            "The type of ARP Entry. Note that static entries can be created."
    ::= { f3L3TrafficArpEntry 4 }

f3L3TrafficArpStorageType OBJECT-TYPE
    SYNTAX     StorageType
    MAX-ACCESS read-create
    STATUS     current
    DESCRIPTION
            "The type of storage configured for this entry."
    ::= { f3L3TrafficArpEntry 5 }

f3L3TrafficArpRowStatus OBJECT-TYPE
    SYNTAX      RowStatus
    MAX-ACCESS  read-write
    STATUS      current
    DESCRIPTION
            "The status of this row.
             The f3L3TrafficArpRowStatus object may be modified if
             the associated instance of this object is equal to active(1),
             notInService(2), or notReady(3)."
    ::= { f3L3TrafficArpEntry 6 }

---
---
---
---f3VrfTrafficRouteMemberTable  OBJECT-TYPE
---    SYNTAX      SEQUENCE OF F3VrfTrafficRouteMemberEntry
---    MAX-ACCESS  not-accessible
---    STATUS      current
---    DESCRIPTION
---            "A list of entries for the Vrf Traffic Route member."
---    ::= { f3L3Objects 15 }
---
---f3VrfTrafficRouteMemberEntry  OBJECT-TYPE
---    SYNTAX      F3VrfTrafficRouteMemberEntry
---    MAX-ACCESS  not-accessible
---    STATUS      current
---    DESCRIPTION
---            "A conceptual row in the f3VrfTrafficRouteMemberTable."
---    INDEX { neIndex, f3VrfIndex, f3VrfTrafficRouteMemberObject }
---    ::= { f3VrfTrafficRouteMemberTable 1 }
---
---F3VrfTrafficRouteMemberEntry ::= SEQUENCE {
---    f3VrfTrafficRouteMemberObject             VariablePointer
---}
---
---f3VrfTrafficRouteMemberObject OBJECT-TYPE
---    SYNTAX      VariablePointer
---    MAX-ACCESS  read-only
---    STATUS      current
---    DESCRIPTION
---           "This object describes the traffic route object."
---    ::= { f3VrfTrafficRouteMemberEntry 1 }

--
-- L3 flow point Current Statistics Table
--
f3L3FlowPointStatsTable OBJECT-TYPE
    SYNTAX      SEQUENCE OF F3L3FlowPointStatsEntry
    MAX-ACCESS  not-accessible
    STATUS      current
    DESCRIPTION
            "A collection of L3 Flow Point related statistics.  
             These reflect the current data."
    ::= { f3L3Performance 1 }

f3L3FlowPointStatsEntry OBJECT-TYPE
    SYNTAX      F3L3FlowPointStatsEntry 
    MAX-ACCESS  not-accessible
    STATUS      current
    DESCRIPTION
            "A conceptual row in the f3L3FlowPointStatsTable.
             Entries exist in this table for each L3 flow point."
    INDEX { neIndex, shelfIndex, slotIndex, f3L3FlowPointPortTypeIndex, 
            f3L3FlowPointPortIndex, f3L3FlowPointIndex, f3L3FlowPointStatsIndex }
    ::= { f3L3FlowPointStatsTable 1 }

F3L3FlowPointStatsEntry ::= SEQUENCE {
    f3L3FlowPointStatsIndex               Integer32,
    f3L3FlowPointStatsIntervalType        CmPmIntervalType,
    f3L3FlowPointStatsValid               TruthValue,
    f3L3FlowPointStatsAction              CmPmBinAction,
    f3L3FlowPointStatsFMG                 PerfCounter64,
    f3L3FlowPointStatsFMY                 PerfCounter64,
    f3L3FlowPointStatsFMRD                PerfCounter64,
    f3L3FlowPointStatsFTD                 PerfCounter64,
    f3L3FlowPointStatsFragmentedDropAcl   PerfCounter64,
    f3L3FlowPointStatsAclRuleDrop         PerfCounter64,
    f3L3FlowPointStatsTtlEqual1Drop       PerfCounter64,
    f3L3FlowPointStatsFrameTx             PerfCounter64,
    f3L3FlowPointStatsFrameRx             PerfCounter64,
    f3L3FlowPointStatsNoRouteDrop         PerfCounter64
}

f3L3FlowPointStatsIndex OBJECT-TYPE
    SYNTAX      Integer32 (1..4)
    MAX-ACCESS  read-only
    STATUS      current
    DESCRIPTION
            "An arbitrary integer index value used to uniquely identify
            this L3 flow point statistics entry. 
            1 - 15min
            2 - 1day
            3 - rollover
            4 - 5min"
    ::= { f3L3FlowPointStatsEntry 1 }

f3L3FlowPointStatsIntervalType OBJECT-TYPE
    SYNTAX      CmPmIntervalType
    MAX-ACCESS  read-only
    STATUS      current
    DESCRIPTION
            "Interval over which Performance Monitoring data is collected."
    ::= { f3L3FlowPointStatsEntry 2 }

f3L3FlowPointStatsValid OBJECT-TYPE
    SYNTAX      TruthValue
    MAX-ACCESS  read-only
    STATUS      current
    DESCRIPTION
            "Indicates the validity of the bin."
    ::= { f3L3FlowPointStatsEntry 3 }

f3L3FlowPointStatsAction OBJECT-TYPE
    SYNTAX      CmPmBinAction
    MAX-ACCESS  read-write
    STATUS      current
    DESCRIPTION
            "Allows the Manager to clear the bin."
    ::= { f3L3FlowPointStatsEntry 4 }

f3L3FlowPointStatsFMG OBJECT-TYPE
     SYNTAX     PerfCounter64
     MAX-ACCESS read-only
     STATUS     current
     DESCRIPTION
         "The number of Frames Marked Green."
     ::= { f3L3FlowPointStatsEntry 5 }

f3L3FlowPointStatsFMY OBJECT-TYPE
     SYNTAX     PerfCounter64
     MAX-ACCESS read-only
     STATUS     current
     DESCRIPTION
         "The number of Frames Marked Yellow."
     ::= { f3L3FlowPointStatsEntry 6 }

f3L3FlowPointStatsFMRD OBJECT-TYPE
     SYNTAX     PerfCounter64
     MAX-ACCESS read-only
     STATUS     current
     DESCRIPTION
         "The number of Frames Marked Red and Discarded."
     ::= { f3L3FlowPointStatsEntry 7 }

f3L3FlowPointStatsFTD OBJECT-TYPE
     SYNTAX     PerfCounter64
     MAX-ACCESS read-only
     STATUS     current
     DESCRIPTION
         "The number of Frames Tail Dropped."
     ::= { f3L3FlowPointStatsEntry 8 }

f3L3FlowPointStatsFragmentedDropAcl OBJECT-TYPE
     SYNTAX     PerfCounter64
     MAX-ACCESS read-only
     STATUS     current
     DESCRIPTION
         "The number of dropped fragmented packets."
     ::= { f3L3FlowPointStatsEntry 9 }

f3L3FlowPointStatsAclRuleDrop OBJECT-TYPE
     SYNTAX     PerfCounter64
     MAX-ACCESS read-only
     STATUS     current
     DESCRIPTION
         "The number of dropped packets due to ACL rule."
     ::= { f3L3FlowPointStatsEntry 10 }

f3L3FlowPointStatsTtlEqual1Drop OBJECT-TYPE
     SYNTAX     PerfCounter64
     MAX-ACCESS read-only
     STATUS     current
     DESCRIPTION
         " the number of dropped packets due to ttl's value is 1."
     ::= { f3L3FlowPointStatsEntry 11 }

f3L3FlowPointStatsFrameTx OBJECT-TYPE
     SYNTAX     PerfCounter64
     MAX-ACCESS read-only
     STATUS     current
     DESCRIPTION
         "The number of total transmitted frames."
     ::= { f3L3FlowPointStatsEntry 12 }

f3L3FlowPointStatsFrameRx OBJECT-TYPE
     SYNTAX     PerfCounter64
     MAX-ACCESS read-only
     STATUS     current
     DESCRIPTION
         " The number of total received frames."
     ::= { f3L3FlowPointStatsEntry 13 }

f3L3FlowPointStatsNoRouteDrop OBJECT-TYPE
     SYNTAX     PerfCounter64
     MAX-ACCESS read-only
     STATUS     current
     DESCRIPTION
         " The number of frames drop due to no route."
     ::= { f3L3FlowPointStatsEntry 14 }

--
-- L3 flow point history Statistics Table
--
f3L3FlowPointHistoryTable OBJECT-TYPE
    SYNTAX      SEQUENCE OF F3L3FlowPointHistoryEntry
    MAX-ACCESS  not-accessible
    STATUS      current
    DESCRIPTION
            "A collection of L3 Flow Point related statistics.  
             These reflect the current data."
    ::= { f3L3Performance 2 }

f3L3FlowPointHistoryEntry OBJECT-TYPE
    SYNTAX      F3L3FlowPointHistoryEntry 
    MAX-ACCESS  not-accessible
    STATUS      current
    DESCRIPTION
            "A conceptual row in the f3L3FlowPointHistoryTable.
             Entries exist in this table for each L3 flow point."
    INDEX { neIndex, shelfIndex, slotIndex, f3L3FlowPointPortTypeIndex, 
            f3L3FlowPointPortIndex, f3L3FlowPointIndex, f3L3FlowPointStatsIndex, f3L3FlowPointHistoryIndex }
    ::= { f3L3FlowPointHistoryTable 1 }

F3L3FlowPointHistoryEntry ::= SEQUENCE {
    f3L3FlowPointHistoryIndex               Integer32,
    f3L3FlowPointHistoryTime                DateAndTime,
    f3L3FlowPointHistoryValid               TruthValue,
    f3L3FlowPointHistoryAction              CmPmBinAction,
    f3L3FlowPointHistoryFMG                 PerfCounter64,
    f3L3FlowPointHistoryFMY                 PerfCounter64,
    f3L3FlowPointHistoryFMRD                PerfCounter64,
    f3L3FlowPointHistoryFTD                 PerfCounter64,
    f3L3FlowPointHistoryFragmentedDropAcl   PerfCounter64,
    f3L3FlowPointHistoryAclRuleDrop         PerfCounter64,
    f3L3FlowPointHistoryTtlEqual1Drop       PerfCounter64,
    f3L3FlowPointHistoryFrameTx             PerfCounter64,
    f3L3FlowPointHistoryFrameRx             PerfCounter64,
    f3L3FlowPointHistoryNoRouteDrop         PerfCounter64
}

f3L3FlowPointHistoryIndex OBJECT-TYPE
    SYNTAX      Integer32 (1..4)
    MAX-ACCESS  read-only
    STATUS      current
    DESCRIPTION
            "An arbitrary integer index value used to uniquely identify
            this L3 flow point statistics entry. 
            1 - 15min
            2 - 1day
            3 - rollover
            4 - 5min"
    ::= { f3L3FlowPointHistoryEntry 1 }

f3L3FlowPointHistoryTime OBJECT-TYPE
    SYNTAX      DateAndTime
    MAX-ACCESS  read-only
    STATUS      current
    DESCRIPTION
            "Indicates the time of history bin creation." 
    ::= { f3L3FlowPointHistoryEntry 2 }

f3L3FlowPointHistoryValid OBJECT-TYPE
    SYNTAX      TruthValue
    MAX-ACCESS  read-only
    STATUS      current
    DESCRIPTION
            "Indicates the validity of the bin."
    ::= { f3L3FlowPointHistoryEntry 3 }

f3L3FlowPointHistoryAction OBJECT-TYPE
    SYNTAX      CmPmBinAction
    MAX-ACCESS  read-write
    STATUS      current
    DESCRIPTION
            "Allows the Manager to clear the bin."
    ::= { f3L3FlowPointHistoryEntry 4 }

f3L3FlowPointHistoryFMG OBJECT-TYPE
     SYNTAX     PerfCounter64
     MAX-ACCESS read-only
     STATUS     current
     DESCRIPTION
         "The number of Frames Marked Green."
     ::= { f3L3FlowPointHistoryEntry 5 }

f3L3FlowPointHistoryFMY OBJECT-TYPE
     SYNTAX     PerfCounter64
     MAX-ACCESS read-only
     STATUS     current
     DESCRIPTION
         "The number of Frames Marked Yellow."
     ::= { f3L3FlowPointHistoryEntry 6 }

f3L3FlowPointHistoryFMRD OBJECT-TYPE
     SYNTAX     PerfCounter64
     MAX-ACCESS read-only
     STATUS     current
     DESCRIPTION
         "The number of Frames Marked Red and Discarded."
     ::= { f3L3FlowPointHistoryEntry 7 }

f3L3FlowPointHistoryFTD OBJECT-TYPE
     SYNTAX     PerfCounter64
     MAX-ACCESS read-only
     STATUS     current
     DESCRIPTION
         "The number of Frames Tail Dropped."
     ::= { f3L3FlowPointHistoryEntry 8 }

f3L3FlowPointHistoryFragmentedDropAcl OBJECT-TYPE
     SYNTAX     PerfCounter64
     MAX-ACCESS read-only
     STATUS     current
     DESCRIPTION
         "The number of dropped fragmented packets."
     ::= { f3L3FlowPointHistoryEntry 9 }

f3L3FlowPointHistoryAclRuleDrop OBJECT-TYPE
     SYNTAX     PerfCounter64
     MAX-ACCESS read-only
     STATUS     current
     DESCRIPTION
         "The number of dropped packets due to ACL rule."
     ::= { f3L3FlowPointHistoryEntry 10 }

f3L3FlowPointHistoryTtlEqual1Drop OBJECT-TYPE
     SYNTAX     PerfCounter64
     MAX-ACCESS read-only
     STATUS     current
     DESCRIPTION
         " the number of dropped packets due to ttl's value is 1."
     ::= { f3L3FlowPointHistoryEntry 11 }

f3L3FlowPointHistoryFrameTx OBJECT-TYPE
     SYNTAX     PerfCounter64
     MAX-ACCESS read-only
     STATUS     current
     DESCRIPTION
         "The number of total transmitted frames."
     ::= { f3L3FlowPointHistoryEntry 12 }

f3L3FlowPointHistoryFrameRx OBJECT-TYPE
     SYNTAX     PerfCounter64
     MAX-ACCESS read-only
     STATUS     current
     DESCRIPTION
         " the number of total recieved frames."
     ::= { f3L3FlowPointHistoryEntry 13 }

f3L3FlowPointHistoryNoRouteDrop OBJECT-TYPE
     SYNTAX     PerfCounter64
     MAX-ACCESS read-only
     STATUS     current
     DESCRIPTION
         " the number of frames dropped due to no route."
     ::= { f3L3FlowPointHistoryEntry 14 }

--
-- L3 Flow Point Threshold Table
--
f3L3FlowPointThresholdTable OBJECT-TYPE
    SYNTAX      SEQUENCE OF F3L3FlowPointThresholdEntry
    MAX-ACCESS  not-accessible
    STATUS      current
    DESCRIPTION
            "A table of entries that allow manageability of L3 Flow Point Thresholds."
    ::= { f3L3Performance 3 }

f3L3FlowPointThresholdEntry OBJECT-TYPE
    SYNTAX      F3L3FlowPointThresholdEntry
    MAX-ACCESS  not-accessible
    STATUS      current
    DESCRIPTION
            "A conceptual row in the f3L3FlowPointThresholdTable."
    INDEX { neIndex, shelfIndex, slotIndex, f3L3FlowPointPortTypeIndex, 
            f3L3FlowPointPortIndex, f3L3FlowPointIndex, f3L3FlowPointStatsIndex, f3L3FlowPointThresholdIndex }
    ::= { f3L3FlowPointThresholdTable 1 }

F3L3FlowPointThresholdEntry ::= SEQUENCE {
    f3L3FlowPointThresholdIndex       Integer32,
    f3L3FlowPointThresholdInterval    CmPmIntervalType,
    f3L3FlowPointThresholdVariable    VariablePointer,
    f3L3FlowPointThresholdValueLo     Unsigned32,
    f3L3FlowPointThresholdValueHi     Unsigned32,
    f3L3FlowPointThresholdMonValue    Counter64
}

f3L3FlowPointThresholdIndex OBJECT-TYPE
    SYNTAX     Integer32 (1..65535)
    MAX-ACCESS read-only
    STATUS     current
    DESCRIPTION
        "An index that uniquely identifies an entry in the
        f3L3FlowPointThresholdTable."
    ::= { f3L3FlowPointThresholdEntry 1 }

f3L3FlowPointThresholdInterval OBJECT-TYPE
    SYNTAX     CmPmIntervalType
    MAX-ACCESS read-only
    STATUS     current
    DESCRIPTION
        "The interval over which monitored value is
        sampled and compared with the specified threshold."
    ::= { f3L3FlowPointThresholdEntry 2 }

f3L3FlowPointThresholdVariable OBJECT-TYPE
    SYNTAX     VariablePointer
    MAX-ACCESS read-only
    STATUS     current
    DESCRIPTION
        "The object identifier of the particular variable to be
        sampled."
    ::= { f3L3FlowPointThresholdEntry 3 }

f3L3FlowPointThresholdValueLo OBJECT-TYPE
    SYNTAX     Unsigned32
    MAX-ACCESS read-write
    STATUS     current
    DESCRIPTION
        "Lower 32 bits of the threshold value."
    ::= { f3L3FlowPointThresholdEntry 4 }

f3L3FlowPointThresholdValueHi OBJECT-TYPE
    SYNTAX     Unsigned32
    MAX-ACCESS read-write
    STATUS     current
    DESCRIPTION
        "Higher 32 bits of the threshold value."
    ::= { f3L3FlowPointThresholdEntry 5 }

f3L3FlowPointThresholdMonValue OBJECT-TYPE
    SYNTAX     Counter64
    MAX-ACCESS read-only
    STATUS     current
    DESCRIPTION
        "Monitored value corresponding to f3L3FlowPointThresholdVariable."
    ::= { f3L3FlowPointThresholdEntry 6 }

--
-- L3 traffic ip interface Current Statistics Table
--
f3L3TrafficIpInterfaceStatsTable OBJECT-TYPE
    SYNTAX      SEQUENCE OF F3L3TrafficIpInterfaceStatsEntry
    MAX-ACCESS  not-accessible
    STATUS      current
    DESCRIPTION
            "A collection of L3 traffic ip interface related statistics.  
             These reflect the current data."
    ::= { f3L3Performance 4 }

f3L3TrafficIpInterfaceStatsEntry OBJECT-TYPE
    SYNTAX      F3L3TrafficIpInterfaceStatsEntry 
    MAX-ACCESS  not-accessible
    STATUS      current
    DESCRIPTION
            "A conceptual row in the f3L3TrafficIpInterfaceStatsTable.
             Entries exist in this table for each L3 traffic ip interface."
    INDEX { neIndex, shelfIndex, slotIndex,
            f3L3FlowPointPortIndex, f3L3FlowPointIndex, f3L3TrafficIPIfIndex, f3L3TrafficIpInterfaceStatsIndex }
    ::= { f3L3TrafficIpInterfaceStatsTable 1 }

F3L3TrafficIpInterfaceStatsEntry ::= SEQUENCE {
    f3L3TrafficIpInterfaceStatsIndex               Integer32,
    f3L3TrafficIpInterfaceStatsIntervalType        CmPmIntervalType,
    f3L3TrafficIpInterfaceStatsValid               TruthValue,
    f3L3TrafficIpInterfaceStatsAction              CmPmBinAction,
    f3L3TrafficIpInterfaceStatsDhcpTx              PerfCounter64,
    f3L3TrafficIpInterfaceStatsDhcpRx              PerfCounter64,
    f3L3TrafficIpInterfaceStatsIcmpTx              PerfCounter64,
    f3L3TrafficIpInterfaceStatsIcmpRx              PerfCounter64,
    f3L3TrafficIpInterfaceStatsArpReqTx            PerfCounter64,
    f3L3TrafficIpInterfaceStatsArpReqRx            PerfCounter64,
    f3L3TrafficIpInterfaceStatsArpReplyTx          PerfCounter64,
    f3L3TrafficIpInterfaceStatsArpReplyRx          PerfCounter64
}

f3L3TrafficIpInterfaceStatsIndex OBJECT-TYPE
    SYNTAX      Integer32 (1..4)
    MAX-ACCESS  read-only
    STATUS      current
    DESCRIPTION
            "An arbitrary integer index value used to uniquely identify
            this L3 flow point statistics entry. 
            1 - 15min
            2 - 1day
            3 - rollover
            4 - 5min"
    ::= { f3L3TrafficIpInterfaceStatsEntry 1 }

f3L3TrafficIpInterfaceStatsIntervalType OBJECT-TYPE
    SYNTAX      CmPmIntervalType
    MAX-ACCESS  read-only
    STATUS      current
    DESCRIPTION
            "Interval over which Performance Monitoring data is collected."
    ::= { f3L3TrafficIpInterfaceStatsEntry 2 }

f3L3TrafficIpInterfaceStatsValid OBJECT-TYPE
    SYNTAX      TruthValue
    MAX-ACCESS  read-only
    STATUS      current
    DESCRIPTION
            "Indicates the validity of the bin."
    ::= { f3L3TrafficIpInterfaceStatsEntry 3 }

f3L3TrafficIpInterfaceStatsAction OBJECT-TYPE
    SYNTAX      CmPmBinAction
    MAX-ACCESS  read-write
    STATUS      current
    DESCRIPTION
            "Allows the Manager to clear the bin."
    ::= { f3L3TrafficIpInterfaceStatsEntry 4 }

f3L3TrafficIpInterfaceStatsDhcpTx OBJECT-TYPE
     SYNTAX     PerfCounter64
     MAX-ACCESS read-only
     STATUS     current
     DESCRIPTION
         "The number of packets DHCP Transmit."
     ::= { f3L3TrafficIpInterfaceStatsEntry 5 }

f3L3TrafficIpInterfaceStatsDhcpRx OBJECT-TYPE
     SYNTAX     PerfCounter64
     MAX-ACCESS read-only
     STATUS     current
     DESCRIPTION
         "The number of packets DHCP Recieved."
     ::= { f3L3TrafficIpInterfaceStatsEntry 6 }

f3L3TrafficIpInterfaceStatsIcmpTx OBJECT-TYPE
     SYNTAX     PerfCounter64
     MAX-ACCESS read-only
     STATUS     current
     DESCRIPTION
         "The number of packets Icmp protocol transmit."
     ::= { f3L3TrafficIpInterfaceStatsEntry 7 }

f3L3TrafficIpInterfaceStatsIcmpRx OBJECT-TYPE
     SYNTAX     PerfCounter64
     MAX-ACCESS read-only
     STATUS     current
     DESCRIPTION
         "The number of packets Icmp protocol recieved."
     ::= { f3L3TrafficIpInterfaceStatsEntry 8 }

f3L3TrafficIpInterfaceStatsArpReqTx OBJECT-TYPE
     SYNTAX     PerfCounter64
     MAX-ACCESS read-only
     STATUS     current
     DESCRIPTION
         "The number of transmit packets due to ARP request."
     ::= { f3L3TrafficIpInterfaceStatsEntry 9 }

f3L3TrafficIpInterfaceStatsArpReqRx OBJECT-TYPE
     SYNTAX     PerfCounter64
     MAX-ACCESS read-only
     STATUS     current
     DESCRIPTION
         " the number of recieved packets due to ARP request."
     ::= { f3L3TrafficIpInterfaceStatsEntry 10 }

f3L3TrafficIpInterfaceStatsArpReplyTx OBJECT-TYPE
     SYNTAX     PerfCounter64
     MAX-ACCESS read-only
     STATUS     current
     DESCRIPTION
         "The number of transmit packets due to ARP reply."
     ::= { f3L3TrafficIpInterfaceStatsEntry 11 }

f3L3TrafficIpInterfaceStatsArpReplyRx OBJECT-TYPE
     SYNTAX     PerfCounter64
     MAX-ACCESS read-only
     STATUS     current
     DESCRIPTION
         " the number of recieved packets due to ARP reply."
     ::= { f3L3TrafficIpInterfaceStatsEntry 12 }

--
-- L3 traffic ip interface history Statistics Table
--
f3L3TrafficIpInterfaceHistoryTable OBJECT-TYPE
    SYNTAX      SEQUENCE OF F3L3TrafficIpInterfaceHistoryEntry
    MAX-ACCESS  not-accessible
    STATUS      current
    DESCRIPTION
            "A collection of L3 traffic ip interface related history statistics.  
             These reflect the history data."
    ::= { f3L3Performance 5 }

f3L3TrafficIpInterfaceHistoryEntry OBJECT-TYPE
    SYNTAX      F3L3TrafficIpInterfaceHistoryEntry 
    MAX-ACCESS  not-accessible
    STATUS      current
    DESCRIPTION
            "A conceptual row in the f3L3TrafficIpInterfaceHistoryTable.
             Entries exist in this table for each L3 traffic ip interface."
    INDEX { neIndex, shelfIndex, slotIndex, 
            f3L3FlowPointPortIndex, f3L3FlowPointIndex, f3L3TrafficIPIfIndex,
            f3L3TrafficIpInterfaceStatsIndex, f3L3TrafficIpInterfaceHistoryIndex }
    ::= { f3L3TrafficIpInterfaceHistoryTable 1 }

F3L3TrafficIpInterfaceHistoryEntry ::= SEQUENCE {
    f3L3TrafficIpInterfaceHistoryIndex               Integer32,
    f3L3TrafficIpInterfaceHistoryTime                DateAndTime,
    f3L3TrafficIpInterfaceHistoryValid               TruthValue,
    f3L3TrafficIpInterfaceHistoryAction              CmPmBinAction,
    f3L3TrafficIpInterfaceHistoryDhcpTx              PerfCounter64,
    f3L3TrafficIpInterfaceHistoryDhcpRx              PerfCounter64,
    f3L3TrafficIpInterfaceHistoryIcmpTx              PerfCounter64,
    f3L3TrafficIpInterfaceHistoryIcmpRx              PerfCounter64,
    f3L3TrafficIpInterfaceHistoryArpReqTx            PerfCounter64,
    f3L3TrafficIpInterfaceHistoryArpReqRx            PerfCounter64,
    f3L3TrafficIpInterfaceHistoryArpReplyTx          PerfCounter64,
    f3L3TrafficIpInterfaceHistoryArpReplyRx          PerfCounter64
}

f3L3TrafficIpInterfaceHistoryIndex OBJECT-TYPE
    SYNTAX      Integer32 (1..4)
    MAX-ACCESS  read-only
    STATUS      current
    DESCRIPTION
            "An arbitrary integer index value used to uniquely identify
            this L3 flow point statistics entry. 
            1 - 15min
            2 - 1day
            3 - rollover
            4 - 5min"
    ::= { f3L3TrafficIpInterfaceHistoryEntry 1 }

f3L3TrafficIpInterfaceHistoryTime OBJECT-TYPE
    SYNTAX      DateAndTime
    MAX-ACCESS  read-only
    STATUS      current
    DESCRIPTION
            "Indicates the time of history bin creation." 
    ::= { f3L3TrafficIpInterfaceHistoryEntry 2 }

f3L3TrafficIpInterfaceHistoryValid OBJECT-TYPE
    SYNTAX      TruthValue
    MAX-ACCESS  read-only
    STATUS      current
    DESCRIPTION
            "Indicates the validity of the bin."
    ::= { f3L3TrafficIpInterfaceHistoryEntry 3 }

f3L3TrafficIpInterfaceHistoryAction OBJECT-TYPE
    SYNTAX      CmPmBinAction
    MAX-ACCESS  read-write
    STATUS      current
    DESCRIPTION
            "Allows the Manager to clear the bin."
    ::= { f3L3TrafficIpInterfaceHistoryEntry 4 }

f3L3TrafficIpInterfaceHistoryDhcpTx OBJECT-TYPE
     SYNTAX     PerfCounter64
     MAX-ACCESS read-only
     STATUS     current
     DESCRIPTION
         "The number of packets DHCP Transmit."
     ::= { f3L3TrafficIpInterfaceHistoryEntry 5 }

f3L3TrafficIpInterfaceHistoryDhcpRx OBJECT-TYPE
     SYNTAX     PerfCounter64
     MAX-ACCESS read-only
     STATUS     current
     DESCRIPTION
         "The number of packets DHCP Recieved."
     ::= { f3L3TrafficIpInterfaceHistoryEntry 6 }

f3L3TrafficIpInterfaceHistoryIcmpTx OBJECT-TYPE
     SYNTAX     PerfCounter64
     MAX-ACCESS read-only
     STATUS     current
     DESCRIPTION
         "The number of packets Icmp protocol transmit."
     ::= { f3L3TrafficIpInterfaceHistoryEntry 7 }

f3L3TrafficIpInterfaceHistoryIcmpRx OBJECT-TYPE
     SYNTAX     PerfCounter64
     MAX-ACCESS read-only
     STATUS     current
     DESCRIPTION
         "The number of packets Icmp protocol recieved."
     ::= { f3L3TrafficIpInterfaceHistoryEntry 8 }

f3L3TrafficIpInterfaceHistoryArpReqTx OBJECT-TYPE
     SYNTAX     PerfCounter64
     MAX-ACCESS read-only
     STATUS     current
     DESCRIPTION
         "The number of transmit packets due to ARP request."
     ::= { f3L3TrafficIpInterfaceHistoryEntry 9 }

f3L3TrafficIpInterfaceHistoryArpReqRx OBJECT-TYPE
     SYNTAX     PerfCounter64
     MAX-ACCESS read-only
     STATUS     current
     DESCRIPTION
         " the number of recieved packets due to ARP request."
     ::= { f3L3TrafficIpInterfaceHistoryEntry 10 }

f3L3TrafficIpInterfaceHistoryArpReplyTx OBJECT-TYPE
     SYNTAX     PerfCounter64
     MAX-ACCESS read-only
     STATUS     current
     DESCRIPTION
         "The number of transmit packets due to ARP reply."
     ::= { f3L3TrafficIpInterfaceHistoryEntry 11 }

f3L3TrafficIpInterfaceHistoryArpReplyRx OBJECT-TYPE
     SYNTAX     PerfCounter64
     MAX-ACCESS read-only
     STATUS     current
     DESCRIPTION
         " the number of recieved packets due to ARP reply."
     ::= { f3L3TrafficIpInterfaceHistoryEntry 12 }

--
-- L3 traffic ip interface Threshold Table
--
f3L3TrafficIpInterfaceThresholdTable OBJECT-TYPE
    SYNTAX      SEQUENCE OF F3L3TrafficIpInterfaceThresholdEntry
    MAX-ACCESS  not-accessible
    STATUS      current
    DESCRIPTION
            "A table of entries that allow manageability of L3 traffic ip interface Thresholds."
    ::= { f3L3Performance 6 }

f3L3TrafficIpInterfaceThresholdEntry OBJECT-TYPE
    SYNTAX      F3L3TrafficIpInterfaceThresholdEntry
    MAX-ACCESS  not-accessible
    STATUS      current
    DESCRIPTION
            "A conceptual row in the f3L3TrafficIpInterfaceThresholdTable."
    INDEX { neIndex, shelfIndex, slotIndex, 
            f3L3FlowPointPortIndex, f3L3FlowPointIndex, f3L3TrafficIPIfIndex,
            f3L3TrafficIpInterfaceStatsIndex, f3L3TrafficIpInterfaceThresholdIndex }
    ::= { f3L3TrafficIpInterfaceThresholdTable 1 }

F3L3TrafficIpInterfaceThresholdEntry ::= SEQUENCE {
    f3L3TrafficIpInterfaceThresholdIndex       Integer32,
    f3L3TrafficIpInterfaceThresholdInterval    CmPmIntervalType,
    f3L3TrafficIpInterfaceThresholdVariable    VariablePointer,
    f3L3TrafficIpInterfaceThresholdValueLo     Unsigned32,
    f3L3TrafficIpInterfaceThresholdValueHi     Unsigned32,
    f3L3TrafficIpInterfaceThresholdMonValue    Counter64
}

f3L3TrafficIpInterfaceThresholdIndex OBJECT-TYPE
    SYNTAX     Integer32 (1..65535)
    MAX-ACCESS read-only
    STATUS     current
    DESCRIPTION
        "An index that uniquely identifies an entry in the
        f3L3TrafficIpInterfaceThresholdTable."
    ::= { f3L3TrafficIpInterfaceThresholdEntry 1 }

f3L3TrafficIpInterfaceThresholdInterval OBJECT-TYPE
    SYNTAX     CmPmIntervalType
    MAX-ACCESS read-only
    STATUS     current
    DESCRIPTION
        "The interval over which monitored value is
        sampled and compared with the specified threshold."
    ::= { f3L3TrafficIpInterfaceThresholdEntry 2 }

f3L3TrafficIpInterfaceThresholdVariable OBJECT-TYPE
    SYNTAX     VariablePointer
    MAX-ACCESS read-only
    STATUS     current
    DESCRIPTION
        "The object identifier of the particular variable to be
        sampled."
    ::= { f3L3TrafficIpInterfaceThresholdEntry 3 }

f3L3TrafficIpInterfaceThresholdValueLo OBJECT-TYPE
    SYNTAX     Unsigned32
    MAX-ACCESS read-write
    STATUS     current
    DESCRIPTION
        "Lower 32 bits of the threshold value."
    ::= { f3L3TrafficIpInterfaceThresholdEntry 4 }

f3L3TrafficIpInterfaceThresholdValueHi OBJECT-TYPE
    SYNTAX     Unsigned32
    MAX-ACCESS read-write
    STATUS     current
    DESCRIPTION
        "Higher 32 bits of the threshold value."
    ::= { f3L3TrafficIpInterfaceThresholdEntry 5 }

f3L3TrafficIpInterfaceThresholdMonValue OBJECT-TYPE
    SYNTAX     Counter64
    MAX-ACCESS read-only
    STATUS     current
    DESCRIPTION
        "Monitored value corresponding to f3L3TrafficIpInterfaceThresholdVariable."
    ::= { f3L3TrafficIpInterfaceThresholdEntry 6 }

--
-- L3 acl rule Current Statistics Table
--
f3L3AclRuleStatsTable OBJECT-TYPE
    SYNTAX      SEQUENCE OF F3L3AclRuleStatsEntry
    MAX-ACCESS  not-accessible
    STATUS      current
    DESCRIPTION
            "A collection of L3 acl rule related statistics.  
             These reflect the current data."
    ::= { f3L3Performance 7 }

f3L3AclRuleStatsEntry OBJECT-TYPE
    SYNTAX      F3L3AclRuleStatsEntry 
    MAX-ACCESS  not-accessible
    STATUS      current
    DESCRIPTION
            "A conceptual row in the f3L3AclRuleStatsTable.
             Entries exist in this table for each Acl rule."
    INDEX { neIndex, shelfIndex, slotIndex,
            f3L3FlowPointPortIndex, f3L3AclRuleParentIndex, f3L3AclRuleIndex, f3L3AclRuleStatsIndex }
    ::= { f3L3AclRuleStatsTable 1 }

F3L3AclRuleStatsEntry ::= SEQUENCE {
    f3L3AclRuleStatsIndex               Integer32,
    f3L3AclRuleStatsIntervalType        CmPmIntervalType,
    f3L3AclRuleStatsValid               TruthValue,
    f3L3AclRuleStatsAction              CmPmBinAction,
    f3L3AclRuleStatsRuleMatch           PerfCounter64
}

f3L3AclRuleStatsIndex OBJECT-TYPE
    SYNTAX      Integer32 (1..4)
    MAX-ACCESS  read-only
    STATUS      current
    DESCRIPTION
            "An arbitrary integer index value used to uniquely identify
            this L3 flow point statistics entry. 
            1 - 15min
            2 - 1day
            3 - rollover
            4 - 5min"
    ::= { f3L3AclRuleStatsEntry 1 }

f3L3AclRuleStatsIntervalType OBJECT-TYPE
    SYNTAX      CmPmIntervalType
    MAX-ACCESS  read-only
    STATUS      current
    DESCRIPTION
            "Interval over which Performance Monitoring data is collected."
    ::= { f3L3AclRuleStatsEntry 2 }

f3L3AclRuleStatsValid OBJECT-TYPE
    SYNTAX      TruthValue
    MAX-ACCESS  read-only
    STATUS      current
    DESCRIPTION
            "Indicates the validity of the bin."
    ::= { f3L3AclRuleStatsEntry 3 }

f3L3AclRuleStatsAction OBJECT-TYPE
    SYNTAX      CmPmBinAction
    MAX-ACCESS  read-write
    STATUS      current
    DESCRIPTION
            "Allows the Manager to clear the bin."
    ::= { f3L3AclRuleStatsEntry 4 }

f3L3AclRuleStatsRuleMatch OBJECT-TYPE
     SYNTAX     PerfCounter64
     MAX-ACCESS read-only
     STATUS     current
     DESCRIPTION
         "The number of packets matching the ACL rule."
     ::= { f3L3AclRuleStatsEntry 5 }

--
-- L3 acl rule history Statistics Table
--
f3L3AclRuleHistoryTable OBJECT-TYPE
    SYNTAX      SEQUENCE OF F3L3AclRuleHistoryEntry
    MAX-ACCESS  not-accessible
    STATUS      current
    DESCRIPTION
            "A collection of L3 acl rule related history statistics.  
             These reflect the history data."
    ::= { f3L3Performance 8 }

f3L3AclRuleHistoryEntry OBJECT-TYPE
    SYNTAX      F3L3AclRuleHistoryEntry 
    MAX-ACCESS  not-accessible
    STATUS      current
    DESCRIPTION
            "A conceptual row in the f3L3AclRuleHistoryTable.
             Entries exist in this table for each L3 acl rule."
    INDEX { neIndex, shelfIndex, slotIndex,
            f3L3FlowPointPortIndex, f3L3AclRuleParentIndex, f3L3AclRuleIndex,
            f3L3AclRuleStatsIndex, f3L3AclRuleHistoryIndex }
    ::= { f3L3AclRuleHistoryTable 1 }

F3L3AclRuleHistoryEntry ::= SEQUENCE {
    f3L3AclRuleHistoryIndex               Integer32,
    f3L3AclRuleHistoryTime                DateAndTime,
    f3L3AclRuleHistoryValid               TruthValue,
    f3L3AclRuleHistoryAction              CmPmBinAction,
    f3L3AclRuleHistoryRuleMatch           PerfCounter64
}

f3L3AclRuleHistoryIndex OBJECT-TYPE
    SYNTAX      Integer32 (1..4)
    MAX-ACCESS  read-only
    STATUS      current
    DESCRIPTION
            "An arbitrary integer index value used to uniquely identify
            this L3 flow point statistics entry. 
            1 - 15min
            2 - 1day
            3 - rollover
            4 - 5min"
    ::= { f3L3AclRuleHistoryEntry 1 }

f3L3AclRuleHistoryTime OBJECT-TYPE
    SYNTAX      DateAndTime
    MAX-ACCESS  read-only
    STATUS      current
    DESCRIPTION
            "Indicates the time of history bin creation." 
    ::= { f3L3AclRuleHistoryEntry 2 }

f3L3AclRuleHistoryValid OBJECT-TYPE
    SYNTAX      TruthValue
    MAX-ACCESS  read-only
    STATUS      current
    DESCRIPTION
            "Indicates the validity of the bin."
    ::= { f3L3AclRuleHistoryEntry 3 }

f3L3AclRuleHistoryAction OBJECT-TYPE
    SYNTAX      CmPmBinAction
    MAX-ACCESS  read-write
    STATUS      current
    DESCRIPTION
            "Allows the Manager to clear the bin."
    ::= { f3L3AclRuleHistoryEntry 4 }

f3L3AclRuleHistoryRuleMatch OBJECT-TYPE
     SYNTAX     PerfCounter64
     MAX-ACCESS read-only
     STATUS     current
     DESCRIPTION
         "The number of packets matching acl rule."
     ::= { f3L3AclRuleHistoryEntry 5 }

--
-- L3 acl rule Threshold Table
--
f3L3AclRuleThresholdTable OBJECT-TYPE
    SYNTAX      SEQUENCE OF F3L3AclRuleThresholdEntry
    MAX-ACCESS  not-accessible
    STATUS      current
    DESCRIPTION
            "A table of entries that allow manageability of L3 acl rule Thresholds."
    ::= { f3L3Performance 9 }

f3L3AclRuleThresholdEntry OBJECT-TYPE
    SYNTAX      F3L3AclRuleThresholdEntry
    MAX-ACCESS  not-accessible
    STATUS      current
    DESCRIPTION
            "A conceptual row in the f3L3AclRuleThresholdTable."
    INDEX { neIndex, shelfIndex, slotIndex,
            f3L3FlowPointPortIndex, f3L3AclRuleParentIndex, f3L3AclRuleIndex,
            f3L3AclRuleStatsIndex, f3L3AclRuleThresholdIndex }
    ::= { f3L3AclRuleThresholdTable 1 }

F3L3AclRuleThresholdEntry ::= SEQUENCE {
    f3L3AclRuleThresholdIndex       Integer32,
    f3L3AclRuleThresholdInterval    CmPmIntervalType,
    f3L3AclRuleThresholdVariable    VariablePointer,
    f3L3AclRuleThresholdValueLo     Unsigned32,
    f3L3AclRuleThresholdValueHi     Unsigned32,
    f3L3AclRuleThresholdMonValue    Counter64
}

f3L3AclRuleThresholdIndex OBJECT-TYPE
    SYNTAX     Integer32 (1..65535)
    MAX-ACCESS read-only
    STATUS     current
    DESCRIPTION
        "An index that uniquely identifies an entry in the
        f3L3AclRuleThresholdTable."
    ::= { f3L3AclRuleThresholdEntry 1 }

f3L3AclRuleThresholdInterval OBJECT-TYPE
    SYNTAX     CmPmIntervalType
    MAX-ACCESS read-only
    STATUS     current
    DESCRIPTION
        "The interval over which monitored value is
        sampled and compared with the specified threshold."
    ::= { f3L3AclRuleThresholdEntry 2 }

f3L3AclRuleThresholdVariable OBJECT-TYPE
    SYNTAX     VariablePointer
    MAX-ACCESS read-only
    STATUS     current
    DESCRIPTION
        "The object identifier of the particular variable to be
        sampled."
    ::= { f3L3AclRuleThresholdEntry 3 }

f3L3AclRuleThresholdValueLo OBJECT-TYPE
    SYNTAX     Unsigned32
    MAX-ACCESS read-write
    STATUS     current
    DESCRIPTION
        "Lower 32 bits of the threshold value."
    ::= { f3L3AclRuleThresholdEntry 4 }

f3L3AclRuleThresholdValueHi OBJECT-TYPE
    SYNTAX     Unsigned32
    MAX-ACCESS read-write
    STATUS     current
    DESCRIPTION
        "Higher 32 bits of the threshold value."
    ::= { f3L3AclRuleThresholdEntry 5 }

f3L3AclRuleThresholdMonValue OBJECT-TYPE
    SYNTAX     Counter64
    MAX-ACCESS read-only
    STATUS     current
    DESCRIPTION
        "Monitored value corresponding to f3L3AclRuleThresholdVariable."
    ::= { f3L3AclRuleThresholdEntry 6 }

--
-- Quality of Service(QOS) Policer Current Statistics Table
--
f3L3QosPolicerStatsTable OBJECT-TYPE
    SYNTAX      SEQUENCE OF F3L3QosPolicerStatsEntry
    MAX-ACCESS  not-accessible
    STATUS      current
    DESCRIPTION
            "A collection of QOS Policer statistics.  
             These reflect the current data."
    ::= { f3L3Performance 10 }

f3L3QosPolicerStatsEntry OBJECT-TYPE
    SYNTAX      F3L3QosPolicerStatsEntry 
    MAX-ACCESS  not-accessible
    STATUS      current
    DESCRIPTION
            "A conceptual row in the f3L3QosPolicerStatsTable.
             Entries exist in this table for each l3 flow point policer."
    INDEX { neIndex, shelfIndex, slotIndex, f3L3FlowPointPortTypeIndex, 
            f3L3FlowPointPortIndex, f3L3FlowPointIndex, f3L3QosPolicerIndex,
            f3L3QosPolicerStatsIndex }
    ::= { f3L3QosPolicerStatsTable 1 }

F3L3QosPolicerStatsEntry ::= SEQUENCE {
    f3L3QosPolicerStatsIndex           Integer32,
    f3L3QosPolicerStatsIntervalType    CmPmIntervalType,
    f3L3QosPolicerStatsValid           TruthValue,
    f3L3QosPolicerStatsAction          CmPmBinAction,
    f3L3QosPolicerStatsFMG             PerfCounter64,
    f3L3QosPolicerStatsFMY             PerfCounter64,
    f3L3QosPolicerStatsFMYD            PerfCounter64,
    f3L3QosPolicerStatsFMRD            PerfCounter64,
    f3L3QosPolicerStatsBytesIn         PerfCounter64,
    f3L3QosPolicerStatsBytesOut        PerfCounter64,
    f3L3QosPolicerStatsABR             PerfCounter64
}

f3L3QosPolicerStatsIndex OBJECT-TYPE
    SYNTAX      Integer32 (1..65535)
    MAX-ACCESS  read-only
    STATUS      current
    DESCRIPTION
            "An integer index value used to uniquely identify
            this QOS Policer statistics entry.
            1 - 15min
            2 - 1day
            3 - rollover
            4 - 5min"
    ::= { f3L3QosPolicerStatsEntry 1 }

f3L3QosPolicerStatsIntervalType OBJECT-TYPE
    SYNTAX      CmPmIntervalType
    MAX-ACCESS  read-only
    STATUS      current
    DESCRIPTION
            "Interval over which Performance Monitoring data is collected."
    ::= { f3L3QosPolicerStatsEntry 2 }

f3L3QosPolicerStatsValid OBJECT-TYPE
    SYNTAX      TruthValue
    MAX-ACCESS  read-only
    STATUS      current
    DESCRIPTION
            "Indicates the validity of the bin."
    ::= { f3L3QosPolicerStatsEntry 3 }

f3L3QosPolicerStatsAction OBJECT-TYPE
    SYNTAX      CmPmBinAction
    MAX-ACCESS  read-write
    STATUS      current
    DESCRIPTION
            "Allows the Manager to clear the bin."
    ::= { f3L3QosPolicerStatsEntry 4 }

f3L3QosPolicerStatsFMG OBJECT-TYPE
     SYNTAX     PerfCounter64
     MAX-ACCESS read-only
     STATUS     current
     DESCRIPTION
         "Frames Marked Green."
     ::= { f3L3QosPolicerStatsEntry 5 }

f3L3QosPolicerStatsFMY OBJECT-TYPE
     SYNTAX     PerfCounter64
     MAX-ACCESS read-only
     STATUS     current
     DESCRIPTION
         "Frames Marked Yellow."
     ::= { f3L3QosPolicerStatsEntry 6 }

f3L3QosPolicerStatsFMYD OBJECT-TYPE
     SYNTAX     PerfCounter64
     MAX-ACCESS read-only
     STATUS     deprecated
     DESCRIPTION
         "Frames Marked Yellow and Dropped."
     ::= { f3L3QosPolicerStatsEntry 7 }

f3L3QosPolicerStatsFMRD OBJECT-TYPE
     SYNTAX     PerfCounter64
     MAX-ACCESS read-only
     STATUS     current
     DESCRIPTION
         "Frames Marked Red and Discarded."
     ::= { f3L3QosPolicerStatsEntry 8 }

f3L3QosPolicerStatsBytesIn OBJECT-TYPE
     SYNTAX     PerfCounter64
     MAX-ACCESS read-only
     STATUS     current
     DESCRIPTION
         "Number of bytes received by the Policer."
     ::= { f3L3QosPolicerStatsEntry 9 }

f3L3QosPolicerStatsBytesOut OBJECT-TYPE
     SYNTAX     PerfCounter64
     MAX-ACCESS read-only
     STATUS     current
     DESCRIPTION
         "Number of bytes transmitted by the Policer."
     ::= { f3L3QosPolicerStatsEntry 10 }

f3L3QosPolicerStatsABR OBJECT-TYPE
     SYNTAX     PerfCounter64
     MAX-ACCESS read-only
     STATUS     current
     DESCRIPTION
         "Average Bit Rate  on the Policer."
     ::= { f3L3QosPolicerStatsEntry 11 }


--
-- Quality of Service(QOS) Policer History Statistics Table
--
f3L3QosPolicerHistoryTable OBJECT-TYPE
    SYNTAX      SEQUENCE OF F3L3QosPolicerHistoryEntry
    MAX-ACCESS  not-accessible
    STATUS      current
    DESCRIPTION
            "A collection of QOS Policer statistics.  
             These reflect the current data."
    ::= { f3L3Performance 11 }

f3L3QosPolicerHistoryEntry OBJECT-TYPE
    SYNTAX      F3L3QosPolicerHistoryEntry 
    MAX-ACCESS  not-accessible
    STATUS      current
    DESCRIPTION
            "A conceptual row in the f3L3QosPolicerHistoryTable.
             Entries exist in this table for each flow point policer."
    INDEX { neIndex, shelfIndex, slotIndex, f3L3FlowPointPortTypeIndex, 
            f3L3FlowPointPortIndex, f3L3FlowPointIndex, f3L3QosPolicerIndex,
            f3L3QosPolicerStatsIndex, f3L3QosPolicerHistoryIndex }
    ::= { f3L3QosPolicerHistoryTable 1 }

F3L3QosPolicerHistoryEntry ::= SEQUENCE {
    f3L3QosPolicerHistoryIndex           Integer32,
    f3L3QosPolicerHistoryTime            DateAndTime,
    f3L3QosPolicerHistoryValid           TruthValue,
    f3L3QosPolicerHistoryAction          CmPmBinAction,
    f3L3QosPolicerHistoryFMG             PerfCounter64,
    f3L3QosPolicerHistoryFMY             PerfCounter64,
    f3L3QosPolicerHistoryFMYD            PerfCounter64,
    f3L3QosPolicerHistoryFMRD            PerfCounter64,
    f3L3QosPolicerHistoryBytesIn         PerfCounter64,
    f3L3QosPolicerHistoryBytesOut        PerfCounter64,
    f3L3QosPolicerHistoryABR             PerfCounter64
}

f3L3QosPolicerHistoryIndex OBJECT-TYPE
    SYNTAX      Integer32 (1..65535)
    MAX-ACCESS  read-only
    STATUS      current
    DESCRIPTION
            "An arbitrary integer index value used to uniquely identify
            this QOS Policer history entry."
    ::= { f3L3QosPolicerHistoryEntry 1 }

f3L3QosPolicerHistoryTime OBJECT-TYPE
    SYNTAX      DateAndTime
    MAX-ACCESS  read-only
    STATUS      current
    DESCRIPTION
            "Indicates the time of history bin creation." 
    ::= { f3L3QosPolicerHistoryEntry 2 }

f3L3QosPolicerHistoryValid OBJECT-TYPE
    SYNTAX      TruthValue
    MAX-ACCESS  read-only
    STATUS      current
    DESCRIPTION
            "Indicates the validity of the bin."
    ::= { f3L3QosPolicerHistoryEntry 3 }

f3L3QosPolicerHistoryAction OBJECT-TYPE
    SYNTAX      CmPmBinAction
    MAX-ACCESS  read-write
    STATUS      current
    DESCRIPTION
            "Allows the Manager to clear the bin."
    ::= { f3L3QosPolicerHistoryEntry 4 }

f3L3QosPolicerHistoryFMG OBJECT-TYPE
     SYNTAX     PerfCounter64
     MAX-ACCESS read-only
     STATUS     current
     DESCRIPTION
         "Frames Marked Green."
     ::= { f3L3QosPolicerHistoryEntry 5 }

f3L3QosPolicerHistoryFMY OBJECT-TYPE
     SYNTAX     PerfCounter64
     MAX-ACCESS read-only
     STATUS     current
     DESCRIPTION
         "Frames Marked Yellow."
     ::= { f3L3QosPolicerHistoryEntry 6 }

f3L3QosPolicerHistoryFMYD OBJECT-TYPE
     SYNTAX     PerfCounter64
     MAX-ACCESS read-only
     STATUS     deprecated
     DESCRIPTION
         "Frames Marked Yellow and Dropped."
     ::= { f3L3QosPolicerHistoryEntry 7 }

f3L3QosPolicerHistoryFMRD OBJECT-TYPE
     SYNTAX     PerfCounter64
     MAX-ACCESS read-only
     STATUS     current
     DESCRIPTION
         "Frames Marked Red and Discarded."
     ::= { f3L3QosPolicerHistoryEntry 8 }

f3L3QosPolicerHistoryBytesIn OBJECT-TYPE
     SYNTAX     PerfCounter64
     MAX-ACCESS read-only
     STATUS     current
     DESCRIPTION
         "Number of bytes received by the Policer."
     ::= { f3L3QosPolicerHistoryEntry 9 }

f3L3QosPolicerHistoryBytesOut OBJECT-TYPE
     SYNTAX     PerfCounter64
     MAX-ACCESS read-only
     STATUS     current
     DESCRIPTION
         "Number of bytes transmitted by the Policer."
     ::= { f3L3QosPolicerHistoryEntry 10 }

f3L3QosPolicerHistoryABR OBJECT-TYPE
     SYNTAX     PerfCounter64
     MAX-ACCESS read-only
     STATUS     current
     DESCRIPTION
         "Average Bit Rate  on the Policer."
     ::= { f3L3QosPolicerHistoryEntry 11 }

--
-- QOS Policer Threshold Table
--
f3L3QosPolicerThresholdTable OBJECT-TYPE
    SYNTAX      SEQUENCE OF F3L3QosPolicerThresholdEntry
    MAX-ACCESS  not-accessible
    STATUS      current
    DESCRIPTION
            "A table of entries that allow manageability of QOS
             Policer Thresholds."
    ::= { f3L3Performance 12 }

f3L3QosPolicerThresholdEntry OBJECT-TYPE
    SYNTAX      F3L3QosPolicerThresholdEntry
    MAX-ACCESS  not-accessible
    STATUS      current
    DESCRIPTION
            "A conceptual row in the f3L3QosPolicerThresholdTable."
    INDEX { neIndex, shelfIndex, slotIndex, f3L3FlowPointPortTypeIndex, 
            f3L3FlowPointPortIndex, f3L3FlowPointIndex, f3L3QosPolicerIndex,
            f3L3QosPolicerStatsIndex, f3L3QosPolicerThresholdIndex }
    ::= { f3L3QosPolicerThresholdTable 1 }

F3L3QosPolicerThresholdEntry ::= SEQUENCE {
    f3L3QosPolicerThresholdIndex       Integer32,
    f3L3QosPolicerThresholdInterval    CmPmIntervalType,
    f3L3QosPolicerThresholdVariable    VariablePointer,
    f3L3QosPolicerThresholdValueLo     Unsigned32,
    f3L3QosPolicerThresholdValueHi     Unsigned32,
    f3L3QosPolicerThresholdMonValue    Counter64
}

f3L3QosPolicerThresholdIndex OBJECT-TYPE
    SYNTAX     Integer32 (1..65535)
    MAX-ACCESS read-only
    STATUS     current
    DESCRIPTION
        "An index that uniquely identifies an entry in the
        f3L3QosPolicerThresholdTable."
    ::= { f3L3QosPolicerThresholdEntry 1 }

f3L3QosPolicerThresholdInterval OBJECT-TYPE
    SYNTAX     CmPmIntervalType
    MAX-ACCESS read-only
    STATUS     current
    DESCRIPTION
        "The interval over which monitored value is
        sampled and compared with the specified threshold."
    ::= { f3L3QosPolicerThresholdEntry 2 }

f3L3QosPolicerThresholdVariable OBJECT-TYPE
    SYNTAX     VariablePointer
    MAX-ACCESS read-only
    STATUS     current
    DESCRIPTION
        "The object identifier of the particular variable to be
        sampled."
    ::= { f3L3QosPolicerThresholdEntry 3 }

f3L3QosPolicerThresholdValueLo OBJECT-TYPE
    SYNTAX     Unsigned32
    MAX-ACCESS read-write
    STATUS     current
    DESCRIPTION
        "Lower 32 bits of the threshold value."
    ::= { f3L3QosPolicerThresholdEntry 4 }

f3L3QosPolicerThresholdValueHi OBJECT-TYPE
    SYNTAX     Unsigned32
    MAX-ACCESS read-write
    STATUS     current
    DESCRIPTION
        "Higher 32 bits of the threshold value."
    ::= { f3L3QosPolicerThresholdEntry 5 }

f3L3QosPolicerThresholdMonValue OBJECT-TYPE
    SYNTAX     Counter64
    MAX-ACCESS read-only
    STATUS     current
    DESCRIPTION
        "Monitored value corresponding to f3L3QosPolicerThresholdVariable."
    ::= { f3L3QosPolicerThresholdEntry 6 }

--
-- L3 flow point Level Quality of Service(QOS) Shaper Current Statistics Table
--
f3L3QosShaperStatsTable OBJECT-TYPE
    SYNTAX      SEQUENCE OF F3L3QosShaperStatsEntry
    MAX-ACCESS  not-accessible
    STATUS      current
    DESCRIPTION
            "A collection of L3 flow point Level QOS Shaper statistics.  
             These reflect the current data."
    ::= { f3L3Performance 13 }

f3L3QosShaperStatsEntry OBJECT-TYPE
    SYNTAX      F3L3QosShaperStatsEntry 
    MAX-ACCESS  not-accessible
    STATUS      current
    DESCRIPTION
            "A conceptual row in the f3L3QosShaperStatsTable.
             Entries exist in this table for each QOS Shaper per L3 flow point."
    INDEX { neIndex, shelfIndex, slotIndex, f3L3FlowPointPortTypeIndex, 
            f3L3FlowPointPortIndex, f3L3FlowPointIndex,
            f3L3QosShaperIndex, f3L3QosShaperStatsIndex }
    ::= { f3L3QosShaperStatsTable 1 }

F3L3QosShaperStatsEntry ::= SEQUENCE {
    f3L3QosShaperStatsIndex             Integer32,
    f3L3QosShaperStatsIntervalType      CmPmIntervalType,
    f3L3QosShaperStatsValid             TruthValue,
    f3L3QosShaperStatsAction            CmPmBinAction,
    f3L3QosShaperStatsBT                PerfCounter64,
    f3L3QosShaperStatsBTD               PerfCounter64,
    f3L3QosShaperStatsFD                PerfCounter64,
    f3L3QosShaperStatsFTD               PerfCounter64,
    f3L3QosShaperStatsBR                PerfCounter64,
    f3L3QosShaperStatsFR                PerfCounter64,
    f3L3QosShaperStatsABRRL             PerfCounter64,
    f3L3QosShaperStatsABRRLR            PerfCounter64,
    f3L3QosShaperStatsBREDD             PerfCounter64,
    f3L3QosShaperStatsFREDD             PerfCounter64
}

f3L3QosShaperStatsIndex OBJECT-TYPE
    SYNTAX      Integer32 (1..65535)
    MAX-ACCESS  read-only
    STATUS      current
    DESCRIPTION
            "An arbitrary integer index value used to uniquely identify
            this QOS Shaper statistics entry.
            1 - 15min
            2 - 1day
            3 - rollover
            4 - 5min"
    ::= { f3L3QosShaperStatsEntry 1 }

f3L3QosShaperStatsIntervalType OBJECT-TYPE
    SYNTAX      CmPmIntervalType
    MAX-ACCESS  read-only
    STATUS      current
    DESCRIPTION
            "Interval over which Performance Monitoring data is collected."
    ::= { f3L3QosShaperStatsEntry 2 }

f3L3QosShaperStatsValid OBJECT-TYPE
    SYNTAX      TruthValue
    MAX-ACCESS  read-only
    STATUS      current
    DESCRIPTION
            "Indicates the validity of the bin."
    ::= { f3L3QosShaperStatsEntry 3 }

f3L3QosShaperStatsAction OBJECT-TYPE
    SYNTAX      CmPmBinAction
    MAX-ACCESS  read-write
    STATUS      current
    DESCRIPTION
            "Allows the Manager to clear the bin."
    ::= { f3L3QosShaperStatsEntry 4 }

f3L3QosShaperStatsBT OBJECT-TYPE
     SYNTAX     PerfCounter64
     MAX-ACCESS read-only
     STATUS     current
     DESCRIPTION
         "Bytes Transmitted."
     ::= { f3L3QosShaperStatsEntry 5 }

f3L3QosShaperStatsBTD OBJECT-TYPE
     SYNTAX     PerfCounter64
     MAX-ACCESS read-only
     STATUS     current
     DESCRIPTION
         "Bytes Tail Dropped."
     ::= { f3L3QosShaperStatsEntry 6 }

f3L3QosShaperStatsFD OBJECT-TYPE
     SYNTAX     PerfCounter64
     MAX-ACCESS read-only
     STATUS     current
     DESCRIPTION
         "Frames Dequeued."
     ::= { f3L3QosShaperStatsEntry 7 }

f3L3QosShaperStatsFTD OBJECT-TYPE
     SYNTAX     PerfCounter64
     MAX-ACCESS read-only
     STATUS     current
     DESCRIPTION
         "Frames Tail Dropped."
     ::= { f3L3QosShaperStatsEntry 8 }

f3L3QosShaperStatsBR OBJECT-TYPE
     SYNTAX     PerfCounter64
     MAX-ACCESS read-only
     STATUS     current
     DESCRIPTION
         "Bytes Replicated."
     ::= { f3L3QosShaperStatsEntry 9 }

f3L3QosShaperStatsFR OBJECT-TYPE
     SYNTAX     PerfCounter64
     MAX-ACCESS read-only
     STATUS     current
     DESCRIPTION
         "Frames Replicated."
     ::= { f3L3QosShaperStatsEntry 10 }

f3L3QosShaperStatsABRRL OBJECT-TYPE
     SYNTAX     PerfCounter64
     MAX-ACCESS read-only
     STATUS     current
     DESCRIPTION
         "Average Bit Rate - Rate Limited."
     ::= { f3L3QosShaperStatsEntry 11 }

f3L3QosShaperStatsABRRLR OBJECT-TYPE
     SYNTAX     PerfCounter64
     MAX-ACCESS read-only
     STATUS     current
     DESCRIPTION
         "Average Bit Rate - Rate Limited, Replicated."
     ::= { f3L3QosShaperStatsEntry 12 }

f3L3QosShaperStatsBREDD OBJECT-TYPE
     SYNTAX     PerfCounter64
     MAX-ACCESS read-only
     STATUS     current
     DESCRIPTION
         "Bytes Random Early Discard, Dropped."
     ::= { f3L3QosShaperStatsEntry 13 }

f3L3QosShaperStatsFREDD OBJECT-TYPE
     SYNTAX     PerfCounter64
     MAX-ACCESS read-only
     STATUS     current
     DESCRIPTION
         "Frames Random Early Discard, Dropped."
     ::= { f3L3QosShaperStatsEntry 14 }

--
-- Quality of Service(QOS) Shaper History Statistics Table
--
f3L3QosShaperHistoryTable OBJECT-TYPE
    SYNTAX      SEQUENCE OF F3L3QosShaperHistoryEntry
    MAX-ACCESS  not-accessible
    STATUS      current
    DESCRIPTION
            "A collection of l3 flow point Level QOS Shaper statistics.
             These reflect the history data."
    ::= { f3L3Performance 14 }

f3L3QosShaperHistoryEntry OBJECT-TYPE
    SYNTAX      F3L3QosShaperHistoryEntry 
    MAX-ACCESS  not-accessible
    STATUS      current
    DESCRIPTION
            "A conceptual row in the f3L3QosShaperHistoryTable.
             Entries exist in this table for each Shaper per l3 flow point."
    INDEX { neIndex, shelfIndex, slotIndex, f3L3FlowPointPortTypeIndex, 
            f3L3FlowPointPortIndex, f3L3FlowPointIndex,
            f3L3QosShaperIndex, f3L3QosShaperStatsIndex, f3L3QosShaperHistoryIndex }
    ::= { f3L3QosShaperHistoryTable 1 }

F3L3QosShaperHistoryEntry ::= SEQUENCE {
    f3L3QosShaperHistoryIndex             Integer32,
    f3L3QosShaperHistoryTime              DateAndTime,
    f3L3QosShaperHistoryValid             TruthValue,
    f3L3QosShaperHistoryAction            CmPmBinAction,
    f3L3QosShaperHistoryBT                PerfCounter64,
    f3L3QosShaperHistoryBTD               PerfCounter64,
    f3L3QosShaperHistoryFD                PerfCounter64,
    f3L3QosShaperHistoryFTD               PerfCounter64,
    f3L3QosShaperHistoryBR                PerfCounter64,
    f3L3QosShaperHistoryFR                PerfCounter64,
    f3L3QosShaperHistoryABRRL             PerfCounter64,
    f3L3QosShaperHistoryABRRLR            PerfCounter64,
    f3L3QosShaperHistoryBREDD             PerfCounter64,
    f3L3QosShaperHistoryFREDD             PerfCounter64
}

f3L3QosShaperHistoryIndex OBJECT-TYPE
    SYNTAX      Integer32 (1..65535)
    MAX-ACCESS  read-only
    STATUS      current
    DESCRIPTION
            "An arbitrary integer index value used to uniquely identify
            this QOS Shaper statistics entry."
    ::= { f3L3QosShaperHistoryEntry 1 }

f3L3QosShaperHistoryTime OBJECT-TYPE
    SYNTAX      DateAndTime
    MAX-ACCESS  read-only
    STATUS      current
    DESCRIPTION
            "Indicates the time of history bin creation." 
    ::= { f3L3QosShaperHistoryEntry 2 }

f3L3QosShaperHistoryValid OBJECT-TYPE
    SYNTAX      TruthValue
    MAX-ACCESS  read-only
    STATUS      current
    DESCRIPTION
            "Indicates the validity of the bin."
    ::= { f3L3QosShaperHistoryEntry 3 }

f3L3QosShaperHistoryAction OBJECT-TYPE
    SYNTAX      CmPmBinAction
    MAX-ACCESS  read-write
    STATUS      current
    DESCRIPTION
            "Allows the Manager to clear the bin."
    ::= { f3L3QosShaperHistoryEntry 4 }

f3L3QosShaperHistoryBT OBJECT-TYPE
     SYNTAX     PerfCounter64
     MAX-ACCESS read-only
     STATUS     current
     DESCRIPTION
         "Bytes Transmitted."
     ::= { f3L3QosShaperHistoryEntry 5 }

f3L3QosShaperHistoryBTD OBJECT-TYPE
     SYNTAX     PerfCounter64
     MAX-ACCESS read-only
     STATUS     current
     DESCRIPTION
         "Bytes Tail Dropped."
     ::= { f3L3QosShaperHistoryEntry 6 }

f3L3QosShaperHistoryFD OBJECT-TYPE
     SYNTAX     PerfCounter64
     MAX-ACCESS read-only
     STATUS     current
     DESCRIPTION
         "Frames Dequeued."
     ::= { f3L3QosShaperHistoryEntry 7 }

f3L3QosShaperHistoryFTD OBJECT-TYPE
     SYNTAX     PerfCounter64
     MAX-ACCESS read-only
     STATUS     current
     DESCRIPTION
         "Frames Tail Dropped."
     ::= { f3L3QosShaperHistoryEntry 8 }

f3L3QosShaperHistoryBR OBJECT-TYPE
     SYNTAX     PerfCounter64
     MAX-ACCESS read-only
     STATUS     current
     DESCRIPTION
         "Bytes Replicated."
     ::= { f3L3QosShaperHistoryEntry 9 }

f3L3QosShaperHistoryFR OBJECT-TYPE
     SYNTAX     PerfCounter64
     MAX-ACCESS read-only
     STATUS     current
     DESCRIPTION
         "Frames Replicated."
     ::= { f3L3QosShaperHistoryEntry 10 }

f3L3QosShaperHistoryABRRL OBJECT-TYPE
     SYNTAX     PerfCounter64
     MAX-ACCESS read-only
     STATUS     current
     DESCRIPTION
         "Average Bit Rate - Rate Limited."
     ::= { f3L3QosShaperHistoryEntry 11 }

f3L3QosShaperHistoryABRRLR OBJECT-TYPE
     SYNTAX     PerfCounter64
     MAX-ACCESS read-only
     STATUS     current
     DESCRIPTION
         "Average Bit Rate - Rate Limited, Replicated."
     ::= { f3L3QosShaperHistoryEntry 12 }

f3L3QosShaperHistoryBREDD OBJECT-TYPE
     SYNTAX     PerfCounter64
     MAX-ACCESS read-only
     STATUS     current
     DESCRIPTION
         "Bytes Random Early Discard, Dropped."
     ::= { f3L3QosShaperHistoryEntry 13 }

f3L3QosShaperHistoryFREDD OBJECT-TYPE
     SYNTAX     PerfCounter64
     MAX-ACCESS read-only
     STATUS     current
     DESCRIPTION
         "Frames Random Early Discard, Dropped."
     ::= { f3L3QosShaperHistoryEntry 14 }

--
-- L3 flow point QOS Shaper Threshold Table
--
f3L3QosShaperThresholdTable OBJECT-TYPE
    SYNTAX      SEQUENCE OF F3L3QosShaperThresholdEntry
    MAX-ACCESS  not-accessible
    STATUS      current
    DESCRIPTION
            "A table of entries that allow manageability of QOS
             Shaper Thresholds."
    ::= { f3L3Performance 15 }

f3L3QosShaperThresholdEntry OBJECT-TYPE
    SYNTAX      F3L3QosShaperThresholdEntry
    MAX-ACCESS  not-accessible
    STATUS      current
    DESCRIPTION
            "A conceptual row in the f3L3QosShaperThresholdTable."
    INDEX { neIndex, shelfIndex, slotIndex, f3L3FlowPointPortTypeIndex, 
            f3L3FlowPointPortIndex, f3L3FlowPointIndex,
            f3L3QosShaperIndex, f3L3QosShaperStatsIndex, 
            f3L3QosShaperThresholdIndex }
    ::= { f3L3QosShaperThresholdTable 1 }

F3L3QosShaperThresholdEntry ::= SEQUENCE {
    f3L3QosShaperThresholdIndex       Integer32,
    f3L3QosShaperThresholdInterval    CmPmIntervalType,
    f3L3QosShaperThresholdVariable    VariablePointer,
    f3L3QosShaperThresholdValueLo     Unsigned32,
    f3L3QosShaperThresholdValueHi     Unsigned32,
    f3L3QosShaperThresholdMonValue    Counter64
}

f3L3QosShaperThresholdIndex OBJECT-TYPE
    SYNTAX     Integer32 (1..65535)
    MAX-ACCESS read-only
    STATUS     current
    DESCRIPTION
        "An index that uniquely identifies an entry in the
        f3L3QosShaperThresholdTable."
    ::= { f3L3QosShaperThresholdEntry 1 }

f3L3QosShaperThresholdInterval OBJECT-TYPE
    SYNTAX     CmPmIntervalType
    MAX-ACCESS read-only
    STATUS     current
    DESCRIPTION
        "The interval over which monitored value is
        sampled and compared with the specified threshold."
    ::= { f3L3QosShaperThresholdEntry 2 }

f3L3QosShaperThresholdVariable OBJECT-TYPE
    SYNTAX     VariablePointer
    MAX-ACCESS read-only
    STATUS     current
    DESCRIPTION
        "The object identifier of the particular variable to be
        sampled."
    ::= { f3L3QosShaperThresholdEntry 3 }

f3L3QosShaperThresholdValueLo OBJECT-TYPE
    SYNTAX     Unsigned32
    MAX-ACCESS read-write
    STATUS     current
    DESCRIPTION
        "Lower 32 bits of the threshold value."
    ::= { f3L3QosShaperThresholdEntry 4 }

f3L3QosShaperThresholdValueHi OBJECT-TYPE
    SYNTAX     Unsigned32
    MAX-ACCESS read-write
    STATUS     current
    DESCRIPTION
        "Higher 32 bits of the threshold value."
    ::= { f3L3QosShaperThresholdEntry 5 }

f3L3QosShaperThresholdMonValue OBJECT-TYPE
    SYNTAX     Counter64
    MAX-ACCESS read-only
    STATUS     current
    DESCRIPTION
        "Monitored value corresponding to f3L3QosShaperThresholdVariable."
    ::= { f3L3QosShaperThresholdEntry 6 }


--
-- L3 A2N acl rule Current Statistics Table
--
f3L2A2NAclRuleStatsTable OBJECT-TYPE
    SYNTAX      SEQUENCE OF F3L2A2NAclRuleStatsEntry
    MAX-ACCESS  not-accessible
    STATUS      current
    DESCRIPTION
            "A collection of L3 acl rule related statistics.  
             These reflect the current data."
    ::= { f3L3Performance 16 }

f3L2A2NAclRuleStatsEntry OBJECT-TYPE
    SYNTAX      F3L2A2NAclRuleStatsEntry 
    MAX-ACCESS  not-accessible
    STATUS      current
    DESCRIPTION
            "A conceptual row in the f3L2A2NAclRuleStatsTable.
             Entries exist in this table for each Acl rule."
    INDEX { neIndex, shelfIndex, slotIndex,
            f3L3FlowPointPortIndex, f3L2A2NAclRuleParentIndex, f3L2A2NAclRuleIndex, f3L2A2NAclRuleStatsIndex }
    ::= { f3L2A2NAclRuleStatsTable 1 }

F3L2A2NAclRuleStatsEntry ::= SEQUENCE {
    f3L2A2NAclRuleStatsIndex               Integer32,
    f3L2A2NAclRuleStatsIntervalType        CmPmIntervalType,
    f3L2A2NAclRuleStatsValid               TruthValue,
    f3L2A2NAclRuleStatsAction              CmPmBinAction,
    f3L2A2NAclRuleStatsRuleMatch           PerfCounter64
}

f3L2A2NAclRuleStatsIndex OBJECT-TYPE
    SYNTAX      Integer32 (1..4)
    MAX-ACCESS  read-only
    STATUS      current
    DESCRIPTION
            "An arbitrary integer index value used to uniquely identify
            this L3 flow point statistics entry. 
            1 - 15min
            2 - 1day
            3 - rollover
            4 - 5min"
    ::= { f3L2A2NAclRuleStatsEntry 1 }

f3L2A2NAclRuleStatsIntervalType OBJECT-TYPE
    SYNTAX      CmPmIntervalType
    MAX-ACCESS  read-only
    STATUS      current
    DESCRIPTION
            "Interval over which Performance Monitoring data is collected."
    ::= { f3L2A2NAclRuleStatsEntry 2 }

f3L2A2NAclRuleStatsValid OBJECT-TYPE
    SYNTAX      TruthValue
    MAX-ACCESS  read-only
    STATUS      current
    DESCRIPTION
            "Indicates the validity of the bin."
    ::= { f3L2A2NAclRuleStatsEntry 3 }

f3L2A2NAclRuleStatsAction OBJECT-TYPE
    SYNTAX      CmPmBinAction
    MAX-ACCESS  read-write
    STATUS      current
    DESCRIPTION
            "Allows the Manager to clear the bin."
    ::= { f3L2A2NAclRuleStatsEntry 4 }

f3L2A2NAclRuleStatsRuleMatch OBJECT-TYPE
     SYNTAX     PerfCounter64
     MAX-ACCESS read-only
     STATUS     current
     DESCRIPTION
         "The number of packets matching the ACL rule."
     ::= { f3L2A2NAclRuleStatsEntry 5 }

--
-- L3 acl rule history Statistics Table
--
f3L2A2NAclRuleHistoryTable OBJECT-TYPE
    SYNTAX      SEQUENCE OF F3L2A2NAclRuleHistoryEntry
    MAX-ACCESS  not-accessible
    STATUS      current
    DESCRIPTION
            "A collection of L3 acl rule related history statistics.  
             These reflect the history data."
    ::= { f3L3Performance 17 }

f3L2A2NAclRuleHistoryEntry OBJECT-TYPE
    SYNTAX      F3L2A2NAclRuleHistoryEntry 
    MAX-ACCESS  not-accessible
    STATUS      current
    DESCRIPTION
            "A conceptual row in the f3L2A2NAclRuleHistoryTable.
             Entries exist in this table for each L3 acl rule."
    INDEX { neIndex, shelfIndex, slotIndex,
            f3L3FlowPointPortIndex, f3L2A2NAclRuleParentIndex, f3L2A2NAclRuleIndex,
            f3L2A2NAclRuleStatsIndex, f3L2A2NAclRuleHistoryIndex }
    ::= { f3L2A2NAclRuleHistoryTable 1 }

F3L2A2NAclRuleHistoryEntry ::= SEQUENCE {
    f3L2A2NAclRuleHistoryIndex               Integer32,
    f3L2A2NAclRuleHistoryTime                DateAndTime,
    f3L2A2NAclRuleHistoryValid               TruthValue,
    f3L2A2NAclRuleHistoryAction              CmPmBinAction,
    f3L2A2NAclRuleHistoryRuleMatch           PerfCounter64
}

f3L2A2NAclRuleHistoryIndex OBJECT-TYPE
    SYNTAX      Integer32 (1..4)
    MAX-ACCESS  read-only
    STATUS      current
    DESCRIPTION
            "An arbitrary integer index value used to uniquely identify
            this L3 flow point statistics entry. 
            1 - 15min
            2 - 1day
            3 - rollover
            4 - 5min"
    ::= { f3L2A2NAclRuleHistoryEntry 1 }

f3L2A2NAclRuleHistoryTime OBJECT-TYPE
    SYNTAX      DateAndTime
    MAX-ACCESS  read-only
    STATUS      current
    DESCRIPTION
            "Indicates the time of history bin creation." 
    ::= { f3L2A2NAclRuleHistoryEntry 2 }

f3L2A2NAclRuleHistoryValid OBJECT-TYPE
    SYNTAX      TruthValue
    MAX-ACCESS  read-only
    STATUS      current
    DESCRIPTION
            "Indicates the validity of the bin."
    ::= { f3L2A2NAclRuleHistoryEntry 3 }

f3L2A2NAclRuleHistoryAction OBJECT-TYPE
    SYNTAX      CmPmBinAction
    MAX-ACCESS  read-write
    STATUS      current
    DESCRIPTION
            "Allows the Manager to clear the bin."
    ::= { f3L2A2NAclRuleHistoryEntry 4 }

f3L2A2NAclRuleHistoryRuleMatch OBJECT-TYPE
     SYNTAX     PerfCounter64
     MAX-ACCESS read-only
     STATUS     current
     DESCRIPTION
         "The number of packets matching acl rule."
     ::= { f3L2A2NAclRuleHistoryEntry 5 }

--
-- L3 acl rule Threshold Table
--
f3L2A2NAclRuleThresholdTable OBJECT-TYPE
    SYNTAX      SEQUENCE OF F3L2A2NAclRuleThresholdEntry
    MAX-ACCESS  not-accessible
    STATUS      current
    DESCRIPTION
            "A table of entries that allow manageability of L3 acl rule Thresholds."
    ::= { f3L3Performance 18 }

f3L2A2NAclRuleThresholdEntry OBJECT-TYPE
    SYNTAX      F3L2A2NAclRuleThresholdEntry
    MAX-ACCESS  not-accessible
    STATUS      current
    DESCRIPTION
            "A conceptual row in the f3L2A2NAclRuleThresholdTable."
    INDEX { neIndex, shelfIndex, slotIndex,
            f3L3FlowPointPortIndex, f3L2A2NAclRuleParentIndex, f3L2A2NAclRuleIndex,
            f3L2A2NAclRuleStatsIndex, f3L2A2NAclRuleThresholdIndex }
    ::= { f3L2A2NAclRuleThresholdTable 1 }

F3L2A2NAclRuleThresholdEntry ::= SEQUENCE {
    f3L2A2NAclRuleThresholdIndex       Integer32,
    f3L2A2NAclRuleThresholdInterval    CmPmIntervalType,
    f3L2A2NAclRuleThresholdVariable    VariablePointer,
    f3L2A2NAclRuleThresholdValueLo     Unsigned32,
    f3L2A2NAclRuleThresholdValueHi     Unsigned32,
    f3L2A2NAclRuleThresholdMonValue    Counter64
}

f3L2A2NAclRuleThresholdIndex OBJECT-TYPE
    SYNTAX     Integer32 (1..65535)
    MAX-ACCESS read-only
    STATUS     current
    DESCRIPTION
        "An index that uniquely identifies an entry in the
        f3L2A2NAclRuleThresholdTable."
    ::= { f3L2A2NAclRuleThresholdEntry 1 }

f3L2A2NAclRuleThresholdInterval OBJECT-TYPE
    SYNTAX     CmPmIntervalType
    MAX-ACCESS read-only
    STATUS     current
    DESCRIPTION
        "The interval over which monitored value is
        sampled and compared with the specified threshold."
    ::= { f3L2A2NAclRuleThresholdEntry 2 }

f3L2A2NAclRuleThresholdVariable OBJECT-TYPE
    SYNTAX     VariablePointer
    MAX-ACCESS read-only
    STATUS     current
    DESCRIPTION
        "The object identifier of the particular variable to be
        sampled."
    ::= { f3L2A2NAclRuleThresholdEntry 3 }

f3L2A2NAclRuleThresholdValueLo OBJECT-TYPE
    SYNTAX     Unsigned32
    MAX-ACCESS read-write
    STATUS     current
    DESCRIPTION
        "Lower 32 bits of the threshold value."
    ::= { f3L2A2NAclRuleThresholdEntry 4 }

f3L2A2NAclRuleThresholdValueHi OBJECT-TYPE
    SYNTAX     Unsigned32
    MAX-ACCESS read-write
    STATUS     current
    DESCRIPTION
        "Higher 32 bits of the threshold value."
    ::= { f3L2A2NAclRuleThresholdEntry 5 }

f3L2A2NAclRuleThresholdMonValue OBJECT-TYPE
    SYNTAX     Counter64
    MAX-ACCESS read-only
    STATUS     current
    DESCRIPTION
        "Monitored value corresponding to f3L2A2NAclRuleThresholdVariable."
    ::= { f3L2A2NAclRuleThresholdEntry 6 }


--
-- L3 N2A acl rule Current Statistics Table
--
f3L2N2AAclRuleStatsTable OBJECT-TYPE
    SYNTAX      SEQUENCE OF F3L2N2AAclRuleStatsEntry
    MAX-ACCESS  not-accessible
    STATUS      current
    DESCRIPTION
            "A collection of L3 acl rule related statistics.  
             These reflect the current data."
    ::= { f3L3Performance 19 }

f3L2N2AAclRuleStatsEntry OBJECT-TYPE
    SYNTAX      F3L2N2AAclRuleStatsEntry 
    MAX-ACCESS  not-accessible
    STATUS      current
    DESCRIPTION
            "A conceptual row in the f3L2N2AAclRuleStatsTable.
             Entries exist in this table for each Acl rule."
    INDEX { neIndex, shelfIndex, slotIndex,
            f3L3FlowPointPortIndex, f3L2N2AAclRuleParentIndex, f3L2N2AAclRuleIndex, f3L2N2AAclRuleStatsIndex }
    ::= { f3L2N2AAclRuleStatsTable 1 }

F3L2N2AAclRuleStatsEntry ::= SEQUENCE {
    f3L2N2AAclRuleStatsIndex               Integer32,
    f3L2N2AAclRuleStatsIntervalType        CmPmIntervalType,
    f3L2N2AAclRuleStatsValid               TruthValue,
    f3L2N2AAclRuleStatsAction              CmPmBinAction,
    f3L2N2AAclRuleStatsRuleMatch           PerfCounter64
}

f3L2N2AAclRuleStatsIndex OBJECT-TYPE
    SYNTAX      Integer32 (1..4)
    MAX-ACCESS  read-only
    STATUS      current
    DESCRIPTION
            "An arbitrary integer index value used to uniquely identify
            this L3 flow point statistics entry. 
            1 - 15min
            2 - 1day
            3 - rollover
            4 - 5min"
    ::= { f3L2N2AAclRuleStatsEntry 1 }

f3L2N2AAclRuleStatsIntervalType OBJECT-TYPE
    SYNTAX      CmPmIntervalType
    MAX-ACCESS  read-only
    STATUS      current
    DESCRIPTION
            "Interval over which Performance Monitoring data is collected."
    ::= { f3L2N2AAclRuleStatsEntry 2 }

f3L2N2AAclRuleStatsValid OBJECT-TYPE
    SYNTAX      TruthValue
    MAX-ACCESS  read-only
    STATUS      current
    DESCRIPTION
            "Indicates the validity of the bin."
    ::= { f3L2N2AAclRuleStatsEntry 3 }

f3L2N2AAclRuleStatsAction OBJECT-TYPE
    SYNTAX      CmPmBinAction
    MAX-ACCESS  read-write
    STATUS      current
    DESCRIPTION
            "Allows the Manager to clear the bin."
    ::= { f3L2N2AAclRuleStatsEntry 4 }

f3L2N2AAclRuleStatsRuleMatch OBJECT-TYPE
     SYNTAX     PerfCounter64
     MAX-ACCESS read-only
     STATUS     current
     DESCRIPTION
         "The number of packets matching the ACL rule."
     ::= { f3L2N2AAclRuleStatsEntry 5 }

--
-- L3 acl rule history Statistics Table
--
f3L2N2AAclRuleHistoryTable OBJECT-TYPE
    SYNTAX      SEQUENCE OF F3L2N2AAclRuleHistoryEntry
    MAX-ACCESS  not-accessible
    STATUS      current
    DESCRIPTION
            "A collection of L3 acl rule related history statistics.  
             These reflect the history data."
    ::= { f3L3Performance 20 }

f3L2N2AAclRuleHistoryEntry OBJECT-TYPE
    SYNTAX      F3L2N2AAclRuleHistoryEntry 
    MAX-ACCESS  not-accessible
    STATUS      current
    DESCRIPTION
            "A conceptual row in the f3L2N2AAclRuleHistoryTable.
             Entries exist in this table for each L3 acl rule."
    INDEX { neIndex, shelfIndex, slotIndex,
            f3L3FlowPointPortIndex, f3L2N2AAclRuleParentIndex, f3L2N2AAclRuleIndex,
            f3L2N2AAclRuleStatsIndex, f3L2N2AAclRuleHistoryIndex }
    ::= { f3L2N2AAclRuleHistoryTable 1 }

F3L2N2AAclRuleHistoryEntry ::= SEQUENCE {
    f3L2N2AAclRuleHistoryIndex               Integer32,
    f3L2N2AAclRuleHistoryTime                DateAndTime,
    f3L2N2AAclRuleHistoryValid               TruthValue,
    f3L2N2AAclRuleHistoryAction              CmPmBinAction,
    f3L2N2AAclRuleHistoryRuleMatch           PerfCounter64
}

f3L2N2AAclRuleHistoryIndex OBJECT-TYPE
    SYNTAX      Integer32 (1..4)
    MAX-ACCESS  read-only
    STATUS      current
    DESCRIPTION
            "An arbitrary integer index value used to uniquely identify
            this L3 flow point statistics entry. 
            1 - 15min
            2 - 1day
            3 - rollover
            4 - 5min"
    ::= { f3L2N2AAclRuleHistoryEntry 1 }

f3L2N2AAclRuleHistoryTime OBJECT-TYPE
    SYNTAX      DateAndTime
    MAX-ACCESS  read-only
    STATUS      current
    DESCRIPTION
            "Indicates the time of history bin creation." 
    ::= { f3L2N2AAclRuleHistoryEntry 2 }

f3L2N2AAclRuleHistoryValid OBJECT-TYPE
    SYNTAX      TruthValue
    MAX-ACCESS  read-only
    STATUS      current
    DESCRIPTION
            "Indicates the validity of the bin."
    ::= { f3L2N2AAclRuleHistoryEntry 3 }

f3L2N2AAclRuleHistoryAction OBJECT-TYPE
    SYNTAX      CmPmBinAction
    MAX-ACCESS  read-write
    STATUS      current
    DESCRIPTION
            "Allows the Manager to clear the bin."
    ::= { f3L2N2AAclRuleHistoryEntry 4 }

f3L2N2AAclRuleHistoryRuleMatch OBJECT-TYPE
     SYNTAX     PerfCounter64
     MAX-ACCESS read-only
     STATUS     current
     DESCRIPTION
         "The number of packets matching acl rule."
     ::= { f3L2N2AAclRuleHistoryEntry 5 }

--
-- L3 acl rule Threshold Table
--
f3L2N2AAclRuleThresholdTable OBJECT-TYPE
    SYNTAX      SEQUENCE OF F3L2N2AAclRuleThresholdEntry
    MAX-ACCESS  not-accessible
    STATUS      current
    DESCRIPTION
            "A table of entries that allow manageability of L3 acl rule Thresholds."
    ::= { f3L3Performance 21 }

f3L2N2AAclRuleThresholdEntry OBJECT-TYPE
    SYNTAX      F3L2N2AAclRuleThresholdEntry
    MAX-ACCESS  not-accessible
    STATUS      current
    DESCRIPTION
            "A conceptual row in the f3L2N2AAclRuleThresholdTable."
    INDEX { neIndex, shelfIndex, slotIndex,
            f3L3FlowPointPortIndex, f3L2N2AAclRuleParentIndex, f3L2N2AAclRuleIndex,
            f3L2N2AAclRuleStatsIndex, f3L2N2AAclRuleThresholdIndex }
    ::= { f3L2N2AAclRuleThresholdTable 1 }

F3L2N2AAclRuleThresholdEntry ::= SEQUENCE {
    f3L2N2AAclRuleThresholdIndex       Integer32,
    f3L2N2AAclRuleThresholdInterval    CmPmIntervalType,
    f3L2N2AAclRuleThresholdVariable    VariablePointer,
    f3L2N2AAclRuleThresholdValueLo     Unsigned32,
    f3L2N2AAclRuleThresholdValueHi     Unsigned32,
    f3L2N2AAclRuleThresholdMonValue    Counter64
}

f3L2N2AAclRuleThresholdIndex OBJECT-TYPE
    SYNTAX     Integer32 (1..65535)
    MAX-ACCESS read-only
    STATUS     current
    DESCRIPTION
        "An index that uniquely identifies an entry in the
        f3L2N2AAclRuleThresholdTable."
    ::= { f3L2N2AAclRuleThresholdEntry 1 }

f3L2N2AAclRuleThresholdInterval OBJECT-TYPE
    SYNTAX     CmPmIntervalType
    MAX-ACCESS read-only
    STATUS     current
    DESCRIPTION
        "The interval over which monitored value is
        sampled and compared with the specified threshold."
    ::= { f3L2N2AAclRuleThresholdEntry 2 }

f3L2N2AAclRuleThresholdVariable OBJECT-TYPE
    SYNTAX     VariablePointer
    MAX-ACCESS read-only
    STATUS     current
    DESCRIPTION
        "The object identifier of the particular variable to be
        sampled."
    ::= { f3L2N2AAclRuleThresholdEntry 3 }

f3L2N2AAclRuleThresholdValueLo OBJECT-TYPE
    SYNTAX     Unsigned32
    MAX-ACCESS read-write
    STATUS     current
    DESCRIPTION
        "Lower 32 bits of the threshold value."
    ::= { f3L2N2AAclRuleThresholdEntry 4 }

f3L2N2AAclRuleThresholdValueHi OBJECT-TYPE
    SYNTAX     Unsigned32
    MAX-ACCESS read-write
    STATUS     current
    DESCRIPTION
        "Higher 32 bits of the threshold value."
    ::= { f3L2N2AAclRuleThresholdEntry 5 }

f3L2N2AAclRuleThresholdMonValue OBJECT-TYPE
    SYNTAX     Counter64
    MAX-ACCESS read-only
    STATUS     current
    DESCRIPTION
        "Monitored value corresponding to f3L2N2AAclRuleThresholdVariable."
    ::= { f3L2N2AAclRuleThresholdEntry 6 }

---
---Notifications
---
f3L3FlowPointThresholdCrossingAlert NOTIFICATION-TYPE
    OBJECTS {
                f3L3FlowPointThresholdIndex,       
                f3L3FlowPointThresholdInterval,
                f3L3FlowPointThresholdVariable,
                f3L3FlowPointThresholdValueLo,
                f3L3FlowPointThresholdValueHi,
                f3L3FlowPointThresholdMonValue
            }
    STATUS  current
    DESCRIPTION
            "This trap is sent each time a threshold on a PM condition
             on an L3 flow point is crossed."
  ::= { f3L3Notifications 1 }

f3L3QosPolicerThresholdCrossingAlert NOTIFICATION-TYPE
    OBJECTS {
                f3L3QosPolicerThresholdIndex,       
                f3L3QosPolicerThresholdInterval,
                f3L3QosPolicerThresholdVariable,
                f3L3QosPolicerThresholdValueLo,
                f3L3QosPolicerThresholdValueHi,
                f3L3QosPolicerThresholdMonValue
            }
    STATUS  current
    DESCRIPTION
            "This trap is sent each time a threshold on a PM condition
             on an L3 Qos Policer is crossed."
  ::= { f3L3Notifications 2 }

f3L3QosShaperThresholdCrossingAlert NOTIFICATION-TYPE
    OBJECTS {
                f3L3QosShaperThresholdIndex,       
                f3L3QosShaperThresholdInterval,
                f3L3QosShaperThresholdVariable,
                f3L3QosShaperThresholdValueLo,
                f3L3QosShaperThresholdValueHi,
                f3L3QosShaperThresholdMonValue
            }
    STATUS  current
    DESCRIPTION
            "This trap is sent each time a threshold on a PM condition
             on an L3 Qos Shaper is crossed."
  ::= { f3L3Notifications 3 }

f3L3TrafficIpInterfaceThresholdCrossingAlert NOTIFICATION-TYPE
    OBJECTS {
                f3L3TrafficIpInterfaceThresholdIndex,       
                f3L3TrafficIpInterfaceThresholdInterval,
                f3L3TrafficIpInterfaceThresholdVariable,
                f3L3TrafficIpInterfaceThresholdValueLo,
                f3L3TrafficIpInterfaceThresholdValueHi,
                f3L3TrafficIpInterfaceThresholdMonValue
            }
    STATUS  current
    DESCRIPTION
            "This trap is sent each time a threshold on a PM condition
             on an L3 traffic ip interface is crossed."
  ::= { f3L3Notifications 4 }

f3L3AclRuleThresholdCrossingAlert NOTIFICATION-TYPE
    OBJECTS {
                f3L3AclRuleThresholdIndex,       
                f3L3AclRuleThresholdInterval,
                f3L3AclRuleThresholdVariable,
                f3L3AclRuleThresholdValueLo,
                f3L3AclRuleThresholdValueHi,
                f3L3AclRuleThresholdMonValue
            }
    STATUS  current
    DESCRIPTION
            "This trap is sent each time a threshold on a PM condition
             on an L3 acl rule is crossed."
  ::= { f3L3Notifications 5 }

f3L2A2NAclRuleThresholdCrossingAlert NOTIFICATION-TYPE
    OBJECTS {
                f3L2A2NAclRuleThresholdIndex,       
                f3L2A2NAclRuleThresholdInterval,
                f3L2A2NAclRuleThresholdVariable,
                f3L2A2NAclRuleThresholdValueLo,
                f3L2A2NAclRuleThresholdValueHi,
                f3L2A2NAclRuleThresholdMonValue
            }
    STATUS  current
    DESCRIPTION
            "This trap is sent each time a threshold on a PM condition
             on an L2 A2N acl rule is crossed."
  ::= { f3L3Notifications 6 }

f3L2N2AAclRuleThresholdCrossingAlert NOTIFICATION-TYPE
    OBJECTS {
                f3L2N2AAclRuleThresholdIndex,       
                f3L2N2AAclRuleThresholdInterval,
                f3L2N2AAclRuleThresholdVariable,
                f3L2N2AAclRuleThresholdValueLo,
                f3L2N2AAclRuleThresholdValueHi,
                f3L2N2AAclRuleThresholdMonValue
            }
    STATUS  current
    DESCRIPTION
            "This trap is sent each time a threshold on a PM condition
             on an L2 N2A acl rule is crossed."
  ::= { f3L3Notifications 7 }


--
-- Conformance
--
f3L3Compliances OBJECT IDENTIFIER ::= {f3L3Conformance 1}
f3L3Groups      OBJECT IDENTIFIER ::= {f3L3Conformance 2}

f3L3Compliance MODULE-COMPLIANCE
    STATUS  current
    DESCRIPTION
            "Describes the requirements for conformance to the L3."
    MODULE  -- this module
        MANDATORY-GROUPS {
              f3L3ObjectsGroup, f3L3PerfGroup
        }
    ::= { f3L3Compliances 1 }

f3L3ObjectsGroup OBJECT-GROUP
    OBJECTS {
        f3DhcpRelayAgentIndex,f3DhcpRelayAgentAlias,f3DhcpRelayAgentAdminState,
        f3DhcpRelayAgentSecondaryState,f3DhcpRelayAgentOperationalState,
        f3DhcpRelayAgentIpVersion,f3DhcpRelayAgentServerIpAddress,
        f3DhcpRelayAgentOp82SubOp9ControlEnabled,f3DhcpRelayAgentOp82SubOp9Value,
        f3DhcpRelayAgentStorageType, f3DhcpRelayAgentRowStatus,

        f3VrfIndex,f3VrfAlias, f3VrfAdminState,f3VrfSecondaryState,f3VrfTraceRouteIpv4Destination,
        f3VrfOperationalState,f3VrfAccIsolationControlEnabled,f3VrfPingResult,f3VrfPingIpv4Destination,
        f3VrfTraceRouteResult,f3VrfAction,f3VrfStorageType,f3VrfRowStatus, f3VrfDhcpRoutesControl,

        f3L3FlowPointPortTypeIndex,f3L3FlowPointPortIndex,
        f3L3FlowPointIndex,f3L3FlowPointAlias,f3L3FlowPointAdminState,f3L3FlowPointSecondaryState,
        f3L3FlowPointOperationalState,f3L3FlowPointMultiCOSEnabled,f3L3FlowPointCOS,f3L3FlowPointUntaggedMemberShipEnabled,
        f3L3FlowPointOuterTagMemberShipEnabled,f3L3FlowPointOuterTagMemberShipVlanId,
        f3L3FlowPointInnerTagMemberShipEnabled,f3L3FlowPointInnerTagMemberShipVlanId,
        f3L3FlowPointFragmentedPktsFwdEnabled,
        f3L3FlowPointHCosMgmtEnabled,f3L3FlowPointHCosGuaranteedBwHi,f3L3FlowPointHCosGuaranteedBwLo,
        f3L3FlowPointHCosMaximumBwHi,f3L3FlowPointHCosMaximumBwLo,f3L3FlowPointPolicingEnabled,
        f3L3FlowPointStorageType,f3L3FlowPointRowStatus,

        f3L3AclRuleParentIndex,f3L3AclRuleIndex,f3L3AclRuleAlias,f3L3AclRuleSrcIpv4AddressControl,
        f3L3AclRuleDynamicSrcIpControl,f3L3AclRuleSrcIpv4AddressLowLimit,f3L3AclRuleDstIpv4AddressControl,
        f3L3AclRuleDstIpv4AddressLowLimit,f3L3AclRuleIpv4PriorityControl,f3L3AclRuleIpv4PriorityLowLimit,
        f3L3AclRuleProtocolControl,f3L3AclRuleProtocolNumber,f3L3AclRuleSrcPortControl,
        f3L3AclRuleSrcPortLowLimit,f3L3AclRuleSrcPortHighLimit,f3L3AclRuleDstPortControl,
        f3L3AclRuleDstPortLowLimit,f3L3AclRuleDstPortHighLimit,f3L3AclRulePriority,f3L3AclRuleCOS,
        f3L3AclRuleOperation,f3L3AclRuleSummary,f3L3AclRuleCosOverrideControl,
        f3L3AclRuleSrcMacAddressControl,f3L3AclRuleDynamicSrcMacAddressControl,
        f3L3AclRuleSrcMacAddress,f3L3AclRuleSrcMacAddressMask,f3L3AclRuleDstMacAddressControl,
        f3L3AclRuleDstMacAddress,f3L3AclRuleDstMacAddressMask,f3L3AclRuleOuterVlanVIDControl,
        f3L3AclRuleOuterVlanVIDLowLimit,f3L3AclRuleOuterVlanVIDHighLimit,
        f3L3AclRuleInnerVlanVIDControl,f3L3AclRuleInnerVlanVIDLowLimit,f3L3AclRuleInnerVlanVIDHighLimit,
        f3L3AclRuleOuterVlanPcpControl,f3L3AclRuleOuterVlanPcpLowLimit,f3L3AclRuleOuterVlanPcpHighLimit,
        f3L3AclRuleInnerVlanPcpControl,f3L3AclRuleInnerVlanPcpLowLimit,f3L3AclRuleInnerVlanPcpHighLimit,
        f3L3AclRuleOuterVlanDeiControl,f3L3AclRuleOuterVlanDei,f3L3AclRuleEtherTypeControl,
        f3L3AclRuleEtherType,f3L3AclRuleTcpFlagsControl,f3L3AclRuleTcpFlags,
        f3L3AclRuleSrcIpv4AddressHighLimit,f3L3AclRuleDstIpv4AddressHighLimit,f3L3AclRuleIpv4PriorityHighLimit,
        f3L3AclRuleStorageType,f3L3AclRuleRowStatus,f3L3AclRuleAdminState,

        f3L2A2NAclRuleParentIndex,f3L2A2NAclRuleIndex,f3L2A2NAclRuleAlias,f3L2A2NAclRuleSrcIpv4AddressControl,
        f3L2A2NAclRuleDynamicSrcIpControl,f3L2A2NAclRuleSrcIpv4AddressLowLimit,f3L2A2NAclRuleDstIpv4AddressControl,
        f3L2A2NAclRuleDstIpv4AddressLowLimit,f3L2A2NAclRuleIpv4PriorityControl,f3L2A2NAclRuleIpv4PriorityLowLimit,
        f3L2A2NAclRuleProtocolControl,f3L2A2NAclRuleProtocolNumber,f3L2A2NAclRuleSrcPortControl,f3L2A2NAclRuleSrcPortLowLimit,
        f3L2A2NAclRuleSrcPortHighLimit,f3L2A2NAclRuleDstPortControl,f3L2A2NAclRuleDstPortLowLimit,f3L2A2NAclRuleDstPortHighLimit,
        f3L2A2NAclRulePriority,f3L2A2NAclRuleCOS,f3L2A2NAclRuleOperation,f3L2A2NAclRuleSummary,f3L2A2NAclRuleCosOverrideControl,
        f3L2A2NAclRuleSrcMacAddressControl,f3L2A2NAclRuleDynamicSrcMacAddressControl,f3L2A2NAclRuleSrcMacAddress,
        f3L2A2NAclRuleSrcMacAddressMask,f3L2A2NAclRuleDstMacAddressControl,f3L2A2NAclRuleDstMacAddress,f3L2A2NAclRuleDstMacAddressMask,
        f3L2A2NAclRuleOuterVlanVIDControl,f3L2A2NAclRuleOuterVlanVIDLowLimit,f3L2A2NAclRuleOuterVlanVIDHighLimit,f3L2A2NAclRuleInnerVlanVIDControl,
        f3L2A2NAclRuleInnerVlanVIDLowLimit,f3L2A2NAclRuleInnerVlanVIDHighLimit,f3L2A2NAclRuleOuterVlanPcpControl,f3L2A2NAclRuleOuterVlanPcpLowLimit,
        f3L2A2NAclRuleOuterVlanPcpHighLimit,f3L2A2NAclRuleInnerVlanPcpControl,f3L2A2NAclRuleInnerVlanPcpLowLimit,f3L2A2NAclRuleInnerVlanPcpHighLimit,
        f3L2A2NAclRuleOuterVlanDeiControl,f3L2A2NAclRuleOuterVlanDei,f3L2A2NAclRuleEtherTypeControl,f3L2A2NAclRuleEtherType,
        f3L2A2NAclRuleTcpFlagsControl,f3L2A2NAclRuleTcpFlags,f3L2A2NAclRuleSrcIpv4AddressHighLimit,f3L2A2NAclRuleDstIpv4AddressHighLimit,
        f3L2A2NAclRuleIpv4PriorityHighLimit,f3L2A2NAclRuleStorageType,f3L2A2NAclRuleRowStatus,f3L2A2NAclRuleAdminState,

        f3L2N2AAclRuleParentIndex,f3L2N2AAclRuleIndex,f3L2N2AAclRuleAlias,f3L2N2AAclRuleSrcIpv4AddressControl,
        f3L2N2AAclRuleDynamicSrcIpControl,f3L2N2AAclRuleSrcIpv4AddressLowLimit,f3L2N2AAclRuleDstIpv4AddressControl,
        f3L2N2AAclRuleDstIpv4AddressLowLimit,f3L2N2AAclRuleIpv4PriorityControl,f3L2N2AAclRuleIpv4PriorityLowLimit,
        f3L2N2AAclRuleProtocolControl,f3L2N2AAclRuleProtocolNumber,f3L2N2AAclRuleSrcPortControl,f3L2N2AAclRuleSrcPortLowLimit,
        f3L2N2AAclRuleSrcPortHighLimit,f3L2N2AAclRuleDstPortControl,f3L2N2AAclRuleDstPortLowLimit,f3L2N2AAclRuleDstPortHighLimit,
        f3L2N2AAclRulePriority,f3L2N2AAclRuleCOS,f3L2N2AAclRuleOperation,f3L2N2AAclRuleSummary,f3L2N2AAclRuleCosOverrideControl,
        f3L2N2AAclRuleSrcMacAddressControl,f3L2N2AAclRuleDynamicSrcMacAddressControl,f3L2N2AAclRuleSrcMacAddress,
        f3L2N2AAclRuleSrcMacAddressMask,f3L2N2AAclRuleDstMacAddressControl,f3L2N2AAclRuleDstMacAddress,f3L2N2AAclRuleDstMacAddressMask,
        f3L2N2AAclRuleOuterVlanVIDControl,f3L2N2AAclRuleOuterVlanVIDLowLimit,f3L2N2AAclRuleOuterVlanVIDHighLimit,f3L2N2AAclRuleInnerVlanVIDControl,
        f3L2N2AAclRuleInnerVlanVIDLowLimit,f3L2N2AAclRuleInnerVlanVIDHighLimit,f3L2N2AAclRuleOuterVlanPcpControl,f3L2N2AAclRuleOuterVlanPcpLowLimit,
        f3L2N2AAclRuleOuterVlanPcpHighLimit,f3L2N2AAclRuleInnerVlanPcpControl,f3L2N2AAclRuleInnerVlanPcpLowLimit,f3L2N2AAclRuleInnerVlanPcpHighLimit,
        f3L2N2AAclRuleOuterVlanDeiControl,f3L2N2AAclRuleOuterVlanDei,f3L2N2AAclRuleEtherTypeControl,f3L2N2AAclRuleEtherType,
        f3L2N2AAclRuleTcpFlagsControl,f3L2N2AAclRuleTcpFlags,f3L2N2AAclRuleSrcIpv4AddressHighLimit,f3L2N2AAclRuleDstIpv4AddressHighLimit,
        f3L2N2AAclRuleIpv4PriorityHighLimit,f3L2N2AAclRuleStorageType,f3L2N2AAclRuleRowStatus,f3L2N2AAclRuleAdminState,

        f3L3QosPolicerIndex,f3L3QosPolicerAdminState,f3L3QosPolicerOperationalState,
        f3L3QosPolicerSecondaryState,f3L3QosPolicerCIRLo,f3L3QosPolicerCIRHi,f3L3QosPolicerEIRLo,
        f3L3QosPolicerEIRHi,f3L3QosPolicerCBS,f3L3QosPolicerEBS,f3L3QosPolicerAlgorithm,
        f3L3QosPolicerColorMode,f3L3QosPolicerCouplingFlag,
        f3L3QosPolicerStorageType,f3L3QosPolicerRowStatus,

        f3L3QosShaperIndex,f3L3QosShaperAdminState,f3L3QosShaperOperationalState,
        f3L3QosShaperSecondaryState,f3L3QosShaperCIRLo,f3L3QosShaperCIRHi,f3L3QosShaperEIRLo,
        f3L3QosShaperEIRHi,f3L3QosShaperBufferSize,f3L3QosShaperCOS,
        f3L3QosShaperWredGreenMinQueueThreshold,f3L3QosShaperWredGreenMaxQueueThreshold,
        f3L3QosShaperWredGreenDropProbability,f3L3QosShaperWredYellowMinQueueThreshold,f3L3QosShaperWredYellowMaxQueueThreshold,
        f3L3QosShaperWredYellowDropProbability,f3L3QosShaperStorageType,f3L3QosShaperRowStatus,

        f3L3TrafficIPIfIndex,f3L3TrafficIPIfName,f3L3TrafficIPIfAdminState,f3L3TrafficIPIfSecondaryState,
        f3L3TrafficIPIfOperationalState,f3L3TrafficIPIfProxyArpEnabled,f3L3TrafficIPIfIpAddressSourceType,
        f3L3TrafficIPIfMgmtUseEnable,f3L3TrafficIPIfIpAddress,f3L3TrafficIPIfMask,
        f3L3TrafficIPIfDhcpRelayInterfaceSide,f3L3TrafficIPIfDhcpRelayVendorClassiDOpt60,
        f3L3TrafficIPIfDhcpRelayVendorClassiDOpt60Control,f3L3TrafficIPIfDhcpRelayUserClassOpt77,
        f3L3TrafficIPIfDhcpRelayUserClassOpt77Control,f3L3TrafficIPIfDhcpRelayInfoOpt82Sub1,
        f3L3TrafficIPIfDhcpRelayInfoOpt82Sub1Enabled,f3L3TrafficIPIfDhcpRelayInfoOpt82Sub2,
        f3L3TrafficIPIfDhcpRelayInfoOpt82Sub2Enabled,f3L3TrafficIPIfDhcpEnabled,f3L3TrafficIPIfDhcpRole,
        f3L3TrafficIPIfDhcpClientIdEnabled,f3L3TrafficIPIfDhcpClientId,f3L3TrafficIPIfDhcpClassIdEnabled,
        f3L3TrafficIPIfDhcpHostNameEnabled,f3L3TrafficIPIfDhcpHostName,
        f3L3TrafficIPIfDhcpClientIdType,f3L3TrafficIPIfDhcpHostNameType,
        f3L3TrafficIPIfStorageType,f3L3TrafficIPIfRowStatus,f3L3TrafficIPIfAction,
        
        f3DhcpRelayAgentTrafficIpIfMemberObject,f3DhcpRelayAgentTrafficIpIfMemberStorageType,
        f3DhcpRelayAgentTrafficIpIfMemberRowStatus,
        
        f3VrfTrafficIpIfMemberObject,f3VrfTrafficIpIfMemberStorageType,f3VrfTrafficIpIfMemberRowStatus,

        f3L3TrafficIpv4RouteDest,
        f3L3TrafficIpv4RouteMask,f3L3TrafficIpv4RouteNextHop,f3L3TrafficIpv4RouteMetric,
        f3L3TrafficIpv4RouteInterface,f3L3TrafficIpv4RouteAdvertise,f3L3TrafficIpv4RouteStatus,
        f3L3TrafficIpv4RouteSourceForwardingEnable,f3L3TrafficIpv4RouteFlags,
        f3L3TrafficIpv4RouteStorageType,f3L3TrafficIpv4RouteRowStatus,f3L3TrafficIpv4RouteType,
        
        f3L3TrafficArpIPAddress, f3L3TrafficArpMacAddress, f3L3TrafficArpInterface,
        f3L3TrafficArpEntryType, f3L3TrafficArpStorageType,f3L3TrafficArpRowStatus
    }
    STATUS  current
    DESCRIPTION
            "A collection of objects used to manage the L3 functionality."
    ::= { f3L3Groups 1 }

f3L3PerfGroup OBJECT-GROUP
    OBJECTS {
        f3L3FlowPointStatsIndex,f3L3FlowPointStatsIntervalType,f3L3FlowPointStatsValid,
        f3L3FlowPointStatsAction,f3L3FlowPointStatsFMG,f3L3FlowPointStatsFMY,f3L3FlowPointStatsFMRD,
        f3L3FlowPointStatsFTD,f3L3FlowPointStatsFragmentedDropAcl,f3L3FlowPointStatsAclRuleDrop,
        f3L3FlowPointStatsTtlEqual1Drop,f3L3FlowPointStatsFrameTx,f3L3FlowPointStatsFrameRx,f3L3FlowPointStatsNoRouteDrop,

        f3L3FlowPointHistoryIndex,f3L3FlowPointHistoryTime,f3L3FlowPointHistoryValid,
        f3L3FlowPointHistoryAction,f3L3FlowPointHistoryFMG,f3L3FlowPointHistoryFMY,
        f3L3FlowPointHistoryFMRD,f3L3FlowPointHistoryFTD,f3L3FlowPointHistoryFragmentedDropAcl,
        f3L3FlowPointHistoryAclRuleDrop,f3L3FlowPointHistoryTtlEqual1Drop,f3L3FlowPointHistoryFrameTx,
        f3L3FlowPointHistoryFrameRx,f3L3FlowPointHistoryNoRouteDrop,

        f3L3FlowPointThresholdIndex,f3L3FlowPointThresholdInterval,f3L3FlowPointThresholdVariable,
        f3L3FlowPointThresholdValueLo,f3L3FlowPointThresholdValueHi,f3L3FlowPointThresholdMonValue,

        f3L3TrafficIpInterfaceStatsIndex,f3L3TrafficIpInterfaceStatsIntervalType,
        f3L3TrafficIpInterfaceStatsValid,f3L3TrafficIpInterfaceStatsAction,f3L3TrafficIpInterfaceStatsDhcpTx,
        f3L3TrafficIpInterfaceStatsDhcpRx,f3L3TrafficIpInterfaceStatsIcmpTx,
        f3L3TrafficIpInterfaceStatsIcmpRx,f3L3TrafficIpInterfaceStatsArpReqTx,f3L3TrafficIpInterfaceStatsArpReqRx,
        f3L3TrafficIpInterfaceStatsArpReplyTx,f3L3TrafficIpInterfaceStatsArpReplyRx,

        f3L3TrafficIpInterfaceHistoryIndex,f3L3TrafficIpInterfaceHistoryTime,f3L3TrafficIpInterfaceHistoryValid,
        f3L3TrafficIpInterfaceHistoryAction,f3L3TrafficIpInterfaceHistoryDhcpTx,f3L3TrafficIpInterfaceHistoryDhcpRx,
        f3L3TrafficIpInterfaceHistoryIcmpTx,f3L3TrafficIpInterfaceHistoryIcmpRx,
        f3L3TrafficIpInterfaceHistoryArpReqTx,f3L3TrafficIpInterfaceHistoryArpReqRx,f3L3TrafficIpInterfaceHistoryArpReplyTx,
        f3L3TrafficIpInterfaceHistoryArpReplyRx,

        f3L3TrafficIpInterfaceThresholdIndex,f3L3TrafficIpInterfaceThresholdInterval,f3L3TrafficIpInterfaceThresholdVariable,
        f3L3TrafficIpInterfaceThresholdValueLo,f3L3TrafficIpInterfaceThresholdValueHi,f3L3TrafficIpInterfaceThresholdMonValue,

        f3L3AclRuleStatsIndex,f3L3AclRuleStatsIntervalType,f3L3AclRuleStatsValid,f3L3AclRuleStatsAction,
        f3L3AclRuleStatsRuleMatch,

        f3L3AclRuleHistoryIndex,f3L3AclRuleHistoryTime,f3L3AclRuleHistoryValid,f3L3AclRuleHistoryAction,
        f3L3AclRuleHistoryRuleMatch,

        f3L3AclRuleThresholdIndex,f3L3AclRuleThresholdInterval,f3L3AclRuleThresholdVariable,
        f3L3AclRuleThresholdValueLo,f3L3AclRuleThresholdValueHi,f3L3AclRuleThresholdMonValue,
        
        f3L2A2NAclRuleStatsIndex,f3L2A2NAclRuleStatsIntervalType,f3L2A2NAclRuleStatsValid,f3L2A2NAclRuleStatsAction,
        f3L2A2NAclRuleStatsRuleMatch,

        f3L2A2NAclRuleHistoryIndex,f3L2A2NAclRuleHistoryTime,f3L2A2NAclRuleHistoryValid,f3L2A2NAclRuleHistoryAction,
        f3L2A2NAclRuleHistoryRuleMatch,

        f3L2A2NAclRuleThresholdIndex,f3L2A2NAclRuleThresholdInterval,f3L2A2NAclRuleThresholdVariable,
        f3L2A2NAclRuleThresholdValueLo,f3L2A2NAclRuleThresholdValueHi,f3L2A2NAclRuleThresholdMonValue,

        f3L2N2AAclRuleStatsIndex,f3L2N2AAclRuleStatsIntervalType,f3L2N2AAclRuleStatsValid,f3L2N2AAclRuleStatsAction,
        f3L2N2AAclRuleStatsRuleMatch,

        f3L2N2AAclRuleHistoryIndex,f3L2N2AAclRuleHistoryTime,f3L2N2AAclRuleHistoryValid,f3L2N2AAclRuleHistoryAction,
        f3L2N2AAclRuleHistoryRuleMatch,

        f3L2N2AAclRuleThresholdIndex,f3L2N2AAclRuleThresholdInterval,f3L2N2AAclRuleThresholdVariable,
        f3L2N2AAclRuleThresholdValueLo,f3L2N2AAclRuleThresholdValueHi,f3L2N2AAclRuleThresholdMonValue,

        f3L3QosPolicerStatsIndex,f3L3QosPolicerStatsIntervalType,f3L3QosPolicerStatsValid,
        f3L3QosPolicerStatsAction,f3L3QosPolicerStatsFMG,f3L3QosPolicerStatsFMY,
        f3L3QosPolicerStatsFMYD,f3L3QosPolicerStatsFMRD,f3L3QosPolicerStatsBytesIn,
        f3L3QosPolicerStatsBytesOut,f3L3QosPolicerStatsABR,

        f3L3QosPolicerHistoryIndex,f3L3QosPolicerHistoryTime,f3L3QosPolicerHistoryValid,
        f3L3QosPolicerHistoryAction,f3L3QosPolicerHistoryFMG,f3L3QosPolicerHistoryFMY,
        f3L3QosPolicerHistoryFMYD,f3L3QosPolicerHistoryFMRD,f3L3QosPolicerHistoryBytesIn,
        f3L3QosPolicerHistoryBytesOut,f3L3QosPolicerHistoryABR,

        f3L3QosPolicerThresholdIndex,
        f3L3QosPolicerThresholdInterval,f3L3QosPolicerThresholdVariable,f3L3QosPolicerThresholdValueLo,
        f3L3QosPolicerThresholdValueHi,f3L3QosPolicerThresholdMonValue,

        f3L3QosShaperStatsIndex,f3L3QosShaperStatsIntervalType,f3L3QosShaperStatsValid,
        f3L3QosShaperStatsAction,f3L3QosShaperStatsBT,f3L3QosShaperStatsBTD,f3L3QosShaperStatsFD,
        f3L3QosShaperStatsFTD,f3L3QosShaperStatsBR,f3L3QosShaperStatsFR,
        f3L3QosShaperStatsABRRL,f3L3QosShaperStatsBREDD,f3L3QosShaperStatsFREDD,

        f3L3QosShaperHistoryIndex,f3L3QosShaperHistoryTime,f3L3QosShaperHistoryValid,
        f3L3QosShaperHistoryAction,f3L3QosShaperHistoryBT,f3L3QosShaperHistoryBTD,
        f3L3QosShaperHistoryFD,f3L3QosShaperHistoryFTD,f3L3QosShaperHistoryBR,
        f3L3QosShaperHistoryFR,f3L3QosShaperHistoryABRRL,f3L3QosShaperHistoryBREDD,
        f3L3QosShaperHistoryFREDD,

        f3L3QosShaperThresholdIndex,f3L3QosShaperThresholdInterval,f3L3QosShaperThresholdVariable,
        f3L3QosShaperThresholdValueLo,f3L3QosShaperThresholdValueHi,f3L3QosShaperThresholdMonValue
    }
    STATUS  current
    DESCRIPTION
            "A collection of objects performance used to manage the L3 functionality."
    ::= { f3L3Groups 2 }

END
