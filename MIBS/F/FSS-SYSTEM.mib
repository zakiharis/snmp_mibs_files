--=============================================================================
-- Copyright (c) 2016 Fujitsu Network Communications, Inc. All Rights Reserved.
--=============================================================================

FSS-SYSTEM DEFINITIONS ::= BEGIN
IMPORTS
    MODULE-IDENTITY, OBJECT-TYPE,
    Integer32, Unsigned32, Counter32, Counter64,
    Gauge32, IpAddress
        FROM SNMPv2-SMI
    TEXTUAL-CONVENTION, RowStatus, TruthValue
        FROM SNMPv2-TC
    fssCommon
        FROM FSS-COMMON-SMI
;

fssSystem MODULE-IDENTITY
    LAST-UPDATED "201606200000Z"
    ORGANIZATION
        "Fujitsu Network Communications, Inc."
    CONTACT-INFO
        "Fujitsu Technical Assistance Center (FTAC),
         1-800-USE-FTAC (1-800-873-3822)"
    DESCRIPTION "This module contains definitions for System Management."

    REVISION "201606200000Z"
    DESCRIPTION "Initial Revision"
    ::= { fssCommon 100 }

String ::= TEXTUAL-CONVENTION
    DISPLAY-HINT "1t"
    STATUS      current
    DESCRIPTION "xs:string"
    SYNTAX      OCTET STRING

ADT-value ::= TEXTUAL-CONVENTION
    STATUS      current
    DESCRIPTION "Deactivation time for alarms in seconds"
    SYNTAX      INTEGER {adt-zero(0),adt-ten(1)}

RestartLevel ::= TEXTUAL-CONVENTION
    STATUS      current
    DESCRIPTION "initialization level for restart"
    SYNTAX      INTEGER {cold(0),warm(1)}

AAT-value ::= TEXTUAL-CONVENTION
    STATUS      current
    DESCRIPTION "Activation time for alarms in seconds"
    SYNTAX      INTEGER {aat-zero(0),aat-twoPointFive(1)}

system OBJECT IDENTIFIER ::= { fssSystem 1 }

systemVendor OBJECT-TYPE
    SYNTAX      String
    MAX-ACCESS  read-write
    STATUS      current
    DESCRIPTION "Vendor Name - 'Fujitsu Limited' "
    ::= { system 1 }

systemName OBJECT-TYPE
    SYNTAX      String (SIZE (7 .. 20))
    MAX-ACCESS  read-write
    STATUS      current
    DESCRIPTION "Admin assigned name to this system"
    ::= { system 2 }

systemLocation OBJECT-TYPE
    SYNTAX      String
    MAX-ACCESS  read-write
    STATUS      current
    DESCRIPTION "location information"
    ::= { system 3 }

systemContact OBJECT-TYPE
    SYNTAX      String
    MAX-ACCESS  read-write
    STATUS      current
    DESCRIPTION "Contact information for this system"
    ::= { system 4 }

systemNeType OBJECT-TYPE
    SYNTAX      String
    MAX-ACCESS  read-only
    STATUS      current
    DESCRIPTION "Network Element type"
    ::= { system 5 }

systemSoftwareVersion OBJECT-TYPE
    SYNTAX      String
    MAX-ACCESS  read-only
    STATUS      current
    DESCRIPTION "Software version of the system"
    ::= { system 6 }

systemUpTime OBJECT-TYPE
    SYNTAX      Unsigned32
    MAX-ACCESS  read-only
    STATUS      current
    DESCRIPTION "Number of TimeTicks ( in one hudredth of second) since last time System was initilized"
    ::= { system 7 }

systemAutoP OBJECT-TYPE
    SYNTAX      TruthValue
    MAX-ACCESS  read-write
    STATUS      current
    DESCRIPTION "Global flag to turn ON/OFF auto provisioning on the system"
    ::= { system 8 }

systemAAT OBJECT-TYPE
    SYNTAX      AAT-value
    MAX-ACCESS  read-write
    STATUS      current
    DESCRIPTION "Alarm Activation Time"
    ::= { system 9 }

systemADT OBJECT-TYPE
    SYNTAX      ADT-value
    MAX-ACCESS  read-write
    STATUS      current
    DESCRIPTION "Alarm De-activation Time"
    ::= { system 10 }

-- Configuration of the system date and time properties.
systemClock OBJECT IDENTIFIER ::= { system 11 }

systemClockTimezone-name OBJECT-TYPE
    SYNTAX      String
    MAX-ACCESS  read-write
    STATUS      current
    DESCRIPTION "The TZ database name to use for the system, such
as 'Europe/Stockholm'."
    ::= { systemClock 1 }

systemNtp OBJECT-TYPE
    SYNTAX      TruthValue
    MAX-ACCESS  read-write
    STATUS      current
    DESCRIPTION "Configuration of the NTP client."
    ::= { system 12 }

systemNtpEnabled OBJECT-TYPE
    SYNTAX      TruthValue
    MAX-ACCESS  read-write
    STATUS      current
    DESCRIPTION "Indicates that the system should attempt to
synchronize the system clock with an NTP server
from the 'ntp/server' list."
    ::= { system 13 }

systemNtp-cfg OBJECT-TYPE
    SYNTAX      TruthValue
    MAX-ACCESS  read-write
    STATUS      current
    DESCRIPTION "Configuration parameters for NTP."
    ::= { system 14 }

systemNtp-cfgNtp-enabled OBJECT-TYPE
    SYNTAX      TruthValue
    MAX-ACCESS  read-write
    STATUS      current
    DESCRIPTION "Controls whether NTP is enabled or disabled
on this device."
    ::= { system 15 }

-- System group operational state.
system-state OBJECT IDENTIFIER ::= { fssSystem 2 }

-- Monitoring of the system date and time properties.
system-stateClock OBJECT IDENTIFIER ::= { system-state 1 }

system-stateClockDatetime OBJECT-TYPE
    SYNTAX      String
    MAX-ACCESS  read-only
    STATUS      current
    DESCRIPTION "The current system date and time."
    ::= { system-stateClock 1 }

END
