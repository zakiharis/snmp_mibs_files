-- File Name : AVENTAIL-NG-SERVER-MIBS

AVENTAIL-NG-SERVER-MIBS	DEFINITIONS ::= BEGIN
	IMPORTS
		aventail
			FROM AVENTAIL-MIB
		InternationalDisplayString 
			FROM HOST-RESOURCES-MIB
		OBJECT-TYPE, Integer32,NOTIFICATION-TYPE, MODULE-IDENTITY
			FROM SNMPv2-SMI;


aventailNGServer MODULE-IDENTITY
             LAST-UPDATED      "200409071432Z" 
             ORGANIZATION      "Aventail"
             CONTACT-INFO       "email:   support@aventail.com"
             DESCRIPTION      "This Aventail MIB provides NG Server Statistics"
        	::= {aventail 5}

ngServerState       OBJECT-TYPE
		SYNTAX			 InternationalDisplayString
		MAX-ACCESS	 read-only 	
		STATUS		        current	
		DESCRIPTION	 "This oid conveys NG service state as \
		                             ACTIVE, DOWN or CRASHED."
		::=  {  aventailNGServer  1  }

numOfNgClientAddrPool OBJECT-TYPE
		SYNTAX			Integer32
		MAX-ACCESS	read-only
		STATUS			current
		DESCRIPTION	"The number of Client Addr Pool assigned"
		::=  {  aventailNGServer  2  }

ngClientAddrPoolRangesTable OBJECT-TYPE
		SYNTAX		        SEQUENCE OF NgClientAddrPoolEntry 
		MAX-ACCESS	 not-accessible
		STATUS		        current
		DESCRIPTION	"This table provides information about how many address \
		                             pools are currently active in a appliance & what are \
		                             their ranges."
		::=  { aventailNGServer 3 }
	
ngClientAddrPoolEntry	OBJECT-TYPE
		SYNTAX		        NgClientAddrPoolEntry
		MAX-ACCESS	 not-accessible
		STATUS		        current
		DESCRIPTION	 "The number of pools are currently active in a appliance."
		INDEX		{  ngClientAddrPoolId  }
		::=  { ngClientAddrPoolRangesTable 1 }

NgClientAddrPoolEntry  ::=  SEQUENCE {
	    ngClientAddrPoolId                     Integer32,
	    ngClientAddrPoolUtilization          Integer32,
	    ngStartRangeOfClientAddrPool     InternationalDisplayString,
	    ngEndRangeOfClientAddrPool       InternationalDisplayString
           }

ngClientAddrPoolId      OBJECT-TYPE	
		SYNTAX			 Integer32
		MAX-ACCESS	 read-only 	
		STATUS		        current	
		DESCRIPTION	 "Index field for client Address Pool Utilization"
		::=  {  ngClientAddrPoolEntry  1  }


ngClientAddrPoolUtilization OBJECT-TYPE
		SYNTAX		        Integer32
		MAX-ACCESS	 read-only
		STATUS		        current
		DESCRIPTION	"Percentages of total how many VIPs are issued from \
		                            this client address pools"
		::=  {  ngClientAddrPoolEntry  2  }

ngStartRangeOfClientAddrPool	OBJECT-TYPE	
		SYNTAX			InternationalDisplayString
		MAX-ACCESS	read-only
		STATUS			current
		DESCRIPTION	"IP address in dot notation stating start range of \
		                            client Address Pool Utilization"
		::=  {  ngClientAddrPoolEntry  3  }

ngEndRangeOfClientAddrPool	OBJECT-TYPE	
		SYNTAX			InternationalDisplayString
		MAX-ACCESS	read-only
		STATUS			current
		DESCRIPTION	"IP address in dot notation stating end range of \
		                            client Address Pool Utilization"
		::=  {  ngClientAddrPoolEntry  4  }

numberOfNGSslTunnels       OBJECT-TYPE	
		SYNTAX			Integer32
		MAX-ACCESS	read-only 	
		STATUS		       current	
		DESCRIPTION	"Total number how many NG tunnels existing on this appliance"
		::=  {  aventailNGServer  4  }


ngSslTunnelTable OBJECT-TYPE
		SYNTAX		       SEQUENCE OF NgSslTunnelEntry 
		MAX-ACCESS	not-accessible
		STATUS		        current
		DESCRIPTION	"The NG Server tunnels statistics."
		::=  { aventailNGServer 5 }
	
ngSslTunnelEntry	OBJECT-TYPE
		SYNTAX		        NgSslTunnelEntry
		MAX-ACCESS	 not-accessible
		STATUS		        current
		DESCRIPTION	 "This represents the NG SSL tunnel table entry"
		INDEX		{  ngSslTunnelId  }
		::=  { ngSslTunnelTable 1 }

NgSslTunnelEntry  ::=  SEQUENCE {
	    ngSslTunnelId                    Integer32,
	    ngSslTunnelUser                 InternationalDisplayString,
	    ngSslTunnelVIP                  InternationalDisplayString,
	    numOfNgFlowsPerTunnel     Integer32,
	    ngSslTunnelUpTime              Integer32
	    }

ngSslTunnelId      OBJECT-TYPE			
              SYNTAX			Integer32
		MAX-ACCESS	read-only 	
		STATUS		       current	
		DESCRIPTION	"Index field for NG SSL Tunnel Table"
		::=  {  ngSslTunnelEntry  1  }

ngSslTunnelUser      OBJECT-TYPE	
		SYNTAX			InternationalDisplayString
		MAX-ACCESS	read-only 	
		STATUS		       current	
		DESCRIPTION	"Username associated with this NG SSL Tunnel."
		::=  {  ngSslTunnelEntry  2  }

ngSslTunnelVIP      OBJECT-TYPE	
		SYNTAX			InternationalDisplayString
		MAX-ACCESS	read-only 	
		STATUS		       current	
		DESCRIPTION	"Virtual IP address associated with this NG SSL tunnel."
		::=  {  ngSslTunnelEntry  3  }

numOfNgFlowsPerTunnel   OBJECT-TYPE	
		SYNTAX			Integer32
		MAX-ACCESS	read-only 	
		STATUS		       current	
		DESCRIPTION	"Number of flows per this NG SSL tunnel."
		::=  {  ngSslTunnelEntry  4  }

ngSslTunnelUpTime	OBJECT-TYPE	
		SYNTAX			Integer32
		MAX-ACCESS	read-only 	
		STATUS		       current	
		DESCRIPTION	"Uptime statistics for this NG SSL tunnel."
		::=  {  ngSslTunnelEntry  5  }


ngclientAddrPoolUtilizationWarning 	NOTIFICATION-TYPE
		STATUS			current
		DESCRIPTION     "When client address-pool utilization per pool \
		                             exceeds threshold a trap should be triggered."
		::=  {  aventailNGServer 100  }

ngServerStateChange 	NOTIFICATION-TYPE
		STATUS			current
		DESCRIPTION	"NG Server core functionality depends upon user \
		                            space processes avssld, avpsd and two avevent \
		                            kernel threads. SNMP agent will monitor these \
		                            four processes and when any of these go down \
		                            this trap will be triggered. Trap description \
		                            will specify NG service is down due to particular \
		                            component for example the description will contain \
		                            names of NG and failed thread for example avssld(0)."
		::=  {  aventailNGServer   101}

nGSSLTunnelHogging  	NOTIFICATION-TYPE
		STATUS			current
		DESCRIPTION		"All the NG tunnels will be monitored to check \
		                                    if they are exceeding threshold of tunnel bandwidth \
		                                    every 5 minutes. If a NG tunnel  is persistently \
		                                    hogging the network for last 10 minutes this trap \
		                                    will be triggered. The NG tunnels statistics \
		                                    given with this trap will include instance of the \
		                                    ngSslTunnelTable for the Session \
		                                    hogging the bandwidth."
		::=  {  aventailNGServer 102}
END
