ARRIS-D5-ENT-CHASSIS-MIB DEFINITIONS ::= BEGIN
 
		IMPORTS
			arrisD5UEQam			
				FROM ARRIS-MIB			
			entPhysicalIndex, entPhysicalEntry			
				FROM ENTITY-MIB			
			OBJECT-GROUP, MODULE-COMPLIANCE			
				FROM SNMPv2-CONF			
			OBJECT-TYPE, MODULE-IDENTITY			
				FROM SNMPv2-SMI			
			TEXTUAL-CONVENTION			
				FROM SNMPv2-TC;

	
		-- 1.3.6.1.4.1.4115.1.8.1.6
		arrisEntChassisMIB MODULE-IDENTITY 
			LAST-UPDATED "201009071432Z" -- 07 Sept 2010 YYYYMMDDHHMMZ
			ORGANIZATION 
				"Arris"
			CONTACT-INFO 
				"Initial MIB creator: Michael B. Sullivan
				Postal: Arris Interactive
				        3871 Lakefield Drive
				        Suite 300
				        Suwanee, GA 30024-1242
				        U.S.A.
				Phone:  +1 770 622 8400
				E-mail: michael.b.sullivan@arrisi.com"
			DESCRIPTION 
				"This is the extension to RFC 2737 ENTITY-MIB to support chassis
				management information."
			REVISION "200512070000Z"		-- December 07, 2005 at 00:00 GMT
			DESCRIPTION 
				"MIB created"
			REVISION "201009070000Z"		-- September 07, 2010 at 00:00 GMT
			DESCRIPTION 
				"Modified the CardType enumeration values back
				to their original values"
			::= { arrisD5UEQam 6 }

		
	
--
-- Textual conventions
--
	
		CardType ::= TEXTUAL-CONVENTION
			STATUS current
			DESCRIPTION 
				"Indicates the type of card in a slot."
			SYNTAX INTEGER
				{
				notApplicable(0),
				mon(1),
				wan(2),
				qam(3),
				doc(4),
				powermodule(5),
				fan(6) 
				}

		AdminState ::= TEXTUAL-CONVENTION
			STATUS current
			DESCRIPTION 
				"Indicates whether the system should attempt to bring a resource
				into service (up) or keep it offline (down)."
			SYNTAX INTEGER
				{
				notApplicable(0),
				up(1),
				down(2)
				}

		OperationalState ::= TEXTUAL-CONVENTION
			STATUS current
			DESCRIPTION 
				"Indicates whether a resource is ready to provide service (IS)
				or is not (OOS)."
			SYNTAX INTEGER
				{
				notApplicable(0),
				is(1),
				oos(2)
				}

		OperationalSubState ::= TEXTUAL-CONVENTION
			STATUS current
			DESCRIPTION 
				"Indicates why a card isn't fully operational when the cause is
				booting-related (DNLD/PUMP/INIT), administrative state-related
				(MAN), runtime-related (ALRM), or unexpected (FLT)."
			SYNTAX INTEGER
				{
				notApplicable(0),
				manual(1),
				fault(2),
				fwPump(3),
				initializing(4),
				alarm(5),
				unequipped(6),
				detecting(7),
				upgrading(8),
				diagnostic(9)
				}

		SlotOwner ::= TEXTUAL-CONVENTION
			STATUS current
			DESCRIPTION 
				"Indicates whether the slot is assigned to WAN-7 or WAN-8"
			SYNTAX INTEGER
				{
				notApplicable(0),
				wan7(7),
				wan8(8)
				}

--
-- Node definitions
--
	
		-- 1.3.6.1.4.1.4115.1.8.1.6.1
		arrisEntChassisObjects OBJECT IDENTIFIER ::= { arrisEntChassisMIB 1 }

		
		-- 1.3.6.1.4.1.4115.1.8.1.6.1.1
		arrisEntTable OBJECT-TYPE
			SYNTAX SEQUENCE OF ArrisEntEntry
			MAX-ACCESS not-accessible
			STATUS current
			DESCRIPTION
				"This table contains one row per physical entity.  There is
				always at least one row for an 'overall' physical entity."
			::= { arrisEntChassisObjects 1 }

		
		-- 1.3.6.1.4.1.4115.1.8.1.6.1.1.1
		arrisEntEntry OBJECT-TYPE
			SYNTAX ArrisEntEntry
			MAX-ACCESS not-accessible
			STATUS current
			DESCRIPTION
				"Chassis management state information for a particular entity.
				
				Chassis management plays a key role in monitoring system
				resource status, managing service turn-up, and deleting
				resources."
			AUGMENTS { entPhysicalEntry }
			::= { arrisEntTable 1 }

		
		ArrisEntEntry ::=
			SEQUENCE { 
				arrisEntProvCardType
					CardType,
				arrisEntDetCardType
					CardType,
				arrisEntAdminState
					AdminState,
				arrisEntOperState
					OperationalState,
				arrisEntOperSubState
					OperationalSubState,
				arrisEntProductCode
					OCTET STRING,
				arrisEntProductRev
					OCTET STRING,
				arrisEntSlotOwner
					SlotOwner
			 }

		-- 1.3.6.1.4.1.4115.1.8.1.6.1.1.1.1
		arrisEntProvCardType OBJECT-TYPE
			SYNTAX CardType
			MAX-ACCESS read-write
			STATUS current
			DESCRIPTION
				"Indicates what type of card is intended to be used in a slot.
				This value is configured by the user and is persistent across
				reboots."
			::= { arrisEntEntry 1 }

		
		-- 1.3.6.1.4.1.4115.1.8.1.6.1.1.1.2
		arrisEntDetCardType OBJECT-TYPE
			SYNTAX CardType
			MAX-ACCESS read-write
			STATUS current
			DESCRIPTION
				"Indicates what type of card is actually inserted in a slot.
				This value is maintained by the system."
			::= { arrisEntEntry 2 }

		
		-- 1.3.6.1.4.1.4115.1.8.1.6.1.1.1.3
		arrisEntAdminState OBJECT-TYPE
			SYNTAX AdminState
			MAX-ACCESS read-write
			STATUS current
			DESCRIPTION
				"Indicates whether the system should attempt to bring a resource
				into service (up) or keep the resource offline (down).  This
				state is configured by the user and is persistent across
				reboots."
			::= { arrisEntEntry 3 }

		
		-- 1.3.6.1.4.1.4115.1.8.1.6.1.1.1.4
		arrisEntOperState OBJECT-TYPE
			SYNTAX OperationalState
			MAX-ACCESS read-only
			STATUS current
			DESCRIPTION
				"Indicates whether a resource is ready to provide service (IS)
				or is not (OOS).  This state is maintained by the system."
			::= { arrisEntEntry 4 }


		-- 1.3.6.1.4.1.4115.1.8.1.6.1.1.1.5
		arrisEntOperSubState OBJECT-TYPE
			SYNTAX OperationalSubState
			MAX-ACCESS read-only
			STATUS current
			DESCRIPTION
				"Indicates why a card isn't fully operational when the cause is
				booting-related (DNLD/PUMP/INIT), administrative state-related
				(MAN), runtime-related (ALRM), or unexpected (FLT).  This state
				is maintained by the system."
			::= { arrisEntEntry 5 }


		-- 1.3.6.1.4.1.4115.1.8.1.6.1.1.1.6
		arrisEntProductCode OBJECT-TYPE
			SYNTAX OCTET STRING (SIZE (0..32))
			MAX-ACCESS read-only
			STATUS current
			DESCRIPTION
				"Arris Product Code for the card"
			::= { arrisEntEntry 6 }

		
		-- 1.3.6.1.4.1.4115.1.8.1.6.1.1.1.7
		arrisEntProductRev OBJECT-TYPE
			SYNTAX OCTET STRING (SIZE (0..32))
			MAX-ACCESS read-only
			STATUS current
			DESCRIPTION
				"Arris Product Revision for the card"
			::= { arrisEntEntry 7 }


		-- 1.3.6.1.4.1.4115.1.8.1.6.1.1.1.8
		arrisEntSlotOwner OBJECT-TYPE
			SYNTAX SlotOwner
			MAX-ACCESS read-write
			STATUS current
			DESCRIPTION
				"Indicates whether the slot is assigned to WAN-7 or WAN-8"
			::= { arrisEntEntry 8 }


		-- 1.3.6.1.4.1.4115.1.8.1.6.2
		arrisEntChassisConformance OBJECT IDENTIFIER ::= { arrisEntChassisMIB 2 }

		
		-- 1.3.6.1.4.1.4115.1.8.1.6.2.1
		arrisEntChassisGroups OBJECT IDENTIFIER ::= { arrisEntChassisConformance 1 }

		
		-- 1.3.6.1.4.1.4115.1.8.1.6.2.1.1
		arrisEntChassisGroup OBJECT-GROUP
			OBJECTS { arrisEntProvCardType, arrisEntDetCardType, arrisEntAdminState, arrisEntOperState, arrisEntOperSubState, arrisEntSlotOwner
				 }
			STATUS current
			DESCRIPTION 
				"The collection of objects which are used to represent
				physical system component states, for which a single agent
				provides management information."
			::= { arrisEntChassisGroups 1 }

		
		-- 1.3.6.1.4.1.4115.1.8.1.6.2.2
		arrisEntChassisCompliances OBJECT IDENTIFIER ::= { arrisEntChassisConformance 2 }

		
		-- 1.3.6.1.4.1.4115.1.8.1.6.2.2.1
		arrisEntChassisCompliance MODULE-COMPLIANCE
			STATUS current
			DESCRIPTION 
				"Describes the requirements for conformance to the Arris
				Entity Chassis MIB module."
			MODULE ARRIS-D5-ENT-CHASSIS-MIB
				MANDATORY-GROUPS { arrisEntChassisGroup }
			::= { arrisEntChassisCompliances 1 }

		
	
	END
