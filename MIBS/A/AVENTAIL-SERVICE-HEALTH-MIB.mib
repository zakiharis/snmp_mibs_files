-- File Name : AVENTAIL-SERVICE-HEALTH

AVENTAIL-SERVICE-HEALTH-MIB	DEFINITIONS ::= BEGIN
	IMPORTS
		aventail
			FROM AVENTAIL-MIB
		RowStatus, DisplayString, TruthValue
			FROM SNMPv2-TC
		InternationalDisplayString 
			FROM HOST-RESOURCES-MIB
                OBJECT-TYPE, MODULE-IDENTITY,  Integer32, enterprises, NOTIFICATION-TYPE
			FROM SNMPv2-SMI;

aventailServiceHealth MODULE-IDENTITY
             LAST-UPDATED       "200409071432Z" 
             ORGANIZATION       "Aventail"
             CONTACT-INFO       "email:   support@aventail.com"
             DESCRIPTION       "This Aventail MIB provides Service Health Info"
        	::= {aventail 3}


serviceTable	OBJECT-TYPE
		SYNTAX		        SEQUENCE  OF  ServiceEntry
		MAX-ACCESS	 not-accessible
		STATUS		        current
		DESCRIPTION	 "The number of ASAP services in the service table."
		::=  { aventailServiceHealth  1 }

serviceEntry	OBJECT-TYPE
		SYNTAX		        ServiceEntry
		MAX-ACCESS	 not-accessible
		STATUS		        current
		DESCRIPTION	"This field represents the service table Entry."
		INDEX		{  serviceId  }
		::=  { serviceTable 1 }

ServiceEntry  ::=  SEQUENCE {
	    serviceId                           Integer32,
		serviceDescription           InternationalDisplayString,
		serviceState                   Integer32,
		serviceTableRowStatus    RowStatus
		}

serviceId	OBJECT-TYPE	
		SYNTAX			 Integer32
		MAX-ACCESS	 read-only 	
		STATUS		        current	
		DESCRIPTION	 "Index field for Service Table comprising following services, \
						Aventail Management console(AMC), Client/Server Access Service(AVPN), \
						Web Access Service(ExtraWeb), ASAP Workplace"
		::=  {  serviceEntry  1  }

serviceDescription	OBJECT-TYPE	
		SYNTAX			InternationalDisplayString
		MAX-ACCESS		read-only
		STATUS			current
		DESCRIPTION		"The name of the ASAP service, currently supported Client/Server \
		                            Access Service (AVPN), Web Access Service (Extraweb),  \
		                            AMC and ASAP Workplace."
		::=  {  serviceEntry  2  }

serviceState	OBJECT-TYPE	
		SYNTAX			Integer32
		MAX-ACCESS	read-only
		STATUS			current
		DESCRIPTION	"This oid conveys service state as \
		                             active(0), notInService(2), or crashed(6)."
		::=  {  serviceEntry  3  }

serviceTableRowStatus	OBJECT-TYPE	
		SYNTAX			RowStatus
		MAX-ACCESS	read-create
		STATUS			current
		DESCRIPTION	"Currently we are supporting row status to be either \
		                            Active(1) Crashed(6) and 2=NotInService states for the services."
		::=  {  serviceEntry  4  }

asapServiceUp	NOTIFICATION-TYPE
		STATUS			current
		DESCRIPTION	"An ASAP service on the single node system; identified \
		                             by the IP address the trap is sent from has gone up. \
		                             The serviceDescription oid is sent along with this trap."
		::=  {  aventailServiceHealth  2  }

asapServiceDown	NOTIFICATION-TYPE
		STATUS			current
		DESCRIPTION	"An ASAP service on the single node system; \
		                             identified by the IP address the trap is sent from has \
		                             gone down. The serviceDescription oid is sent along with this trap."
		::=  {  aventailServiceHealth  3  }

END
