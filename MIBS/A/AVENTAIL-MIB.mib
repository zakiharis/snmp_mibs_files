-- File Name : AVENTAIL

AVENTAIL-MIB	DEFINITIONS ::= BEGIN
	IMPORTS
		enterprises, MODULE-IDENTITY
			FROM SNMPv2-SMI;

	aventail	MODULE-IDENTITY
		LAST-UPDATED	"200409071432Z"
		ORGANIZATION	"Aventail"
		CONTACT-INFO	"email:support@aventail.com"
		DESCRIPTION	"This file defines the private Aventail enterprise OID "
		REVISION	"200409071432Z"
		DESCRIPTION	"Aventail Corporation Private Namespace"
		::=  {  enterprises  4331  }

END
