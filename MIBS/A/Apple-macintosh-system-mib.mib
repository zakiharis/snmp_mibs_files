Apple-macintosh-system-mib DEFINITIONS ::= BEGIN
 
IMPORTS
	TRAP-TYPE FROM RFC-1215
   enterprises, OBJECT-TYPE
   FROM RFC1155-SMI
            DisplayString
                      FROM SNMPv2-TC;
 
-- A UnicodeString is restricted to the Unicode character set as defined in
 
   UnicodeString ::= OCTET STRING
 
--  This MIB module uses the extended OBJECT-TYPE macro as  defined in [9]
 
-- Macintosh System MIB
 
apple  OBJECT IDENTIFIER ::= { enterprises 63 }
macintosh  OBJECT IDENTIFIER ::= { apple 1 }
appleTalk  OBJECT IDENTIFIER ::= { apple 2 }
 
-- A user generated trap
 
userInTrouble  TRAP-TYPE
               ENTERPRISE  apple
                VARIABLES   { snmpName, defaultZone }
               DESCRIPTION
"A userInTrouble trap signifies that the sending SNMP application's user is
having some kind of trouble relaing to the network and wishes to commandeer
some help from a knowledgable network manager."
               ::= 0
 
-- The Groups
 
system OBJECT IDENTIFIER ::= { macintosh 1 }
software   OBJECT IDENTIFIER ::= { macintosh 2 }
hardware   OBJECT IDENTIFIER ::= { macintosh 3 }
 
 
-- The System Group
 
snmpName   OBJECT-TYPE
   SYNTAX  DisplayString
   ACCESS  read-write
   STATUS  mandatory
   DESCRIPTION
"A text string that contains the name advertised over NBP with type 'SNMP
Agent'.  The default is the same as the Macintosh name set in the Sharing Setup
Control Panel ,  if there is no Macintosh name present, a random unique name
will be chosen."
   REFERENCE
   "IM VI:7-6"
   ::= { system 1 }
 
machineIcon    OBJECT-TYPE
   SYNTAX  OCTET STRING
   ACCESS  read-only
   STATUS  mandatory
   DESCRIPTION
"A 32 x 32 pixel image that represents the Macintosh computer.  The bits of the
first four octets are interpreted in network order as the pixels in right to
left order of the top row of the image.  Ensuing four octet groups are
interpreted as descending rows.  "
   REFERENCE
   "IM VI: 3-41"
   ::= { system 2 }
 
contentsTable  OBJECT-TYPE
   SYNTAX  SEQUENCE OF ContentsEntry
   ACCESS  not-accessible
   STATUS  mandatory
   DESCRIPTION
"The contentsTable contains information about
Subagents and Subtrees of variables (usually a group) registered on this
node."
   ::= { system 3 }
 
contentsEntry  OBJECT-TYPE
   SYNTAX  ContentsEntry
   ACCESS  not-accessible
   STATUS  mandatory
   DESCRIPTION
"Each entry contains information about a Subagent
and one of its Subtrees of variables (usually a    group) that have been
registered at this node, the   Index is the table entry  number from 1...n."
--   INDEX { INTEGER }
   ::= { contentsTable  1 }
 
ContentsEntry  ::= SEQUENCE {
   contentsSubagent DisplayString,
   contentsSubtree DisplayString,
   contentsObjectID OBJECT IDENTIFIER
   }
 
contentsAgent  OBJECT-TYPE
   SYNTAX  DisplayString
   ACCESS  read-only
   STATUS  mandatory
   DESCRIPTION
"The name of the Subagent owning this Subtree."
   ::= { contentsEntry 1 }
 
contentsGroup  OBJECT-TYPE
   SYNTAX  DisplayString
   ACCESS  read-only
   STATUS  mandatory
   DESCRIPTION
"The name of the Subtree (usually a group)."
   ::= { contentsEntry 2 }
 
contentsObjectID   OBJECT-TYPE
   SYNTAX  OBJECT IDENTIFIER
   ACCESS  read-only
   STATUS  mandatory
   DESCRIPTION
"The Object Identifier of the root of the Subtree."
   ::= { contentsEntry 3 }
 
trapTable  OBJECT-TYPE
   SYNTAX  SEQUENCE OF TrapRequestEntry
   ACCESS  not-accessible
   STATUS  mandatory
   DESCRIPTION
"The trapTable contains a list of all traps that a console supporting a
particular community  wishes  to receive.  The Index is the table entry  number
from 1...n."
--   INDEX { INTEGER }
   ::= { system 4 }
 
trapRequestEntry   OBJECT-TYPE
   SYNTAX  TrapRequestEntry
   ACCESS  not-accessible
   STATUS  mandatory
   DESCRIPTION
   "Each entry contains a complete description of a
   trap's destination."
--   INDEX { INTEGER }
   ::= { trapTable 1 }
 
TrapRequestEntry   ::= SEQUENCE {
   trapCommunity   DisplayString,
   trapID  OBJECT IDENTIFIER,
   trapProtocol OBJECT IDENTIFIER,
   trapPort OCTET STRING( SIZE( 4 ) ),
   trapDestination OCTET STRING,
   trapValidity INTEGER
   }
 
trapCommunity  OBJECT-TYPE
   SYNTAX  DisplayString
   ACCESS  read-write
   STATUS  mandatory
   DESCRIPTION
   "The community that must be associated with the
   trap when sent."
   ::= { trapRequestEntry 1 }
 
trapID OBJECT-TYPE
   SYNTAX OBJECT IDENTIFIER
   ACCESS  read-write
   STATUS  mandatory
   DESCRIPTION
   "The object identifier of the trap."
   REFERENCE
   "RFC-1215."
   ::= { trapRequestEntry 2 }
 
trapProtocol   OBJECT-TYPE
   SYNTAX  DisplayString ( SIZE( 4 ) )
   ACCESS  read-write
   STATUS  mandatory
   DESCRIPTION
   "The object identifier of the protocol that the trap    should  use."
   ::= { trapRequestEntry 3 }
 
trapPort   OBJECT-TYPE
   SYNTAX  DisplayString ( SIZE( 4 ) )
   ACCESS  read-write
   STATUS  mandatory
   DESCRIPTION
   "The identifier of the port that the trap must
   use.  For example, for lP this would be 'UDP ', for
   AppleTalk this would be 'DDP ', etc.  Drivers for the
   particular stacks are expected to register the same
   string with the SNMP Manager so that it will be
   able to provide multi-protocol support. "
   REFERENCE
   "MacSNMP Programmer's Guide, Apple  Computer, Inc."
   ::= { trapRequestEntry 4 }
 
trapDestination    OBJECT-TYPE
   SYNTAX  OCTET STRING
   ACCESS  read-write
   STATUS  mandatory
   DESCRIPTION
"The information required to obtain the address of the console requesting the
trap.  This information would be different for each protocol.  For example, for
IP, the IP address stored in dot notation is sufficient. For AppleTalk, the NBP
entry is sufficient and reliable, but also  including the present DDP address
greatly improves the efficiency."
   REFERENCE
"MacSNMP Administrator's Guide, Apple Computer, Inc."
   ::= { trapRequestEntry 5 }
 
trapValidity   OBJECT-TYPE
   SYNTAX  INTEGER {
   valid(1),
   invalid(2)
   }
   ACCESS  read-write
   STATUS  mandatory
   DESCRIPTION
   "This entry defines whether the row is still active and valid."
   ::= { trapRequestEntry 6 }
 
defaultZone    OBJECT-TYPE
   SYNTAX  DisplayString( SIZE( 31) )
   ACCESS  read-only
   STATUS  mandatory
   DESCRIPTION
"A text string that contains the name of the zone the machine is in."
   ::= { system 5 }
 
 
-- The Software Group
 
 
gestaltTable   OBJECT-TYPE
   SYNTAX  SEQUENCE OF GestaltEntry
   ACCESS  not-accessible
   STATUS  mandatory
   DESCRIPTION
"The gestaltTable contains the results from the gestalt call that allow you to
get to information about the operating environment in a simple and efficient
manner.  Some interesting Gestalt selectors (in ascii) are 'ram ' for bytes of
physical ram, 'romv' for ROM version, 'sysv' for system version, and 'atlk' for
AppleTalk version. "
   REFERENCE
"IM VI: 3-28 to 3-53."
   ::= { software 1 }
 
gestaltEntry   OBJECT-TYPE
   SYNTAX  GestaltEntry
   ACCESS  not-accessible
   STATUS  mandatory
   DESCRIPTION
"Each entry contains the gestalt selector, the response, and the response
type."
   INDEX { gestaltSelector }
   ::= { gestaltTable 1 }
 
GestaltEntry   ::= SEQUENCE {
   gestaltSelector OCTET STRING( SIZE (4) ),
   gestaltResponseType INTEGER,
   gestaltResponse OCTET STRING( SIZE (4) )
}
 
gestaltSelector    OBJECT-TYPE
   SYNTAX  OCTET STRING( SIZE (4) )
   ACCESS  read-only
   STATUS  mandatory
   DESCRIPTION
"The gestaltSelector is a 4 octet string that determines what information you
want.  It usually consists of ascii characters."
   ::= { gestaltEntry 1 }
 
gestaltResponseType    OBJECT-TYPE
   SYNTAX  INTEGER {
   other(1),
   attr(2),
   count(3),
   size(4),
   table(5),
   type(6),
   version(7)
   }
   ACCESS  read-only
   STATUS  mandatory
   DESCRIPTION
"The gestaltResponseType describes how to interpret the corresponding gestalt
response.   Attr is a bit-field, Count is how many of the indicated type exist,
Size is usually in bytes, Table is the memory address of a table, Version is in
binary coded decimal (BCD.)"
   REFERENCE
"IM VI: 3-33 to 3-34. "
   ::= { gestaltEntry 2 }
 
gestaltResponse    OBJECT-TYPE
   SYNTAX  OCTET STRING( SIZE(4) )
   ACCESS  read-only
   STATUS  mandatory
   DESCRIPTION
"The gestaltResponse is the information you requested.  Its interpretation
depends upon the corresponding gestalt type."
   ::= { gestaltEntry 3 }
 
printerName    OBJECT-TYPE
   SYNTAX  OCTET STRING( SIZE(31) )
   ACCESS  read-only
   STATUS  mandatory
   DESCRIPTION
"The name of the printer currently chosen."
   ::= { software 2 }
 
printerZone    OBJECT-TYPE
   SYNTAX  OCTET STRING( SIZE(31) )
   ACCESS  read-only
   STATUS  mandatory
   DESCRIPTION
"The zone of the printer currently chosen."
   ::= { software 3 }
 
printerType    OBJECT-TYPE
   SYNTAX  OCTET STRING( SIZE(31) )
   ACCESS  read-only
   STATUS  mandatory
   DESCRIPTION
"The name of the printer driver currently chosen."
   ::= { software 4 }
 
systemFilesTable   OBJECT-TYPE
   SYNTAX  SEQUENCE OF FileEntry
   ACCESS  not-accessible
   STATUS  mandatory
   DESCRIPTION
"The systemFilesTable contains a list of all of the files in the active system
folder and its subfolders."
   ::= { software 5 }
 
fileEntry  OBJECT-TYPE
   SYNTAX  FileEntry
   ACCESS  not-accessible
   STATUS  mandatory
   DESCRIPTION
"Each entry contains a complete description of a file and its location.   The
index starts at 1 and increments by one for each file."
--   INDEX { INTEGER }
   ::= { systemFilesTable 1 }
 
FileEntry  ::= SEQUENCE {
   fileVRefNum INTEGER,
   fileID  INTEGER,
   fileDirID   INTEGER,
   fileDirName DisplayString( SIZE(31) ),
   fileName DisplayString( SIZE(31) ),
   fileType OCTET STRING( SIZE(4) ),
   fileCreator OCTET STRING( SIZE(4)),
   fileSize INTEGER,
   fileCreatDate   INTEGER,
   fileModDate INTEGER,
   fileVersion OCTET STRING
   }
 
fileVRefNum    OBJECT-TYPE
   SYNTAX  INTEGER
   ACCESS  read-only
   STATUS  mandatory
   DESCRIPTION
"A unique ID that determines the volume the file is in.  The name of the volume
and its other parameters can be determined from the Volume list with the
matching volRefNum.  This volume is local."
   ::= { fileEntry 1 }
 
fileID OBJECT-TYPE
   SYNTAX  INTEGER
   ACCESS  read-only
   STATUS  mandatory
   DESCRIPTION
"A unique ID that determines the file."
   REFERENCE
"IM VI:25-25."
   ::= { fileEntry 2 }
 
fileDirID  OBJECT-TYPE
   SYNTAX  INTEGER
   ACCESS  read-only
   STATUS  mandatory
   DESCRIPTION
"A unique ID that determines the directory the file is in."
   REFERENCE
"IM IV-92."
   ::= { fileEntry 3 }
 
fileDirName    OBJECT-TYPE
   SYNTAX  DisplayString( SIZE (31) )
   ACCESS  read-only
   STATUS  mandatory
   DESCRIPTION
"The name of the directory the file is in. The ascii character for ':' is
forbidden."
   ::= { fileEntry 4 }
 
fileName   OBJECT-TYPE
   SYNTAX  DisplayString( SIZE (31) )
   ACCESS  read-only
   STATUS  mandatory
   DESCRIPTION
"The name of the file. The ascii character for ':' is forbidden."
   ::= { fileEntry 5 }
 
fileType   OBJECT-TYPE
   SYNTAX  OCTET STRING( SIZE(4) )
   ACCESS  read-only
   STATUS  mandatory
   DESCRIPTION
"The type of the file. Usually ascii characters."
   ::= { fileEntry 6 }
 
fileCreator    OBJECT-TYPE
   SYNTAX  OCTET STRING( SIZE(4) )
   ACCESS  read-only
   STATUS  mandatory
   DESCRIPTION
"The creator of the file. Usually ascii characters."
   ::= { fileEntry 7  }
 
fileSize   OBJECT-TYPE
   SYNTAX  INTEGER
   ACCESS  read-only
   STATUS  mandatory
   DESCRIPTION
"The size of the file in bytes."
   ::= { fileEntry 8  }
 
fileCreatDate  OBJECT-TYPE
   SYNTAX  INTEGER
   ACCESS  read-only
   STATUS  mandatory
   DESCRIPTION
"The creation date of the file in seconds from midnight January 1, 1904."
   ::= { fileEntry 9  }
 
fileModDate    OBJECT-TYPE
   SYNTAX  INTEGER
   ACCESS  read-only
   STATUS  mandatory
   DESCRIPTION
"The modification date of the file in seconds from midnight January 1, 1904."
   ::= { fileEntry 10  }
 
fileVersion    OBJECT-TYPE
   SYNTAX  OCTET STRING
   ACCESS  read-only
   STATUS  mandatory
   DESCRIPTION
"The version of the application."
   REFERENCE
 "IM III: 1-10."
   ::= { fileEntry 11  }
 
applFilesTable OBJECT-TYPE
   SYNTAX  SEQUENCE OF ApplEntry
   ACCESS  not-accessible
   STATUS  mandatory
   DESCRIPTION
"The Application Files Table contains a list of all of the applications on the
local volumes."
   ::= { software 6 }
 
applEntry  OBJECT-TYPE
   SYNTAX  ApplEntry
   ACCESS  not-accessible
   STATUS  mandatory
   DESCRIPTION
"Each entry contains a complete description of a file and where it is.  The 2nd
index starts at 1 and is increment by one for each file."
--   INDEX { applVRefNum, INTEGER }
   ::= { applFilesTable 1 }
 
ApplEntry  ::= SEQUENCE {
   applVRefNum INTEGER,
   applFileID  INTEGER,
   applDirID   INTEGER,
   applDirName DisplayString( SIZE (31) ),
   applName DisplayString( SIZE (31) ),
   applType OCTET STRING( SIZE(4) ),
   applCreator OCTET STRING( SIZE(4) ),
   applSize INTEGER,
   applCreatDate   INTEGER,
   applModDate INTEGER,
   applVersion OCTET STRING
}
 
applVRefNum    OBJECT-TYPE
   SYNTAX  INTEGER
   ACCESS  read-only
   STATUS  mandatory
   DESCRIPTION
"A unique ID that determines the volume the application is in.  The name of the
volume and its other parameters can be determined from the Volume list with the
matching volRefNum.  This volume is local."
   ::= { applEntry 1 }
 
applFileID OBJECT-TYPE
   SYNTAX  INTEGER
   ACCESS  read-only
   STATUS  mandatory
   DESCRIPTION
"A unique ID that determines the application file."
   REFERENCE
"IM VI:25-25."
   ::= { applEntry 2 }
 
applDirID  OBJECT-TYPE
   SYNTAX  INTEGER
   ACCESS  read-only
   STATUS  mandatory
   DESCRIPTION
"A unique ID that determines the directory the application is in."
   REFERENCE
"IM IV-92."
   ::= { applEntry 2 }
 
applDirName    OBJECT-TYPE
   SYNTAX  DisplayString( SIZE (31) )
   ACCESS  read-only
   STATUS  mandatory
   DESCRIPTION
"The name of the directory the application is in."
   ::= { applEntry 3 }
 
applName   OBJECT-TYPE
   SYNTAX  DisplayString( SIZE (31) )
   ACCESS  read-only
   STATUS  mandatory
   DESCRIPTION
"The name of the application."
   ::= { applEntry 4 }
 
applSize   OBJECT-TYPE
   SYNTAX  INTEGER
   ACCESS  read-only
   STATUS  mandatory
   DESCRIPTION
"The size of the application in bytes."
   ::= { applEntry 6  }
 
applCreator    OBJECT-TYPE
   SYNTAX  OCTET STRING( SIZE(4) )
   ACCESS  read-only
   STATUS  mandatory
   DESCRIPTION
"The creator of the application. Usually ascii characters."
   ::= { applEntry 5  }
 
applCreatDate  OBJECT-TYPE
   SYNTAX  INTEGER
   ACCESS  read-only
   STATUS  mandatory
   DESCRIPTION
"The creation date of the application in seconds from midnight, January 1,
1904."
   ::= { applEntry 7  }
 
applModDate    OBJECT-TYPE
   SYNTAX  INTEGER
   ACCESS  read-only
   STATUS  mandatory
   DESCRIPTION
"The modification date of the application in seconds from midnight, January 1,
1904."
   ::= { applEntry 8  }
 
applVersion    OBJECT-TYPE
   SYNTAX  DisplayString
   ACCESS  read-only
   STATUS  mandatory
   DESCRIPTION
"The version of the application. "
   REFERENCE
"IM III: 1-10."
   ::= { applEntry 9  }
 
 
-- The Hardware Group
 
nuBusTable OBJECT-TYPE
   SYNTAX  SEQUENCE OF NuBusEntry
   ACCESS  not-accessible
   STATUS  mandatory
   DESCRIPTION
"The NuBus Table contains a list of all of the NuBus cards contained in the
Macintosh."
   ::= { hardware 1 }
 
nuBusEntry OBJECT-TYPE
   SYNTAX  NuBusEntry
   ACCESS  not-accessible
   STATUS  mandatory
   DESCRIPTION
"Each entry contains a complete description of a NuBus card."
   REFERENCE
"Designing Cards and Drivers for the Macintosh II and the Macintosh SE,
Addison-Wesley Publishing Company, Inc., Menlo Park CA, 1987, chapter 8."
   INDEX { nuBusSlot}
   ::= { nuBusTable 1 }
 
NuBusEntry ::= SEQUENCE {
   nuBusSlot   INTEGER,
   nuBusType   INTEGER,
   nuBusBoardID INTEGER,
   nuBusBoardName  DisplayString,
   nuBusVendorName DisplayString,
   nuBusPartNumber DisplayString,
   nuBusSerialNumber   DisplayString,
   nuBusRevNumber  DisplayString, 
   nuBusRevDate DisplayString
}
 
nuBusSlot  OBJECT-TYPE
   SYNTAX  INTEGER
   ACCESS  read-only
   STATUS  mandatory
   DESCRIPTION
"The slot number of the board."
   ::= { nuBusEntry 1  }
 
nuBusType  OBJECT-TYPE
   SYNTAX  INTEGER
   ACCESS  read-only
   STATUS  mandatory
   DESCRIPTION
"The Category and cType of the board."
   ::= { nuBusEntry 2  }
 
nuBusBoardID   OBJECT-TYPE
   SYNTAX  INTEGER
   ACCESS  read-only
   STATUS  mandatory
   DESCRIPTION
"The Id of the board."
   ::= { nuBusEntry 3  }
 
nuBusBoardName OBJECT-TYPE
   SYNTAX  DisplayString
   ACCESS  read-only
   STATUS  mandatory
   DESCRIPTION
"The name of the board."
   ::= { nuBusEntry 4  }
 
nuBusVendor    OBJECT-TYPE
   SYNTAX  DisplayString
   ACCESS  read-only
   STATUS  mandatory
   DESCRIPTION
"The name of the vendor."
   ::= { nuBusEntry 5  }
 
nuBusPartNumber    OBJECT-TYPE
   SYNTAX  DisplayString
   ACCESS  read-only
   STATUS  mandatory
   DESCRIPTION
"The part number of the board."
   ::= { nuBusEntry 6  }
 
nuBusSerialNumber  OBJECT-TYPE
   SYNTAX  DisplayString
   ACCESS  read-only
   STATUS  mandatory
   DESCRIPTION
"The serial number of the board."
   ::= { nuBusEntry 7  }
 
nuBusRevNumber OBJECT-TYPE
   SYNTAX  DisplayString
   ACCESS  read-only
   STATUS  mandatory
   DESCRIPTION
"The revision number of the board."
   ::= { nuBusEntry 8  }
 
nuBusRevDate   OBJECT-TYPE
   SYNTAX  DisplayString
   ACCESS  read-only
   STATUS  mandatory
   DESCRIPTION
"The revision date of the board."
   ::= { nuBusEntry 9  }
 
scsiTable  OBJECT-TYPE
   SYNTAX  SEQUENCE OF ScsiEntry
   ACCESS  not-accessible
   STATUS  mandatory
   DESCRIPTION
"The SCSI Table contains a list of all of the SCSI devices contained in the
Macintosh."
   ::= { hardware 2 }
 
scsiEntry  OBJECT-TYPE
   SYNTAX  ScsiEntry
   ACCESS  not-accessible
   STATUS  mandatory
   DESCRIPTION
"Each entry contains a complete description of a SCSI device.   In addition it
contains an object identifier for the scsi device's MIB, if one has been
provided by the manufacturer.  The index is equal to the scsiID + 1."
   REFERENCE
   "[13]"
--   INDEX { INTEGER }
   ::= { scsiTable 1 }
 
ScsiEntry  ::= SEQUENCE {
   scsiID  INTEGER,
   scsiType DisplayString,
   scsiVendor  DisplayString,
   scsiProduct DisplayString,
   scsiVersion DisplayString
}
 
scsiID OBJECT-TYPE
   SYNTAX  INTEGER
   ACCESS  read-only
   STATUS  mandatory
   DESCRIPTION
"The bus ID of the SCSI device."
   ::= { scsiEntry 1  }
 
scsiType   OBJECT-TYPE
   SYNTAX  DisplayString
   ACCESS  read-only
   STATUS  mandatory
   DESCRIPTION
"The type of the SCSI device."
   ::= { scsiEntry 2  }
 
scsiVendor OBJECT-TYPE
   SYNTAX  DisplayString
   ACCESS  read-only
   STATUS  mandatory
   DESCRIPTION
"The vendor of the SCSI device."
   ::= { scsiEntry 3  }
 
scsiProduct    OBJECT-TYPE
   SYNTAX  DisplayString
   ACCESS  read-only
   STATUS  mandatory
   DESCRIPTION
"The product name of the SCSI device."
   ::= { scsiEntry 4  }
 
scsiVersion    OBJECT-TYPE
   SYNTAX  DisplayString
   ACCESS  read-only
   STATUS  mandatory
   DESCRIPTION
"The version of the SCSI device."
   ::= { scsiEntry 5  }
 
volumeTable    OBJECT-TYPE
   SYNTAX  SEQUENCE OF VolumeEntry
   ACCESS  not-accessible
   STATUS  mandatory
   DESCRIPTION
"The Volume Table contains a list of all of the volumes connected to by the
Macintosh."
   ::= { hardware 3 }
 
volumeEntry    OBJECT-TYPE
   SYNTAX  VolumeEntry
   ACCESS  not-accessible
   STATUS  mandatory
   DESCRIPTION
"Each entry contains a complete description of a volume."
   INDEX { volRefNum }
   ::= { volumeTable 1 }
 
VolumeEntry    ::= SEQUENCE {
   volRefNum   INTEGER,
   volName DisplayString( SIZE( 27 ) ),
   volKind DisplayString,
   volLocation DisplayString,
   volBytesUsed INTEGER,
   volBytesFree INTEGER
}
 
volRefNum  OBJECT-TYPE
   SYNTAX  INTEGER
   ACCESS  read-only
   STATUS  mandatory
   DESCRIPTION
"The reference number of the volume.  Usually a negative number."
   ::= { volumeEntry 1  }
 
volName    OBJECT-TYPE
   SYNTAX  DisplayString( SIZE (27) )
   ACCESS  read-only
   STATUS  mandatory
   DESCRIPTION
"The name of the volume.  The character ':' is not allowed."
   ::= { volumeEntry 2  }
 
volKind    OBJECT-TYPE
   SYNTAX  DisplayString
   ACCESS  read-only
   STATUS  mandatory
   DESCRIPTION
"The kind of the volume."
   ::= { volumeEntry 3  }
 
volLocation    OBJECT-TYPE
   SYNTAX  DisplayString
   ACCESS  read-only
   STATUS  mandatory
   DESCRIPTION
"The location of the volume."
   ::= { volumeEntry 4  }
 
volBytesUsed   OBJECT-TYPE
   SYNTAX  INTEGER
   ACCESS  read-only
   STATUS  mandatory
   DESCRIPTION
"The number of bytes used on the volume."
   ::= { volumeEntry 5  }
 
volBytesFree   OBJECT-TYPE
   SYNTAX  INTEGER
   ACCESS  read-only
   STATUS  mandatory
   DESCRIPTION
"The number of bytes free on the volume."
   ::= { volumeEntry 6  }
 
END
