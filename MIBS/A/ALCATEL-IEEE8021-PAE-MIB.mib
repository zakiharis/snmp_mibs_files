ALCATEL-IEEE8021-PAE-MIB DEFINITIONS ::= BEGIN

IMPORTS
    IpAddress, MODULE-IDENTITY,
    OBJECT-TYPE, Unsigned32                     FROM SNMPv2-SMI

    MODULE-COMPLIANCE, OBJECT-GROUP             FROM SNMPv2-CONF

    RowStatus,
    TEXTUAL-CONVENTION                          FROM SNMPv2-TC

    alcatelCommonMIBModules, alcatelObjects, 
    alcatelNotifyPrefix, alcatelConformance     FROM TIMETRA-GLOBAL-MIB

    TPolicyStatementNameOrEmpty,
    ServiceAdminStatus,
    TNamedItem                                  FROM TIMETRA-TC-MIB

    dot1xAuthConfigEntry                        FROM IEEE8021-PAE-MIB              
    ;

alcatelIEEE8021PaeMIBModule MODULE-IDENTITY
    LAST-UPDATED    "0701010000Z"
    ORGANIZATION    "Alcatel-Lucent"
    CONTACT-INFO
        "Alcatel-Lucent SROS Support
         Web: http://support.alcatel-lucent.com "
    DESCRIPTION
        "This  document  is  the  SNMP MIB module to manage and
         provision  the 7x50 extensions to the IEEE8021-PAE-MIB         
         (Port Access Entity nodule for managing IEEE 802.X) feature for
         the Alcatel 7x50 device.

         Copyright 2004-2011 Alcatel-Lucent. All rights reserved.        
         Reproduction of this document is authorized on the condition that
         the foregoing copyright notice is included.

         This SNMP MIB module (Specification) embodies Alcatel-Lucent's
         proprietary intellectual property.  Alcatel-Lucent retains
         all title and ownership in the Specification, including any
         revisions.

         Alcatel-Lucent grants all interested parties a non-exclusive
         license to use and distribute an unmodified copy of this
         Specification in connection with management of Alcatel-Lucent
         products, and without fee, provided this copyright notice and
         license appear on all copies.

         This Specification is supplied 'as is', and Alcatel-Lucent
         makes no warranty, either express or implied, as to the use,
         operation, condition, or performance of the Specification."

   REVISION     "0701010000Z"
   DESCRIPTION  "Rev 5.0                01 Jan 2007 00:00
                 5.0 release of the ALCATEL-IEEE8021-PAE-MIB."
   REVISION     "0508310000Z"
   DESCRIPTION  "Rev 3.0                31 Aug 2005 00:00   
                 3.0 release of the ALCATEL-IEEE8021-PAE-MIB."
   REVISION     "0503290000Z"
   DESCRIPTION  "Rev 2.0                29 Mar 2005 00:00   
                 2.0 release of the ALCATEL-IEEE8021-PAE-MIB."
   REVISION     "0408030000Z"
   DESCRIPTION  "Rev 1.0                03 Aug 2004 00:00   
                 1.0 release of the ALCATEL-IEEE8021-PAE-MIB."

   ::= { alcatelCommonMIBModules 3 } 

-- ----------------------------------------------------------------------------
--
--  Alcatel 7x50 series IEEE 802.1X PAE feature
--  MIB structure
--
-- ----------------------------------------------------------------------------
alxDot1xObjs                                OBJECT IDENTIFIER ::= { alcatelObjects 3 }      
    alxDot1xAuthenticatorObjs               OBJECT IDENTIFIER ::= { alxDot1xObjs 1 }
    alxDot1xRadiusObjs                      OBJECT IDENTIFIER ::= { alxDot1xObjs 2 }

alxDot1xConformance                         OBJECT IDENTIFIER ::= { alcatelConformance 3 }
    alxDot1xAuthenticatorConformance        OBJECT IDENTIFIER ::= { alxDot1xConformance 1 } 
        alxDot1xAuthenticatorCompliancs     OBJECT IDENTIFIER ::= { alxDot1xAuthenticatorConformance 1 }
        alxDot1xAuthenticatorGroups         OBJECT IDENTIFIER ::= { alxDot1xAuthenticatorConformance 2 }

    alxDot1xRadiusConformance               OBJECT IDENTIFIER ::= { alxDot1xConformance 2 } 
        alxDot1xRadiusCompliancs            OBJECT IDENTIFIER ::= { alxDot1xRadiusConformance 1 }
        alxDot1xRadiusGroups                OBJECT IDENTIFIER ::= { alxDot1xRadiusConformance 2 }

alxDot1xNotificationsPrefix           OBJECT IDENTIFIER ::= { alcatelNotifyPrefix 3 }
    alxDot1xNotifications                      OBJECT IDENTIFIER ::= { alxDot1xNotificationsPrefix 0 } 

-- ----------------------------------------------------------------------------
--
--  Textual Conventions   (alphabetical)
--
-- ----------------------------------------------------------------------------
AlxDot1xRadiusServerType ::= TEXTUAL-CONVENTION
        STATUS       current
        DESCRIPTION
            "The AlxDot1xRadiusServerType data type is used to denote
             the type of the RADIUS server."
        SYNTAX  INTEGER  {
                  authorization (0),
                  accounting    (1),
                  combined      (2)
                }

-- ----------------------------------------------------------------------------
--
--  The PAE Authenticator Group
--
-- ----------------------------------------------------------------------------

-- --------------------------------------------------------
-- 
-- Alxdot1xAuthConfigTable
-- 
-- --------------------------------------------------------
alxdot1xAuthConfigTable OBJECT-TYPE
    SYNTAX          SEQUENCE OF Alxdot1xAuthConfigEntry
    MAX-ACCESS      not-accessible
    STATUS          current
    DESCRIPTION
        "The  table alxdot1xAuthConfigTable allows configuration of 
         RADIUS authentication parameters for the 802.1X PAE
         feature on port level." 
    ::= { alxDot1xAuthenticatorObjs 1 }

alxDot1xAuthConfigEntry OBJECT-TYPE
    SYNTAX          Alxdot1xAuthConfigEntry
    MAX-ACCESS      not-accessible
    STATUS          current
    DESCRIPTION
        "alxDot1xAuthConfigEntry is an entry (conceptual row) in the
         alxdot1xAuthConfigTable. Each entry represents the configuration
         for Radius Authentication on a port. Entries have a presumed
         StorageType of nonVolatile."
    AUGMENTS { dot1xAuthConfigEntry }
    ::= { alxdot1xAuthConfigTable 1 }                                              
                                                                                  
Alxdot1xAuthConfigEntry ::= SEQUENCE {                                             
     alxDot1xAuthRadiusPlcy   TPolicyStatementNameOrEmpty     
}

alxDot1xAuthRadiusPlcy OBJECT-TYPE
    SYNTAX          TPolicyStatementNameOrEmpty
    MAX-ACCESS      read-write
    STATUS          current
    DESCRIPTION     
        "alxDot1xAuthRadiusPlcy   specifies  the  name  of  the
         Radius   Policy.   The   Radius  Policy  specifies  the        
         parameters that control the Radius Protocol. If no Policy is
         specified (empty string) no Radius authentication will be
         possible. This object can only be set to a policy that is defined
         in the alxdot1xRadiusServerPlcyTable."
    DEFVAL { "" } 
    ::= { alxDot1xAuthConfigEntry 50 }

-- ----------------------------------------------------------------------------
--
--  The RADIUS Group
--
-- ----------------------------------------------------------------------------

-- --------------------------------------------------------
-- 
-- Alxdot1xRadiusServerPlcyTable
-- 
-- --------------------------------------------------------
alxDot1xRadiusServerPlcyTable OBJECT-TYPE
    SYNTAX          SEQUENCE OF AlxDot1xRadiusServerPlcyEntry
    MAX-ACCESS      not-accessible
    STATUS          current
    DESCRIPTION
        "The  alxDot1xRadiusServerPlcyTable allows configuration of
         RADIUS  authentication  parameters  for  the 802.1X PAE
         feature."
    ::= { alxDot1xRadiusObjs 1 }

alxDot1xRadiusServerPlcyEntry OBJECT-TYPE
    SYNTAX          AlxDot1xRadiusServerPlcyEntry
    MAX-ACCESS      not-accessible
    STATUS          current
    DESCRIPTION
        "alxDot1xRadiusServerPlcyEntry is an entry (conceptual row) in the
         alxDot1xRadiusServerPlcyTable. Each entry represents the configuration for
         a 802.1X Radius Policy. Entries in this table can be created and deleted
         via SNMP SET operations to alxDot1xRadiusPlcyRowStatus. Entries have
         a presumed StorageType of nonVolatile."
    INDEX { alxDot1xRadiusPlcyName }
    ::= { alxDot1xRadiusServerPlcyTable 1 }                                              
                                                                                  
AlxDot1xRadiusServerPlcyEntry ::= SEQUENCE {                                             
    alxDot1xRadiusPlcyName             TNamedItem,
    alxDot1xRadiusPlcySrceAddr         IpAddress,
    alxDot1xRadiusPlcyAdminState       ServiceAdminStatus,  
    alxDot1xRadiusPlcyRowStatus        RowStatus,
    alxDot1xRadiusPlcyRetryAttempts    Unsigned32,
    alxDot1xRadiusPlcyTimeout          Unsigned32
}

alxDot1xRadiusPlcyName OBJECT-TYPE
    SYNTAX      TNamedItem
    MAX-ACCESS  not-accessible
    STATUS      current
    DESCRIPTION
        "The value of the object alxDot1xRadiusPlcyName specifies
         a specific radius server Policy to be used for 802.1X
         authentication."
    ::= { alxDot1xRadiusServerPlcyEntry 1 }

alxDot1xRadiusPlcySrceAddr OBJECT-TYPE
    SYNTAX      IpAddress
    MAX-ACCESS  read-create
    STATUS      current
    DESCRIPTION
        "The value of the object alxDot1xRadiusPlcySrceAddr  specifies the
         source  address  of  the  Radius packet. It must be a         
         valid unicast address. (otherwise a wrongValue error is returned.)

         If  this  object is configured with the address of the         
         router interface, the Radius client uses it while making a request
         to the server.
    
         If the address is not configured or is not the address of
         the one of interfaces, the source address is based on the address
         of the Radius server. If the server address is in-band, the client
         uses the system ip address. If it is out-of-band, the source
         address is the address of the management interface."
    DEFVAL { '00000000'H }  -- 0.0.0.0
    ::= { alxDot1xRadiusServerPlcyEntry 2 }

alxDot1xRadiusPlcyAdminState OBJECT-TYPE
    SYNTAX      ServiceAdminStatus
    MAX-ACCESS  read-create
    STATUS      current
    DESCRIPTION
        "The  value of the object alxDot1xRadiusPlcyAdminState specifies a
         specific radius server Policy to be used for 802.1x
         authentication."
    DEFVAL { down }
    ::= { alxDot1xRadiusServerPlcyEntry 3 }

alxDot1xRadiusPlcyRowStatus OBJECT-TYPE
    SYNTAX      RowStatus
    MAX-ACCESS  read-create
    STATUS      current
    DESCRIPTION
        "alxDot1xRadiusPlcyRowStatus controls the creation and deletion
         of rows in the table."
    ::= { alxDot1xRadiusServerPlcyEntry 4 }

alxDot1xRadiusPlcyRetryAttempts OBJECT-TYPE
    SYNTAX      Unsigned32 (1..10)
    MAX-ACCESS  read-create
    STATUS      current
    DESCRIPTION
        "The value of the object alxDot1xRadiusPlcyRetryAttempts specifies the
         number  of  RADIUS  requests  towards  the  same RADIUS server."
    DEFVAL { 3 }
    ::= { alxDot1xRadiusServerPlcyEntry 5 }

alxDot1xRadiusPlcyTimeout OBJECT-TYPE
    SYNTAX      Unsigned32 (1..90)
    UNITS       "seconds"
    MAX-ACCESS  read-create
    STATUS      current
    DESCRIPTION
        "The value of alxDot1xRadiusPlcyTimeout specifies the time,
         in seconds, between request retries towards the same RADIUS server."
    DEFVAL { 5 }
    ::= { alxDot1xRadiusServerPlcyEntry 6 }

-- --------------------------------------------------------
-- 
-- AlxDot1xRadiusServerTable
-- 
-- --------------------------------------------------------
alxDot1xRadiusServerTable OBJECT-TYPE
    SYNTAX      SEQUENCE OF AlxDot1xRadiusServerEntry
    MAX-ACCESS  not-accessible
    STATUS      current
    DESCRIPTION
        "The alxDot1xRadiusServerTable has an entry for each RADIUS
         server used for 802.1x authentication."
::= { alxDot1xRadiusObjs 2 }

alxDot1xRadiusServerEntry OBJECT-TYPE
    SYNTAX      AlxDot1xRadiusServerEntry
    MAX-ACCESS  not-accessible
    STATUS      current
    DESCRIPTION
        "alxDot1xRadiusServerEntry is an entry (conceptual row)
         in the alxDot1xRadiusServerTable. Each entry represents        
         the configuration for a RADIUS server. Entries in this table can
         be created and deleted via SNMP SET operations on
         alxDot1xRadiusServerRowStatus."
    INDEX {alxDot1xRadiusServerPlcyName, alxDot1xRadiusServerIndex}
    ::= { alxDot1xRadiusServerTable 1 }

AlxDot1xRadiusServerEntry ::=
    SEQUENCE {          
        alxDot1xRadiusServerPlcyName        TNamedItem,
        alxDot1xRadiusServerIndex           Unsigned32,
        alxDot1xRadiusServerAddress         IpAddress,
        alxDot1xRadiusServerSecret          OCTET STRING,        
        alxDot1xRadiusServerAuthPort        Unsigned32,  
        alxDot1xRadiusServerOperStatus      INTEGER,
        alxDot1xRadiusServerRowStatus       RowStatus,
        alxDot1xRadiusServerType            AlxDot1xRadiusServerType,
        alxDot1xRadiusServerAcctPort        Unsigned32  
    }

alxDot1xRadiusServerPlcyName OBJECT-TYPE
    SYNTAX      TNamedItem
    MAX-ACCESS  not-accessible
    STATUS      current
    DESCRIPTION
        "The  value of the object alxDot1xRadiusServerPlcyName specifies 
         the radius server  Policy  to be used for 802.1x
         authentication as defined in the alxDot1xRadiusServerPlcyTable.
         Row creation will be denied if no policy with the same name does
         not occur in the alxDot1xRadiusServerPlcyTable."
    ::= { alxDot1xRadiusServerEntry 1 }

alxDot1xRadiusServerIndex OBJECT-TYPE
    SYNTAX      Unsigned32 (1..5)
    MAX-ACCESS  not-accessible
    STATUS      current
    DESCRIPTION
        "The value of the object alxDot1xRadiusServerIndex specifies 
         a specific radius server in the policy."
    ::= { alxDot1xRadiusServerEntry 2 }

alxDot1xRadiusServerAddress OBJECT-TYPE
    SYNTAX      IpAddress
    MAX-ACCESS  read-create
    STATUS      current
    DESCRIPTION
        "The value of the object alxDot1xRadiusServerAddress specifies
         the IP address of the RADIUS server. A valid unicast
         IP address must be specified for row creation to succeed."
    ::= { alxDot1xRadiusServerEntry 3 }

alxDot1xRadiusServerSecret OBJECT-TYPE
    SYNTAX      OCTET STRING (SIZE (1..20))
    MAX-ACCESS  read-create
    STATUS      current
    DESCRIPTION
        "The value of the object alxDot1xRadiusServerSecret specifies
         the secret  key associated with the RADIUS server. An
         Empty key is not accepted."
    ::= { alxDot1xRadiusServerEntry 4 }

alxDot1xRadiusServerAuthPort OBJECT-TYPE
    SYNTAX      Unsigned32 (1..65535) 
    MAX-ACCESS  read-create
    STATUS      current
    DESCRIPTION
        "The value of the object alxDot1xRadiusServerAuthPort specifies
         the  UDP  port  number on which to contact the RADIUS
         server for authentication."
    DEFVAL { 1812 }
    ::= { alxDot1xRadiusServerEntry 5 }

alxDot1xRadiusServerOperStatus OBJECT-TYPE
    SYNTAX      INTEGER {
                    up   (1),
                    down (2)
                }
    MAX-ACCESS  read-only
    STATUS      current
    DESCRIPTION   
        "The value of the object alxDot1xRadiusServerOperStatus indicates
         the current status of the RADIUS server."
    ::= { alxDot1xRadiusServerEntry 6 }

alxDot1xRadiusServerRowStatus OBJECT-TYPE
    SYNTAX      RowStatus
    MAX-ACCESS  read-create
    STATUS      current
    DESCRIPTION
        "alxDot1xRadiusServerRowStatus controls the creation and deletion
         of rows in the table."
    ::= { alxDot1xRadiusServerEntry 7 }

alxDot1xRadiusServerType OBJECT-TYPE
    SYNTAX      AlxDot1xRadiusServerType 
    MAX-ACCESS  read-create
    STATUS      current
    DESCRIPTION   
        "The value of the object alxDot1xRadiusServerType  indicates
         the  type  of the RADIUS server."
    ::= { alxDot1xRadiusServerEntry 8 }

alxDot1xRadiusServerAcctPort OBJECT-TYPE
    SYNTAX      Unsigned32 (1..65535) 
    MAX-ACCESS  read-create
    STATUS      current
    DESCRIPTION
        "The value of the object alxDot1xRadiusServerAcctPort  specifies
         the  UDP port number  on  which  to  contact  the  RADIUS  server for
         accounting."
    DEFVAL { 1813 }
    ::= { alxDot1xRadiusServerEntry 9 }

-- ----------------------------------------------------------------------------
--                                     
--  Notifications
--
-- ----------------------------------------------------------------------------


-- ----------------------------------------------------------------------------
-- 
--  Conformance information
--
-- ----------------------------------------------------------------------------
-- --------------------------------------------------------
--
--  The PAE Authenticator Group
--
-- --------------------------------------------------------
alxDot1xAuthConfigGroup  OBJECT-GROUP
    OBJECTS {
             alxDot1xAuthRadiusPlcy  
            }
    STATUS      current
    DESCRIPTION
        "The  group  of  objects supporting management of Radius
        authentication   for  the  IEEE801.1X  PAE  feature  on
        Alcatel 7x50 SR series systems."
    ::= { alxDot1xAuthenticatorGroups 1 }

-- --------------------------------------------------------
-- 
--  The RADIUS Group
-- 
-- --------------------------------------------------------
alxDot1xRadiusPlcyGroup  OBJECT-GROUP
    OBJECTS {
        alxDot1xRadiusPlcySrceAddr,  
        alxDot1xRadiusPlcyAdminState, 
        alxDot1xRadiusPlcyRowStatus, 
        alxDot1xRadiusPlcyRetryAttempts,
        alxDot1xRadiusPlcyTimeout,
        alxDot1xRadiusServerAddress,      
        alxDot1xRadiusServerSecret,       
        alxDot1xRadiusServerAuthPort, 
        alxDot1xRadiusServerAcctPort, 
        alxDot1xRadiusServerOperStatus,   
        alxDot1xRadiusServerRowStatus,    
        alxDot1xRadiusServerType            
        }
    STATUS      current
    DESCRIPTION
        "The  group  of  objects supporting management of Radius
         authentication   for  the  IEEE801.1X  PAE  feature  on
         Alcatel 7x50 SR series systems."
    ::= { alxDot1xRadiusGroups 1 }

-- ----------------------------------------------------------------------------
-- 
--  Conformance information
--
-- ----------------------------------------------------------------------------
-- --------------------------------------------------------
-- 
--  Dot1x related Compliance statements
-- 
-- --------------------------------------------------------
alxDot1xAuthenticatorCompliance  MODULE-COMPLIANCE
    STATUS  current
    DESCRIPTION
            "The  compliance statement for management of Radius
             authentication  for  the  IEEE801.1X PAE feature on
             Alcatel 7x50 SR series systems."
    MODULE  -- this module
        MANDATORY-GROUPS { 
            alxDot1xAuthConfigGroup,
            alxDot1xRadiusPlcyGroup
        }
    ::= { alxDot1xAuthenticatorCompliancs 1 }

END
