ASKEY-SYSTEM-MIB DEFINITIONS ::= BEGIN

IMPORTS
    ifIndex,
    InterfaceIndex             FROM IF-MIB
    MODULE-IDENTITY,
    OBJECT-TYPE,
    IpAddress,
    Unsigned32,
    Counter32,
    TimeTicks                  FROM SNMPv2-SMI
    DisplayString              FROM RFC1213-MIB
    RowStatus,
    TEXTUAL-CONVENTION         FROM SNMPv2-TC
    InetAddress                FROM INET-ADDRESS-MIB
    EnabledStatus              FROM P-BRIDGE-MIB
    ipDslam                    FROM ASKEY-DSLAM-MIB
    SnmpAdminString            FROM SNMP-FRAMEWORK-MIB
    aeAlarmPhysicalIndex       FROM ASKEY-ENTITY-ALARM-MIB
;

askeySystemMib MODULE-IDENTITY
    LAST-UPDATED    "200311260000Z"  -- november 26, 2003
    ORGANIZATION    "ASKEY Inc."
    CONTACT-INFO    "ASKEY Inc.
                    E-mail: cwfu@askey.com.tw"

    DESCRIPTION     "ASKEY ADSL MIB OID defines and documentation."
    ::= { ipDslam 1 }


MacAddress ::= OCTET STRING (SIZE (6))    -- a 6 octet address in
                                          -- the "canonical" order
  -- defined by IEEE 802.1a, i.e., as if it were transmitted least
  -- significant bit first, even though 802.5 (in contrast to other
  -- 802.x protocols) requires MAC addresses to be transmitted most
  -- significant bit first.
  --
  -- 16-bit addresses, if needed, are represented by setting their
  -- upper 4 octets to all 0's, i.e., AAFF would be represented
  -- as 00000000AAFF.


  -- Similarly, all representations of Bridge-Id in this MIB Module
  -- use, as a textual convention (i.e. this convention does not affect
  -- their encoding), the data type:

IPSectionIndex ::= TEXTUAL-CONVENTION
    DISPLAY-HINT "d"
    STATUS  current
    DESCRIPTION
            "A unique value, greater than zero, for denoting an IP section.
            The IP section represents a range of the IP address from some IP to
            another IP."
    SYNTAX  INTEGER (1..10)

VLANList ::= TEXTUAL-CONVENTION
    STATUS  current
    DESCRIPTION
            "Each octet within this value specifies a set of eight
            VLAN IDs, with the first octet specifying VLAN ID 0 through
            7, the second octet specifying VLAN ID 8 through 15, etc.
            Within each octet, the most significant bit represents
            the lowest numbered VLAN ID, and the least significant bit
            represents the highest numbered VLAN ID.  Thus, each VLAN ID
            is represented by a single bit within the value of this object.
            If that bit has a value of '1' then that VLAN is included in
            the set of VLANs; the VLAN is not included if its bit has
            a value of '0'."
    SYNTAX  OCTET STRING


--
-- 1. IP configuration of the system, node, management(out-band) port
--
ipConfig OBJECT IDENTIFIER ::= { askeySystemMib 1 }

nodeIP OBJECT IDENTIFIER ::= { ipConfig 1 }

nodeIPAddr OBJECT-TYPE
    SYNTAX  IpAddress
    MAX-ACCESS  read-write
    STATUS  current
    DESCRIPTION
            "The IP address of node. It applies to the trunk (up-link) port."
    ::= { nodeIP 1 }

nodeIPNetMask OBJECT-TYPE
    SYNTAX  IpAddress
    MAX-ACCESS  read-write
    STATUS  current
    DESCRIPTION
            "The subnet mask associated with the IP address of this node.  The
            value of the mask is an IP address with all the network bits set
            to 1 and all the hosts bits set to 0."
    ::= { nodeIP 2 }

nodeMACAddr OBJECT-TYPE
    SYNTAX  MacAddress
    MAX-ACCESS  read-only
    STATUS  current
    DESCRIPTION
            "The MAC address of the trunk (up-link) port."
    ::= { nodeIP 3 }

gatewayIPAddr OBJECT-TYPE
    SYNTAX  IpAddress
    MAX-ACCESS  read-write
    STATUS  current
    DESCRIPTION
            "The gateway IP address of node.  It applies to the trunk
            (up-link) port."
    ::= { nodeIP 4 }

mgmtIP OBJECT IDENTIFIER ::= { ipConfig 2 }

mgmtIPAddr OBJECT-TYPE
    SYNTAX  IpAddress
    MAX-ACCESS  read-write
    STATUS  current
    DESCRIPTION
            "The IP address of the management (out-band) port."
    ::= { mgmtIP 1 }

mgmtIPNetMask OBJECT-TYPE
    SYNTAX  IpAddress
    MAX-ACCESS  read-write
    STATUS  current
    DESCRIPTION
            "The subnet mask associated with the IP address of the management
            port.  The value of the mask is an IP address with all the network
            bits set to 1 and all the hosts bits set to 0."
    ::= { mgmtIP 2 }

mgmtMACAddr OBJECT-TYPE
    SYNTAX  MacAddress
    MAX-ACCESS  read-only
    STATUS  current
    DESCRIPTION
            "The MAC address of the manaement (out-band) port."
    ::= { mgmtIP 3 }


--
-- 2. Time Setting
--
nodeTime OBJECT IDENTIFIER ::= { askeySystemMib 2 }

time OBJECT-TYPE
    SYNTAX  DisplayString (SIZE(14..19))
    MAX-ACCESS  read-write
    STATUS  current
    DESCRIPTION
            "The time <yyyy-mm-dd hh:mm:ss> of the system."
    ::= { nodeTime 1 }

zone OBJECT-TYPE
    SYNTAX  INTEGER (-12..13)
    MAX-ACCESS  read-write
    STATUS  current
    DESCRIPTION
            "The time zone of the system."
    ::= { nodeTime 2 }


--
-- 6. SNMP Trap
--
snmpTrapMib OBJECT IDENTIFIER ::= { askeySystemMib 6 }

snmpTrapTable OBJECT-TYPE
    SYNTAX  SEQUENCE OF SnmpTrapEntry
    MAX-ACCESS  not-accessible
    STATUS  current
    DESCRIPTION
            "This table contains information for SNMP Trap."
    ::= { snmpTrapMib 1 }

snmpTrapEntry OBJECT-TYPE
    SYNTAX  SnmpTrapEntry
    MAX-ACCESS  not-accessible
    STATUS  current
    DESCRIPTION
            "An entry of parameters in snmpTrap table."
    INDEX { snmpTrapStation }
    ::= { snmpTrapTable 1 }

SnmpTrapEntry ::= SEQUENCE {
    snmpTrapStation         IpAddress,
    snmpTrapCommunity       DisplayString,
    snmpTrapSNMPVersion     INTEGER,
    snmpTrapRowStatus       RowStatus
}

snmpTrapStation OBJECT-TYPE
    SYNTAX  IpAddress
    MAX-ACCESS  not-accessible
    STATUS  current
    DESCRIPTION
            "The IP address of the workstation which the SNMP Trap is sent to."
    ::= { snmpTrapEntry 1 }

snmpTrapCommunity OBJECT-TYPE
    SYNTAX  DisplayString (SIZE(1..20))
    MAX-ACCESS  read-create
    STATUS  current
    DESCRIPTION
            "DURABLE: { 'public','':all }
            The SNMPv1/v2c community name string.  Duplicate community names
            are not allowed in this table.  Note that a null string is not a
            valid community name.  Attempting to set this object to a null
            string or to a duplicate value results in the agent returning a
            'badValue' error for SNMPv1 or 'inconsistentValue' error for
            SNMPv2c/v3."
    ::= { snmpTrapEntry 2 }

snmpTrapSNMPVersion  OBJECT-TYPE
    SYNTAX  INTEGER {
                snmpv1(1),
                snmpv2c(2)
            }
    MAX-ACCESS  read-only
    STATUS  current
    DESCRIPTION
            "This object indicates the version of SNMPv1 or SNMPv2c."
::= { snmpTrapEntry 3 }

snmpTrapRowStatus  OBJECT-TYPE
    SYNTAX  RowStatus
    MAX-ACCESS  read-create
    STATUS  current
    DESCRIPTION
            "This object indicates the status of SNMP trap."
::= { snmpTrapEntry 4}


--
--  7. snmpCommunityMib
--
snmpCommunityMib OBJECT IDENTIFIER ::= { askeySystemMib 7 }

snmpCommunityTable OBJECT-TYPE
    SYNTAX  SEQUENCE OF SnmpCommunityEntry
    MAX-ACCESS not-accessible
    STATUS  current
    DESCRIPTION
            "A table of SNMPv1/v2c community string to SNMPv3 view name
            mappings."
    ::= { snmpCommunityMib 1 }

snmpCommunityEntry OBJECT-TYPE
    SYNTAX  SnmpCommunityEntry
    MAX-ACCESS  not-accessible
    STATUS  current
    DESCRIPTION
            "An entry containing objects about SNMP community at this systemp."
    INDEX {IMPLIED snmpCommunityName }
    ::= { snmpCommunityTable 1 }

SnmpCommunityEntry ::= SEQUENCE {
    snmpCommunityName           DisplayString,
    snmpCommunityPermission     INTEGER,
    snmpCommunityRowStatus      RowStatus
}

snmpCommunityName OBJECT-TYPE
    SYNTAX  DisplayString (SIZE(1..20))
    MAX-ACCESS  not-accessible
    STATUS  current
    DESCRIPTION
            "The SNMPv1/v2c community name string.  Duplicate community names
            are not allowed in this table.  Note that a null string is not a
            valid community name.  Attempting to set this object to a null
            string or to a duplicate value results in the agent returning a
            'badValue' error for SNMPv1 or 'inconsistentValue' error for
            SNMPv2c/v3."
    ::= { snmpCommunityEntry 1 }

snmpCommunityPermission OBJECT-TYPE
    SYNTAX  INTEGER {
                readOnly(1),
                readWrite(2)
            }
    MAX-ACCESS  read-create
    STATUS  current
    DESCRIPTION
            "This object specifies the type of access allowed. 'readOnly(1)'
            allows GET operations (i.e., GET, GET-NEXT, GET-BULK) and
            'readWrite(2)' allows both GET and SET operations."
    DEFVAL { readWrite }
    ::= { snmpCommunityEntry 2 }

snmpCommunityRowStatus OBJECT-TYPE
    SYNTAX  RowStatus
    MAX-ACCESS  read-create
    STATUS  current
    DESCRIPTION
            "This object indicates the status of this entry.  A row in this
            table can be created using the 'createAndGo(4)' (if all objects
            without default values are supplied with valid values in a single
            SNMP PDU) or the 'createAndWait(5)' action states.  Until all
            parameters are valid for a conceptual row, this object is
            'notReady(3)'.  All parameters must be valid before this object
            can be set to 'active(1)'.

            Any object in a conceptual row can be modified independent of the
            value of this object (that is, can be changed while 'active(1)',
            notInService(2) or 'notReady(3)')."
    ::= { snmpCommunityEntry 3 }


--
-- 9. Forwarding Table MIB, by port and get table from hardware
--
askeyDslamFdbTable OBJECT-TYPE
    SYNTAX  SEQUENCE OF AskeyDslamFdbEntry
    MAX-ACCESS  not-accessible
    STATUS  current
    DESCRIPTION
            "A table that contains information about unicast entries for which
            the IP-DSLAM has forwarding and/or filtering information.  This
            information is used by the transparent bridging function in
            determining how to propagate a received frame."
    ::= { askeySystemMib 9 }

askeyDslamFdbEntry OBJECT-TYPE
    SYNTAX AskeyDslamFdbEntry
    MAX-ACCESS  not-accessible
    STATUS  current
    DESCRIPTION
            "Information about a specific unicast MAC address on a specific
            line for which the IP-DSLAM has some forwarding and/or filtering
            information."
    INDEX { ifIndex, fdbMacIndex }
    ::= { askeyDslamFdbTable 1 }

AskeyDslamFdbEntry ::= SEQUENCE {
    fdbMacIndex             INTEGER,
    fdbVpi                  INTEGER,
    fdbVci                  INTEGER,
    macAddress              MacAddress,
    askeyDslamFdbStatus     INTEGER
}

fdbMacIndex OBJECT-TYPE
    SYNTAX  INTEGER (1..8)
    MAX-ACCESS  read-only
    STATUS  current
    DESCRIPTION
            "A simple index into 'askeyDslamFdbTable'."
    ::= { askeyDslamFdbEntry 1 }

fdbVpi OBJECT-TYPE
    SYNTAX  INTEGER (0..255)
    MAX-ACCESS  read-only
    STATUS  current
    DESCRIPTION
            "The VPI value of the VCL. The maximum VPI value cannot exceed the
            value allowable by the atmInterfaceMaxVpiBits."
    ::= {askeyDslamFdbEntry 2}

fdbVci OBJECT-TYPE
    SYNTAX  INTEGER (0..65535)
    MAX-ACCESS  read-only
    STATUS  current
    DESCRIPTION
            "The VCI value of the VCL. The maximum VCI value cannot exceed the
            value allowable by the atmInterfaceMaxVciBits."
    ::= {askeyDslamFdbEntry 3}

macAddress OBJECT-TYPE
    SYNTAX  MacAddress
    MAX-ACCESS  read-only
    STATUS  current
    DESCRIPTION
            "A unicast MAC address for which the bridge has forwarding and/or
            filtering information."
    ::= { askeyDslamFdbEntry 4 }

askeyDslamFdbStatus OBJECT-TYPE
    SYNTAX  INTEGER {
                learned-unique(1),
                learned-spoofed-active(2),
                learned-spoofed-inactive(3),
                mgmt-forbid(4),
                mgmt-permit(5),
                learned-routed(6)
            }
    MAX-ACCESS  read-only
    STATUS  current
    DESCRIPTION
            "The status of this entry.  The meanings of the values are:
            learned_unique(1): the value of the corresponding instance of
                               macAddress was learned, and is being used.
                               It indicates that the macAddress is an unique
                               one and there is no duplicated (spoofed) one
                               detected in the IP-DSLAM.
            learned_spoofed_active(2) : the value of the corresponding instance
                               of macAddress was learned, and is being used.
                               It indicates that there is an duplicated
                               (spoofed) one detected in theIP-DSLAM.
            learned_spoofed_inactive(3) : the value of the corresponding
                               instance of macAddress was learned, and is NOT
                               being used.  It indicates that there is an
                               duplicated(spoofed) one detected in the IP-DSLAM.
            mgmt_forbid(4): the value of the corresponding instance of
                               macAddress was set by the operator.  It
                               indicates that an Ethernet frame of
                               srcMac='macAddress' is to be dropped by the
                               IP-DSLAM.
            mgmt_permit(5): the value of the corresponding instance of
                               macAddress was set by the operator.  It
                               indicates that an Ethernet frame of
                               srcMac='macAddress' is to be forwarded by the
                               IP-DSLAM.
            learned_routed(6): the value of the corresponding instance of
                               macAddress was learned, and is being used.  It
                               indicates that the macAddress is added by the
                               IP-DSLAM."
    ::= { askeyDslamFdbEntry 5 }


--
-- 10. Configuration Data MIB
--
configDataMib OBJECT-TYPE
    SYNTAX  INTEGER {
                save(1),
                restore(2)
            }
    MAX-ACCESS  read-write
    STATUS  current
    DESCRIPTION
            "save(1): save the current configuration data to NVRAM(flash) as
                      the main configuration data.
            restore(2): replace the main configuration data with the backup
                      configuration data."
    ::= { askeySystemMib 10 }


--
-- 11. Card information table
--
askeyCardInfoTable OBJECT-TYPE
    SYNTAX  SEQUENCE OF AskeyCardInfoEntry
    MAX-ACCESS  not-accessible
    STATUS  current
    DESCRIPTION
            "This table is information about card/slot on ASKEY IPDSLAM."
    ::= { askeySystemMib 11 }

askeyCardInfoEntry OBJECT-TYPE
    SYNTAX  AskeyCardInfoEntry
    MAX-ACCESS  not-accessible
    STATUS  current
    DESCRIPTION
            "An entry about information of the card/slot."
    INDEX { aeAlarmPhysicalIndex }
    ::= { askeyCardInfoTable 1 }

AskeyCardInfoEntry ::= SEQUENCE {
    askeyCardPlannedType                INTEGER,
    askeyCardType                       INTEGER,
    askeyCardHWVersion                  DisplayString,
    askeyCardSWVersion                  DisplayString,
    askeyCardImage                      DisplayString,
    askeyCardUptime                     INTEGER,
    askeyCardRole                       INTEGER,
    askeyCardSerialNumber               DisplayString,
    askeyCardAdminStatus                INTEGER,
    askeyCardOperStatus                 INTEGER,
    lineCardAdminVlanTagPassEnabled     INTEGER,
    lineCardOperVlanTagPassEnabled      INTEGER,
    lineCardAdminRfc2684Encap           INTEGER,
    lineCardOperRfc2684Encap            INTEGER,
    lineCardServiceTypeControl          INTEGER,
    shdslFirmwareUpgrade                INTEGER,
    shdslFirmwareUpgradeState           INTEGER,
    taggedModeAdminStatus               INTEGER,
    taggedModeOperStatus                INTEGER
}

askeyCardPlannedType OBJECT-TYPE
    SYNTAX  INTEGER
    MAX-ACCESS  read-write
    STATUS  current
    DESCRIPTION
            "Supposed type of this card."
    ::= { askeyCardInfoEntry 1 }

askeyCardType OBJECT-TYPE
    SYNTAX  INTEGER
    MAX-ACCESS  read-only
    STATUS  current
    DESCRIPTION
            "Current working type of this card."
    ::= { askeyCardInfoEntry 2 }

askeyCardHWVersion OBJECT-TYPE
    SYNTAX  DisplayString (SIZE(1..20))
    MAX-ACCESS  read-only
    STATUS  current
    DESCRIPTION
            "The Hardware version of this card."
    ::= { askeyCardInfoEntry 3 }

askeyCardSWVersion OBJECT-TYPE
    SYNTAX  DisplayString (SIZE(1..20))
    MAX-ACCESS  read-only
    STATUS  current
    DESCRIPTION
            "The Software version of this card."
    ::= { askeyCardInfoEntry 4 }

askeyCardImage OBJECT-TYPE
    SYNTAX  DisplayString (SIZE(1..20))
    MAX-ACCESS  read-only
    STATUS  current
    DESCRIPTION
            "Description for the location of the image."
    ::= { askeyCardInfoEntry 5 }

askeyCardUptime OBJECT-TYPE
    SYNTAX  INTEGER
    MAX-ACCESS  read-only
    STATUS  current
    DESCRIPTION
            "The uptime (in seconds) of this card."
    ::= { askeyCardInfoEntry 6 }

askeyCardRole OBJECT-TYPE
    SYNTAX  INTEGER {
                active(1),
                standby(2)
            }
    MAX-ACCESS  read-only
    STATUS  current
    DESCRIPTION
            "This object descibes the card role."
    ::= { askeyCardInfoEntry 7 }

askeyCardSerialNumber OBJECT-TYPE
    SYNTAX  DisplayString (SIZE(1..40))
    MAX-ACCESS  read-only
    STATUS  current
    DESCRIPTION
            "The card serial number which is an unique number."
    ::= { askeyCardInfoEntry 8 }

askeyCardAdminStatus OBJECT-TYPE
    SYNTAX  INTEGER {
                reset(1)
            }
    MAX-ACCESS  read-write
    STATUS  current
    DESCRIPTION
            "The operation of this card.  Only value is 'reset(1)' will reset
            this card."
    ::= { askeyCardInfoEntry 9 }

askeyCardOperStatus OBJECT-TYPE
    SYNTAX  INTEGER {
                operational(1),
                notOperational(2),
                notPresent(3)
            }
    MAX-ACCESS  read-only
    STATUS  current
    DESCRIPTION
            "This object indicates the card's operational status.  The
            notPresent(3) status indicates the card is physically removed
            (note this may or may not be possible depending on the type of
            card.)  The operational(1) status indicates that the card is
            enabled (see rptrPortAdminStatus) and working, even though it might
            be auto-partitioned (see rptrPortAutoPartitionState).

            If this object has the value operational(1) and cwmAdminStatus is
            set to disabled(2), it is expected that this object's value will
            soon change to notOperational(2)."
    ::= { askeyCardInfoEntry 10 }

lineCardAdminVlanTagPassEnabled  OBJECT-TYPE
    SYNTAX INTEGER {
                enabled(1),
                disabled(2)
            }
    MAX-ACCESS read-write
    STATUS current
    DESCRIPTION
            "Enable(1) or disable VLAN tag pass through function."
    DEFVAL { disabled }
    ::= { askeyCardInfoEntry 11 }

lineCardOperVlanTagPassEnabled  OBJECT-TYPE
    SYNTAX  INTEGER {
                unknown(0),
                enabled(1),
                disabled(2)
            }
    MAX-ACCESS  read-only
    STATUS  current
    DESCRIPTION
            "Current status of VLAN tag passes through funtion."
    ::= { askeyCardInfoEntry 12 }

lineCardAdminRfc2684Encap  OBJECT-TYPE
    SYNTAX  INTEGER {
                unknown(0),
                llc(1),
                vcMux(2)
            }
    MAX-ACCESS  read-write
    STATUS  current
    DESCRIPTION
            "Setting this object to LLC (1) to encapsulate the packet to
            LLC style.  Setting it to vcMux (2) to encapsulate the packet to
            VC-MUX style."
    DEFVAL { llc }
    ::= { askeyCardInfoEntry 13}

lineCardOperRfc2684Encap  OBJECT-TYPE
    SYNTAX  INTEGER {
                unknown(0),
                llc(1),
                vcMux(2)
            }
    MAX-ACCESS  read-only
    STATUS  current
    DESCRIPTION
            "Current applied rfc2684 encapsulation method."
    ::= { askeyCardInfoEntry 14}

lineCardServiceTypeControl  OBJECT-TYPE
    SYNTAX  INTEGER {
                unknown(0),
                enabled(1),
                disabled(2)
            }
    MAX-ACCESS  read-write
    STATUS  current
    DESCRIPTION
            "Set or get applied control of service type."
    ::= { askeyCardInfoEntry 15}

shdslFirmwareUpgrade  OBJECT-TYPE
    SYNTAX  INTEGER {
                upgrade(0)
            }
    MAX-ACCESS  read-write
    STATUS  current
    DESCRIPTION
            "Upgrade SHDSL line card firmware."
    ::= { askeyCardInfoEntry 16}

shdslFirmwareUpgradeState  OBJECT-TYPE
    SYNTAX  INTEGER {
                unknown(0),
                inital(1),
                transmission(2),
                burning(3),
                finished(4),
                failedToBurn(5),
                driverError(6),
                noFirmwareImage(7),
                failedToTransmitImage(8)
            }
    MAX-ACCESS  read-only
    STATUS  current
    DESCRIPTION
            "SHDSL line card firmware pgrade state."
    ::= { askeyCardInfoEntry 17}

-- for D-Link tagged/untagged mode
taggedModeAdminStatus  OBJECT-TYPE
    SYNTAX  INTEGER {
                tagged-only(1),
                untagged-only(2)
            }
    MAX-ACCESS  read-write
    STATUS  current
    DESCRIPTION
            "Card administrative tagged mode. This entry indicates tagged mode
            configured on the specific card."
    ::= { askeyCardInfoEntry 18}

taggedModeOperStatus  OBJECT-TYPE
    SYNTAX  INTEGER {
                tagged-only(1),
                untagged-only(2)
            }
    MAX-ACCESS  read-only
    STATUS  current
    DESCRIPTION
            "Card operational tagged mode. This entry indicates tagged mode
            running on the specific card. All ports of the tagged type card will
            drop packets that don't have tagged header. And all ports of
            untagged type card will drop packets that have tagged header.
            Do nothing for 'noAction' case."
    ::= { askeyCardInfoEntry 19}

--
-- 12. Line Port Information MIB
--

linePortInfo OBJECT IDENTIFIER ::= { askeySystemMib 12 }

linePortInfoTable OBJECT-TYPE
    SYNTAX  SEQUENCE OF LinePortInfoEntry
    MAX-ACCESS  not-accessible
    STATUS  current
    DESCRIPTION
            "A list of line port information entries."
    ::= { linePortInfo 1 }

linePortInfoEntry OBJECT-TYPE
    SYNTAX  LinePortInfoEntry
    MAX-ACCESS  not-accessible
    STATUS  current
    DESCRIPTION
            "An information entry containing objects for each line port."
    INDEX  { ifIndex }
    ::= { linePortInfoTable 1 }

LinePortInfoEntry ::= SEQUENCE {
--  portId                  INTEGER,
    linePortAdminStatus     INTEGER,
    linePortOperStatus      INTEGER,
    circuitID               SnmpAdminString,
    remoteID                SnmpAdminString
}

--portId OBJECT-TYPE
--    SYNTAX  INTEGER
--    MAX-ACCESS  read-only
--    STATUS  current
--    DESCRIPTION
--            "The identity of this port.
--              11~490: ethernet port
--              1~4: giga port !!!
--              "
--    ::= { portInfoEntry 1 }

linePortAdminStatus OBJECT-TYPE
    SYNTAX  INTEGER {
                enable(1),
                disable(2),
                testing(3),
                reset(4)
            }
    MAX-ACCESS  read-write
    STATUS  current
    DESCRIPTION
            "The desired state of the line port.  The enable(1) state ready
            to pass packets. The disable(2) state stop passing any packets.
            The testing(3) state indicates that no operational packets can be
            passed, it is for debug only.  Finally, reset(4) state will reset
            this line port."
    ::= { linePortInfoEntry 1 }

linePortOperStatus OBJECT-TYPE
    SYNTAX  INTEGER {
                operational(1),
                notOperational(2),
                notPresent(3)
            }
    MAX-ACCESS  read-only
    STATUS  current
    DESCRIPTION
            "This object indicates the line port's operational status.  The
            notPresent(3) status indicates the line port is physically removed
            (note this may or may not be possible depending on the type of
            port).  The operational(1) status indicates that the port is
            enabled (see rptrPortAdminStatus) and working, even though it might
            be auto-partitioned (see rptrPortAutoPartitionState).  If this
            object has the value operational(1) and rptrPortAdminStatus is set
            to disabled(2), it is expected that this object's value will soon
            change to notOperational(2)."
    ::= { linePortInfoEntry 2 }

circuitID OBJECT-TYPE
    SYNTAX  SnmpAdminString
    MAX-ACCESS  read-only
    STATUS  current
    DESCRIPTION
            "The identity for this circuit.  The value is 'shelf.slot.port'."
    ::= { linePortInfoEntry 3 }

remoteID OBJECT-TYPE
    SYNTAX  SnmpAdminString (SIZE (0..63))
    MAX-ACCESS  read-write
    STATUS  current
    DESCRIPTION
            "The string is sent transparently to authorization service."
    ::= { linePortInfoEntry 4 }

--wanPortInfoTable OBJECT-TYPE
--    SYNTAX  SEQUENCE OF WanPortInfoEntry
--    MAX-ACCESS  not-accessible
--    STATUS  current
--    DESCRIPTION
--            "A table that contains information about unicast
--            entries for which the bridge has forwarding and/or
--            filtering information.  This information is used
--            by the transparent bridging function in
--            determining how to propagate a received frame."
--    ::= { portInfo 1 }
--
--wanPortInfoEntry OBJECT-TYPE
--    SYNTAX  WanPortInfoEntry
--    MAX-ACCESS  not-accessible
--    STATUS  current
--    DESCRIPTION
--            "Information about a specific forwarding table ID which the bridge
--            has some forwarding and/or filtering information."
--    INDEX   { wanPortId }
--    ::= { wanPortInfoTable 1 }
--
--WanPortInfoEntry ::=
--    SEQUENCE {
--        wanPortId           INTEGER,
--        wanPortAdminStatus          INTEGER,
--        wanPortOperStatus        INTEGER
--    }
--
--wanPortId OBJECT-TYPE
--    SYNTAX  INTEGER
--    MAX-ACCESS  read-only
--    STATUS  current
--    DESCRIPTION
--            "The identity of this port."
--    ::= { wanPortInfoEntry 1 }
--
--wanPortAdminStatus OBJECT-TYPE
--    SYNTAX  INTEGER {
--         enable(1),
--         disable(2),
--         testing(3)
--    }
--    MAX-ACCESS  read-write
--    STATUS  current
--    DESCRIPTION
--            "The operation of this line card.
--             enable: enable this card.
--             disable: disable this card.
--             reset: reset this card"
--    ::= { wanPortInfoEntry 2 }
--
--wanPortOperStatus OBJECT-TYPE
--    SYNTAX  INTEGER {
--       operational(1),
--       notOperational(2),
--       notPresent(3)
--    }
--    MAX-ACCESS  read-only
--    STATUS  current
--    DESCRIPTION
--         "This object indicates the port's operational
--         status.  The notPresent(3) status indicates the
--         port is physically removed (note this may or may
--         not be possible depending on the type of port.)
--         The operational(1) status indicates that the port
--         is enabled (see rptrPortAdminStatus) and working,
--         even though it might be auto-partitioned (see
--         rptrPortAutoPartitionState).
--
--         If this object has the value operational(1) and
--         rptrPortAdminStatus is set to disabled(2), it is
--         expected that this object's value will soon change
--         to notOperational(2)."
--    ::= { wanPortInfoEntry 3 }
--
--linePortInfoTable OBJECT-TYPE
--    SYNTAX  SEQUENCE OF LinePortInfoEntry
--    MAX-ACCESS  not-accessible
--    STATUS  current
--    DESCRIPTION
--            "A table that contains information about unicast
--            entries for which the bridge has forwarding and/or
--            filtering information.  This information is used
--            by the transparent bridging function in
--            determining how to propagate a received frame."
--    ::= { portInfo 2 }
--
--linePortInfoEntry OBJECT-TYPE
--    SYNTAX  LinePortInfoEntry
--    MAX-ACCESS  not-accessible
--    STATUS  current
--    DESCRIPTION
--            "Information about a specific forwarding table ID which the bridge
--            has some forwarding and/or filtering information."
--    INDEX   { linePortId }
--    ::= { linePortInfoTable 1 }
--
--LinePortInfoEntry ::=
--    SEQUENCE {
--        linePortId           INTEGER,
--        linePorOper          INTEGER,
--        linePorStatus        INTEGER
--    }
--
--linePortId OBJECT-TYPE
--    SYNTAX  INTEGER
--    MAX-ACCESS  read-only
--    STATUS  current
--    DESCRIPTION
--            "The identity of this port."
--    ::= { linePortInfoEntry 1 }
--
--linePorOper OBJECT-TYPE
--    SYNTAX  INTEGER {
--         enable(1),
--         disable(2)
--    }
--    MAX-ACCESS  read-write
--    STATUS  current
--    DESCRIPTION
--            "The operation of this line card.
--             enable: enable this card.
--             disable: disable this card.
--             reset: reset this card"
--    ::= { linePortInfoEntry 2 }
--
--linePorStatus OBJECT-TYPE
--    SYNTAX  INTEGER {
--       unknown(0),
--       running(1),
--       warning(2),
--       testing(3),
--       down(4)
--    }
--    MAX-ACCESS  read-only
--    STATUS  current
--    DESCRIPTION
--        "The current operational state of the device
--        described by this row of the table.  A value
--        unknown(0) indicates that the current state of the
--        device is unknown.  running(1) indicates that the
--        device is up and running and that no unusual error
--        conditions are known.  The warning(2) state
--        indicates that agent has been informed of an
--        unusual error condition by the operational software
--        (e.g., a disk device driver) but that the device is
--        still 'operational'.  An example would be high
--        number of soft errors on a disk.  A value of
--        testing(3), indicates that the device is not
--        available for use because it is in the testing
--        state.  The state of down(4) is used only when the
--        agent has been informed that the device is not
--        available for any use."
--    ::= { linePortInfoEntry 3 }


--
-- 13. MAC againg
--
dot1TpMACAging OBJECT-TYPE
    SYNTAX  INTEGER {
                aged(1),
                nonaged(2)
            }
    MAX-ACCESS  read-write
    STATUS  current
    DESCRIPTION
            "This object decides MAC enrties aged out or not.
            aged: MAC entries will be aged out
            nonaged: MAC entries will never be aged out"
    ::= { askeySystemMib 13 }


--
-- 14. reboot system
--
askeyRebootSystemAction OBJECT-TYPE
    SYNTAX  INTEGER {
                reboot(1)
            }
    MAX-ACCESS  read-write
    STATUS  current
    DESCRIPTION
            "Reboot the system."
    ::= { askeySystemMib 14 }


-- -------------------------------------------------------------
-- 14. Remote Upload/Download
-- -------------------------------------------------------------
--      remoteTXRX      OBJECT IDENTIFIER ::= { askeySystemMib 14 }
--
--      tftpTransType OBJECT-TYPE
--         SYNTAX      INTEGER {
--               systemImageDownload(1),
--               firmwareDownload(2),
--               configDataUpload(3),
--               configDataDownload(4)
--         }
--         MAX-ACCESS  read-write
--         STATUS      current
--         DESCRIPTION
--                 "systemImageDownload(1): Download System Image File from Remote TFTP Server
--                  firmwareDownload(2): Download Firmware from Remote TFTP Server
--                  configDataUpload(3): Upload Configuration Data File to Remote TFTP Server
--                  configDataDownload(4): Download Configuration Data File from Remote TFTP Server"
--         ::= { remoteTXRX 1 }
--
--      tftpServerIPAddr OBJECT-TYPE
--         SYNTAX      IpAddress
--         MAX-ACCESS  read-write
--         STATUS      current
--         DESCRIPTION
--                 "The IP address of TFTP server"
--         ::= { remoteTXRX 2 }
--
--      ftpUserName OBJECT-TYPE
--         SYNTAX      DisplayString (SIZE(1..15))
--         MAX-ACCESS  read-write
--         STATUS      current
--         DESCRIPTION
--                 "FTP user name"
--         ::= { remoteTXRX 3 }
--
--      ftpPassword OBJECT-TYPE
--         SYNTAX      DisplayString (SIZE(1..15))
--       MAX-ACCESS  read-write
--       STATUS      current
--       DESCRIPTION
--               "FTP password"
--       ::= { remoteTXRX 4 }
--
--    tftpFileName OBJECT-TYPE
--       SYNTAX      DisplayString (SIZE(1..32))
--       MAX-ACCESS  read-write
--       STATUS      current
--       DESCRIPTION
--               "The name of the file that will be transferred."
--       ::= { remoteTXRX 5 }
--
--    tftpStatus OBJECT-TYPE
--       SYNTAX      DisplayString (SIZE(1..32))
--       MAX-ACCESS  read-only
--       STATUS      current
--         DESCRIPTION
--                 "Not Started: The action doesn't start yet
--                  Tranferring: The action is running
--                  Done: The action is completed
--                  Error: The actin failed"
--         ::= { remoteTXRX 6 }


--
-- 15. ATM OAM F4/F5 Loopback cell
--
askeyDslamOam OBJECT IDENTIFIER ::= { askeySystemMib 15 }

oamF5 OBJECT IDENTIFIER ::= { askeyDslamOam 1 }

oamF5IfIndex OBJECT-TYPE
    SYNTAX  INTEGER
    MAX-ACCESS  read-write
    STATUS  current
    DESCRIPTION
            "The ifIndex of the line."
    ::= {oamF5 1}

oamF5Vpi OBJECT-TYPE
    SYNTAX  INTEGER (0..255)
    MAX-ACCESS  read-write
    STATUS  current
    DESCRIPTION
            "The VPI value of the VCL.  The maximum VPI value cannot exceed the
            value allowable by the atmInterfaceMaxVpiBits."
    ::= {oamF5 2}

oamF5Vci OBJECT-TYPE
    SYNTAX  INTEGER (0..65535)
    MAX-ACCESS  read-write
    STATUS  current
    DESCRIPTION
            "The VCI value of the VCL.  The maximum VCI value cannot exceed the
            value allowable by the atmInterfaceMaxVciBits."
    ::= {oamF5 3}

oamF5Scope OBJECT-TYPE
    SYNTAX  INTEGER {
                end-to-end(1),
                segment-to-segment(2),
                both-end2end-segment2segment(3)
            }
    MAX-ACCESS  read-write
    STATUS  current
    DESCRIPTION
            "The scope of the OAM F5 loopback cell.  Set this object will
            trigger OAM processing."
    ::= { oamF5 4 }


--
-- 16. EMS VLAN ID
--
askeySystemManagementInfo OBJECT IDENTIFIER ::= { askeySystemMib 16 }

askeyEmsVlanId OBJECT-TYPE
    SYNTAX  INTEGER (1..4094)
    MAX-ACCESS  read-write
    STATUS  current
    DESCRIPTION
            "In-band management VLAN ID."
    ::= { askeySystemManagementInfo 1 }

askeyBootDevice OBJECT IDENTIFIER ::= { askeySystemManagementInfo 2 }

askeyNextBootDevice OBJECT-TYPE
    SYNTAX  INTEGER {
                opCodeA(1),
                opCodeB(2)
            }
    MAX-ACCESS  read-write
    STATUS  current
    DESCRIPTION
            "Configure the next boot partition."
    ::= { askeyBootDevice 1 }

askeyCurrentBootDevice OBJECT-TYPE
    SYNTAX  INTEGER {
                network(0),
                opCodeA(1),
                opCodeB(2)
            }
    MAX-ACCESS  read-only
    STATUS  current
    DESCRIPTION
            "Show current the boot partition."
    ::= { askeyBootDevice 2 }

askeySystemManagementIgmp OBJECT-TYPE
    SYNTAX  INTEGER {
                enableIgmpsnoop(1),
                enableIgmpproxy(2),
                disableIgmp(3)
            }
    MAX-ACCESS  read-write
    STATUS  current
    DESCRIPTION
            "Configure the IGMP proxy and IGMP snoop."
    ::= { askeySystemManagementInfo 3 }

askeyRedundancy OBJECT IDENTIFIER ::= { askeySystemManagementInfo 4 }

askeyRedundancyAutoSyncEnabled OBJECT-TYPE
    SYNTAX  INTEGER {
                enabled(1),
                disabled(2)
            }
    MAX-ACCESS  read-write
    STATUS  current
    DESCRIPTION
            "The Askey IPDSLAM can auto synchronize standby NC configuration
             with active NC.  This object enables or disables such
             synchronization."
    ::= { askeyRedundancy 1 }

askeyRedundancyAutoSyncPeriod OBJECT-TYPE
    SYNTAX  INTEGER (30..3600)
    MAX-ACCESS  read-write
    STATUS  current
    DESCRIPTION
            "Auto synchronization period.  The value unit is in second."
    ::= { askeyRedundancy 2 }

askeyRedundancySync OBJECT-TYPE
    SYNTAX  INTEGER {
                syncNow(1)
            }
    MAX-ACCESS  read-write
    STATUS  current
    DESCRIPTION
            "Synchronize redundancy immediately."
    ::= { askeyRedundancy 3 }


askeySystemManagementInfoVlan  OBJECT IDENTIFIER ::= { askeySystemManagementInfo 5 }

askeySystemManagementInfoVlanMacLimitTable OBJECT-TYPE
    SYNTAX  SEQUENCE OF AskeySystemManagementInfoVlanMacLimitEntry
    MAX-ACCESS  not-accessible
    STATUS  current
    DESCRIPTION
            "A table that contains information about the MAC limit per VLAN ID."
    ::= { askeySystemManagementInfoVlan 1}

askeySystemManagementInfoVlanMacLimitEntry OBJECT-TYPE
    SYNTAX  AskeySystemManagementInfoVlanMacLimitEntry
    MAX-ACCESS  not-accessible
    STATUS  current
    DESCRIPTION
            "Information about the MAC limit per VLAN."
    INDEX { askeySystemManagementInfoVlanID }
    ::= { askeySystemManagementInfoVlanMacLimitTable 1 }

AskeySystemManagementInfoVlanMacLimitEntry ::= SEQUENCE {
    askeySystemManagementInfoVlanID                 INTEGER,
    askeySystemManagementInfoVlanMacLimit           INTEGER,
    askeySystemManagementInfoVlanMacLimitEnabled    INTEGER
}

askeySystemManagementInfoVlanID OBJECT-TYPE
    SYNTAX  INTEGER (1..4094)
    MAX-ACCESS  not-accessible
    STATUS  current
    DESCRIPTION
            "The ID of target VLAN which MAC limits."
    ::= { askeySystemManagementInfoVlanMacLimitEntry 1 }

askeySystemManagementInfoVlanMacLimit OBJECT-TYPE
    SYNTAX  INTEGER (5..50000)
    MAX-ACCESS  read-write
    STATUS  current
    DESCRIPTION
            "MAC limit on specific VLAN.  Default values are 5376 for AM0021
             and 1568 for AM0031."
    ::= { askeySystemManagementInfoVlanMacLimitEntry 2 }

askeySystemManagementInfoVlanMacLimitEnabled OBJECT-TYPE
    SYNTAX  INTEGER {
                unknown(0),
                enabled(1),
                disabled(2)
            }
    MAX-ACCESS  read-write
    STATUS  current
    DESCRIPTION
            "Enable or disable MAC limit."
    ::= { askeySystemManagementInfoVlanMacLimitEntry 3 }


--     askeySystemManagementInfoVlanMappingTable OBJECT-TYPE
--        SYNTAX  SEQUENCE OF AskeySystemManagementInfoVlanMappingEntry
--        MAX-ACCESS  not-accessible
--        STATUS  current
--        DESCRIPTION
--                "A table that contains information about cos queues
--                mapping with 802.1p."
--        ::= { askeySystemManagementInfoVlan 3}

--    askeyRstpAdminStatus  OBJECT-TYPE
--        SYNTAX INTEGER {
--               enable(1),
--               disable(2)
--          }
--        MAX-ACCESS read-write
--        STATUS current
--        DESCRIPTION
--            "Setting this object to enable (1) enables RSTP Protocol.  Setting
--             it to disable (2) disables RSTP Protocol."
--        ::= { askeySystemMib 17 }


--
-- 18. COS queue
--
askeyCosQueue OBJECT IDENTIFIER ::= { askeySystemMib 18 }

askeyCosQueueMappingTable OBJECT-TYPE
    SYNTAX  SEQUENCE OF AskeyCosQueueMappingEntry
    MAX-ACCESS  not-accessible
    STATUS  current
    DESCRIPTION
            "A table that contains information about COS queues mapping with
            802.1p."
    ::= { askeyCosQueue 1 }

askeyCosQueueMappingEntry OBJECT-TYPE
    SYNTAX  AskeyCosQueueMappingEntry
    MAX-ACCESS  not-accessible
    STATUS  current
    DESCRIPTION
            "Information about COS queue mapping."
    INDEX { askeyCosQueueMapping8021p }
    ::= { askeyCosQueueMappingTable 1 }

AskeyCosQueueMappingEntry ::= SEQUENCE {
    askeyCosQueueMapping8021p       INTEGER,
    askeyCosQueueIndex              INTEGER
}

askeyCosQueueMapping8021p OBJECT-TYPE
    SYNTAX  INTEGER (0..7)
    MAX-ACCESS  read-only
    STATUS  current
    DESCRIPTION
            "The identity of the specific 802.1p priority mapping."
    ::= { askeyCosQueueMappingEntry 1 }

askeyCosQueueIndex OBJECT-TYPE
    SYNTAX  INTEGER (1..8)
    MAX-ACCESS  read-write
    STATUS  current
    DESCRIPTION
            "The index of COS queue."
    ::= { askeyCosQueueMappingEntry 2 }


--
-- 19. User account table
--
askeySystemUserAccountTable OBJECT-TYPE
    SYNTAX  SEQUENCE OF AskeySystemUserAccountEntry
    MAX-ACCESS  not-accessible
    STATUS  current
    DESCRIPTION
             "This table contains information of system user account.  One
             entry in this table reflects a user information."
    ::= { askeySystemMib 19}

askeySystemUserAccountEntry OBJECT-TYPE
    SYNTAX  AskeySystemUserAccountEntry
    MAX-ACCESS  not-accessible
    STATUS  current
    DESCRIPTION
            "An entry reflects a user information."
    INDEX { askeySystemUserAccountUserName }
    ::= { askeySystemUserAccountTable 1 }

AskeySystemUserAccountEntry ::= SEQUENCE {
    askeySystemUserAccountUserName      SnmpAdminString,
    askeySystemUserAccountPassword      SnmpAdminString,
    askeySystemUserAccountGroup         INTEGER,
    askeySystemUserAccountRowStatus     RowStatus
}

askeySystemUserAccountUserName OBJECT-TYPE
    SYNTAX  SnmpAdminString (SIZE (1..16))
    MAX-ACCESS  read-create
    STATUS  current
    DESCRIPTION
            "The name of account user."
    ::= { askeySystemUserAccountEntry 1 }

askeySystemUserAccountPassword  OBJECT-TYPE
    SYNTAX  SnmpAdminString (SIZE (1..16))
    MAX-ACCESS  read-create
    STATUS  current
    DESCRIPTION
            "The password of account user."
  ::= { askeySystemUserAccountEntry 2 }

askeySystemUserAccountGroup OBJECT-TYPE
    SYNTAX  INTEGER {
                guest(1),
                admin(2)
            }
    MAX-ACCESS  read-create
    STATUS  current
    DESCRIPTION
            "The group which account belongs to."
    ::= { askeySystemUserAccountEntry 3 }

askeySystemUserAccountRowStatus OBJECT-TYPE
    SYNTAX  RowStatus
    MAX-ACCESS  read-create
    STATUS  current
    DESCRIPTION
            "This object controls creation/deletion of the associated
            entry in this table as per the semantics of RowStatus."
    ::= { askeySystemUserAccountEntry 4 }


--
-- 20. the ASKEY PPPoE enty
--

askeyPPPoE OBJECT IDENTIFIER ::= { askeySystemMib 20 }

suboption OBJECT-TYPE
    SYNTAX  INTEGER {
                enabled(1),
                disabled(2)
            }
    MAX-ACCESS  read-write
    STATUS  current
    DESCRIPTION
            "Enable or disable PPPoE suboption.  The circuit information
            recorded on 'linePortInfo' table will be transferred to
            authorization service, for example, a radius server, if this
            function enabled."
    ::= { askeyPPPoE 1 }

--
-- DNS service
--

dnsService OBJECT IDENTIFIER ::= { askeySystemMib 21 }

dnsServer1IPAddress OBJECT-TYPE
    SYNTAX  IpAddress
    MAX-ACCESS  read-write
    STATUS  current
    DESCRIPTION
            "The IP address of DNS server.  This server is used first priority."
    ::= { dnsService 1 }

dnsServer2IPAddress OBJECT-TYPE
    SYNTAX  IpAddress
    MAX-ACCESS  read-write
    STATUS  current
    DESCRIPTION
            "The IP address of DNS server.  This server is used second
            priority."
    ::= { dnsService 2 }

dnsServer3IPAddress OBJECT-TYPE
    SYNTAX  IpAddress
    MAX-ACCESS  read-write
    STATUS  current
    DESCRIPTION
            "The IP address of DNS server.  This server is used lowest
            priority."
    ::= { dnsService 3 }


--
-- 22. time service
--

timeService OBJECT IDENTIFIER ::= { askeySystemMib 22 }

protocol OBJECT-TYPE
    SYNTAX  INTEGER {
                none(0),
                sntp(1)
            }
    MAX-ACCESS  read-write
    STATUS  current
    DESCRIPTION
            "The time service is used which protocol."
    ::= { timeService 1 }

updatePeriod OBJECT-TYPE
    SYNTAX  Unsigned32 (1..1440)
    MAX-ACCESS  read-write
    STATUS  current
    DESCRIPTION
            "Synchronize time which system update time by time servers.
            This object unit is in minute."
    ::= { timeService 2 }

timeServer1InetAddress OBJECT-TYPE
    SYNTAX  InetAddress (SIZE(0..63))
    MAX-ACCESS  read-write
    STATUS  current
    DESCRIPTION
            "The address of time server1.  This server is used first priority."
    ::= { timeService 3 }

timeServer2InetAddress OBJECT-TYPE
    SYNTAX  InetAddress (SIZE(0..63))
    MAX-ACCESS  read-write
    STATUS  current
    DESCRIPTION
            "The address of time server2.  This server is used second priority."
    ::= { timeService 4 }

timeServer3InetAddress OBJECT-TYPE
    SYNTAX  InetAddress (SIZE(0..63))
    MAX-ACCESS  read-write
    STATUS  current
    DESCRIPTION
            "The address of time server3.  This server is used lowest priority."
    ::= { timeService 5 }

timeServer1Status OBJECT-TYPE
    SYNTAX  INTEGER {
                notSet(0),
                networkTimeSource(1),
                backupMode(2),
                failToResolveDomainName(3),
                serverNoResponse(4)
            }
    MAX-ACCESS  read-only
    STATUS  current
    DESCRIPTION
            "server1 current status."
    ::= { timeService 6 }

timeServer2Status OBJECT-TYPE
    SYNTAX  INTEGER {
                notSet(0),
                networkTimeSource(1),
                backupMode(2),
                failToResolveDomainName(3),
                serverNoResponse(4)
            }
    MAX-ACCESS  read-only
    STATUS  current
    DESCRIPTION
            "server2 current status."
    ::= { timeService 7 }

timeServer3Status OBJECT-TYPE
    SYNTAX  INTEGER {
                notSet(0),
                networkTimeSource(1),
                backupMode(2),
                failToResolveDomainName(3),
                serverNoResponse(4)
            }
    MAX-ACCESS  read-only
    STATUS  current
    DESCRIPTION
            "server3 current status."
    ::= { timeService 8 }

timeZone OBJECT-TYPE
    SYNTAX  INTEGER (-12..13)
    MAX-ACCESS  read-write
    STATUS  current
    DESCRIPTION
            "The system time zone."
    ::= { timeService 9 }


--
-- 23. UGE functions
--

ugeMIBObjects OBJECT IDENTIFIER ::= { askeySystemMib 23 }

-- subtend OBJECT-TYPE
--       SYNTAX  INTEGER {
--                 enabled(1),
--                 disabled(2)
--             }
--     MAX-ACCESS  read-write
--     STATUS  current
--     DESCRIPTION
--             "Enable or disable NC VLAN subtend."
--     ::= { ugeMIBObjects 1 }

ugeAutoNegotiationTable OBJECT-TYPE
    SYNTAX  SEQUENCE OF UgeAutoNegotionEntry
    MAX-ACCESS  not-accessible
    STATUS  current
    DESCRIPTION
            "The table indicates UGE auto negotiation states."
    ::= { ugeMIBObjects 2 }

ugeAutoNegotionEntry OBJECT-TYPE
    SYNTAX  UgeAutoNegotionEntry
    MAX-ACCESS  not-accessible
    STATUS  current
    DESCRIPTION
            "An entry indicates UGE auto negotiation states."
    INDEX { ifIndex }
    ::= { ugeAutoNegotiationTable 1 }

UgeAutoNegotionEntry ::= SEQUENCE {
    autoNegotiationState        INTEGER
}

autoNegotiationState OBJECT-TYPE
    SYNTAX  INTEGER {
                enabled(1),
                disabled(2)
            }
    MAX-ACCESS  read-write
    STATUS  current
    DESCRIPTION
            "Enable or disable UGE port auto negotiation."
    ::= { ugeAutoNegotionEntry 1 }

ugePauseFrameStatisticTable OBJECT-TYPE
    SYNTAX  SEQUENCE OF UgePauseFrameStatisticEntry
    MAX-ACCESS  not-accessible
    STATUS  current
    DESCRIPTION
            "The table indicates UGE pause packet statistic."
    ::= { ugeMIBObjects 3 }

ugePauseFrameStatisticEntry OBJECT-TYPE
    SYNTAX  UgePauseFrameStatisticEntry
    MAX-ACCESS  not-accessible
    STATUS  current
    DESCRIPTION
            "An entry indicates UGE pause packet statistic."
    INDEX { ifIndex }
    ::= { ugePauseFrameStatisticTable 1 }

UgePauseFrameStatisticEntry ::= SEQUENCE {
    rxPausePackets      Unsigned32,
    txPausePackets      Unsigned32
}

rxPausePackets OBJECT-TYPE
    SYNTAX  Unsigned32
    MAX-ACCESS  read-only
    STATUS  current
    DESCRIPTION
            "The counter indicates pause packets received from this UGE."
    ::= { ugePauseFrameStatisticEntry 1 }

txPausePackets OBJECT-TYPE
    SYNTAX  Unsigned32
    MAX-ACCESS  read-only
    STATUS  current
    DESCRIPTION
            "The counter indicates pause packets transmitted by this UGE."
    ::= { ugePauseFrameStatisticEntry 2 }

subtendVLANTable OBJECT-TYPE
    SYNTAX  SEQUENCE OF SubtendVLANEntry
    MAX-ACCESS  not-accessible
    STATUS  current
    DESCRIPTION
            "The table indicates which VLAN packets can pass through subtending
            ports."
    ::= { ugeMIBObjects 4 }

subtendVLANEntry OBJECT-TYPE
    SYNTAX  SubtendVLANEntry
    MAX-ACCESS  not-accessible
    STATUS  current
    DESCRIPTION
            "An entry for subtendVLANTable."
    INDEX { ifIndex }
    ::= { subtendVLANTable 1 }

SubtendVLANEntry ::= SEQUENCE {
    subtendState    INTEGER,
    subtendVLAN     VLANList
}

subtendState OBJECT-TYPE
    SYNTAX  INTEGER {
                enabled(1),
                disabled(2)
            }
    MAX-ACCESS  read-write
    STATUS  current
    DESCRIPTION
            "Enable or disable NC VLAN subtend."
    ::= { subtendVLANEntry 1 }

subtendVLAN OBJECT-TYPE
    SYNTAX  VLANList
    MAX-ACCESS  read-write
    STATUS  current
    DESCRIPTION
            "Specify what VLAN can pass through by subtending port."
    ::= { subtendVLANEntry 2 }

ugeVLANTable OBJECT-TYPE
    SYNTAX  SEQUENCE OF UgeVLANEntry
    MAX-ACCESS  not-accessible
    STATUS  current
    DESCRIPTION
            "This table indicates relation between UGEs and packets with
            specific VLAN tags. Only packets with tag values can been send out
            from UGEs, otherwise will not."
    ::= { ugeMIBObjects 5 }

ugeVLANEntry OBJECT-TYPE
    SYNTAX  UgeVLANEntry
    MAX-ACCESS  not-accessible
    STATUS  current
    DESCRIPTION
            "An entry for ugeVLANTable."
    INDEX { ifIndex }
    ::= { ugeVLANTable 1 }

UgeVLANEntry ::= SEQUENCE {
    ugeVLAN     VLANList
}

ugeVLAN OBJECT-TYPE
    SYNTAX  VLANList
    MAX-ACCESS  read-only
    STATUS  current
    DESCRIPTION
            "Specify what VLAN can pass through by UGE port."
    ::= { ugeVLANEntry 1 }


--
-- 24. secured hosts
--
securedHosts OBJECT IDENTIFIER ::= { askeySystemMib 24 }

securedHostAdminStatus OBJECT-TYPE
    SYNTAX  INTEGER {
                enabled(1),
                disabled(2)
            }
    MAX-ACCESS  read-write
    STATUS  current
    DESCRIPTION
            "Enable or disable secured host function."
    ::= { securedHosts 1 }

securedHostTable OBJECT-TYPE
    SYNTAX  SEQUENCE OF SecuredHostEntry
    MAX-ACCESS  not-accessible
    STATUS  current
    DESCRIPTION
            "This table provides the information of the secured hosts which may
            access managed system."
    ::= { securedHosts 2 }

securedHostEntry OBJECT-TYPE
    SYNTAX  SecuredHostEntry
    MAX-ACCESS  not-accessible
    STATUS  current
    DESCRIPTION
            "An entry to information of the secured hosts which may access
            managed system."
    INDEX { securedIPSectorIndex }
    ::= { securedHostTable 1 }

SecuredHostEntry ::= SEQUENCE {
    securedIPSectorIndex        IPSectionIndex,
    securedIPSectorStartIP      IpAddress,
    securedIPSectorEndIP        IpAddress,
    allowedServiceType          BITS
}

securedIPSectorIndex OBJECT-TYPE
    SYNTAX  IPSectionIndex
    MAX-ACCESS  not-accessible
    STATUS  current
    DESCRIPTION
            "An IP sector index."
    ::= { securedHostEntry 1 }

securedIPSectorStartIP OBJECT-TYPE
    SYNTAX  IpAddress
    MAX-ACCESS  read-write
    STATUS  current
    DESCRIPTION
            "An IP address expresses IP sector starting."
    ::= { securedHostEntry 2 }

securedIPSectorEndIP OBJECT-TYPE
    SYNTAX  IpAddress
    MAX-ACCESS  read-write
    STATUS  current
    DESCRIPTION
            "An IP address expresses IP sector ending."
    ::= { securedHostEntry 3 }

allowedServiceType OBJECT-TYPE
    SYNTAX  BITS {
                snmp(0),
                telnet(1),
                ftp(2),
                tftp(3)
            }
    MAX-ACCESS  read-write
    STATUS  current
    DESCRIPTION
            "Contains indicates whether access mode is enabled or disabled.
            This is a bit-map of possible settings."
    ::= { securedHostEntry 4 }


--
-- 25. NetBIOS filter
--
netBIOSFilter OBJECT IDENTIFIER ::= { askeySystemMib 25 }

netBIOSFilterAction OBJECT-TYPE
    SYNTAX  INTEGER {
                dropping(1),
                forwarding(2)
            }
    MAX-ACCESS  read-write
    STATUS  current
    DESCRIPTION
            "Drop or forward NetBIOS/NetBEUI packets."
    ::= { netBIOSFilter 1 }


--
-- 26. cascaded management
--

-- cascadedMgt OBJECT IDENTIFIER ::= { askeySystemMib 26 }
--
-- cascadedMgtOpTable OBJECT-TYPE
--     SYNTAX  SEQUENCE OF CascadedMgtOpEntry
--     MAX-ACCESS  not-accessible
--     STATUS  current
--     DESCRIPTION
--             "This table provides the media of cascaded management."
--     ::= { cascadedMgt 1 }
--
-- cascadedMgtOpEntry OBJECT-TYPE
--     SYNTAX  CascadedMgtOpEntry
--     MAX-ACCESS  not-accessible
--     STATUS  current
--     DESCRIPTION
--             "An dummy entry for cascaded management."
--     INDEX { cascadedMgtSlaveId,
--             cascadedMgtOpMgrIp,
--             cascadedMgtOpMgrPort,
--             cascadedMgtOpMgrReqId,
--             cascadedMgtOpMgrCommunity }
--     ::= { cascadedMgtOpTable 1 }
--
-- CascadedMgtOpEntry ::= SEQUENCE {
--     cascadedMgtOpMgrIp        IpAddress,
--     cascadedMgtOpMgrPort      Unsigned32,
--     cascadedMgtOpMgrReqId     Unsigned32,
--     cascadedMgtOpMgrCommunity DisplayString,
--     cascadedMgtOpData         INTEGER
-- }
--
-- cascadedMgtOpMgrIp OBJECT-TYPE
--     SYNTAX  IpAddress
--     MAX-ACCESS  not-accessible
--     STATUS  current
--     DESCRIPTION
--             "SNMP manager IP."
--     ::= { cascadedMgtOpEntry 1 }
--
-- cascadedMgtOpMgrPort OBJECT-TYPE
--     SYNTAX  Unsigned32
--     MAX-ACCESS  not-accessible
--     STATUS  current
--     DESCRIPTION
--             "SNMP manager socket port number."
--     ::= { cascadedMgtOpEntry 2 }
--
-- cascadedMgtOpMgrReqId OBJECT-TYPE
--     SYNTAX  Unsigned32
--     MAX-ACCESS  not-accessible
--     STATUS  current
--     DESCRIPTION
--             "SNMP manager request ID."
--     ::= { cascadedMgtOpEntry 3 }
--
-- cascadedMgtOpMgrCommunity OBJECT-TYPE
--     SYNTAX  DisplayString (SIZE(20))
--     MAX-ACCESS  not-accessible
--     STATUS  current
--     DESCRIPTION
--             "SNMP manager request community."
--     ::= { cascadedMgtOpEntry 4 }
--
-- cascadedMgtOpData OBJECT-TYPE
--     SYNTAX  INTEGER
--     MAX-ACCESS  read-write
--     STATUS  current
--     DESCRIPTION
--             "dummy data."
--     ::= { cascadedMgtOpEntry 5 }
--
-- cascadedMgtEnabled  OBJECT-TYPE
--     SYNTAX INTEGER {
--                 enabled(1),
--                 disabled(2)
--             }
--     MAX-ACCESS read-write
--     STATUS current
--     DESCRIPTION
--             "Enable(1) or disable cascaded management function.
--              An disabled NE can accept SNMP requests with ticket to root.
--              Disabling cascaded management means root NE doesn't relay
--              SNMP requests & responses with slave NEs and slave NEs also
--              don't accept SNMP requests from root NE."
--     DEFVAL { disabled }
--     ::= { cascadedMgt 2 }
--
-- cascadedMgtRole  OBJECT-TYPE
--     SYNTAX INTEGER {
--                 root(1),
--                 slave(2)
--             }
--     MAX-ACCESS read-write
--     STATUS current
--     DESCRIPTION
--             "Role of this NE for cascaded management function.
--              It is configured by way of CLI."
--     DEFVAL { root }
--     ::= { cascadedMgt 3 }
--
-- cascadedMgtSlaveTable OBJECT-TYPE
--     SYNTAX  SEQUENCE OF CascadedMgtSlaveEntry
--     MAX-ACCESS  not-accessible
--     STATUS  current
--     DESCRIPTION
--             "This table provides the slave DSLAMs' information for cascaded management."
--     ::= { cascadedMgt 4 }
--
-- cascadedMgtSlaveEntry OBJECT-TYPE
--     SYNTAX  CascadedMgtSlaveEntry
--     MAX-ACCESS  not-accessible
--     STATUS  current
--     DESCRIPTION
--             "An entry of slave DSLAM information for cascaded management."
--     INDEX { cascadedMgtSlaveId }
--     ::= { cascadedMgtSlaveTable 1 }
--
-- CascadedMgtSlaveEntry ::= SEQUENCE {
--     cascadedMgtSlaveId                 Unsigned32,
--     cascadedMgtSlaveIp                 IpAddress,
--     cascadedMgtSlaveName               DisplayString,
--     cascadedMgtSlaveCommunity          DisplayString,
--     cascadedMgtSlaveLoginUserName      DisplayString,
--     cascadedMgtSlaveLoginPassword      DisplayString,
--     cascadedMgtSlaveOperStatus         INTEGER,
--     cascadedMgtSlaveRowStatus          RowStatus
-- }
--
-- cascadedMgtSlaveId OBJECT-TYPE
--     SYNTAX  Unsigned32 (1..2147483647)
--     MAX-ACCESS  not-accessible
--     STATUS  current
--     DESCRIPTION
--             "target slave DSLAM's ID."
--     ::= { cascadedMgtSlaveEntry 1 }
--
-- cascadedMgtSlaveIp OBJECT-TYPE
--     SYNTAX  IpAddress
--     MAX-ACCESS  read-create
--     STATUS  current
--     DESCRIPTION
--             "slave DSLAM's private IP. It MUST be unique
--              if cascadedMgtSlaveRowStatus is 1(acitve)."
--     ::= { cascadedMgtSlaveEntry 2 }
--
-- cascadedMgtSlaveName OBJECT-TYPE
--     SYNTAX  DisplayString (SIZE(1..128))
--     MAX-ACCESS  read-create
--     STATUS  current
--     DESCRIPTION
--             "slave DSLAM's name. It MUST be unique
--              if cascadedMgtSlaveRowStatus is 1(acitve)."
--     ::= { cascadedMgtSlaveEntry 3 }
--
-- cascadedMgtSlaveCommunity OBJECT-TYPE
--     SYNTAX  DisplayString (SIZE(1..20))
--     MAX-ACCESS  read-create
--     STATUS  current
--     DESCRIPTION
--             "slave DSLAM's SNMP read-write community."
--     ::= { cascadedMgtSlaveEntry 4 }
--
-- cascadedMgtSlaveLoginUserName OBJECT-TYPE
--     SYNTAX  DisplayString (SIZE(1..16))
--     MAX-ACCESS  read-create
--     STATUS  current
--     DESCRIPTION
--             "slave DSLAM's login user name."
--     ::= { cascadedMgtSlaveEntry 5 }
--
-- cascadedMgtSlaveLoginPassword OBJECT-TYPE
--     SYNTAX  DisplayString (SIZE(1..16))
--     MAX-ACCESS  read-create
--     STATUS  current
--     DESCRIPTION
--             "slave DSLAM's login password."
--     ::= { cascadedMgtSlaveEntry 6 }
--
-- cascadedMgtSlaveOperStatus  OBJECT-TYPE
--     SYNTAX  INTEGER {
--                 notActive(0),
--                 connected(1),
--                 disconnected(2)
--             }
--     MAX-ACCESS  read-create
--     STATUS  current
--     DESCRIPTION
--             "This object indicates the operational status of slave DSLAM.
--             notActive(0) means data entry is not active
--             (cascadedMgtSlaveRowStatus isn't active(1)). connected(1) and
--             disconnected(2) indicate that slave DSLAM is connectible or not,
--             respectively."
-- ::= { cascadedMgtSlaveEntry 7 }
--
-- cascadedMgtSlaveRowStatus  OBJECT-TYPE
--     SYNTAX  RowStatus
--     MAX-ACCESS  read-create
--     STATUS  current
--     DESCRIPTION
--             "This object indicates the status of this entry.  A row in this
--             table can be created using the 'createAndGo(4)' (if all objects
--             without default values are supplied with valid values in a single
--             SNMP PDU) or the 'createAndWait(5)' action states.  Until all
--             parameters are valid for a conceptual row, this object is
--             'notReady(3)'.  All parameters must be valid before this object
--             can be set to 'active(1)'.
--
--             Any object in a conceptual row can be modified independent of the
--             value of this object (that is, can be changed while 'active(1)',
--             notInService(2) or 'notReady(3)')."
-- ::= { cascadedMgtSlaveEntry 8 }


--
-- 27. protocol-based VLAN
--

-- <comment ref="protocol_vlan_unuse_temporarily"
--  description="mark all protocol VLAN MIB"/>
--protocolVLAN OBJECT IDENTIFIER ::= { askeySystemMib 27 }

--protocolVLANAdminStatus OBJECT-TYPE
--    SYNTAX  INTEGER {
--                enabled(1),
--                disabled(2)
--            }
--    MAX-ACCESS  read-write
--    STATUS  current
--    DESCRIPTION
--            "Enable or disable protocol-based VLAN feature."
--    ::= { protocolVLAN 1 }

--protocolVLANTable OBJECT-TYPE
--    SYNTAX  SEQUENCE OF ProtocolVLANEntry
--    MAX-ACCESS  not-accessible
--    STATUS  current
--    DESCRIPTION
--            "This table provides the media of protocol-based VLAN."
--    ::= { protocolVLAN 2 }

--protocolVLANEntry OBJECT-TYPE
--    SYNTAX  ProtocolVLANEntry
--    MAX-ACCESS  not-accessible
--    STATUS  current
--    DESCRIPTION
--            "An dummy entry for protocol-based VLAN."
--    INDEX { protocolVLANEthernetType }
--    ::= { protocolVLANTable 1 }

--ProtocolVLANEntry ::= SEQUENCE {
--    protocolVLANEthernetType    Unsigned32 (1..65535),
--    protocolVLANTypeName        SnmpAdminString (SIZE (1..32)),
--    protocolVLANID              INTEGER (1..4094),
--    protocolVLANRowStatus       RowStatus
--}

--protocolVLANEthernetType OBJECT-TYPE
--    SYNTAX  Unsigned32 (1..65535)
--    MAX-ACCESS  not-accessible
--    STATUS  current
--    DESCRIPTION
--            "Ethernet type."
--    ::= { protocolVLANEntry 1 }

--protocolVLANTypeName OBJECT-TYPE
--    SYNTAX  SnmpAdminString (SIZE (1..32))
--    MAX-ACCESS  read-create
--    STATUS  current
--    DESCRIPTION
--            "This object is used to providing ethernet type name which will
--            identifies a row of this table."
--    ::= { protocolVLANEntry 2 }

--protocolVLANID OBJECT-TYPE
--    SYNTAX  INTEGER (1..4094)
--    MAX-ACCESS  read-create
--    STATUS  current
--    DESCRIPTION
--            "The VLAN ID is mapped on this ethernet type."
--    ::= { protocolVLANEntry 3 }

--protocolVLANRowStatus OBJECT-TYPE
--    SYNTAX  RowStatus
--    MAX-ACCESS  read-create
--    STATUS  current
--    DESCRIPTION
--            "This object is used to create a new row or delete an existing row
--            in this table.
--
--            The object status is active if its other values are valid,
--            alternatively, it is 'not-ready' if other values are not valid.
--            And setting this object to 'destroy' or 'not-in-service' will
--            delete it."
--    ::= { protocolVLANEntry 4 }
--

END
