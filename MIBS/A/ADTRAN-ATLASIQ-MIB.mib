ADTRAN-ATLASIQ-MIB   DEFINITIONS ::= BEGIN

-- TITLE:       ADTRAN ATLASIQ MIB
-- PRODUCT:     1200.263L1
-- VERSION:     1.0
-- DATE:        98/12/18
-- HISTORY:
-- 05/12/00 B. Flory
--          Moved adATLASFrSwToBkup and adATLASFrSwToPrimary traps from Atintf.mib.

IMPORTS
    enterprises, Counter, IpAddress, Gauge
        FROM RFC1155-SMI
    OBJECT-TYPE
        FROM RFC-1212
    DisplayString, ifIndex
        FROM RFC1213-MIB
    TRAP-TYPE
        FROM RFC-1215
    frCircuitIfIndex,
    frCircuitDlci
        FROM RFC1315-MIB
    adProdPhysAddress, adProducts, adMgmt
        FROM ADTRAN-MIB;

-- OBJECT IDENTIFIERS
adATLASIQ                  OBJECT IDENTIFIER ::= { adProducts 155 }
adATLASmg                  OBJECT IDENTIFIER ::= { adMgmt 154 }
adATLASIQmg                OBJECT IDENTIFIER ::= { adMgmt 155 }
adATLASIQSystemConfig      OBJECT IDENTIFIER ::= { adATLASIQmg 1 }
adATLASIQNetPortConfig     OBJECT IDENTIFIER ::= { adATLASIQmg 2 }
adATLASIQDtePortConfig     OBJECT IDENTIFIER ::= { adATLASIQmg 3 }
adATLASIQPvcConfig         OBJECT IDENTIFIER ::= { adATLASIQmg 4 }
adATLASIQCurrentStatus     OBJECT IDENTIFIER ::= { adATLASIQmg 5 }
adATLASIQIntT1Status       OBJECT IDENTIFIER ::= { adATLASIQmg 6 }
adATLASIQDayT1Status       OBJECT IDENTIFIER ::= { adATLASIQmg 7 }
adATLASIQDiagnostic        OBJECT IDENTIFIER ::= { adATLASIQmg 8 }
adATLASIQ1406Time          OBJECT IDENTIFIER ::= { adATLASIQmg 9 }
adATLASIQDBUConfig         OBJECT IDENTIFIER ::= { adATLASIQmg 10 }
adATLASIQIntDBUStatus      OBJECT IDENTIFIER ::= { adATLASIQmg 11 }
adATLASIQDayDBUStatus      OBJECT IDENTIFIER ::= { adATLASIQmg 12 }
adATLASIQTrapManager       OBJECT IDENTIFIER ::= { adATLASIQmg 13 }

--
--The ATLASIQ System Config Group

adATLASIQTOD OBJECT-TYPE
	 SYNTAX      DisplayString
	 ACCESS      read-write
	 STATUS      mandatory
	 DESCRIPTION
	"Sets the Time of Day with format hh:mm."
	 ::= { adATLASIQSystemConfig 1 }

adATLASIQDate OBJECT-TYPE
	 SYNTAX      DisplayString
	 ACCESS      read-write
	 STATUS      mandatory
	 DESCRIPTION
	"Sets the Date with the format MM-DD-YY."
	 ::= { adATLASIQSystemConfig 2 }

--
--The ATLASIQ Network Port Config Group
--


adATLASIQNetPortMaxPVCs    OBJECT-TYPE
	 SYNTAX      INTEGER (1..100)
	 ACCESS      read-write
	 STATUS      mandatory
	 DESCRIPTION
        "Sets the maxium PVCs supported by the IQ unit. (Range 1 -1000)."
         ::= { adATLASIQNetPortConfig 20 }

adATLASIQNetPortHistIntervals    OBJECT-TYPE
	 SYNTAX      INTEGER
	 ACCESS      read-write
	 STATUS      mandatory
	 DESCRIPTION
	"Sets the number of history intervals for storage."
         ::= { adATLASIQNetPortConfig 21 }

adATLASIQNetPortHistIntervalsAvailable    OBJECT-TYPE
	 SYNTAX      INTEGER
	 ACCESS      read-only
	 STATUS      mandatory
	 DESCRIPTION
	"Returns the number of history intervals allowed based on the maxium number of PVCs selected."
         ::= { adATLASIQNetPortConfig 22 }

--
--The ATLASIQ Dte Port Config Group
-- (Currently Not Supported)

--
--The ATLASIQ PVC config table
-- (Currently Not Supported)

--
--The ATLASIQ Current status Group
-- (Currently Not Supported)

--
--The ATLASIQ Int T1 status table
-- (Currently Not Supported)

--
--The ATLASIQ day T1 status table
-- (Currently Not Supported)

--
--The ATLASIQ Diagnostic table
-- (Currently Not Supported)
--
--The RFC 1406 time stamp table
--

adATLASIQ1406TimeTable OBJECT-TYPE
         SYNTAX      SEQUENCE OF AdATLASIQ1406TimeEntry
	 ACCESS      not-accessible
	 STATUS      mandatory
	 DESCRIPTION
	   "n/a."
         ::= { adATLASIQ1406Time 1 }

adATLASIQ1406TimeEntry OBJECT-TYPE
         SYNTAX      AdATLASIQ1406TimeEntry
	 ACCESS      not-accessible
	 STATUS      mandatory
	 DESCRIPTION
	   "n/a"
         INDEX { adATLASIQ1406TimeSlotIndex }
         ::= { adATLASIQ1406TimeTable 1 }

AdATLASIQ1406TimeEntry ::=
	SEQUENCE {
        adATLASIQ1406TimeSlotIndex
	INTEGER,
        adATLASIQ1406TimeStamp
	DisplayString
	}

adATLASIQ1406TimeSlotIndex OBJECT-TYPE
	 SYNTAX  INTEGER
	 ACCESS  read-only
	 STATUS  mandatory
	 DESCRIPTION
	   "n/a."
         ::= { adATLASIQ1406TimeEntry 1 }

adATLASIQ1406TimeStamp OBJECT-TYPE
	 SYNTAX  DisplayString
	 ACCESS  read-only
	 STATUS  mandatory
	 DESCRIPTION
	   "Time interval started. Format H:M if not midnight else M-D"
         ::= { adATLASIQ1406TimeEntry 2 }

--
--The ATLASIQ Dial Backup Config Group
-- (Currently Not Supported)
--
-- ISDN Dial Backup Options
-- (Currently Not Supported)

--
-- V34 Dial Backup Options
-- (Not implemented)


--
-- External DCE Dial Backup Options
-- (Not implemented)


--
--The ATLASIQ interval DBU Port status table
-- (Not implemented)

--
--The ATLASIQ day DBU Port status table
--  (Not implemented)


-------------------------------------------
-- ATLASIQ Enterprise Specific Traps
-------------------------------------------

adATLASFrSwToBkup TRAP-TYPE
        ENTERPRISE     adATLASmg
        VARIABLES {
                 frCircuitIfIndex,
                 frCircuitDlci
        }
        DESCRIPTION
                "This trap indicates that the indicated
                 Virtual Circuit has switch to a backup state."
        --#TYPE       "Error - A Switch to Backup Event has Occured"
        --#SUMMARY    "ATLAS 15440:  Switch to backup has occured for "
        --#SUMMARY    "Line %d, DLCI %d."
        --#ARGUMENTS  {0,1}
        --#SEVERITY   MAJOR
        --#GENERIC    6
        --#CATEGORY   "Error Events"
        --#SOURCE_ID  "A"
        --#TIMEINDEX  0
        ::= 15440

adATLASFrSwToPrimary TRAP-TYPE
        ENTERPRISE     adATLASmg
        VARIABLES {
                 frCircuitIfIndex,
                 frCircuitDlci
        }
        DESCRIPTION
                "This trap indicates that the indicated Virtual
                 Circuit has been restored to the primary state."
        --#TYPE       "Error - A Switch to Primary Event has Occured"
        --#SUMMARY    "ATLAS 15441:  Restore to primary has occured for "
        --#SUMMARY    "Line %d, DLCI %d."
        --#ARGUMENTS  {0,1}
        --#SEVERITY   MAJOR
        --#GENERIC    6
        --#CATEGORY   "Error Events"
        --#SOURCE_ID  "A"
        --#TIMEINDEX  0
        ::= 15441

  END
