-- -----------------------------------------------------------------
-- Copyright (c) 3Com Corporation. All Rights Reserved.
-- -----------------------------------------------------------------
A3COM0034-PROBECONFIG-EXTENSION DEFINITIONS ::= BEGIN


	IMPORTS
		probeConfigNetExtensions FROM A3COM0027-RMON-EXTENSIONS
		ifIndex FROM RFC1213-MIB
		IpAddress, OBJECT-TYPE FROM RFC-1212
		;

extNetConfigTable OBJECT-TYPE
      SYNTAX      SEQUENCE OF ExtNetConfigEntry
      ACCESS      not-accessible
      STATUS      mandatory
      DESCRIPTION "A table augmenting the netConfigEntries defined in RFCxxxx."
      ::= {probeConfigNetExtensions 1}

extNetConfigEntry OBJECT-TYPE
      SYNTAX      ExtNetConfigEntry
      ACCESS      not-accessible
      STATUS      mandatory
      DESCRIPTION "A set of configuration parameters for a particular network 
        interface on this device. If the device has no network interface, this 
        table is empty.

        The index is composed of the ifIndex assigned to the corresponding 
        interface."
      INDEX       {ifIndex}
      ::= {extNetConfigTable 1}

ExtNetConfigEntry ::= SEQUENCE {
                  extNetConfigDefaultGateway  IpAddress,
                  extNetConfigBootP           INTEGER
                  }

extNetConfigDefaultGateway OBJECT-TYPE
      SYNTAX      IpAddress
      ACCESS      read-write
      STATUS      mandatory
      DESCRIPTION "The IP Address of the default gateway.  If this value is 
        undefined or unknown, it shall have the value 0.0.0.0."
      ::= {extNetConfigEntry 1}

extNetConfigBootP OBJECT-TYPE
      SYNTAX      INTEGER  {
                  notAvailable (1),
                  enable (2),
                  disable (3)
      }
      ACCESS      read-write
      STATUS      mandatory
      DESCRIPTION "This parameter is intended for controlling an interfaces
        used for management which may have an IP address. The object enables 
        or disables the BootP mechanism for obtaining a bootP configuration. 
        The default value for this object for a specific interface depends 
	on the product."
      ::= {extNetConfigEntry 2}



END
