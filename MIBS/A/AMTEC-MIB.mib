-- ===========================================================================

--

--           M I B    P r o p r i e t a r i a    A M T E C

-- 

-- 

--                    per apparati con SW GAIA 

--

--

--  private  - enterprises - amtec (1954)

--

--

-- (c)  Prodotti di Rete - AMTEC SpA            

--

--

-- Versione per GAIA4 Ver.2.0.8

--

-- *************************************************************

-- 

-- 14/11/02 R.Flamini

-- VERSIONE CORRETTA PER IL COMPILATORE MG-SOFT

-- 

-- 03/12/02 R.Flamini

-- CORRETTI ATM, ADSL, DNS RESOLVER

--

-- *************************************************************

--                                                               

-- ===========================================================================







AMTEC-MIB --{ iso org(3) dod(6) internet(1) private(4) enterprises(1) 1954 }



DEFINITIONS ::= BEGIN



IMPORTS

	enterprises, OBJECT-TYPE, Gauge, Counter, TimeTicks, IpAddress

		FROM RFC1155-SMI
	Counter32, Gauge32 FROM SNMPv2-SMI
		TRAP-TYPE FROM RFC-1215

	DisplayString

		 FROM SNMPv2-TC;





amtec OBJECT IDENTIFIER ::= { enterprises 1954 }





prodotti  OBJECT IDENTIFIER                     ::= { amtec 1 }

sys       OBJECT IDENTIFIER                     ::= { amtec 2 }

protocol  OBJECT IDENTIFIER                     ::= { amtec 3 }

general-configuration  OBJECT IDENTIFIER  ::= { amtec 4 }

	

-- *****************************************************************************

--  GRUPPO PRODOTTI

--                  Questo gruppo contiene l'elenco dei prodotti AMTEC         

--                  gestibili tramite la MIB: ogni variabile corrisponde ad    

--                  un unico apparato e/o modello.                             

--                  La variabile "sysObjectId" della MIB II deve contenere     

--                  l'object identifier corrispondente.                        

-- *****************************************************************************



ra360a          OBJECT-TYPE

		SYNTAX  INTEGER

		ACCESS  not-accessible

		STATUS  mandatory

	DESCRIPTION

		"Apparato RA360A"

	::= { prodotti 1 }



ra360c          OBJECT-TYPE

		SYNTAX  INTEGER

		ACCESS  not-accessible

		STATUS  mandatory

	DESCRIPTION

		"Apparato RA360C"

	::= { prodotti 2 }



lwi             OBJECT-TYPE

		SYNTAX  INTEGER

		ACCESS  not-accessible

		STATUS  mandatory

	DESCRIPTION

		"Scheda LWI (M-PAT/R)"

	::= { prodotti 3 }



ra360-m         OBJECT-TYPE

		SYNTAX  INTEGER

		ACCESS  not-accessible

		STATUS  mandatory

	DESCRIPTION

		"Apparato RA360/M"

	::= { prodotti 4 }



ra302-a         OBJECT-TYPE

		SYNTAX  INTEGER

		ACCESS  not-accessible

		STATUS  mandatory

	DESCRIPTION

		"Apparato RA302/A"

	::= { prodotti 5 }



ra302-b         OBJECT-TYPE

		SYNTAX  INTEGER

		ACCESS  not-accessible

		STATUS  mandatory

	DESCRIPTION

		"Apparato RA302/B"

	::= { prodotti 6 }



p302            OBJECT-TYPE

		SYNTAX  INTEGER

		ACCESS  not-accessible

		STATUS  mandatory

	DESCRIPTION

		"Apparato P302"

	::= { prodotti 7 }



cs860            OBJECT-TYPE

		SYNTAX  INTEGER

		ACCESS  not-accessible

		STATUS  mandatory

	DESCRIPTION

		"Apparato CS-860"

	::= { prodotti 8 }



ra860            OBJECT-TYPE

		SYNTAX  INTEGER

		ACCESS  not-accessible

		STATUS  mandatory

	DESCRIPTION

		"Apparato RA-860"

	::= { prodotti 9 }



sas860 	     OBJECT-TYPE

		SYNTAX  INTEGER

		ACCESS  not-accessible

		STATUS  mandatory

	DESCRIPTION

		"Apparato SAS860"

	::= { prodotti 10 }



sas860-enh 	     OBJECT-TYPE

		SYNTAX  INTEGER

		ACCESS  not-accessible

		STATUS  mandatory

	DESCRIPTION

		"Apparato SAS860 ENHANCED"

	::= { prodotti 11 }





-- END OF PRODOTTI





-- *****************************************************************************

--  GRUPPO SYS (SISTEMA)

--          Questo gruppo ha la seguente ramificazione:

--               - hw:     gruppo contenente informazioni sull'equipaggiamento

--                         hardware della scheda.

--               - sw:     gruppo contenente informazioni sull'equipaggiamento

--                         di una scheda, legate al software.

--               - ft:     gruppo contenente le variabili necessarie alla gestio-

--                         ne di un file transfer (TFTP) da SNMP.

--               - SysIfc: questo gruppo contiene informazioni che caratterizza-

--                         no una interfaccia (caratteristiche fisiche,proto-

--                         colli configurati sulla interfaccia etc).

--              - SysAct:  questo gruppo ha lo scopo di raccogliere variabili

--                         che impostano azioni particolari sulla macchina.

-- *****************************************************************************



hw      	OBJECT IDENTIFIER ::= { sys 1 }

sw      	OBJECT IDENTIFIER ::= { sys 2 }

ft      	OBJECT IDENTIFIER ::= { sys 3 }

sysIfc  	OBJECT IDENTIFIER ::= { sys 4 }

sysAct  	OBJECT IDENTIFIER ::= { sys 5 }

sysSecur	OBJECT IDENTIFIER ::= { sys 6 }

sysCPU		OBJECT IDENTIFIER ::= { sys 7 }



sysLog		OBJECT IDENTIFIER ::= { sys 8 }



-- *****************************************************************************

-- Gruppo Hw

--           - HwSNumber

--           - HwRamSize

-- *****************************************************************************



hwSNumber       OBJECT-TYPE

		SYNTAX DisplayString

		ACCESS read-only

		STATUS mandatory

	DESCRIPTION

		"Serial number della scheda"

	::= { hw 1 }



hwRamSize       OBJECT-TYPE

		SYNTAX  INTEGER {

			mb4-Ram (1),

			mb4-Ram (2)

			}

		ACCESS  read-only

		STATUS  mandatory

	DESCRIPTION

		"Dimensione della  RAM espressa in MB"

	::= { hw 2 }



-- *****************************************************************************

-- Gruppo Sw

--           - SwBootRel

--           - SwUsageRel

--           - SwRecPres

--           - SwLastReset

--           - SwPart      - SwpartApllSize

--                         - SwPartRecSize

--                         - SwPartCnfSize

--           - SwCnf       - SysSwCnfType

--           - SwRam       - SwRamNPart

--                         - SwRamTab        (TABELLA)

-- *****************************************************************************



swBootRel       OBJECT-TYPE

		SYNTAX  DisplayString

		ACCESS  read-only

		STATUS  mandatory

	DESCRIPTION

		"Release del software di BOOT"

	::= { sw 1 }



swUsageRel      OBJECT-TYPE

		SYNTAX  DisplayString

		ACCESS  read-only

		STATUS  mandatory

	DESCRIPTION

		"Release del sw applicativo operativo sulla macchina

		 (quello attivato dal sw di boot)"

	::= { sw 2 }



swStatus        OBJECT-TYPE

		SYNTAX  INTEGER{

				gestito-un-solo-SW (0),

				sw-appl-good-SW-rec-good (1),

				sw-appl-good-SW-rec-bad (2),

				sw-appl-bad-SW-rec-good (3)

				}

		ACCESS  read-only

		STATUS  mandatory

	DESCRIPTION

		"Questa variabile contiene informazioni relative ai software

		 gestisti dalla scheda, in funzione del software di boot.

		 Viene data indicazione della presenza o meno del doppio

		 software e per ogni sw gestito lo stato del CRC."

	::= { sw 3 }



swLastReset     OBJECT-TYPE

		SYNTAX DisplayString

		ACCESS read-only

		STATUS mandatory

	DESCRIPTION

		"Descrizione della causa dell'ultimo RESET della scheda"

	::= { sw 4 }





-- **************************

--        Gruppo SwPart

-- **************************



swPart          OBJECT IDENTIFIER ::= { sw 5 }



	swPartApplSize          OBJECT-TYPE

			SYNTAX  Gauge

			ACCESS  read-only

			STATUS  mandatory

		DESCRIPTION

			"Ampiezza della partizione riservata al SW Applicativo

			 (principale) nella memoria permanente (flash)"

		::= { swPart 1 }



	swPartRecSize           OBJECT-TYPE

			SYNTAX  Gauge

			ACCESS  read-only

			STATUS  mandatory

		DESCRIPTION

			"Ampiezza della partizione riservata al SW di Recupero

			 nella memoria permanente (flash)"

		::= { swPart 2 }



	swPartCnfSize           OBJECT-TYPE

			SYNTAX  Gauge

			ACCESS  read-only

			STATUS  mandatory

		DESCRIPTION

			"Ampiezza della partizione riservata alla Configura-

			 zione nella memoria permanente (es: flash)"

		::= { swPart 3 }





-- **************************

--        Gruppo SwCnf

-- **************************



swCnf           OBJECT IDENTIFIER ::= { sw 6 }



	sysSwCnfType    OBJECT-TYPE

			SYNTAX  INTEGER {

				di-Fabbrica (1),

				di-Default (2),

				di-Lavoro (4),

				di-Fabbrica-impostata-utente (9),

				di-Default-impostata-utente (10),

				di-Lavoro-impostata-utente (12)

				}

			ACCESS  read-only

			STATUS  mandatory

		DESCRIPTION

			"Questa variabile specifica il tipo di configurazione

			 con cui la scheda sta operando e se questa configura-

			 zione e' stata forzata da console (al boot tramite

			 UART)"

		::= { swCnf 1 }



        sysVersionCnf	    OBJECT-TYPE

			    SYNTAX  OCTET STRING

			    ACCESS  read-only

			    STATUS  mandatory

		DESCRIPTION

			"Questa variabile specifica la versione della configurazione

			 con cui la scheda sta operando."

		::= { swCnf 2 }



	sysCommitState	    OBJECT-TYPE

			    SYNTAX  INTEGER

			    ACCESS  read-write

			    STATUS  mandatory

		DESCRIPTION

			"Questa variabile specifica lo stato di upload con commit

			 della configurazione con cui la scheda sta operando."

		::= { swCnf 3 }

	



	sysSwCnfMD5	    OBJECT-TYPE

			    SYNTAX  OCTET STRING

			    ACCESS  read-only

			    STATUS  mandatory

		DESCRIPTION

			"Questa variabile specifica l'hashing della configurazione

			 con cui la scheda sta operando."

		::= { swCnf 4 }





-- **************************

--        Gruppo SwRam 

-- **************************



swRam           OBJECT IDENTIFIER ::= { sw 7 }



	swRamNPart      OBJECT-TYPE

			SYNTAX  INTEGER

			ACCESS  read-only

			STATUS  mandatory

		DESCRIPTION

			"Numero delle partizioni RAM riservate al Pool Buffers"

		::= { swRam 1 }





-- -------------------------------------------------------------------------

--     TABELLA SwRamTab     

--                                               TABELLA POOL BUFFER

-- -------------------------------------------------------------------------





	swRamTable        OBJECT-TYPE

			SYNTAX  SEQUENCE OF SwRamEntry

			ACCESS  not-accessible

			STATUS  mandatory

		DESCRIPTION

			"Tabella delle partizioni RAM riservate al Pool di 

			 Buffers."

		::= { swRam 2 }



	swRamEntry              OBJECT-TYPE

				SYNTAX SwRamEntry

				ACCESS not-accessible

				STATUS mandatory

			DESCRIPTION

				"Entry tabella SwRamTab"

--				INDEX { RamPartIndex }

			::= { swRamTable 1 }



		SwRamEntry ::= SEQUENCE {

			ramPartIndex    INTEGER,

			ramSizeBuf      INTEGER (0..65535),

			ramBufTot       INTEGER (0..65535),

			ramBufFreeMin   INTEGER (0..65535),

			ramBufFreeMax   INTEGER (0..65535),

			ramBufFreeNow   INTEGER (0..65535)

			}



		ramPartIndex    OBJECT-TYPE

				SYNTAX INTEGER

				ACCESS read-only

				STATUS mandatory

			DESCRIPTION

			"E' la numerazione della partizione (INDICE) RAM

			 per Poll di Buffer.

			 Ha un valore compreso tra 1 e il valore della 

			 variabile SwRamNPart."

			::= { swRamEntry 1 } 



		ramSizeBuf      OBJECT-TYPE

				SYNTAX INTEGER (0..65535)

				ACCESS read-only

				STATUS mandatory

			DESCRIPTION

			"Dimensione di ogni buffer all'interno della parti-

			 zione RAM. "

			::= { swRamEntry 2 } 



		ramBufTot       OBJECT-TYPE

				SYNTAX INTEGER (0..65535)

				ACCESS read-only

				STATUS mandatory

			DESCRIPTION

			"Numero dei buffers totoli all'interno della parti-

			 zione RAM"

			::= { swRamEntry 3 } 



		ramBufFreeMin   OBJECT-TYPE

				SYNTAX INTEGER (0..65535)

				ACCESS read-only

				STATUS mandatory

			DESCRIPTION

			"Minumo numero di buffers liberi raggiunto.

			 Ad ogni GET SNMP il contenuto di questa variabile

			 viene reinizializzato."

			::= { swRamEntry 4 } 



		ramBufFreeMax   OBJECT-TYPE

				SYNTAX INTEGER (0..65535)

				ACCESS read-only

				STATUS mandatory

			DESCRIPTION

			"Massimo numero di buffers liberi raggiunto.

			 Ad ogni GET SNMP il contenuto di questa variabile

			 viene reinizializzato."

			::= { swRamEntry 5 } 



		ramBufFreeNow   OBJECT-TYPE

				SYNTAX INTEGER (0..65535)

				ACCESS read-only

				STATUS mandatory

			DESCRIPTION

			"Numero di buffers liberi correnti."

			::= { swRamEntry 6 } 



-- *****************************************************************************

-- Gruppo Ft

--           - FtConf      - FtConfValidate

--                         - FtConfIpAddr

--                         - FtConfPathFile

--                         - FtConfRW

--                         - FtConfObj

--                         - FtConfLen

--                         - FtConfSecLev

--           - FtDiag      - FtDiagStatAck

--                         - FtDiagState

--                         - FtDiagInfo

--                         - FtDiagCountBlk

--                         - FtDiagCountNoSeq

--

--  Il gruppo Ft contiente due rami (FtConf e FtDiag), il primo serve per

--  impostare e i parametri di file transfer, il secondo per controllare

--  l'andamento e l'esito del file transfer.            

-- *****************************************************************************



ftconf    OBJECT IDENTIFIER ::= { ft 1 }

ftdiag    OBJECT IDENTIFIER ::= { ft 2 }



-- **************************

--        Gruppo FtConf

-- **************************



ftConfValidate  OBJECT-TYPE

		SYNTAX  INTEGER

		ACCESS  write-only

		STATUS  mandatory

	DESCRIPTION

		"E'la variabile il cui SET snmp ad un valore

		 diverso da 0 valida le variabili che definiscono

		 i parametri di file transfer.

		 La Get restituisce sempre valore 0"

	::= { ftconf 1 }





ftConfIpAddr    OBJECT-TYPE

		SYNTAX  IpAddress

		ACCESS  read-write

		STATUS  mandatory

	DESCRIPTION

		"Definisce indirizzo IP dell'Host con cui effettuare 

		 il file transfer."

	::= { ftconf 2 }



ftConfPathFile  OBJECT-TYPE

		SYNTAX  DisplayString

		ACCESS  read-write

		STATUS  mandatory

	DESCRIPTION

		"Definisce il percorso e il nome del file da leggere

		 o scrivere, relativo all'Host."

	::= { ftconf 3 }



ftConfRW        OBJECT-TYPE

		SYNTAX  INTEGER {

			unspecOp (0),

			put (1),

			get (2)

			}

		ACCESS  read-write

		STATUS  mandatory

	DESCRIPTION

		"Definisce la direzione del file transfer:

		 - PUT per trasferire il file da Agent verso Host;

		 - GET per trasferire il file da Host verso Agent."

	::= { ftconf 4 }



ftConfObj       OBJECT-TYPE

		SYNTAX  INTEGER {

			none (0),

			sw (1),

			conf (2),

			agenda(3)

			}

		ACCESS  read-write

		STATUS  mandatory

	DESCRIPTION

		"Definisce l'oggetto del file transfer:

		- Software

		- Configurazione

		- Agenda"

	::= { ftconf 5 }



ftConfLen       OBJECT-TYPE

		SYNTAX  Gauge

		ACCESS  read-write

		STATUS  mandatory

	DESCRIPTION

		"Definisce la lunghezza del file da leggere da Host.

		 La variabile ha dunque senso solo se FtConfRW=GET"

	::= { ftconf 6 }



ftConfSecLev    OBJECT-TYPE

		SYNTAX  INTEGER {

			notspecified (0),

			direct-on-flash-use (1),

			on-Ram (2),

			on-2nd-Flash (3)

			}

		ACCESS  read-write

		STATUS  mandatory

	DESCRIPTION

		"Definisce il livello di sicurezza dell'operazione di

		 file transfer (parametro questo tra l'altro funzione

		 dell'equipaggiamento hardware di una scheda) nel caso

		 di GET del SW.

		 Si hanno le seguenti opzioni di SET:

		 - Direct-on-flash-use: il sw viene scritto direttamente nella

		   partizione di memoria permanente (flash) relativa al sw in

		   uso (quello mandato in esecuzione al boot)

		 - On-Ram: il sw viene scritto in RAM e a FT terminato

		   scaricato nella memoria permanente.

		 - On-2nd-Flash: il sw viene scritto prima nella partizione di

		   memoria riservata al sw non in esecuzione (normalmente 

		   quello di recupero) e a fine FT trasferito nella partizione

		   di memoria permanente riservata al sw in esecuzione."

	::= { ftconf 7 }



-- **************************

--        Gruppo FtDiag

-- **************************

--

ftDiagStatAck   OBJECT-TYPE

		SYNTAX  INTEGER

		ACCESS  write-only

		STATUS  mandatory

	DESCRIPTION

		"Questa variabile serve al Manager (SET con valore

		 diverso da 0 ) per chiudere la sessione di FT con

		 l'Agent. A fine FT (OK o ABORT) pertanto deve essere

		 impostata per innescare una nuovo sessione di FT"

	::= { ftdiag 1 }



ftDiagState     OBJECT-TYPE

		SYNTAX  INTEGER {

			free (0),

			abort (1),

			done (2),

			impossible (3),

			running (4),

			analizing (5),

			writing (6)

			}

		ACCESS  read-only

		STATUS  mandatory

	DESCRIPTION

		"Definisce la stato della sessione FT.

		 Valori assunti:

		- FREE: stato di libero

		- ABORT: il FT e' terminato per errore

		- DONE: il FT e' terminato correttamente

		- IMPOSSIBLE: il FT e' terminato perche' non sono

		  state rilevate le condizione di sicurezza (FfConfSecLev),

		  stato questo significativo per operazione GET SW

		- RUNNING: il FT e' in esecuzione

		- ANALIZING: stato valido solo per operazione GET CONF,

		  l'Agent effettua una analisi sintattica/semantica sul

		  file di configurazione ricevuto.

		- WRITING: stato in cui si trasferisce il file da RAM->FLASH

		  o da FLASH->FLASH (vedi FtConfSecLev), valido solo nel caso

		  di operazione GET SW."

	::= { ftdiag 2 }



ftDiagInfo      OBJECT-TYPE

		SYNTAX  DisplayString

		ACCESS  read-only

		STATUS  mandatory

	DESCRIPTION

		"E' una descrizione delle operazioni di FT, e' legato al

		 valore assunto da FtDiagState."

	::= { ftdiag 3 }



ftDiagCountBlk  OBJECT-TYPE

		SYNTAX  Counter

		ACCESS  read-only

		STATUS  mandatory

	DESCRIPTION

		"Contatore di blocchi: trasferiti dall'Agent durante l'ope-

		 razione PUT, ricevuti dall'Agent durante l'operazione GET"

	::= { ftdiag 4 }



ftDiagCountNoSeq OBJECT-TYPE

		SYNTAX  Counter

		ACCESS  read-only

		STATUS  mandatory

	DESCRIPTION

		"Contatore di blocchi fuori sequenza: trasferiti dall'Agent

		 durante l'operazione PUT, ricevuti dall'Agent durante

		 l'operazione GET"

	::= { ftdiag 5 }





-- *****************************************************************************

-- Gruppo SysIfc

--           - SysIfcNum

--           - SysIfcTab (TABELLA INTERFACCE)

--           - SysPhysSerial - PhysSerdiag

--                                         - PhysSerOpTab

-- *****************************************************************************



sysIfcNum       OBJECT-TYPE

		SYNTAX  INTEGER

		ACCESS  read-only

		STATUS  mandatory

	DESCRIPTION

		"Numero di interfacce presenti nella scheda

		(quelle descritte nella tabella SysIfcTAB).

		Corrisponde a ifNumber definito nella MIB-II"

	::= { sysIfc 1 }



-- -------------------------------------------------------------------------

--        TABELLA SysIfcTab

--                                               TABELLA INTERFACCE

-- -------------------------------------------------------------------------



sysIfcTable     OBJECT-TYPE

		SYNTAX  SEQUENCE OF SysIfcEntry

		ACCESS  not-accessible

		STATUS  mandatory

	DESCRIPTION

		"Questa tabella descrive il tipo d'interfaccia e la

		 pila dei protocolli configurati su essa."

	::= { sysIfc 2 }



	sysIfcEntry  OBJECT-TYPE

			SYNTAX  SysIfcEntry

			ACCESS  not-accessible

			STATUS  mandatory

		DESCRIPTION

			"Entry tabella interfacce"

			INDEX   { ifcProtIndex }

		::= { sysIfcTable 1 }

		

	SysIfcEntry ::= SEQUENCE {

		ifcProtIndex    INTEGER,

		ifcType         INTEGER,

		ifcProtCnf      OCTET STRING

		}



	ifcProtIndex    OBJECT-TYPE

			SYNTAX  INTEGER

			ACCESS  read-only

			STATUS  mandatory

		DESCRIPTION

			"Indice dell'interfaccia.

			 Corrisponde a ifIndex definito nella MIB-II."

		::= { sysIfcEntry 1 }



	ifcType         OBJECT-TYPE

			SYNTAX  INTEGER {

				lan-ethernet-1(0),

				serial-1(1),

				bri-B1(2),

				bri-D(3),

				serial-2(4),

				serial-3(5),

				serial-4(6),

				lan-ethernet-2(7),

				lan-ethernet-3(8),

				lan-ethernet-4(9),

				compact-pci(10),

				lan-ethernet-5(11),

				bri-B2(12),

				bri-B(13),

				lan-ethernet-6(14)

				}

			ACCESS  read-only

			STATUS  mandatory

		DESCRIPTION

			"Descrive il tipo d'interfaccia."

		::= { sysIfcEntry 2 }



	ifcProtCnf      OBJECT-TYPE

			SYNTAX  OCTET STRING

			ACCESS  read-only

			STATUS  mandatory

		DESCRIPTION

			"Vettore che riporta gli identificativi (Hex) dei

			 protocolli configurati sull'interfaccia.

			 -----------------------------------------------

				Identificativi protocolli:

			 -----------------------------------------------

				LAPB             2

				LAPD             3

				I802             4

				ETH              5

				PPP              6

				TRA              7

				SDLC             8

				X25              9

				Q931            10

				QLLC            11

				LLC2            12

				IP              15

				ISDN            21

				RIP             22

				X28             23

				FRAME RELAY     24

			"

		::= { sysIfcEntry 3 }



-- **************************

--     Gruppo SysPhysSerial

-- **************************

sysPhysSerial   OBJECT IDENTIFIER       ::= { sysIfc 3 }

physSerdiag     OBJECT IDENTIFIER       ::= { sysPhysSerial 2}







physSerOpTable    OBJECT-TYPE

		SYNTAX  SEQUENCE OF PhysSerOpEntry

		ACCESS  not-accessible

		STATUS  mandatory

	DESCRIPTION

		"Questa tabella, relativa ad interfacce seriali

		 fornisce indicazioni sui segnali di interfaccia"

	::= { physSerdiag 2 }



	physSerOpEntry  OBJECT-TYPE

			SYNTAX  PhysSerOpEntry

			ACCESS  not-accessible

			STATUS  mandatory

		DESCRIPTION

			"Entry tabella PhysSerOpTab"

			INDEX   { physSerOpIndex }

		::= {physSerOpTable  1 }

	PhysSerOpEntry ::= SEQUENCE {

		physSerOpIndex  INTEGER,

		physSerDsr      INTEGER,

		physSerCts      INTEGER,

		physSerDcd      INTEGER,

		physSerDtr      INTEGER,

		physSerRts      INTEGER

		}



	physSerOpIndex  OBJECT-TYPE

			SYNTAX  INTEGER

			ACCESS  read-only

			STATUS  mandatory

		DESCRIPTION

			"Indice interfaccia.

			 Corrisponde a ifIndex definito nella MIB-II"

		::= { physSerOpEntry 1 }



	physSerDsr      OBJECT-TYPE

			SYNTAX  INTEGER {

				dSR-OFF (0),

				dSR-ON  (1)

				}

			ACCESS  read-only

			STATUS  mandatory

		DESCRIPTION

			"Stato del DSR"

		::= { physSerOpEntry 2 }



	physSerCts      OBJECT-TYPE

			SYNTAX  INTEGER {

				cts-OFF (0),

				cts-ON  (1)

				}

			ACCESS  read-only

			STATUS  mandatory

		DESCRIPTION

			"Stato del CTS"

		::= { physSerOpEntry 3 }



	physSerDcd      OBJECT-TYPE

			SYNTAX  INTEGER {

				dcd-OFF (0),

				dcd-ON  (1)

				}

			ACCESS  read-only

			STATUS  mandatory

		DESCRIPTION

			"Stato del DCD"

		::= { physSerOpEntry 4 }

	physSerDtr      OBJECT-TYPE

			SYNTAX  INTEGER {

				dtr-OFF (0),

				dtr-ON  (1)

				}

			ACCESS  read-only

			STATUS  mandatory

		DESCRIPTION

			"Stato del DTR"

		::= { physSerOpEntry 5 }

	physSerRts      OBJECT-TYPE

			SYNTAX  INTEGER {

				rts-OFF (0),

				rts-ON  (1)

				}

			ACCESS  read-only

			STATUS  mandatory

		DESCRIPTION

			"Stato del RTS"

		::= { physSerOpEntry 6 }



-- *****************************************************************************

-- Gruppo SysAct

--           - SysActReset

-- *****************************************************************************



sysActReset     OBJECT-TYPE

		SYNTAX  INTEGER

		ACCESS  write-only

		STATUS  mandatory

	DESCRIPTION

		"Il SET di questa variabile imposta un azione di

		 reset sulla macchina"

	::= { sysAct 1 }



sysWriteConf OBJECT-TYPE

		SYNTAX  INTEGER

		ACCESS  write-only

		STATUS  mandatory

	DESCRIPTION

		"Il SET di questa variabile permette la scrittura

		 della configurazione nella memoria non volatile della macchina"

	::= { sysAct 2 }



sysConnConfig OBJECT-TYPE

		SYNTAX  INTEGER  {

		 configuration-channel-close(0),

		 configuration-channel-open(1)

		}

		ACCESS  read-write

		STATUS  mandatory

	DESCRIPTION

		"Apre il canale di comunicazione con l'applicazione di configurazione

		 per permettere la scrittura permanente della configurazione"

	::= { sysAct 3 }



-- *****************************************************************************

-- Gruppo SysSecur

--           - SysSecurCertState

-- *****************************************************************************

sysSecurCertTable OBJECT-TYPE

		SYNTAX  SEQUENCE OF SysSecurCertEntry 

		ACCESS  not-accessible

		STATUS  mandatory

	DESCRIPTION

		"Questa tabella, contiene i campi per identificare un certificato

		 stato,nome della ca,numero seriale delcert,data di scadenza,procedure fallite" 

	::= { sysSecur 1 }



sysSecurCertEntry  OBJECT-TYPE

			SYNTAX  SysSecurCertEntry  

			ACCESS  not-accessible

			STATUS  mandatory

		DESCRIPTION

			"Entry tabella SysSecurTabCert"

			INDEX   { sysSecurCertIndex }

		::= {sysSecurCertTable 1 }

	SysSecurCertEntry  ::= SEQUENCE {

		sysSecurCertIndex  INTEGER,

		sysSecurCertState  INTEGER,

		sysSecurCertComNam DisplayString,

		sysSecurCertSerNum DisplayString,

		sysSecurCertDataScad DisplayString,

		sysSecurFailedProc INTEGER      

		}



sysSecurCertIndex       OBJECT-TYPE

			SYNTAX  INTEGER

			ACCESS  read-only

			STATUS  mandatory

		DESCRIPTION

			"indice"

		::= { sysSecurCertEntry 1 }



sysSecurCertState       OBJECT-TYPE

			SYNTAX  INTEGER {

				certificato-assente (1),

				certificato-valido  (2),

				certificato-valido-e-certificato-rinnovato (3),

				certificato-in-scadenza (4),

				certificato-non-ancora-valido (5),

				certificato-scaduto (6)

				}

			ACCESS  read-only

			STATUS  mandatory

		DESCRIPTION

			"Stato del certificato del SAS"

		::= { sysSecurCertEntry 2 }



sysSecurCertComNam       OBJECT-TYPE

			SYNTAX  DisplayString

			ACCESS  read-only

			STATUS  mandatory

		DESCRIPTION

			"nome della certification authority"

		::= { sysSecurCertEntry 3 }



sysSecurCertSerNum       OBJECT-TYPE

			SYNTAX  DisplayString

			ACCESS  read-only

			STATUS  mandatory

		DESCRIPTION

			"numero identificativo del certificato"

		::= { sysSecurCertEntry 4 }



sysSecurCertDataScad       OBJECT-TYPE

			SYNTAX  DisplayString

			ACCESS  read-only

			STATUS  mandatory

		DESCRIPTION

			"data di scadenza del certificato"

		::= { sysSecurCertEntry 5 }



sysSecurFailedProc       OBJECT-TYPE

			SYNTAX  INTEGER { 

			 	fallito-rinnovo (1),

				fallito-backup(2),

				fallito-backup-di-rinnovo (3)

				}

			ACCESS  read-only

			STATUS  mandatory

		DESCRIPTION

			" procedure fallite "

		::= { sysSecurCertEntry 6 }



-- *****************************************************************************

-- Gruppo SysCPU

-- *****************************************************************************

cPUBusy OBJECT-TYPE

        SYNTAX      Counter

        MAX-ACCESS  read-only

        STATUS      current

        DESCRIPTION

            " Valore corrente della percentuale di utilizzo della CPU."

        ::= { sysCPU 1 }



cPUBusyMax5 OBJECT-TYPE

        SYNTAX      Counter

        MAX-ACCESS  read-only

        STATUS      current

        DESCRIPTION

            " Valore massimo della percentuale di utilizzo della CPU negli ultimi 5 minuti."

        ::= { sysCPU 2 }

cPUBusyAvr5 OBJECT-TYPE

        SYNTAX      Counter

        MAX-ACCESS  read-only

        STATUS      current

        DESCRIPTION

             " Valore medio della percentuale di utilizzo della CPU negli ultimi 5 minuti."

        ::= { sysCPU 3 }





-- *****************************************************************************

-- Gruppo SysLog

-- *****************************************************************************

sysLogBuffer OBJECT-TYPE

        SYNTAX      INTEGER

        MAX-ACCESS  read-write

        STATUS      current

        DESCRIPTION

            " Attivazione con numero di buffer a disposizione dell'attivita` di SYS LOG."

        ::= { sysLog 1 }



sysLogLevel OBJECT-TYPE

        SYNTAX      INTEGER

        MAX-ACCESS  read-write

        STATUS      current

        DESCRIPTION

            " Livello di funzionamento del SYS LOG."

        ::= { sysLog 2 }



sysLogIpAddress OBJECT-TYPE

        SYNTAX      IpAddress

        MAX-ACCESS  read-write

        STATUS      current

        DESCRIPTION

            " Indirizzo IP di invio pacchetti di SYS LOG."

        ::= { sysLog 3 }



sysLogUdpPort OBJECT-TYPE

        SYNTAX      INTEGER (1..65535)

        MAX-ACCESS  read-write

        STATUS      current

        DESCRIPTION

            " Porta di destinazione e sorgente del pacchetto di SYS LOG."

        ::= { sysLog 4 }



sysLogEraseBuffer OBJECT-TYPE

        SYNTAX      INTEGER 

        MAX-ACCESS  read-write

        STATUS      current

        DESCRIPTION

            " Inserendo un valore diverso da zero questa variabile,

		 il file di log viene vuotato."

        ::= { sysLog 5 }



sysLogTrap     OBJECT IDENTIFIER ::= { sysLog 6 }



sysLogTrapEnable OBJECT-TYPE

        SYNTAX      INTEGER { enabled(1), disabled(2) }

        MAX-ACCESS  read-write

        STATUS      mandatory

        DESCRIPTION

            "Abilitazione della trap di riempimento buffer log."

        DEFVAL { disabled }

        ::= { sysLogTrap 1 }



sysLogTrapLimit OBJECT-TYPE

        SYNTAX      INTEGER (1..99)

        MAX-ACCESS  read-write

        STATUS      current

        DESCRIPTION

            "Percentuale del buffer a cui va inviata la trap ."

        ::= { sysLogTrap 2 }



sysLogTrapBufferStatus OBJECT-TYPE

        SYNTAX      INTEGER

        MAX-ACCESS  read-only

        STATUS      current

        DESCRIPTION

            "Percentuale del buffer attuale."

        ::= { sysLogTrap 3 }



sysLogBufferWarning	TRAP-TYPE

		ENTERPRISE  amtec

		-- VARIABLES  {}

		DESCRIPTION

			"Viene inviata nel caso in cui il buffer ha raggiunto la

			 soglia di warning e a meta` della soglia stessa."



		-- #TEXTSTRING ""

		-- #SYMBOL AUTH-TRAP 0x9005

		::= 36869



sysLogBufferFull	TRAP-TYPE

		ENTERPRISE  amtec

		-- VARIABLES  {}

		DESCRIPTION

			"Viene inviata nel caso in cui il buffer e` pieno e

			inizia la sovrascrizione dello stesso."



		-- #TEXTSTRING ""

		-- #SYMBOL AUTH-TRAP 0x9006

		::= 36870



-- *****************************************************************************

--  GRUPPO PROTOCOLLI

--          Questo gruppo contiene una ramificazione per ogni protocollo

--          gestito dagli apparati AMTEC.

--                      - x25

--                      - Lapb

--                      - Lapd

--                      - Q931

--                      - Ip

--                      - i802-2

--                      - X28

--                      - Frame Relay (FRY)

--                      - PPP

--			- IKE

--			- DLSW

--			- ADSL

--			- ATM

--			- DNS

-- *****************************************************************************



x25     OBJECT IDENTIFIER ::= { protocol 1 }

lapb    OBJECT IDENTIFIER ::= { protocol 2 }

lapd    OBJECT IDENTIFIER ::= { protocol 3 }

q931    OBJECT IDENTIFIER ::= { protocol 4 }

ip      OBJECT IDENTIFIER ::= { protocol 5 }

i802-2  OBJECT IDENTIFIER ::= { protocol 6 }

x28     OBJECT IDENTIFIER ::= { protocol 7 }

fry     OBJECT IDENTIFIER ::= { protocol 8 }

ppp     OBJECT IDENTIFIER ::= { protocol 9 }

ike	OBJECT IDENTIFIER ::= { protocol 10 }

dlsw	OBJECT IDENTIFIER ::= { protocol 11 }

-- sebastiani

adsl	OBJECT IDENTIFIER ::= { protocol 12}

atm	OBJECT IDENTIFIER ::= { protocol 13}

-- fine sebastiani

dns	OBJECT IDENTIFIER ::= { protocol 14 }



-- *****************************************************************************

-- Gruppo X25

--        Ha le seguenti ramificazioni:

--        - X25Diag     - X25DiagIfc        - X25CnfTab     (TABELLA)

--                                          - X25OpTab      (TABELLA)

--                                          - X25CvTab      (TABELLA)

--                                          - X25CvClrTab   (TABELLA)

--                      - tX25DiagX25Rout    - X25RoutTab    (TABELLA)

--                                          - X25PvcTab     (TABELLA)

--                      - X25DiagAgenda

--        - X25Secur    - X25KeyGen 

-- *****************************************************************************



x25Diag         OBJECT IDENTIFIER ::= { x25 2 }

x25Secur        OBJECT IDENTIFIER ::= { x25 3 }

x25DiagIfc      OBJECT IDENTIFIER ::= { x25Diag 1 }

x25DiagX25Rout  OBJECT IDENTIFIER ::= { x25Diag 2 }









-- -------------------------------------------------------------------------

--     TABELLA X25CnfTab     

--                                               TABELLA CONFIGURAZIONE X25

-- -------------------------------------------------------------------------



x25CnfTable       OBJECT-TYPE

		SYNTAX  SEQUENCE OF X25CnfEntry

		ACCESS  not-accessible

		STATUS  mandatory

	DESCRIPTION

		" Questa tabella contiene i parametri X25 di configurazione

		  di una interfaccia."

	::= { x25DiagIfc 1 }



	x25CnfEntry     OBJECT-TYPE

			SYNTAX  X25CnfEntry

			ACCESS  not-accessible

			STATUS  mandatory

		DESCRIPTION

			"Entry tabella X25CnfTab"

			INDEX   { x25CnfIfc }

		::= { x25CnfTable 1 }

	X25CnfEntry ::= SEQUENCE {

		x25CnfIfc       INTEGER,

		x25CnfSec       INTEGER,

		x25CnfMode      INTEGER,

		x25CnfX121      DisplayString,

		x25CnfPvc       INTEGER,

		x25CnfOvc       INTEGER,

		x25CnfBsvc      INTEGER,

		x25CnfIvc       INTEGER,

		x25CnfPSizeTx   INTEGER,

		x25CnfPSizeRx   INTEGER,

		x25CnfWSize     INTEGER,

		x25CnfModule    INTEGER,

		x25CnfCrin      INTEGER,

		x25CnfLenCrin   INTEGER,

		x25CnfBckIfc    INTEGER,

		x25CnfBckMode   INTEGER

		}



	x25CnfIfc       OBJECT-TYPE

			SYNTAX  INTEGER

			ACCESS  read-only

			STATUS  mandatory

		DESCRIPTION

			"Indice dell'interfaccia su cui e` configurata

			 l'entita` X25. Questo valore coincide con quello

			 riportato dalla variabile ifIndex della MIB-II." 

		::= { x25CnfEntry 1 }



	x25CnfSec       OBJECT-TYPE

			SYNTAX  INTEGER{

					off (0),

					on (1)

					}       

			ACCESS  read-write

			STATUS  mandatory

		DESCRIPTION

			"Stabilisce se operazioni di crittazione sono

			 abilitate o meno sulla entito X25."

		::= { x25CnfEntry 2 }



	x25CnfMode      OBJECT-TYPE

			SYNTAX  INTEGER{

					dte (0),

					dce (128)

					}

			ACCESS  read-only

			STATUS  mandatory

		DESCRIPTION

			"Identifica la modalita' Dte/Dce con cui opera

			 l'interfaccia (liv.3)"

		::= { x25CnfEntry 3 }



	x25CnfX121      OBJECT-TYPE

			SYNTAX  DisplayString

			ACCESS  read-only

			STATUS  mandatory

		DESCRIPTION

			"X121 address relativo all'interfaccia.

			 Puo' ritornare una stringa vuota se il NUA non

			 e' stato impostato tramite configurazione."

		::= { x25CnfEntry 4 }



	x25CnfPvc       OBJECT-TYPE

			SYNTAX  INTEGER

			ACCESS  read-only

			STATUS  mandatory

		DESCRIPTION

			"Numero dei PVC configurati sull'interfaccia."

		::= { x25CnfEntry 5 }



	x25CnfOvc       OBJECT-TYPE

			SYNTAX  INTEGER

			ACCESS  read-only

			STATUS  mandatory

		DESCRIPTION

			"Numero OSVC configurati sull'interfaccia."

		::= { x25CnfEntry 6 }



	x25CnfBsvc      OBJECT-TYPE

			SYNTAX  INTEGER

			ACCESS  read-only

			STATUS  mandatory

		DESCRIPTION

			"Numero BSVC configurati sull'interfaccia."

		::= { x25CnfEntry 7 }



	x25CnfIvc       OBJECT-TYPE

			SYNTAX  INTEGER

			ACCESS  read-only

			STATUS  mandatory

		DESCRIPTION

			"Numero ISVC configurati sull'interfaccia"

		::= { x25CnfEntry 8 }



	x25CnfPSizeTx   OBJECT-TYPE

			SYNTAX  INTEGER

			ACCESS  read-only

			STATUS  mandatory

		DESCRIPTION

			"Packet Size in trasmissione relativa alla

			 interfaccia.

			 Valori possibili: 128,256,512,1024."

		::= { x25CnfEntry 9 }



	x25CnfPSizeRx   OBJECT-TYPE

			SYNTAX  INTEGER

			ACCESS  read-only

			STATUS  mandatory

		DESCRIPTION

			"Packet Size in ricezione relativa alla

			 interfaccia.

			 Valori possibili: 128,256,512,1024."

		::= { x25CnfEntry 10 }



	x25CnfWSize     OBJECT-TYPE

			SYNTAX  INTEGER

			ACCESS  read-only

			STATUS  mandatory

		DESCRIPTION

			"Window  size (1...7) relativa alla interfaccia."

		::= { x25CnfEntry 11 }



	x25CnfModule    OBJECT-TYPE

			SYNTAX  INTEGER{

					modulo-8 (0),

					modulo-128 (64)

					}

			ACCESS  read-only

			STATUS  mandatory

		DESCRIPTION

			"Modulo relativo al livello 3"

		::= { x25CnfEntry 12 }



	x25CnfCrin      OBJECT-TYPE

			SYNTAX  INTEGER{

					criterio-NUALEN (1),

					criterio-SUBLEN (2),

					criterio-NONE (3)

					}

			ACCESS  read-only

			STATUS  mandatory

		DESCRIPTION

			"Criterio instradamento configurato

			 (NUALEN/SUBLEN/NONE).

			(vedi manuale configurazione GAIA)."

		::= { x25CnfEntry 13 }



	x25CnfLenCrin   OBJECT-TYPE

			SYNTAX  INTEGER

			ACCESS  read-only

			STATUS  mandatory

		DESCRIPTION

			"Lunghezza utilizzata dal criterio di instradamento:

			 Valori ammessi: 0 se X25CnfCrin = NONE,

			 da 1...15 se X25CnfCrin = NUALEN e SUBLEN"

		::= { x25CnfEntry 14 }



	x25CnfBckIfc    OBJECT-TYPE

			SYNTAX  INTEGER

			ACCESS  read-only

			STATUS  mandatory

		DESCRIPTION

			"Indice SNMP (ifIndex MIB-II) della interfaccia

			 di backup, assume  valore 0 se non configurato

			 il backup."

		::= { x25CnfEntry 15 }



	x25CnfBckMode   OBJECT-TYPE

			SYNTAX  INTEGER{

					gradual-Backup (0),

					immediate-Backup (1)

					}

			ACCESS  read-only

			STATUS  mandatory

		DESCRIPTION

			"Modalita' di rientro dal backup (Immediata/Graduale) "

		::= { x25CnfEntry 16 }





-- -------------------------------------------------------------------------

--     TABELLA X25OpTab     

--                                               TABELLA OPERATIVA X25

-- -------------------------------------------------------------------------



x25OpTable        OBJECT-TYPE

		SYNTAX  SEQUENCE OF X25OpEntry

		ACCESS  not-accessible

		STATUS  mandatory

	DESCRIPTION

		"Questa tabella definisce i parametri OPERATIVI su una

		 interfaccia X25."

	::= { x25DiagIfc 2 }



	x25OpEntry      OBJECT-TYPE

			SYNTAX  X25OpEntry

			ACCESS  not-accessible

			STATUS  mandatory

		DESCRIPTION

			"Entry tabella X25OpTab"

			INDEX   { x25OpIfc }

		::= { x25OpTable 1 }

	X25OpEntry ::= SEQUENCE {

		x25OpIfc                INTEGER,

		x25OpState              INTEGER,

		x25OpCvAct              Counter,

		x25OpPckTx              Counter,

		x25OpPckRx              Counter,

		x25OpBckNum             Counter,

		x25OpBckState           INTEGER,

		x25OpBckTime            TimeTicks

		}



	x25OpIfc        OBJECT-TYPE

			SYNTAX  INTEGER

			ACCESS  read-only

			STATUS  mandatory

		DESCRIPTION

			"Indice SNMP (ifIndex MIB-II) dell'interfaccia X.25 "

		::= { x25OpEntry 1 }



	x25OpState      OBJECT-TYPE

			SYNTAX  INTEGER{

			not-configured (0),

			not-established (1),

			not-ready (2),

			restart-req-restart-ind (3),

			dte-restart-req (4),

			ready-r1 (5)

			}

			ACCESS  read-only

			STATUS  mandatory

		DESCRIPTION

			"Stato operativo dell'interfaccia logica di livello 3"

		::= { x25OpEntry 2 }



	x25OpCvAct      OBJECT-TYPE

			SYNTAX  Counter

			ACCESS  read-only

			STATUS  mandatory

		DESCRIPTION

			"Numero dei Circuiti Virtuali attivi (X25OpSate 

			 diverso da Not-Ready), ovvero la somma dei circuiti

			 tipo PVC e SVC inpegnati in una chiamata."

		::= { x25OpEntry 3 }



	x25OpPckTx      OBJECT-TYPE

			SYNTAX  Counter

			ACCESS  read-only

			STATUS  mandatory

		DESCRIPTION

			"Contatore dei pacchetti Dati trasmessi a livello 3"

		::= { x25OpEntry 4 }



	x25OpPckRx      OBJECT-TYPE

			SYNTAX  Counter

			ACCESS  read-only

			STATUS  mandatory

		DESCRIPTION

			"Contatore dei pacchetti Dati ricevuti a livello 3"

		::= { x25OpEntry 5 }



	x25OpBckNum     OBJECT-TYPE

			SYNTAX  Counter

			ACCESS  read-only

			STATUS  mandatory

		DESCRIPTION

			"Contatore dei backup effettuati a partire

			 dal restart dell'apparato."

		::= { x25OpEntry 6 }



	x25OpBckState   OBJECT-TYPE

			SYNTAX  INTEGER{

			non-operativo (0),

			operativo (1)

			}

			ACCESS  read-only

			STATUS  mandatory

		DESCRIPTION

			"Stato corrente del backup"

		::= { x25OpEntry 7 }



	x25OpBckTime    OBJECT-TYPE

			SYNTAX  TimeTicks

			ACCESS  read-only

			STATUS  mandatory

		DESCRIPTION

			"Valore di sysUpTime relativo allo stato

			 corrente del backup."

		::= { x25OpEntry 8 }





-- -------------------------------------------------------------------------

--     TABELLA X25CvTab     

--                                                TABELLA C.V. ATTIVI X25

-- -------------------------------------------------------------------------



x25CvTable        OBJECT-TYPE

		SYNTAX  SEQUENCE OF X25CvEntry

		ACCESS  not-accessible

		STATUS  mandatory

	DESCRIPTION

		"Tabella dello Stato dei C.V. ATTIVI sull'interfaccia"

	::= { x25DiagIfc 3 }



	x25CvEntry      OBJECT-TYPE

			SYNTAX  X25CvEntry

			ACCESS  not-accessible

			STATUS  mandatory

		DESCRIPTION

			"Entry tabella X25CvTab"

			INDEX   { x25CvIfcInd, x25CvLcgnLcn }

		::= { x25CvTable 1 }

	X25CvEntry ::= SEQUENCE {

		x25CvIfcInd             INTEGER,

		x25CvLcgnLcn            INTEGER,

		x25CvState              INTEGER,

		x25CvType               INTEGER,

		x25CvTimeAct            TimeTicks,

		x25CvPktSizeTx          INTEGER,

		x25CvPktSizeRx          INTEGER,

		x25CvWSize              INTEGER,

		x25CvCalling            DisplayString,

		x25CvCalled             DisplayString,

		x25CvProtId             DisplayString,

		x25CvIfcApplDest        INTEGER,

		x25CvPktTx              Counter,

		x25CvPktRx              Counter,

		x25CvResTx              Counter,

		x25CvReiRx              Counter,

		x25CvLastResTxRx        INTEGER,

		x25CvCauseLastRes       INTEGER,

		x25CvDiagLastRes        INTEGER

		}



	x25CvIfcInd     OBJECT-TYPE

			SYNTAX  INTEGER

			ACCESS  read-only

			STATUS  mandatory

		DESCRIPTION

			"Indice dell'interfaccia X.25 "

		::= { x25CvEntry 1 }



	x25CvLcgnLcn   OBJECT-TYPE

			SYNTAX  INTEGER

			ACCESS  read-only

			STATUS  mandatory

		DESCRIPTION

			"Indice C.V. LCGN+LCN "

		::= { x25CvEntry 2 }



	x25CvState      OBJECT-TYPE

			SYNTAX  INTEGER {

				ready-P1 (0),

				wait-Peer-DTE-waiting-P2-DCE-waiting-P3 (1),

				wait-upper-DTE-waiting-P3-DCE-waiting-P2 (2),

				call-collision-p5 (3),

				clr-DTE-p6-CLR-DCE-p7 (4),

				clear-request-upper-DTE-clear-request-p6 (5),

				flow-control-ready-Data-transfer-p4-d1 (6),

				res-DTE-d2-RES-DCE-d3 (7),

				reset-request-upper-DTE-reset-request-d2 (8),

				rnr-RX-sottostato-dello-stato-6 (101),

				rnr-TX-sottostato-dello-stato-6 (102),

				rnr-RXTX-sottostato-dello-stato-6 (103)

				}

			ACCESS  read-only

			STATUS  mandatory

		DESCRIPTION

			"Stato operativo del C.V. X25"

		::= { x25CvEntry 3 }



	x25CvType       OBJECT-TYPE

			SYNTAX  INTEGER {

				svc (0),

				pvc (1)

			}

			ACCESS  read-only

			STATUS  mandatory

		DESCRIPTION

			"Tipo C.V. impegnato (SVC, PVC)"

		::= { x25CvEntry 4 }



	x25CvTimeAct    OBJECT-TYPE

			SYNTAX  TimeTicks

			ACCESS  read-only

			STATUS  mandatory

		DESCRIPTION

			"Valore di sysUpTime relativo all'attivazione del C.V."

		::= { x25CvEntry 5 }



	x25CvPktSizeTx  OBJECT-TYPE

			SYNTAX  INTEGER

			ACCESS  read-only

			STATUS  mandatory

		DESCRIPTION

			"Corrente Packet Size in trasmissione, sul C.V."

		::= { x25CvEntry 6 }



	x25CvPktSizeRx  OBJECT-TYPE

			SYNTAX  INTEGER

			ACCESS  read-only

			STATUS  mandatory

		DESCRIPTION

			"Corrente Packet Size in ricezione, sul C.V."

		::= { x25CvEntry 7 }



	x25CvWSize      OBJECT-TYPE

			SYNTAX  INTEGER

			ACCESS  read-only

			STATUS  mandatory

		DESCRIPTION

			"Corrente Windows Size del C.V."

		::= { x25CvEntry 8 }



	x25CvCalling    OBJECT-TYPE

			SYNTAX  DisplayString

			ACCESS  read-only

			STATUS  mandatory

		DESCRIPTION

			"NUA Chiamante "

		::= { x25CvEntry 9 }



	x25CvCalled     OBJECT-TYPE

			SYNTAX  DisplayString

			ACCESS  read-only

			STATUS  mandatory

		DESCRIPTION

			"NUA Chiamato "

		::= { x25CvEntry 10 }



	x25CvProtId     OBJECT-TYPE

			SYNTAX  OCTET STRING

			ACCESS  read-only

			STATUS  mandatory

		DESCRIPTION

			"I primi 4 BYTES del Call User Data

			 (Protocol Identifier)."

		::= { x25CvEntry 11 }



	x25CvIfcApplDest OBJECT-TYPE

			SYNTAX  INTEGER {

				aPPLICAZIONE-IP         (1020)

				}

			ACCESS  read-only

			STATUS  mandatory

		DESCRIPTION

			"Indice della interfaccia (ifIndex relativo) o

			 applicazione destinataria.

			 Valori:

				 >1000 = applicazione

				 -1    = interfaccia non connessa"

		::= { x25CvEntry 12 }



	x25CvPktTx      OBJECT-TYPE

			SYNTAX  Counter

			ACCESS  read-only

			STATUS  mandatory

		DESCRIPTION

			"Totale pacchetti Dati trasmessi a livello 3

			 sul C.V."

		::= { x25CvEntry 13 }



	x25CvPktRx      OBJECT-TYPE

			SYNTAX  Counter

			ACCESS  read-only

			STATUS  mandatory

		DESCRIPTION

			"Totale pacchetti Dati Rx a livello 3 sul C.V."

		::= { x25CvEntry 14 }



	x25CvResTx      OBJECT-TYPE

			SYNTAX  Counter

			ACCESS  read-only

			STATUS  mandatory

		DESCRIPTION

			"Totale pacchetti Reset trasmessi sul C.V."

		::= { x25CvEntry 15 }



	x25CvReiRx      OBJECT-TYPE

			SYNTAX  Counter

			ACCESS  read-only

			STATUS  mandatory

		DESCRIPTION

			"Totale pacchetti Reset ricevuti sul C.V."

		::= { x25CvEntry 16 }



	x25CvLastResTxRx OBJECT-TYPE

			SYNTAX  INTEGER {

				nessun-RES (0),

				res-TX (1),

				res-RX (2)

				}

			ACCESS  read-only

			STATUS  mandatory

		DESCRIPTION

			"Direzione ultimo Reset sul C.V."

		::= { x25CvEntry 17 }



	x25CvCauseLastRes       OBJECT-TYPE

			SYNTAX  INTEGER

			ACCESS  read-only

			STATUS  mandatory

		DESCRIPTION

			"Causa ultimo Reset"

		::= { x25CvEntry 18 }



	x25CvDiagLastRes        OBJECT-TYPE

			SYNTAX  INTEGER

			ACCESS  read-only

			STATUS  mandatory

		DESCRIPTION

			"Diagnostica ultimo Reset"

		::= { x25CvEntry 19 }







-- **************************

--     Gruppo X25cvclr     

-- **************************



x25CvClr        OBJECT IDENTIFIER ::= { x25DiagIfc 4 }



x25CvNEntryReq  OBJECT-TYPE

		SYNTAX  INTEGER

		ACCESS  read-write

		STATUS  mandatory

	DESCRIPTION

		"Il numero di entry richieste, ovvero le tabelle

		 X25CvTab relative ad ogni interfaccia"

	::= { x25CvClr 1 }



x25CvNEntryGar  OBJECT-TYPE

		SYNTAX  INTEGER

		ACCESS  read-only

		STATUS  mandatory

	DESCRIPTION

		"Il numero di entry massime garantite, ovvero

		 il numero massimo di tabelle X25CvTab relative all'interfaccia"

	::= { x25CvClr 2 }





-- -------------------------------------------------------------------------

--     TABELLA X25CvClrTab     

--                                                TABELLA C.V. CLR X25

-- -------------------------------------------------------------------------





x25CvClrTable     OBJECT-TYPE

		SYNTAX  SEQUENCE OF X25CvClrEntry

		ACCESS  not-accessible

		STATUS  mandatory

	DESCRIPTION

		"Tabella dello Stato dei C.V. ABBATTUTI sull'interfaccia"

	::= { x25CvClr 3 }



	x25CvClrEntry   OBJECT-TYPE

			SYNTAX  X25CvClrEntry

			ACCESS  not-accessible

			STATUS  mandatory

		DESCRIPTION

			"Entry tabella X25CvClrTab"

			INDEX   { x25CvClrIfcInd, x25CvClrInd }

		::= { x25CvClrTable 1 }

	X25CvClrEntry ::= SEQUENCE {

		x25CvClrIfcInd          INTEGER,

		x25CvClrInd             INTEGER,

		x25CvTimeEst            TimeTicks,

		x25CvTimeClr            TimeTicks,

		x25CvLcnLcgn            INTEGER,

		x25CvLastClrDir         INTEGER,

		x25CvLastClrDir         INTEGER,

		x25CvClrCause           INTEGER,

		x25CvClrDiag            INTEGER,

		x25CvClrCalling         OCTET STRING,

		x25CvClrCalled          OCTET STRING,

		x25CvClrProtId          OCTET STRING

		}



	x25CvClrIfcInd  OBJECT-TYPE

			SYNTAX  INTEGER

			ACCESS  read-only

			STATUS  mandatory

		DESCRIPTION

			"Indice dell'interfaccia X.25 "

		::= { x25CvClrEntry 1 }



	x25CvClrInd     OBJECT-TYPE

			SYNTAX  INTEGER

			ACCESS  read-only

			STATUS  mandatory

		DESCRIPTION

			"Questo indice (65520 ...1) identifica in

			 maniera univoca la entry relativa al C.V.

			 abbattuto. L'indice parte da 65520 ed e'

			 decrementato per ogni nuova entry addizionata

			 alla tabella. Quando l'indice va a 0 si 

			 riparte da 65520 e tutte le entry sono ripulite

			 per ripartire da capo.

			 La getnext con indice 0 fornira' la entry piu'

			 recente, dunque con indice piu' basso.

			 Si ricorda che il numero massimo di entry memoriz-

			 zate in tabella sono pari al valore assunto dalla

			 variabile X25CvNEntryReq."

		::= { x25CvClrEntry 2 }



	x25CvTimeEst    OBJECT-TYPE

			SYNTAX  TimeTicks

			ACCESS  read-only

			STATUS  mandatory

		DESCRIPTION

			"Valore di sysUpTime relativo all'attivazione del C.V."

		::= { x25CvClrEntry 3 }



	x25CvTimeClr    OBJECT-TYPE

			SYNTAX  TimeTicks

			ACCESS  read-only

			STATUS  mandatory

		DESCRIPTION

			"Valore di sysUpTime relativo all'abbattimento del C.V."

		::= { x25CvClrEntry 4 }



	x25CvLcnLcgn    OBJECT-TYPE

			SYNTAX  INTEGER

			ACCESS  read-only

			STATUS  mandatory

		DESCRIPTION

			"Numero del C.V. (0...4095) che e' stato abbattuto

			 (LCGN+LCN)."

		::= { x25CvClrEntry 5 }



	x25CvLastClrDir OBJECT-TYPE

			SYNTAX  INTEGER {

				clr-TX (1),

				clr-RX (2)

				}

			ACCESS  read-only

			STATUS  mandatory

		DESCRIPTION

			"Direzione (Tx/Rx) dell'ultimo pacchetto di CLR

			 sul C.V."

		::= { x25CvClrEntry 6 }



	x25CvClrCause   OBJECT-TYPE

			SYNTAX  INTEGER

			ACCESS  read-only

			STATUS  mandatory

		DESCRIPTION

			"Causa relativa all'ultimo pacchetto di CLR

			 sul C.V."

		::= { x25CvClrEntry 7 }



	x25CvClrDiag    OBJECT-TYPE

			SYNTAX  INTEGER

			ACCESS  read-only

			STATUS  mandatory

		DESCRIPTION

			"Diagnostica relativa all'ultimo pacchetto di CLR

			 sul C.V."

		::= { x25CvClrEntry 8 }



	x25CvClrCalling OBJECT-TYPE

			SYNTAX  DisplayString

			ACCESS  read-only

			STATUS  mandatory

		DESCRIPTION

			"NUA chiamante del C.V. abbattuto."

		::= { x25CvClrEntry 9 }



	x25CvClrCalled  OBJECT-TYPE

			SYNTAX  DisplayString

			ACCESS  read-only

			STATUS  mandatory

		DESCRIPTION

			"NUA chiamato del C.V. abbattuto."

		::= { x25CvClrEntry 10 }



	x25CvClrProtId  OBJECT-TYPE

			SYNTAX  OCTET STRING

			ACCESS  read-only

			STATUS  mandatory

		DESCRIPTION

			"Protocol Identifier del C.V. abbattuto."

		::= { x25CvClrEntry 11 }



-- -------------------------------------------------------------------------

--     TABELLA X25RoutTab     

--                                                TABELLA INSTRADAMENTO X25

-- -------------------------------------------------------------------------





x25RoutTable      OBJECT-TYPE

		SYNTAX  SEQUENCE OF X25RoutEntry

		ACCESS  not-accessible

		STATUS  mandatory

	DESCRIPTION

		"Tabella instradamento X25/L4

		 Ogni riga di configurazione e' relativa all'instradamento X25

			ADD CONNECTION <ifc> <integer> <ifc> <integer>

		(vedi manuale di configurazione del SW GAIA) e'

		 una entry ." 

	::= { x25DiagX25Rout 1 }



	x25RoutEntry    OBJECT-TYPE

			SYNTAX  X25RoutEntry

			ACCESS  not-accessible

			STATUS  mandatory

		DESCRIPTION

			"Entry tabella X25RoutTab"

			INDEX   { x25RoutInd }

		::= { x25RoutTable 1 }



	X25RoutEntry ::= SEQUENCE {

		x25RoutInd              INTEGER,

		x25RoutIfcSource        INTEGER,

		x25RoutAddrSource       DisplayString,

		x25RoutIfcDest          INTEGER,

		x25RoutLinkDest         INTEGER

		}



	x25RoutInd      OBJECT-TYPE

			SYNTAX  INTEGER

			ACCESS  read-only

			STATUS  mandatory

		DESCRIPTION

			"Indice corrispondente al numero di entry in tabella"

		::= { x25RoutEntry 1 }



	x25RoutIfcSource        OBJECT-TYPE

				SYNTAX  INTEGER

				ACCESS  read-only

				STATUS  mandatory

		DESCRIPTION

			"Interfaccia sorgente"

		::= { x25RoutEntry 2 }



	x25RoutAddrSource       OBJECT-TYPE

				SYNTAX  DisplayString

				ACCESS  read-only

				STATUS  mandatory

		DESCRIPTION

			"Indirizzo sorgente (NUA o Sottoindirizzo)"

		::= { x25RoutEntry 3 }



	x25RoutIfcDest          OBJECT-TYPE

				SYNTAX  INTEGER

				ACCESS  read-only

				STATUS  mandatory

		DESCRIPTION

			"Interfaccia destinataria"

		::= { x25RoutEntry 4 }



	x25RoutLinkDest OBJECT-TYPE

				SYNTAX  INTEGER

				ACCESS  read-only

				STATUS  mandatory

		DESCRIPTION

			"Link destinatario valido solo per

			 interfacce destinatarie SDLC e 802"

		::= { x25RoutEntry 5 }





-- -------------------------------------------------------------------------

--     TABELLA X25PvcTab     

--                                                TABELLA CONNESSIONE PVC X25

-- -------------------------------------------------------------------------



x25PvcTable       OBJECT-TYPE

		SYNTAX  SEQUENCE OF X25PvcEntry

		ACCESS  not-accessible

		STATUS  mandatory

	DESCRIPTION

		"Tabella connessione PVC relativa a X25/L4.

		 Ad ogni entry corrisponde una riga del comando

		 di configurazione:

			ADD CONNECTION PVC <ifc> <integer> <ifc> <integer>

		(vedi manuale di configurazione del SW GAIA)."

	::= { x25DiagX25Rout 2 }



	x25PvcEntry     OBJECT-TYPE

			SYNTAX  X25PvcEntry

			ACCESS  not-accessible

			STATUS  mandatory

		DESCRIPTION

			"Entry tabella X25PvcTab"

			INDEX   { x25PvcInd }

		::= { x25PvcTable 1 }



	X25PvcEntry ::= SEQUENCE {

		x25PvcInd               INTEGER,

		x25PvcIfcSource         INTEGER,

		x25PvcPvcSource         INTEGER,

		x25PvcIfcDest           INTEGER,

		x25PvcPvcDest           INTEGER

		}



	x25PvcInd       OBJECT-TYPE

			SYNTAX  INTEGER

			ACCESS  read-only

			STATUS  mandatory

		DESCRIPTION

			"Indice corrispondente al numero di entry in tabella"

		::= { x25PvcEntry 1 }



	x25PvcIfcSource OBJECT-TYPE

				SYNTAX  INTEGER

				ACCESS  read-only

				STATUS  mandatory

		DESCRIPTION

			"Interfaccia sorgente"

		::= { x25PvcEntry 2 }



	x25PvcPvcSource OBJECT-TYPE

				SYNTAX  INTEGER

				ACCESS  read-only

				STATUS  mandatory

		DESCRIPTION

			"Numero PVC sorgente"

		::= { x25PvcEntry 3 }



	x25PvcIfcDest           OBJECT-TYPE

				SYNTAX  INTEGER

				ACCESS  read-only

				STATUS  mandatory

		DESCRIPTION

			"Interfaccia destinataria"

		::= { x25PvcEntry 4 }



	x25PvcPvcDest   OBJECT-TYPE

				SYNTAX  INTEGER

				ACCESS  read-only

				STATUS  mandatory

		DESCRIPTION

			"Numero PVC destinatario"

		::= { x25PvcEntry 5 }







-- -------------------------------------------------------------------------

--     TABELLA Agenda     

--                                                Agenda di un apparato con funzioni di

--                                                crittografia

-- -------------------------------------------------------------------------

agendaTable  OBJECT-TYPE

		SYNTAX  SEQUENCE OF AgendaEntry

		ACCESS  not-accessible

		STATUS  mandatory

	DESCRIPTION

		" tabella agenda "

	::= { x25Diag 3 }





agendaEntry         OBJECT-TYPE

		SYNTAX  AgendaEntry

		ACCESS  not-accessible

		STATUS  mandatory 

	DESCRIPTION

	  "Entry tabella Agenda"

	INDEX { x25AgIndex }

	::= { agendaTable 1 }        



AgendaEntry ::= SEQUENCE {

	x25AgIndex              INTEGER,

	x25AgNua                INTEGER,

	x25AgCypher             INTEGER,

	x25AgChain              INTEGER,

	x25AgIntegr             INTEGER,

	x25AgSignt              INTEGER,

	x25AgAuth               INTEGER,

	x25AgAccessctrl INTEGER,

	x25AgAuthintv   TimeTicks

	}





	x25AgIndex OBJECT-TYPE

			SYNTAX  INTEGER

			ACCESS  read-write

			STATUS  mandatory

		DESCRIPTION

			"Indice della generica entry di agenda"

		::= { agendaEntry 1 }



	

	x25AgNua        OBJECT-TYPE

			SYNTAX  INTEGER

			ACCESS  read-write

			STATUS  mandatory

		DESCRIPTION

			"nua memorizzato in agenda"

		::= { agendaEntry 2 }





	x25AgCypher     OBJECT-TYPE

			SYNTAX  INTEGER

			ACCESS  read-write

			STATUS  mandatory

		DESCRIPTION

			"cifratura on/off"

		::= { agendaEntry 3 }





	x25AgChain      OBJECT-TYPE

			SYNTAX  INTEGER

			ACCESS  read-write

			STATUS  mandatory

		DESCRIPTION

			"concatenazione on/off"

		::= { agendaEntry 4 }





	x25AgIntegr     OBJECT-TYPE

			SYNTAX  INTEGER

			ACCESS  read-write

			STATUS  mandatory

		DESCRIPTION

			"integrazione on/off"

		::= { agendaEntry 5 }





	x25AgSignt      OBJECT-TYPE

			SYNTAX  INTEGER

			ACCESS  read-write

			STATUS  mandatory

		DESCRIPTION

			"firma on/off"

		::= { agendaEntry 6 }





	x25AgAuth       OBJECT-TYPE

			SYNTAX  INTEGER

			ACCESS  read-write

			STATUS  mandatory

		DESCRIPTION

			"autenticazione on/off"

		::= { agendaEntry 7 }





	x25AgAccessctrl OBJECT-TYPE

			SYNTAX  INTEGER

			ACCESS  read-write

			STATUS  mandatory

		DESCRIPTION

			"controllo di accesso on/off"

		::= { agendaEntry 8 }





	x25AgAuthintv    OBJECT-TYPE

			SYNTAX  TimeTicks

			ACCESS  read-write

			STATUS  mandatory

		DESCRIPTION

			"intervallo di autenticazione"

		::= { agendaEntry 9 }





-- ****************************************************************************





agState     OBJECT-TYPE

		SYNTAX  INTEGER

		ACCESS  read-write

		STATUS  mandatory

	DESCRIPTION

		"Questa variabile definisce i possibili stati della tabella Agenda.

		 Valori possibili:

		 0:     Agenda corrotta;

		 1:     Agenda presente e avente almeno una entry;

		 2:     Agenda presente e avente 0 entries;

		 3:     Agenda non presente (il che significa che non e presente

			l'apparato di crittografia)."

	::= { x25Diag 4 }







cryCardInOut     OBJECT-TYPE

		SYNTAX  INTEGER

		ACCESS  read-write

		STATUS  mandatory

	DESCRIPTION

		"Questa variabile specifica se, in un apparato con CryptoCard, essa

		 e inserita o meno.

		 Valori possibili:

		 1:     Crypto Card in

		 0:     Crypto Card out

		 Negli apparati con Crypto Device, essa vale sempre 1."

	::= { x25Diag 5 }





x25Rmtkey       OBJECT-TYPE

		SYNTAX  OCTET STRING

		ACCESS  read-write

		STATUS  mandatory

	DESCRIPTION

		"chiave pubblica del dispositivo rmt"

	::= { x25Diag 6 }





x25Ltc  OBJECT-TYPE

		SYNTAX  INTEGER

		ACCESS  read-write

		STATUS  mandatory

	DESCRIPTION

		"last trap confirmed yes/no"

	::= { x25Diag 7 }





-- -------------------------------------------------------------------------

--     FOGLIE del nodo X25Secur  

-- -------------------------------------------------------------------------



x25KeyGen OBJECT-TYPE

		SYNTAX  INTEGER

		ACCESS  read-write

		STATUS  mandatory

	DESCRIPTION

		"Questa variabile gestisce il processo di generazione delle chiavi

		 Valori possibili:

		 0:     Non viene intrapresa nessuna azione;

		 1:     Avvia la procedura di generazione delle chiavi;

		 2:     Scrittura delle chiavi generate e loro cancellazione;

		 3:     Cancellazione delle chiavi generate senza scrittura."

	::= { x25Secur 1 }



x25IdReq OBJECT-TYPE

		SYNTAX  INTEGER

		ACCESS  read-write

		STATUS  mandatory

	DESCRIPTION

		"Questa variabile gestisce:

		1 - aggiornamento dell'agenda se settata a -1;

		2 - servizio di autolearning, in questo caso viene settata dal CGS in seguito ad una trap inviata dal dispositivo e pu assumere un valore >= 0;"

	::= { x25Secur 2 }



x25KeyReq-h OBJECT-TYPE

		SYNTAX  DisplayString

		ACCESS  read-write

		STATUS  mandatory

	DESCRIPTION

		"Questa variabile contiene i primi 244 byte del record agenda inviato dal CGS."

	::= { x25Secur 3 }



x25KeyReq-l OBJECT-TYPE

		SYNTAX  DisplayString

		ACCESS  read-write

		STATUS  mandatory

	DESCRIPTION

		"Questa variabile contiene gli ultimi 243 byte del record agenda inviato dal CGS."

	::= { x25Secur 4 }





-- *****************************************************************************

-- Gruppo Lapb

--        Ha le seguenti ramificazioni:

--        - LapbDiag    - LapdDiagIfc       - LapbCnfTab     (TABELLA)

--                                          - LapbOpTab      (TABELLA)

-- *****************************************************************************



lapbDiag        OBJECT IDENTIFIER ::= { lapb 2 }

lapbDiagIfc     OBJECT IDENTIFIER ::= { lapbDiag 1}







-- -------------------------------------------------------------------------

--     TABELLA LapbCnfTab     

--                                               TABELLA CONFIGURAZIONE LAPB

-- -------------------------------------------------------------------------

lapbCnfTable      OBJECT-TYPE

		SYNTAX  SEQUENCE OF LapbCnfEntry

		ACCESS  not-accessible

		STATUS  mandatory

	DESCRIPTION

		"Tabella dei parametri di configurazione Lapb relativi

		 ad una interfaccia."

	::= { lapbDiagIfc 1 }



	lapbCnfEntry    OBJECT-TYPE

			SYNTAX  LapbCnfEntry

			ACCESS  not-accessible

			STATUS  mandatory

		DESCRIPTION

			"Entry tabella LapbCnfTab"

			INDEX   { lapbCnfIfc }

		::= { lapbCnfTable 1 }

	LapbCnfEntry ::= SEQUENCE {

		lapbCnfIfc      INTEGER,

		lapbType        INTEGER,

		lapbModule      INTEGER,

		lapbN1          INTEGER,

		lapbK           INTEGER,

		lapbN2          INTEGER,

		lapbT1          INTEGER

		}



	lapbCnfIfc      OBJECT-TYPE

			SYNTAX  INTEGER

			ACCESS  read-only

			STATUS  mandatory

		DESCRIPTION

			"L'interfaccia su cui e` configurata l'entita` LAPB,

			 corrisponde a ifIndex della MIB II."

		::= { lapbCnfEntry 1 }



	lapbType        OBJECT-TYPE

			SYNTAX  INTEGER {

				dte   (1),

				dce   (2)

				}

			ACCESS  read-only

			STATUS  mandatory

		DESCRIPTION

			"La modalita` DTE/DCE LAPB"

		::= { lapbCnfEntry 2 }



	lapbModule      OBJECT-TYPE

			SYNTAX  INTEGER

			ACCESS  read-only

			STATUS  mandatory

		DESCRIPTION

			"Il modulo (8 / 128)"

		::= { lapbCnfEntry 3 }



	lapbN1          OBJECT-TYPE

			SYNTAX  INTEGER

			ACCESS  read-only

			STATUS  mandatory

		DESCRIPTION

			"Il valore di N1"

		::= { lapbCnfEntry 4 }



	lapbK           OBJECT-TYPE

			SYNTAX  INTEGER

			ACCESS  read-only

			STATUS  mandatory

		DESCRIPTION

			"Il valore di k"

		::= { lapbCnfEntry 5 }



	lapbN2          OBJECT-TYPE

			SYNTAX  INTEGER

			ACCESS  read-only

			STATUS  mandatory

		DESCRIPTION

			"Il valore di N2"

		::= { lapbCnfEntry 6 }



	lapbT1          OBJECT-TYPE

			SYNTAX  INTEGER

			ACCESS  read-only

			STATUS  mandatory

		DESCRIPTION

			"Il valore di T1"

		::= { lapbCnfEntry 7 }



-- sebastiani





	 adslmib OBJECT IDENTIFIER ::= { adsl 1}

	 adsllinemib OBJECT IDENTIFIER ::= { adslmib 1 }

         adslMibObject OBJECT IDENTIFIER ::= { adsllinemib 1 }





-- ------------------------------------------------------------------------



--       VARIABILE AdslLineCodingType	



-- ------------------------------------------------------------------------

  

       adslLineCodingType OBJECT-TYPE

             SYNTAX      INTEGER {

                 noChannel (1),        -- no channels exist

                 fastOnly (2),         -- fast channel exists only

                 interleavedOnly (3),  -- interleaved channel exists

                                       -- only

                 fastOrInterleaved (4),-- either fast or interleaved

                                       -- channels can exist, but

                                       -- only one at any time

                 fastAndInterleaved (5)-- both fast or interleaved

                                       -- channels exist

             }

            ACCESS  read-only

            STATUS  mandatory

            DESCRIPTION

                 "Defines the type of ADSL physical line

                 entity that exists, by defining whether and how

                 the line is channelized.  If the line is channelized,

                 the value will be other than noChannel(1).  This

                 object defines which channel type(s) are supported.

                 In the case that the line is channelized, the manager

                 can use the ifStackTable to determine the ifIndex for

                 the associated channel(s)."

	    ::= { adslMibObject 1 }





-- -------------------------------------------------------------------------

--

--    TABELLA  adslAturPhysTable        

--                                               

-- -------------------------------------------------------------------------



        adslAturPhysTable        OBJECT-TYPE

             SYNTAX          SEQUENCE OF AdslAturPhysEntry

             MAX-ACCESS      not-accessible

             STATUS          current

             DESCRIPTION

                 "This table provides one row for each ATUR

                 Each row contains the Physical Layer Parameters

                 table for that ATUR. ADSL physical interfaces are

                 those ifEntries where ifType is equal to adsl(94)."

	  ::= { adslMibObject 2 }

         adslAturPhysEntry       OBJECT-TYPE

             SYNTAX          AdslAturPhysEntry

             MAX-ACCESS      not-accessible

             STATUS          current

             DESCRIPTION     "An entry in the adslAturPhysTable."

             INDEX           { adslAturifIndex ,adslAturIndex }

         ::= { adslAturPhysTable 1 }

         AdslAturPhysEntry ::=

             SEQUENCE {

	     adslAturifIndex		     INTEGER,

	     adslAturIndex		     INTEGER,	

             adslAturInvSerialNumber         OCTET STRING,

             adslAturInvVendorID             OCTET STRING,

             adslAturInvVersionNumber        OCTET STRING,

             adslAturCurrSnrMgn              INTEGER,

             adslAturCurrAtn                 Gauge32,

             adslAturCurrStatus              INTEGER,

             adslAturCurrOutputPwr           INTEGER,

             adslAturCurrAttainableRate      Gauge

             }

         -- inventory group

         --



         adslAturifIndex  OBJECT-TYPE

             SYNTAX      INTEGER (-640..640)

             UNITS       " units "

             MAX-ACCESS  read-only

             STATUS      current

             DESCRIPTION

                 " IFindex "

         ::= { adslAturPhysEntry 1 }



         adslAturIndex   OBJECT-TYPE

             SYNTAX      INTEGER (-640..640)

             UNITS       " units "

             MAX-ACCESS  read-only

             STATUS      current

             DESCRIPTION

                 " index "

         ::= { adslAturPhysEntry 2 }





         adslAturInvSerialNumber OBJECT-TYPE

             SYNTAX      OCTET STRING

             MAX-ACCESS  read-only

             STATUS      current

             DESCRIPTION

                 "The vendor specific string that identifies the

                 vendor equipment."

         ::= { adslAturPhysEntry 3 }

         adslAturInvVendorID OBJECT-TYPE

             SYNTAX      OCTET STRING

             MAX-ACCESS  read-only

             STATUS      current

             DESCRIPTION

                 "The vendor ID code is a copy of the binary

                 vendor identification field defined by the

                 PHY[10] and expressed as readable characters."

             REFERENCE "ANSI T1.413"

         ::= { adslAturPhysEntry 4 }

         adslAturInvVersionNumber OBJECT-TYPE

             SYNTAX      OCTET STRING

             MAX-ACCESS  read-only

             STATUS      current

             DESCRIPTION

                 "The vendor specific version number sent by this ATU

                 as part of the initialization messages.  It is a copy

                 of the binary version number field defined by the

                 PHY[10] and expressed as readable characters."

             REFERENCE "ANSI T1.413"

         ::= { adslAturPhysEntry 5 }

         -- current status group

         --

         adslAturCurrSnrMgn OBJECT-TYPE

             SYNTAX      INTEGER (-640..640)

             UNITS       "tenth dB"

             MAX-ACCESS  read-only

             STATUS      current

             DESCRIPTION

                 "Noise Margin as seen by this ATU with respect to its

                 received signal in tenth dB."

         ::= { adslAturPhysEntry 6 }

         adslAturCurrAtn OBJECT-TYPE

             SYNTAX      Gauge32

             UNITS       "tenth dB"

             MAX-ACCESS  read-only

             STATUS      current

             DESCRIPTION

                 "Measured difference in the total power transmitted by

                 the peer ATU and the total power received by this ATU."

         ::= { adslAturPhysEntry 7 }

        adslAturCurrStatus OBJECT-TYPE

             SYNTAX     INTEGER {

                              noDefect(0),

                              lossOfFraming(1),

                              lossOfSignal(2),

                              lossOfPower(3),

                              lossOfSignalQuality(4)

                             }

             MAX-ACCESS  read-only

             STATUS      current

             DESCRIPTION

                 "Indicates current state of the ATUR line.  This is a

                 bit-map of possible conditions.  Due to the isolation

                 of the ATUR when line problems occur, many state

                 conditions like loss of power, loss of quality signal,

                 and initialization errors,  can not be determined.

                 While trouble shooting ATUR, also use object,

                 adslAtucCurrStatus.  The various bit positions are:

          0      noDefect             There no defects on the line

          1      lossOfFraming        ATUR failure due to not

                                      receiving valid frame

          2      lossOfSignal         ATUR failure due to not

                                      receiving signal

          3      lossOfPower          ATUR failure due to loss of

                                      power

          4      lossOfSignalQuality  Loss of Signal Quality is

                                      declared when the Noise Margin

                                      falls below the Minimum Noise

                                      Margin, or the

                                      bit-error-rate exceeds 10^-7.

                 This is intended to supplement ifOperStatus."

         ::= { adslAturPhysEntry 8 }

         adslAturCurrOutputPwr OBJECT-TYPE

             SYNTAX      INTEGER (-310..310)

             UNITS       "tenth dBm"

             MAX-ACCESS  read-only

             STATUS      current

             DESCRIPTION

                 "Measured total output power transmitted by this ATU.

                 This is the measurement that was reported during

                 the last activation sequence."

         ::= { adslAturPhysEntry 9 }

         adslAturCurrAttainableRate OBJECT-TYPE

             SYNTAX      Gauge

             UNITS       "bps"

             MAX-ACCESS  read-only

             STATUS      current

             DESCRIPTION

                 "Indicates the maximum currently attainable data rate

                 by the ATU.  This value will be equal or greater than

                 the current line rate."

         ::= { adslAturPhysEntry 10 }



-- -------------------------------------------------------------------------

--

--    TABELLA  adslAtucPhysTable       

--                                               

-- -------------------------------------------------------------------------



        adslAtucPhysTable        OBJECT-TYPE

             SYNTAX          SEQUENCE OF AdslAtucPhysEntry

             MAX-ACCESS      not-accessible

             STATUS          current

             DESCRIPTION

                 "This table provides one row for each ATUC

                 Each row contains the Physical Layer Parameters

                 table for that ATUC. ADSL physical interfaces are

                 those ifEntries where ifType is equal to adsl(94)."

	  ::= { adslMibObject 3 }



         adslAtucPhysEntry       OBJECT-TYPE

             SYNTAX          AdslAtucPhysEntry

             MAX-ACCESS      not-accessible

             STATUS          current

             DESCRIPTION     "An entry in the adslAturPhysTable."

             INDEX           { adslAtucifIndex ,adslAtucIndex }

         ::= { adslAtucPhysTable 1 }



         AdslAtucPhysEntry ::=

             SEQUENCE {

	     adslAtucifIndex		     INTEGER,	

	     adslAtucIndex		     INTEGER,	

             adslAtucInvVendorID             OCTET STRING,

             adslAtucInvVersionNumber        OCTET STRING,

             adslAtucCurrStatus              INTEGER,

             adslAtucCurrOutputPwr           INTEGER,

             adslAtucCurrAttainableRate      Gauge

             }

         -- inventory group

         --



         adslAtucifIndex  OBJECT-TYPE

             SYNTAX      INTEGER (-640..640)

             UNITS       " units "

             MAX-ACCESS  read-only

             STATUS      current

             DESCRIPTION

                 " IFindex "

         ::= { adslAtucPhysEntry 1 }



         adslAtucIndex  OBJECT-TYPE

             SYNTAX      INTEGER (-640..640)

             UNITS       " units "

             MAX-ACCESS  read-only

             STATUS      current

             DESCRIPTION

                 " index "

         ::= { adslAtucPhysEntry 2 }



         adslAtucInvVendorID OBJECT-TYPE

             SYNTAX      OCTET STRING

             MAX-ACCESS  read-only

             STATUS      current

             DESCRIPTION

                 "The vendor ID code is a copy of the binary

                 vendor identification field defined by the

                 PHY[10] and expressed as readable characters."

             REFERENCE "ANSI T1.413"

         ::= { adslAtucPhysEntry 3 }



         adslAtucInvVersionNumber OBJECT-TYPE

             SYNTAX      OCTET STRING

             MAX-ACCESS  read-only

             STATUS      current

             DESCRIPTION

                 "The vendor specific version number sent by this ATU

                 as part of the initialization messages.  It is a copy

                 of the binary version number field defined by the

                 PHY[10] and expressed as readable characters."

             REFERENCE "ANSI T1.413"

         ::= { adslAtucPhysEntry 4 }

         -- current status group

         --

        adslAtucCurrStatus OBJECT-TYPE

             SYNTAX     INTEGER {

                              noDefect(0),

                              lossOfFraming(1),

                              lossOfSignal(2),

                              lossOfPower(3),

                              lossOfSignalQuality(4)

                             }

             MAX-ACCESS  read-only

             STATUS      current

             DESCRIPTION

                 "Indicates current state of the ATUR line.  This is a

                 bit-map of possible conditions.  Due to the isolation

                 of the ATUR when line problems occur, many state

                 conditions like loss of power, loss of quality signal,

                 and initialization errors,  can not be determined.

                 While trouble shooting ATUR, also use object,

                 adslAtucCurrStatus.  The various bit positions are:

          0      noDefect             There no defects on the line

          1      lossOfFraming        ATUR failure due to not

                                      receiving valid frame

          2      lossOfSignal         ATUR failure due to not

                                      receiving signal

          3      lossOfPower          ATUR failure due to loss of

                                      power

          4      lossOfSignalQuality  Loss of Signal Quality is

                                      declared when the Noise Margin

                                      falls below the Minimum Noise

                                      Margin, or the

                                      bit-error-rate exceeds 10^-7.

                 This is intended to supplement ifOperStatus."

         ::= { adslAtucPhysEntry 5 }



         adslAtucCurrOutputPwr OBJECT-TYPE

             SYNTAX      INTEGER (-310..310)

             UNITS       "tenth dBm"

             MAX-ACCESS  read-only

             STATUS      current

             DESCRIPTION

                 "Measured total output power transmitted by this ATU.

                 This is the measurement that was reported during

                 the last activation sequence."

         ::= { adslAtucPhysEntry 6 }



         adslAtucCurrAttainableRate OBJECT-TYPE

             SYNTAX      Gauge

             UNITS       "bps"

             MAX-ACCESS  read-only

             STATUS      current

             DESCRIPTION

                 "Indicates the maximum currently attainable data rate

                 by the ATU.  This value will be equal or greater than

                 the current line rate."

         ::= { adslAtucPhysEntry 7 }





-- -------------------------------------------------------------------------

--

--    TABELLA  adslAturChanTable       

--                                               

-- -------------------------------------------------------------------------





        adslAturChanTable       OBJECT-TYPE

             SYNTAX          SEQUENCE OF AdslAturChanEntry

             MAX-ACCESS      not-accessible

             STATUS          current

             DESCRIPTION

                 "This table provides one row for each ATUC channel"

	  ::= { adslMibObject 4 }



         adslAturChanEntry       OBJECT-TYPE

             SYNTAX          AdslAturChanEntry

             MAX-ACCESS      not-accessible

             STATUS          current

             DESCRIPTION     "An entry in the adslAtucChanTable."

             INDEX           { adslAturChanIfIndex, adslAturChanIndex }

         ::= { adslAturChanTable 1 }



         AdslAturChanEntry ::=

             SEQUENCE {

	     adslAturChanIfIndex     	     INTEGER,

	     adslAturChanIndex	     	     INTEGER,		

             adslAturChanCurrTxRate          Gauge32,

	     adslAturChanCorrectedBlks       Counter32,

             adslAturChanUncorrectBlks       Counter32,

	     adslAturChanReceivedCells	     Counter32,	

	     adslAturChanTransmittedCells    Counter32	

             }



        adslAturChanIfIndex  OBJECT-TYPE

             SYNTAX      INTEGER (-640..640)

             UNITS       " units "

             MAX-ACCESS  read-only

             STATUS      current

             DESCRIPTION

                 " index "

         ::= { adslAturChanEntry 1 }



       adslAturChanIndex OBJECT-TYPE

             SYNTAX      INTEGER (-640..640)

             UNITS       " units "

             MAX-ACCESS  read-only

             STATUS      current

             DESCRIPTION

                 " index "

         ::= { adslAturChanEntry 2 }





         adslAturChanCurrTxRate  OBJECT-TYPE

             SYNTAX      Gauge32

             UNITS       "bps"

             MAX-ACCESS  read-only

             STATUS      current

             DESCRIPTION

                 "Actual transmit rate on this channel."

         ::= { adslAturChanEntry 3 }



         adslAturChanCorrectedBlks  OBJECT-TYPE

             SYNTAX      Counter32

             MAX-ACCESS  read-only

             STATUS      current

             DESCRIPTION

                 "Count of all blocks received with errors that were

                 corrected since agent reset.  These blocks are passed

                 on as good data."

         ::= { adslAturChanEntry 4 }



         adslAturChanUncorrectBlks  OBJECT-TYPE

             SYNTAX      Counter32

             MAX-ACCESS  read-only

             STATUS      current

             DESCRIPTION

                 "Count of all blocks received with uncorrectable

                 errors since agent reset."

         ::= { adslAturChanEntry 5 }



         adslAturChanReceivedCells  OBJECT-TYPE

             SYNTAX      Counter32

             MAX-ACCESS  read-only

             STATUS      current

             DESCRIPTION

                 "Count of all cells received "

         ::= { adslAturChanEntry 6 }



         adslAturChanTransmittedCells  OBJECT-TYPE

             SYNTAX      Counter32

             MAX-ACCESS  read-only

             STATUS      current

             DESCRIPTION

                 "Count of all cells transmitted "

         ::= { adslAturChanEntry 7 }



 

-- -------------------------------------------------------------------------

--

--    TABELLA  adslAtucChanTable

--                                               

-- -------------------------------------------------------------------------





        adslAtucChanTable       OBJECT-TYPE

             SYNTAX          SEQUENCE OF AdslAtucChanEntry

             MAX-ACCESS      not-accessible

             STATUS          current

             DESCRIPTION

                 "This table provides one row for each ATUC channel"

	  ::= { adslMibObject 5 }





         adslAtucChanEntry       OBJECT-TYPE

             SYNTAX          AdslAtucChanEntry

             MAX-ACCESS      not-accessible

             STATUS          current

             DESCRIPTION     "An entry in the adslAtucChanTable."

             INDEX           { adslAtucChanIfIndex ,adslAtucChanIndex }

         ::= { adslAtucChanTable 1 }





         AdslAtucChanEntry ::=

             SEQUENCE {

	     adslAtucChanIfIndex     	     INTEGER,

	     adslAtucChanIndex     	     INTEGER,	

             adslAtucChanCurrTxRate          Gauge32,

	     adslAtucChanCorrectedBlks       Counter32,

             adslAtucChanUncorrectBlks       Counter32

             }



         adslAtucChanIfIndex OBJECT-TYPE

             SYNTAX      INTEGER 

             UNITS       " units "

             MAX-ACCESS  read-only

             STATUS      current

             DESCRIPTION

                 " index "

         ::= { adslAtucChanEntry 1 }



         adslAtucChanIndex OBJECT-TYPE

             SYNTAX      INTEGER 

             UNITS       " units "

             MAX-ACCESS  read-only

             STATUS      current

             DESCRIPTION

                 " index "

         ::= { adslAtucChanEntry 2 }



         adslAtucChanCurrTxRate  OBJECT-TYPE

             SYNTAX      Gauge32

             UNITS       "bps"

             MAX-ACCESS  read-only

             STATUS      current

             DESCRIPTION

                 "Actual transmit rate on this channel."

         ::= { adslAtucChanEntry 3 }



         adslAtucChanCorrectedBlks  OBJECT-TYPE

             SYNTAX      Counter32

             MAX-ACCESS  read-only

             STATUS      current

             DESCRIPTION

                 "Count of all blocks received with errors that were

                 corrected since agent reset.  These blocks are passed

                 on as good data."

         ::= { adslAtucChanEntry 4 }



         adslAtucChanUncorrectBlks  OBJECT-TYPE

             SYNTAX      Counter32

             MAX-ACCESS  read-only

             STATUS      current

             DESCRIPTION

                 "Count of all blocks received with uncorrectable

                 errors since agent reset."

         ::= { adslAtucChanEntry 5 }









 	atmmib OBJECT IDENTIFIER ::= { atm 1}

	atmMibObject OBJECT IDENTIFIER ::= { atmmib 1 }









      

	     atmPvcTable       OBJECT-TYPE

             SYNTAX          SEQUENCE OF AtmPvcEntry

             MAX-ACCESS      read-only

             STATUS          mandatory

             DESCRIPTION

                 "This table provides one row for each PVC"

		  ::= { atmMibObject 1 }





             atmPvcEntry	OBJECT-TYPE

             SYNTAX          AtmPvcEntry	

             MAX-ACCESS      read-only

             STATUS          mandatory

             DESCRIPTION     "An entry in the atmPvcTable ."

             INDEX           { atmifIndex, atmpvcIndex }

	         ::= { atmPvcTable 1 }





             AtmPvcEntry::=

             SEQUENCE {

	     atmifIndex			INTEGER,

	     atmpvcIndex		INTEGER,	

	     atmPvc			INTEGER,		

             atmVpi           		INTEGER,

	     atmVci           		INTEGER,

             atmVccAalType       	DisplayString (SIZE (0..255)),

	     atmVccMode			DisplayString (SIZE (0..255)), 	

	     atmAalEncapsType		DisplayString (SIZE (0..255)),

	     atmPvcSpeed    		Counter,

	     atmPvcInOctets             Counter,

             atmPvcUcastPkts            Counter,

             atmPvcNUcastPkts           Counter,

             atmPvcDiscards             Counter,

             atmPvcErrors               Counter,

             atmPvcUnknownProtos        Counter,

             atmPvcOutOctets            Counter,

             atmPvcOutUcastPkts         Counter,

             atmPvcOutNUcastPkts        Counter,

             atmPvcOutDiscards          Counter,

             atmPvcOutErrors            Counter

             }





	     atmifIndex OBJECT-TYPE

	     SYNTAX      INTEGER 

	     UNITS       " units "

	     MAX-ACCESS  read-only

             STATUS      mandatory

	     DESCRIPTION

                 " index "

	         ::= { atmPvcEntry	1 }





	     atmpvcIndex OBJECT-TYPE

	     SYNTAX      INTEGER 

	     UNITS       " units "

	     MAX-ACCESS  read-only

             STATUS      mandatory

	     DESCRIPTION

                 " index "

	         ::= { atmPvcEntry	2 }





	     atmPvc         OBJECT-TYPE

             SYNTAX         INTEGER

             MAX-ACCESS     read-only

             STATUS         current

             DESCRIPTION

               "The PVC value of the VCC."

          	::= { atmPvcEntry 3}



	     atmVpi           OBJECT-TYPE

             SYNTAX         INTEGER

             MAX-ACCESS     read-only

             STATUS         current

             DESCRIPTION

               "The VPI value of the VCC."

          	::= { atmPvcEntry 4}









             atmVci         OBJECT-TYPE

             SYNTAX         INTEGER

             MAX-ACCESS     read-only

             STATUS         current

             DESCRIPTION

             "The VCI value of the PVC."

             	::= { atmPvcEntry 5}







	     atmVccAalType       OBJECT-TYPE

             SYNTAX         DisplayString

             MAX-ACCESS    read-only

             STATUS        current

             DESCRIPTION

             "The type of AAL used on this VCC.

              The AAL type includes AAL1, AAL2, AAL3/4,

              and AAL5. The other(4) may be user-defined

              AAL type.  The unknown type indicates that

              the AAL type cannot be determined."

              DEFVAL { aal5 }

	          ::= { atmPvcEntry 6 }



	     atmVccMode       OBJECT-TYPE

             SYNTAX        DisplayString

             MAX-ACCESS    read-only

             STATUS        current

             DESCRIPTION

             "The type of pacing mode"

--              DEFVAL { aal5 }

	          ::= { atmPvcEntry 7 }



	     atmAalEncapsType  OBJECT-TYPE

             SYNTAX         DisplayString

             MAX-ACCESS     read-only

             STATUS         current

             DESCRIPTION

            "An instance of this object only exists when the

            local VCL end-point is also the VCC end-point,

            and AAL5 is in use.

            The type of data encapsulation used over

            the AAL5 SSCS layer. The definitions reference

            RFC 1483 Multiprotocol Encapsulation

            over ATM AAL5 and to the ATM Forum

            LAN Emulation specification."

                  ::= { atmPvcEntry 8 }







     	   atmPvcSpeed  OBJECT-TYPE

 	   SYNTAX         Counter

	   ACCESS         read-only

	   STATUS         mandatory

	   DESCRIPTION

	   "Pvc bit rate as percentage of the 

	    maximum available bandwidth (100 %) "

	       	 ::= { atmPvcEntry 9 }



           atmPvcInOctets OBJECT-TYPE

              SYNTAX  Counter

              ACCESS  read-only

              STATUS  mandatory

              DESCRIPTION

                      "The number of octets received on the

                      pvc, including framing characters."

              ::= { atmPvcEntry 10 }



           atmPvcUcastPkts OBJECT-TYPE

              SYNTAX  Counter

              ACCESS  read-only

              STATUS  mandatory

              DESCRIPTION

                      "The number of subnetwork-unicast packets

                      delivered to a higher-layer protocol on pvc."

              ::= { atmPvcEntry 11 }

           atmPvcNUcastPkts OBJECT-TYPE

              SYNTAX  Counter

              ACCESS  read-only

              STATUS  mandatory

              DESCRIPTION

                      "The number of non-unicast (i.e., subnetwork-

                      broadcast or subnetwork-multicast) packets

                      delivered to a higher-layer protocol over pvc."

              ::= { atmPvcEntry 12 }

           atmPvcDiscards OBJECT-TYPE

              SYNTAX  Counter

              ACCESS  read-only

              STATUS  mandatory

              DESCRIPTION

                      "The number of inbound packets for pvc which were chosen

                      to be discarded even though no errors had been

                      detected to prevent their being deliverable to a

                      higher-layer protocol.  One possible reason for

                      discarding such a packet could be to free up

                      buffer space."

              ::= { atmPvcEntry 13 }

          atmPvcErrors OBJECT-TYPE

              SYNTAX  Counter

              ACCESS  read-only

              STATUS  mandatory

              DESCRIPTION

                      "The number of inbound packets for pvc that contained

                      errors preventing them from being deliverable to a

                      higher-layer protocol."

              ::= { atmPvcEntry 14 }

          atmPvcUnknownProtos OBJECT-TYPE

              SYNTAX  Counter

              ACCESS  read-only

              STATUS  mandatory

              DESCRIPTION

                      "The number of packets for pvc received via the interface

                      which were discarded because of an unknown or

                      unsupported protocol."

              ::= { atmPvcEntry 15 }

          atmPvcOutOctets OBJECT-TYPE

              SYNTAX  Counter

              ACCESS  read-only

              STATUS  mandatory

              DESCRIPTION

                      "The number of octets for pvc transmitted out of the

                      interface, including framing characters."

              ::= { atmPvcEntry 16 }

          atmPvcOutUcastPkts OBJECT-TYPE

              SYNTAX  Counter

              ACCESS  read-only

              STATUS  mandatory

              DESCRIPTION

                      "The number of packets for pvc that higher-level

                      protocols requested be transmitted to a

                      subnetwork-unicast address, including those that

                      were discarded or not sent."

              ::= { atmPvcEntry 17 }

          atmPvcOutNUcastPkts OBJECT-TYPE

              SYNTAX  Counter

              ACCESS  read-only

              STATUS  mandatory

              DESCRIPTION

                      "The number of packets for pvc that higher-level

                      protocols requested be transmitted to a non-

                      unicast (i.e., a subnetwork-broadcast or

                      subnetwork-multicast) address, including those

                      that were discarded or not sent."

              ::= { atmPvcEntry 18 }

          atmPvcOutDiscards OBJECT-TYPE

              SYNTAX  Counter

              ACCESS  read-only

              STATUS  mandatory

              DESCRIPTION

                      "The number of outbound packets for pvc which were chosen

                      to be discarded even though no errors had been

                      detected to prevent their being transmitted.  One

                      possible reason for discarding such a packet could

                      be to free up buffer space."

              ::= { atmPvcEntry 19 }

          atmPvcOutErrors OBJECT-TYPE

              SYNTAX  Counter

              ACCESS  read-only

              STATUS  mandatory

              DESCRIPTION

                      "The number of outbound packets for pvc that could not be

                      transmitted because of errors."

              ::= { atmPvcEntry 20 }

 





-- sebastiani fine





-- -------------------------------------------------------------------------

--     TABELLA LapbOpTab     

--                                               TABELLA OPERATIVA LAPB

-- -------------------------------------------------------------------------



lapbOpTable       OBJECT-TYPE

		SYNTAX  SEQUENCE OF LapbOpEntry

		ACCESS  not-accessible

		STATUS  mandatory

	DESCRIPTION

		"Questa tabella fornisce i parametri operativi 

		 di una interfaccia Lapb."

	::= { lapbDiagIfc 2 }



	lapbOpEntry     OBJECT-TYPE

			SYNTAX  LapbOpEntry

			ACCESS  not-accessible

			STATUS  mandatory

		DESCRIPTION

			"Entry tabella LapbOpTab"

			INDEX   { lapbOpIfc }

		::= { lapbOpTable 1 }

	LapbOpEntry ::= SEQUENCE {

		lapbOpIfc       INTEGER,

		lapbOpState     INTEGER,

		lapbNRejTx      Counter,

		lapbNRejRx      Counter,

		lapbNRitr       Counter,

		lapbNFrmrTx     Counter,

		lapbNFrmrRx     Counter,

		lapbNIframeTx   Counter,

		lapbNIframeRx   Counter,

		lapbNRRTx       Counter,

		lapbNRRRx       Counter,

		lapbNRNRTx      Counter,

		lapbNRNRRx      Counter,

		lapbNNsErr      Counter

		}



	lapbOpIfc       OBJECT-TYPE

			SYNTAX  INTEGER

			ACCESS  read-only

			STATUS  mandatory

		DESCRIPTION

			"Indice dell'interfaccia su cui e` operativa

			 l'entita` LAPB,corrisponde a ifIndex della

			 MIB II."

		::= { lapbOpEntry 1 }



	lapbOpState     OBJECT-TYPE

			SYNTAX  INTEGER {

				disconnected  (0),

				await-Est     (1),

				await-Rel     (2),

				established   (3),

				frmr-Condition (5),

				rej-sent      (6),

				busy-on-TX    (7),

				busy-on-RX    (8),

				busy-on-TXRX  (9)

				}

			ACCESS  read-only

			STATUS  mandatory

		DESCRIPTION

			"Lo stato del Lapb"

		::= { lapbOpEntry 2 }



	lapbNRejTx      OBJECT-TYPE

			SYNTAX  Counter

			ACCESS  read-only

			STATUS  mandatory

		DESCRIPTION

			"Contatore REJ trasmessi"

		::= { lapbOpEntry 3 }



	lapbNRejRx      OBJECT-TYPE

			SYNTAX  Counter

			ACCESS  read-only

			STATUS  mandatory

		DESCRIPTION

			"Contatore REJ ricevuti"

		::= { lapbOpEntry 4 }



	lapbNRitr       OBJECT-TYPE

			SYNTAX  Counter

			ACCESS  read-only

			STATUS  mandatory

		DESCRIPTION

			"Contatore ritrasmissioni"

		::= { lapbOpEntry 5 }



	lapbNFrmrTx     OBJECT-TYPE

			SYNTAX  Counter

			ACCESS  read-only

			STATUS  mandatory

		DESCRIPTION

			"Contatore FRMR trasmessi"

		::= { lapbOpEntry 6 }



	lapbNFrmrRx     OBJECT-TYPE

			SYNTAX  Counter

			ACCESS  read-only

			STATUS  mandatory

		DESCRIPTION

			"Contatore FRMR ricevuti"

		::= { lapbOpEntry 7 }



	lapbNIframeTx   OBJECT-TYPE

			SYNTAX  Counter

			ACCESS  read-only

			STATUS  mandatory

		DESCRIPTION

			"Contatore I-Frame trasmesse"

		::= { lapbOpEntry 8 }



	lapbNIframeRx   OBJECT-TYPE

			SYNTAX  Counter

			ACCESS  read-only

			STATUS  mandatory

		DESCRIPTION

			"Contatore I-Frame ricevute"

		::= { lapbOpEntry 9 }



	lapbNRRTx       OBJECT-TYPE

			SYNTAX  Counter

			ACCESS  read-only

			STATUS  mandatory

		DESCRIPTION

			"Contatore RR trasmessi"

		::= { lapbOpEntry 10 }



	lapbNRRRx       OBJECT-TYPE

			SYNTAX  Counter

			ACCESS  read-only

			STATUS  mandatory

		DESCRIPTION

			"Contatore RR ricevuti"

		::= { lapbOpEntry 11 }



	lapbNRNRTx      OBJECT-TYPE

			SYNTAX  Counter

			ACCESS  read-only

			STATUS  mandatory

		DESCRIPTION

			"Contatore RNR trasmessi"

		::= { lapbOpEntry 12 }



	lapbNRNRRx      OBJECT-TYPE

			SYNTAX  Counter

			ACCESS  read-only

			STATUS  mandatory

		DESCRIPTION

			"Contatore RNR ricevuti"

		::= { lapbOpEntry 13 }



	lapbNNsErr      OBJECT-TYPE

			SYNTAX  Counter

			ACCESS  read-only

			STATUS  mandatory

		DESCRIPTION

			"Contatore N(s) Errors"

		::= { lapbOpEntry 14 }



-- *****************************************************************************

-- Gruppo LAPD

--        Ha le seguenti ramificazioni:

--        - LapdDiag    - LapdDiagIfc       - LapdCnfTab     (TABELLA)

--                                          - LapdOpTab      (TABELLA)

-- *****************************************************************************





lapdDiag        OBJECT IDENTIFIER ::= { lapd 2 }

lapdDiagIfc     OBJECT IDENTIFIER ::= { lapdDiag 1 }





-- -------------------------------------------------------------------------

--     TABELLA LapdCnfTab     

--                                                TABELLA CONFIGURAZIONE LAPD

-- -------------------------------------------------------------------------





lapdCnfTable      OBJECT-TYPE

		SYNTAX  SEQUENCE OF LapdCnfEntry

		ACCESS  not-accessible

		STATUS  mandatory

	DESCRIPTION

		"Questa tabella descrive i parametri relativi alla

		 configurazione Lapd per ogni link Lapd.

		 Se si lavora in TEI automatico la entry viene

		 aggiunta in tabella al momento dell'attivazione del

		 link e rimane anche se il liv.2 viene abbattuto.

		 Questo significa che se interrogo la tabella all'attiva-

		 zione della macchina (inizializzazione lapd) non trovo

		 nessuna entry relativa ai link lapd di lavoro (TEI tra

		 63...127), se e' stato attivato il colloquio Lapd trovero'

		 la entry con un una numerazione del link dove il TEI e'

		 quello assegnato dalla rete.

		 Se si lavora con TEI fisso la entry viene aggiunta alla

		 tabella all'inizializzazione del protocollo Lapd ed e'

		 sempre presente."

	::= { lapdDiagIfc 1 }



	lapdCnfEntry    OBJECT-TYPE

			SYNTAX  LapdCnfEntry

			ACCESS  not-accessible

			STATUS  mandatory

		DESCRIPTION

			"Entry tabella LapdCnfTab"

			INDEX   { lapdCnfIfc, lapdCnfTeiSapi }

		::= { lapdCnfTable 1 }



	LapdCnfEntry ::= SEQUENCE {

		lapdCnfIfc              INTEGER,

		lapdCnfTeiSapi          INTEGER,

		lapdCnfN200             INTEGER,

		lapdCnfN201             INTEGER,

		lapdCnfT200             INTEGER,

		lapdCnfT203             INTEGER,

		lapdCnfK                INTEGER

		}





	lapdCnfIfc      OBJECT-TYPE

			SYNTAX  INTEGER

			ACCESS  read-only

			STATUS  mandatory

		DESCRIPTION

			"Indice dell'interfaccia su cui e` configurata

			 l'entita` Lapd, corrisponde a ifIndex della MIB II."

		::= { lapdCnfEntry 1 }



	lapdCnfTeiSapi  OBJECT-TYPE

			SYNTAX  INTEGER

			ACCESS  read-only

			STATUS  mandatory

		DESCRIPTION

			"Questa variabile (2^ indice) identifica l'indirizzo

			 del link LAPD, dato dall'accoppiata TEI+SAPI.

			 E' l'espressione decimale del TEI * 100 a cui viene

			 addizionato il SAPI (TEI*100+SAPI).

			 Es: indice=12763 corrisponde a TEI=127 SAPI=63.

			 Si ricorda a tal proposito che i valori che puo'

			 assumere il TEI vanno da 0...127 e il SAPI da 0..63."

		::= { lapdCnfEntry 2 }



	lapdCnfN200     OBJECT-TYPE

			SYNTAX  INTEGER

			ACCESS  read-only

			STATUS  mandatory

		DESCRIPTION

			"Valore parametro N200"

		::= { lapdCnfEntry 3 }





	lapdCnfN201     OBJECT-TYPE

			SYNTAX  INTEGER

			ACCESS  read-only

			STATUS  mandatory

		DESCRIPTION

			"Massima lunghezza campo Info"

		::= { lapdCnfEntry 4 }



	lapdCnfT200     OBJECT-TYPE

			SYNTAX  INTEGER

			ACCESS  read-only

			STATUS  mandatory

		DESCRIPTION

			"Tempo replica"

		::= { lapdCnfEntry 5 }





	lapdCnfT203     OBJECT-TYPE

			SYNTAX  INTEGER

			ACCESS  read-only

			STATUS  mandatory

		DESCRIPTION

			"Tempo max senza trasmissione trame"

		::= { lapdCnfEntry 6 }





	lapdCnfK        OBJECT-TYPE

			SYNTAX  INTEGER

			ACCESS  read-only

			STATUS  mandatory

		DESCRIPTION

			"Numero massimo di trame in attesa risposta (finestra)"

		::= { lapdCnfEntry 7 }





-- -------------------------------------------------------------------------

--     TABELLA LapdOpTab     

--                                                TABELLA OPERATIVA LAPD

-- -------------------------------------------------------------------------





lapdOpTable       OBJECT-TYPE

		SYNTAX  SEQUENCE OF LapdOpEntry

		ACCESS  not-accessible

		STATUS  mandatory

	DESCRIPTION

		"Questa tabella descrive i parametri operativi

		 per ogni link LAPD. 

		Per l'inserimento di una entry vale quanto detto per

		la tabella LapdCnfTab."

	::= { lapdDiagIfc 2 }



	lapdOpEntry     OBJECT-TYPE

			SYNTAX  LapdOpEntry

			ACCESS  not-accessible

			STATUS  mandatory

		DESCRIPTION

			"Entry tabella LapdOpTab"

			INDEX   { lapdOpIfc, lapdOpTeiSapi }

		::= { lapdOpTable 1 }



	LapdOpEntry ::= SEQUENCE {

		lapdOpIfc               INTEGER,

		lapdOpTeiSapi           INTEGER,

		lapdOpState             INTEGER,

		lapdOpNRejTx            Counter,

		lapdOpNRejRx            Counter,

		lapdOpNRitr             Counter,

		lapdOpNFrmrTx           Counter,

		lapdOpNFrmrRx           Counter,

		lapdOpNIframeTx         Counter,

		lapdOpNIframeRx         Counter,

		lapdOpNRrTx             Counter,

		lapdOpNRrRx             Counter,

		lapdOpNRnrTx            Counter,

		lapdOpNRnrRx            Counter,

		lapdOpNsErr             Counter,

		lapdOpNUiTx             Counter,

		lapdOpNUiRx             Counter

		}





	lapdOpIfc       OBJECT-TYPE

			SYNTAX  INTEGER

			ACCESS  read-only

			STATUS  mandatory

		DESCRIPTION

			"Indice dell'interfaccia su cui e` configurata

			 l'entita` X25. Si noti che questo valore coincide

			 con quello riportato dalla ifIndex"

		::= { lapdOpEntry 1 }



	lapdOpTeiSapi           OBJECT-TYPE

				SYNTAX  INTEGER

				ACCESS  read-only

				STATUS  mandatory

		DESCRIPTION

			"Questa variabile (2^ indice) identifica l'indirizzo

			 del link LAPD, dato dall'accoppiata TEI+SAPI.

			 E' l'espressione deciamle del TEI * 100 a cui viene

			 addizionato il SAPI (TEI*100+SAPI).

			 Es: indice=12763 corrisponde a TEI=127 SAPI=63.

			 Si ricorda a tal proposito che i valori che puo'

			 assumere il TEI vanno da 0...127 e il SAPI da 0..63."

		::= { lapdOpEntry 2 }



	lapdOpState     OBJECT-TYPE

			SYNTAX  INTEGER{

			tei-unassigned (0),

			assign-awaiting-TEI (1),

			establish-awaiting-TEI (2),

			tei-assigned (3),

			awaiting-establish (4),

			awaiting-release (5),

			multiple-frame-established (6),

			timer-recovery (7),

			broadcast-information-transfer (8),

			state-Rej-sottostato-di-6-7 (9),

			state-Tx-Inibit-sottostato-di-6-7 (10),

			state-Rx-inibit-sottostato-di-6-7 (11)

			}

			ACCESS  read-only

			STATUS  mandatory

		DESCRIPTION

			"Sato relativo al link specificato con gli indici

			 - Nota: un link con TEI 127 e' sempre nello stato

			   broadcast"

		::= { lapdOpEntry 3 }



	lapdOpNRejTx    OBJECT-TYPE

				SYNTAX  Counter

				ACCESS  read-only

				STATUS  mandatory

		DESCRIPTION

			"Contatore REJ trasmessi"

		::= { lapdOpEntry 4 }



	lapdOpNRejRx    OBJECT-TYPE

				SYNTAX  Counter

				ACCESS  read-only

				STATUS  mandatory

		DESCRIPTION

			"Contatore REJ ricevuti"

		::= { lapdOpEntry 5 }



	lapdOpNRitr     OBJECT-TYPE

				SYNTAX  Counter

				ACCESS  read-only

				STATUS  mandatory

		DESCRIPTION

			"Contatore ritrasmissioni"

		::= { lapdOpEntry 6 }



	lapdOpNFrmrTx   OBJECT-TYPE

				SYNTAX  Counter

				ACCESS  read-only

				STATUS  mandatory

		DESCRIPTION

			"Contatore FRMR trasmessi"

		::= { lapdOpEntry 7 }



	lapdOpNFrmrRx   OBJECT-TYPE

				SYNTAX  Counter

				ACCESS  read-only

				STATUS  mandatory

		DESCRIPTION

			"Contatore FRMR ricevuti"

		::= { lapdOpEntry 8 }



	lapdOpNIframeTx OBJECT-TYPE

				SYNTAX  Counter

				ACCESS  read-only

				STATUS  mandatory

		DESCRIPTION

			"Contatore I-FRAME trasmesse"

		::= { lapdOpEntry 9 }



	lapdOpNIframeRx OBJECT-TYPE

				SYNTAX  Counter

				ACCESS  read-only

				STATUS  mandatory

		DESCRIPTION

			"Contatore I-FRAME ricevute"

		::= { lapdOpEntry 10 }



	lapdOpNRrTx     OBJECT-TYPE

				SYNTAX  Counter

				ACCESS  read-only

				STATUS  mandatory

		DESCRIPTION

			"Contatore RR trasmessi"

		::= { lapdOpEntry 11 }



	lapdOpNRrRx     OBJECT-TYPE

				SYNTAX  Counter

				ACCESS  read-only

				STATUS  mandatory

		DESCRIPTION

			"Contatore RR ricevuti"

		::= { lapdOpEntry 12 }



	lapdOpNRnrTx    OBJECT-TYPE

				SYNTAX  Counter

				ACCESS  read-only

				STATUS  mandatory

		DESCRIPTION

			"Contatore RNR trasmessi"

		::= { lapdOpEntry 13 }



	lapdOpNRnrRx    OBJECT-TYPE

				SYNTAX  Counter

				ACCESS  read-only

				STATUS  mandatory

		DESCRIPTION

			"Contatore RNR ricevuti"

		::= { lapdOpEntry 14 }



	lapdOpNsErr     OBJECT-TYPE

				SYNTAX  Counter

				ACCESS  read-only

				STATUS  mandatory

		DESCRIPTION

			"Contatore N(s) Errati"

		::= { lapdOpEntry 15 }



	lapdOpNUiTx     OBJECT-TYPE

				SYNTAX  Counter

				ACCESS  read-only

				STATUS  mandatory

		DESCRIPTION

			"Contatore UI trasmesse"

		::= { lapdOpEntry 16 }



	lapdOpNUiRx     OBJECT-TYPE

				SYNTAX  Counter

				ACCESS  read-only

				STATUS  mandatory

		DESCRIPTION

			"Contatore UI ricevute"

		::= { lapdOpEntry 17 }







-- *****************************************************************************

-- Gruppo Q931

--        Ha le seguenti ramificazioni:

--        - Q931Diag

--                      - Q931OpTab      (TABELLA)

-- *****************************************************************************



q931Diag        OBJECT IDENTIFIER ::= { q931 2 }





-- -------------------------------------------------------------------------

--     TABELLA Q931OpTab     

--                                               TABELLA OPERATIVA Q931

-- -------------------------------------------------------------------------

q931OpTable       OBJECT-TYPE

		SYNTAX  SEQUENCE OF Q931OpEntry

		ACCESS  not-accessible

		STATUS  mandatory

	DESCRIPTION

		"Tabella operativa Q931"

	::= { q931Diag 2 }



	q931OpEntry     OBJECT-TYPE

			SYNTAX  Q931OpEntry

			ACCESS  not-accessible

			STATUS  mandatory

		DESCRIPTION

			"Entry tabella Q931OpTab"

			INDEX   { q931OpIfc }

		::= { q931OpTable 1 }

	Q931OpEntry ::= SEQUENCE {

		q931OpIfc               INTEGER,

		q931OpState               INTEGER,

		q931LastCalled          DisplayString,

		q931LastCalling         DisplayString,

		q931LastCauseDisc       INTEGER

		}



	q931OpIfc       OBJECT-TYPE

			SYNTAX  INTEGER

			ACCESS  read-only

			STATUS  mandatory

		DESCRIPTION

			"Indice dell'interfaccia relativa al canale B ISDN

			 controllato dal Q931, ha corrispondenza con

			ifIndex della MIB II."

		::= { q931OpEntry 1 }



	q931OpState     OBJECT-TYPE

			SYNTAX  INTEGER {

				null                          (0),

				call-Initiated                (1),

				overlap-Sending               (2),

				outgoing-Call-Proceeding      (3),

				call-Delivered                (4),

				call-Present                  (5),

				call-Received                 (6),

				connect-Request               (7),

				incoming-Call-Proceeding      (8),

				active                        (9),

				disconnect-Request           (10),

				disconnect-Indication        (11),

				suspend-Request              (12),

				resume-Request               (13),

				release-Request              (14),

				overlap-Receiving            (15)

				}

			ACCESS  read-only

			STATUS  mandatory

		DESCRIPTION

			"Stato della Chiamata Q931"

		::= { q931OpEntry 2 }



	q931LastCalled  OBJECT-TYPE

			SYNTAX  DisplayString

			ACCESS  read-only

			STATUS  mandatory

		DESCRIPTION

			"Ultimo numero di telefono Isdn chiamato"

		::= { q931OpEntry 3 }



	q931LastCalling OBJECT-TYPE

			SYNTAX  DisplayString

			ACCESS  read-only

			STATUS  mandatory

		DESCRIPTION

			"Ultimo numero di telefono Isdn chiamante"

		::= { q931OpEntry 4 }



	q931LastCauseDisc       OBJECT-TYPE

				SYNTAX  INTEGER 

				ACCESS  read-only

				STATUS  mandatory

		DESCRIPTION

			"Ultima causa di Disconnessione dalla Rete"

		::= { q931OpEntry 5 }



-- *****************************************************************************

-- Gruppo IP

--        Ha le seguenti ramificazioni:

--        - IpDiag      - IpDiagIfc         - IpIfcCnfTab     (TABELLA)

--                                          - IpRouteAct      (TABELLA) 

--        				- IpGlob

--						- IpDiagAccessList

--        - IpSec

--

--

-- NB: Le variabili hanno nome Ip... (con I maiuscola) per distinguerle da

-- quelle della MIB-II che hanno nome ip.... (con la i minuscola)

-- MODIFICA : aggiunto il ramo per la sicurezza Ip (IpSec) ed il ramo della Access List.

-- AUTORE : Antonio Tosi

-- DATA : 04-05-1998

-- *****************************************************************************

ipDiag                  OBJECT IDENTIFIER ::= { ip 2 }

ipSec                   OBJECT IDENTIFIER ::= { ip 3 }

ipDiagIfc               OBJECT IDENTIFIER ::= { ipDiag 1 }

ipGlob                  OBJECT IDENTIFIER ::= { ipDiag 2 }

ipDiagAccessList        OBJECT IDENTIFIER ::= { ipDiag 4 }







-- -------------------------------------------------------------------------

--     TABELLA IpIfcCnfTab     

--                                               TABELLA CONFIGURAZIONE IP

-- -------------------------------------------------------------------------



ipIfcCnfTable     OBJECT-TYPE

		SYNTAX  SEQUENCE OF IpIfcCnfEntry

		ACCESS  not-accessible

		STATUS  mandatory

	DESCRIPTION

		"Questa tabella riassume i parametri di configurazione

		 relativi ad una interfaccia di tipo IP."

	::= { ipDiagIfc 1 }





	ipIfcCnfEntry   OBJECT-TYPE

			SYNTAX  IpIfcCnfEntry

			ACCESS  not-accessible

			STATUS  mandatory

		DESCRIPTION

			"Entry configurazione ifc IP"

			INDEX { ipIfcCnfInd }

		::= { ipIfcCnfTable 1 }



	IpIfcCnfEntry ::= SEQUENCE {

		ipIfcCnfInd             INTEGER,

		ipIfcAddress            IpAddress,

		ipMask                  IpAddress,

		ipIdleTmo               Gauge,

		ipMtu                   Gauge,

		ipRedirect              INTEGER

		}



	ipIfcCnfInd     OBJECT-TYPE

			SYNTAX  INTEGER

			ACCESS  read-only

			STATUS  mandatory

		DESCRIPTION

			"Indice interfaccia IP corrispondente a ifIndex

			 della MIB II."

		::= { ipIfcCnfEntry 1 }



	ipIfcAddress    OBJECT-TYPE

			SYNTAX  IpAddress

			ACCESS  read-only

			STATUS  mandatory

		DESCRIPTION

			"Indirizzo IP dell'interfaccia."

		::= { ipIfcCnfEntry 2 }



	ipMask          OBJECT-TYPE

			SYNTAX  IpAddress

			ACCESS  read-only

			STATUS  mandatory

		DESCRIPTION

			"Subnet mask"

		::= { ipIfcCnfEntry 3 }



	ipIdleTmo       OBJECT-TYPE

			SYNTAX  Gauge

			ACCESS  read-only

			STATUS  mandatory

		DESCRIPTION

			"Valore relativo a Idle timeout (tempo di

			 inattivita' relativo alla connessione IP)

			 Valori ammessi da  0...65535, in relazione

			 al comando di configurazione."

		::= { ipIfcCnfEntry 4 }



	ipMtu           OBJECT-TYPE

			SYNTAX  Gauge

			ACCESS  read-only

			STATUS  mandatory

		DESCRIPTION

			"MTU relativa al livello IP sull'interfaccia

			 (dimensione massima del pacchetto dati)."

		::= { ipIfcCnfEntry 5 }



	ipRedirect      OBJECT-TYPE

			SYNTAX  INTEGER {

				off   (0),

				on    (1)

				}

			ACCESS  read-only

			STATUS  mandatory

		DESCRIPTION

			"Abilitazione all'invio di una trama di Redirect"

		::= { ipIfcCnfEntry 6 }





 ipDefGtw       OBJECT-TYPE

		SYNTAX  IpAddress

		ACCESS  read-only

		STATUS  mandatory

	DESCRIPTION

		"Default gateway (0.0.0.0 se non configurato)."

	::= { ipGlob 1 }



 ipDGtwIfc      OBJECT-TYPE

		SYNTAX  INTEGER

		ACCESS  read-only

		STATUS  mandatory

	DESCRIPTION

		"Indice interfaccia (ifIndex) su cui 

		 il Default gateway e' attivo."

	::= { ipGlob 2 }



 ipSROpt        OBJECT-TYPE

		SYNTAX  INTEGER {

			off   (0),

			on    (1)

			}

		ACCESS  read-only

		STATUS  mandatory

	DESCRIPTION

		"Abilitazione dell'opzione  Source Route."

	::= { ipGlob 3 }





-- -------------------------------------------------------------------------

--     TABELLA IpRouteTab     

--                                               TABELLA DELLE "ROUTE" IP

-- -------------------------------------------------------------------------



ipRouteTable      OBJECT-TYPE

		SYNTAX  SEQUENCE OF IpRouteEntry

		ACCESS  not-accessible

		STATUS  mandatory

	DESCRIPTION

		"Questa tabella fornisce informazioni sulla <ROUTE>

		 geografica (intesa come instradamento verso un 

		 gateway), aperta attraverso una interfaccia e sul 

		 traffico svolto da essa.

		 La tabella e' indicizzata per interfaccia e per 

		 gateway ed e' interrogabile solo su interfacce di

		 tipo switched come X25 e Frame Relay.

		 Una entry viene inserita in tabella quando la ROUTE

		 viene aperta: all'inizializzazione delle interfacce per

		 i PVC, alla formazione della chiamata per gli SVC. Per

		 gli SVC la entry viene tolta dalla tabella al momento

		 dell'abbattimento della chiamata."

	::= { ipDiag 3 }





	ipRouteEntry OBJECT-TYPE

			SYNTAX  IpRouteEntry

			ACCESS  not-accessible

			STATUS  mandatory

		DESCRIPTION

			""

			INDEX { ipRouteTabIfc,

				ipRouteTabGtw }

		::= { ipRouteTable 1 }



	IpRouteEntry ::= SEQUENCE {

		ipRouteTabIfc   INTEGER,

		ipRouteTabGtw   IpAddress,

		ipRouteTabPkTx  Counter,

		ipRouteTabPkRx  Counter,

		ipRouteTabPSW   INTEGER,

		ipRouteTabTime  TimeTicks

		}



	ipRouteTabIfc   OBJECT-TYPE

			SYNTAX  INTEGER

			ACCESS  read-only

			STATUS  mandatory

		DESCRIPTION

			"Indice relativo all'interfaccia, corrisponde

			 a ifIndex della MIB II."

		::= { ipRouteEntry 1 }



	ipRouteTabGtw   OBJECT-TYPE

			SYNTAX  IpAddress

			ACCESS  read-only

			STATUS  mandatory

		DESCRIPTION

			"Gateway raggiunto (remoto)."

		::= { ipRouteEntry 2 }



	ipRouteTabPkTx  OBJECT-TYPE

			SYNTAX  Counter

			ACCESS  read-only

			STATUS  mandatory

		DESCRIPTION

			"Contatore di pacchetti trasmessi."

		::= { ipRouteEntry 3 }



	ipRouteTabPkRx  OBJECT-TYPE

			SYNTAX  Counter

			ACCESS  read-only

			STATUS  mandatory

		DESCRIPTION

			"Contatore pacchetti ricevuti."

		::= { ipRouteEntry 4 }



	ipRouteTabPSW   OBJECT-TYPE

			SYNTAX  INTEGER {

				switched      (0)

				}

			ACCESS  read-only

			STATUS  mandatory

		DESCRIPTION

			"Tipo circuito: permanent o switched.

			 Nel caso di  PVC indica il numero di

			 circuito, per gli SVC viene indicato il 

			 valore 0."

		::= { ipRouteEntry 5 }



	ipRouteTabTime  OBJECT-TYPE

			SYNTAX  TimeTicks

			ACCESS  read-only

			STATUS  mandatory

		DESCRIPTION

			"Tempo di sistema relativo all'apertura della

			 <ROUTE>."

		::= { ipRouteEntry 6 }





-- ------------------------------------------------------------------------------------------------------------------------------

--     NODE IpDiagAccessList : diagnosis of the access list tables of IP module     

--     AUTHOR : Antonio Tosi

--     DATE : 04-05-1998        

--     OBJECTS :

--      IpDiagAlInternalEnable

--      IpDiagAlRoutingEnable

--      IpDiagAlNumInternalEntry

--      IpDiagAlNumRoutingEntry

--      IpDiagAlRoute (TABLE)

--      IpDiagAlIntern (TABLE)

-- ------------------------------------------------------------------------------------------------------------------------------



-- ------------------------------------------------------------------------------------------------------------------------

--     VARIABLE IpDiagAlInternalEnable

--                                               Access List abilitation flag

-- ------------------------------------------------------------------------------------------------------------------------

	ipDiagAlInternalEnable	OBJECT-TYPE

			SYNTAX  INTEGER{

					enabled(1),

					disabled(0)

					}

			ACCESS  read-only

			STATUS  mandatory

		DESCRIPTION

			" Internal access List abilitation flag."

			::= { ipDiagAccessList 1 }



-- ------------------------------------------------------------------------------------------------------------------------

--     VARIABLE IpDiagAlRoutingEnable

--                                               Access List abilitation flag

-- ------------------------------------------------------------------------------------------------------------------------

	ipDiagAlRoutingEnable	OBJECT-TYPE

			SYNTAX  INTEGER{

					enabled(1),

					disabled(0)

					}

			ACCESS  read-only

			STATUS  mandatory

		DESCRIPTION

			" Routing access List abilitation flag."

			::= { ipDiagAccessList 2 }



-- ------------------------------------------------------------------------------------------------------------------------

--     VARIABLE IpDiagAlNumInternalEntry

--                                      Access List's number of entries

-- ------------------------------------------------------------------------------------------------------------------------

	ipDiagAlNumInternalEntry	OBJECT-TYPE

			SYNTAX  INTEGER

			ACCESS  read-only

			STATUS  mandatory

		DESCRIPTION

			" Internal access List's number of entries."

			::= { ipDiagAccessList 3 }



-- ------------------------------------------------------------------------------------------------------------------------

--     VARIABLE IpDiagAlNumRoutingEntry

--                                      Access List's number of entries

-- ------------------------------------------------------------------------------------------------------------------------

	ipDiagAlNumRoutingEntry	OBJECT-TYPE

			SYNTAX  INTEGER

			ACCESS  read-only

			STATUS  mandatory

		DESCRIPTION

			" Routing access List's number of entries."

			::= { ipDiagAccessList 4 }









-- ------------------------------------------------------------------------------------------------------------------------

--     TABLE  IpDiagAlIntern    

--                                               Access List Intern table

-- ------------------------------------------------------------------------------------------------------------------------



ipDiagAlInternTable       OBJECT-TYPE

		SYNTAX  SEQUENCE OF IpDiagAlInternEntry

		ACCESS  read-only

		STATUS  mandatory

	DESCRIPTION

		"Access List Intern table."

	::= { ipDiagAccessList 5 }





	ipDiagAlInternEntry OBJECT-TYPE

			SYNTAX  IpDiagAlInternEntry

			ACCESS  read-only

			STATUS  mandatory

		DESCRIPTION

			"Entry of the Access List Intern table."

			INDEX { ipDiagAlInternIndex }

		::= { ipDiagAlInternTable 1 }



	IpDiagAlInternEntry ::= SEQUENCE {

		ipDiagAlInternIndex   		INTEGER,

		ipDiagAlInternPermDenFlag   	INTEGER,

		ipDiagAlInternIpSrc   		IpAddress,

		ipDiagAlInternMaskSrc   	IpAddress,

		ipDiagAlInternIpDest    	IpAddress,

		ipDiagAlInternMaskDst  		IpAddress,

		ipDiagAlInternIfc    		INTEGER,

		ipDiagAlInternTcpProt    	INTEGER,

		ipDiagAlInternTcpPort    	INTEGER,

		ipDiagAlInternPConnSt    	INTEGER,

		ipDiagAlInternUdpProt    	INTEGER,

		ipDiagAlInternUdpPort     	INTEGER,

		ipDiagAlInternIcmpProt    	INTEGER,

		ipDiagAlInternAhProt  		INTEGER,

		ipDiagAlInternEspProt   	INTEGER

		}



	ipDiagAlInternIndex   OBJECT-TYPE

			SYNTAX  INTEGER

			ACCESS  read-only

			STATUS  mandatory

		DESCRIPTION

			"Index of the Access List Intern table entries."

		::= { ipDiagAlInternEntry 1 }



	ipDiagAlInternPermDenFlag  OBJECT-TYPE

			SYNTAX  INTEGER{

					permitted(0),

					denied(1)

					}

			ACCESS  read-only

			STATUS  mandatory

		DESCRIPTION

			"Entry flag permitted-denied."

		::= { ipDiagAlInternEntry 2 }



	ipDiagAlInternIpSrc  OBJECT-TYPE

			SYNTAX  IpAddress

			ACCESS  read-only

			STATUS  mandatory

		DESCRIPTION

			"Sender IP address."

		::= { ipDiagAlInternEntry 3 }



	ipDiagAlInternMaskSrc  OBJECT-TYPE

			SYNTAX  IpAddress

			ACCESS  read-only

			STATUS  mandatory

		DESCRIPTION

			"Sender IP mask."

		::= { ipDiagAlInternEntry 4 }



	ipDiagAlInternIpDest  OBJECT-TYPE

			SYNTAX  IpAddress

			ACCESS  read-only

			STATUS  mandatory

		DESCRIPTION

			"Receiver IP address."

		::= { ipDiagAlInternEntry 5 }



	ipDiagAlInternMaskDst OBJECT-TYPE

			SYNTAX  IpAddress

			ACCESS  read-only

			STATUS  mandatory

		DESCRIPTION

			"Receiver IP mask."

		::= { ipDiagAlInternEntry 6 }



	ipDiagAlInternIfc  OBJECT-TYPE

			SYNTAX  INTEGER{

					notChecked(-1),

					ethernet1(0),

					serial1(1),

					isdn1-B1(2),

					isdn1-D(3),

					serial2(4),

					serial3(5),

					serial4(6),

					ethernet2(7),

					ethernet3(8),

					ethernet4(9),

					cpci(10),

					ethernet5(11),

					isdn1-B2(12),

					isdn1-B(13),

					ethernet6(14)

					}

			ACCESS  read-only

			STATUS  mandatory

		DESCRIPTION

			"Interface."

		::= { ipDiagAlInternEntry 7 }



	ipDiagAlInternTcpProt  OBJECT-TYPE

			SYNTAX  INTEGER{

					notChecked(0),

					checked(1)

					}

			ACCESS  read-only

			STATUS  mandatory

		DESCRIPTION

			"Check on Tcp protocol enabled-disabled."

		::= { ipDiagAlInternEntry 8 }



	ipDiagAlInternTcpPort  OBJECT-TYPE

			SYNTAX  INTEGER{

					notChecked(0)

					}

			ACCESS  read-only

			STATUS  mandatory

		DESCRIPTION

			"Tcp port."

		::= { ipDiagAlInternEntry 9 }



	ipDiagAlInternPConnSt  OBJECT-TYPE

			SYNTAX  INTEGER{

					enabled(1),

					disabled(0)

					}

			ACCESS  read-only

			STATUS  mandatory

		DESCRIPTION

			"Check on connection state enabled-disabled."

		::= { ipDiagAlInternEntry 10 }



	ipDiagAlInternUdpProt  OBJECT-TYPE

			SYNTAX  INTEGER{

					notChecked(0),

					checked(1)

					}

			ACCESS  read-only

			STATUS  mandatory

		DESCRIPTION

			" Check on Udp protocol enabled-disabled."

		::= { ipDiagAlInternEntry 11 }



	ipDiagAlInternUdpPort  OBJECT-TYPE

			SYNTAX  INTEGER{

					notChecked(0)

					}

			ACCESS  read-only

			STATUS  mandatory

		DESCRIPTION

			"Udp port."

		::= { ipDiagAlInternEntry 12 }



	ipDiagAlInternIcmpProt  OBJECT-TYPE

			SYNTAX  INTEGER{

					notChecked(0),

					checked(1)

					}

			ACCESS  read-only

			STATUS  mandatory

		DESCRIPTION

			" Check on Icmp protocol enabled-disabled."

		::= { ipDiagAlInternEntry 13 }



	ipDiagAlInternAhProt  OBJECT-TYPE

			SYNTAX  INTEGER{

					notChecked(0),

					checked(1)

					}

			ACCESS  read-only

			STATUS  mandatory

		DESCRIPTION

			" Check on Ah protocol enabled-disabled."

		::= { ipDiagAlInternEntry 14 }



	ipDiagAlInternEspProt  OBJECT-TYPE

			SYNTAX  INTEGER{

					notChecked(0),

					checked(1)

					}

			ACCESS  read-only

			STATUS  mandatory

		DESCRIPTION

			" Check on Esp protocol enabled-disabled."

		::= { ipDiagAlInternEntry 15 }





-- ------------------------------------------------------------------------------------------------------------------------

--     TABLE  IpDiagAlRoute    

--                                               Access List Route table

-- ------------------------------------------------------------------------------------------------------------------------



ipDiagAlRouteTable       OBJECT-TYPE

		SYNTAX  SEQUENCE OF IpDiagAlRouteEntry

		ACCESS  read-only

		STATUS  mandatory

	DESCRIPTION

		"Access List Route table."

	::= { ipDiagAccessList 6 }



ipDiagAlRouteEntry OBJECT-TYPE

			SYNTAX  IpDiagAlRouteEntry

			ACCESS  read-only

			STATUS  mandatory

		DESCRIPTION

			"Entry of the Access List Route table."

			INDEX { ipDiagAlRouteIndex }

		::= { ipDiagAlRouteTable 1 }



	IpDiagAlRouteEntry ::= SEQUENCE {

		ipDiagAlRouteIndex   	INTEGER,

		ipDiagAlRoutePermDenFlag   INTEGER,

		ipDiagAlRouteIpSrc   	IpAddress,

		ipDiagAlRouteMaskSrc   	IpAddress,

		ipDiagAlRouteIpDest    	IpAddress,

		ipDiagAlRouteMaskDst  	IpAddress,

		ipDiagAlRouteIfc    	INTEGER,

		ipDiagAlRouteTcpProt    INTEGER,

		ipDiagAlRouteTcpPort    INTEGER,

		ipDiagAlRoutePConnSt    INTEGER,

		ipDiagAlRouteUdpProt    INTEGER,

		ipDiagAlRouteUdpPort    INTEGER,

		ipDiagAlRouteIcmpProt   INTEGER,

		ipDiagAlRouteAhProt    	INTEGER,

		ipDiagAlRouteEspProt    INTEGER

		}



	ipDiagAlRouteIndex   OBJECT-TYPE

			SYNTAX  INTEGER

			ACCESS  read-only

			STATUS  mandatory

		DESCRIPTION

			"Index of the Access List Route table entries."

		::= { ipDiagAlRouteEntry 1 }



	ipDiagAlRoutePermDenFlag  OBJECT-TYPE

			SYNTAX  INTEGER{

					permitted(0),

					denied(1)

					}

			ACCESS  read-only

			STATUS  mandatory

		DESCRIPTION

			"Entry flag permitted-denied."

		::= { ipDiagAlRouteEntry 2 }



	ipDiagAlRouteIpSrc  OBJECT-TYPE

			SYNTAX  IpAddress

			ACCESS  read-only

			STATUS  mandatory

		DESCRIPTION

			"Sender IP address."

		::= { ipDiagAlRouteEntry 3 }



	ipDiagAlRouteMaskSrc  OBJECT-TYPE

			SYNTAX  IpAddress

			ACCESS  read-only

			STATUS  mandatory

		DESCRIPTION

			"Sender IP mask."

		::= { ipDiagAlRouteEntry 4 }



	ipDiagAlRouteIpDest  OBJECT-TYPE

			SYNTAX  IpAddress

			ACCESS  read-only

			STATUS  mandatory

		DESCRIPTION

			"Receiver IP address."

		::= { ipDiagAlRouteEntry 5 }



	ipDiagAlRouteMaskDst OBJECT-TYPE

			SYNTAX  IpAddress

			ACCESS  read-only

			STATUS  mandatory

		DESCRIPTION

			"Receiver IP mask."

		::= { ipDiagAlRouteEntry 6 }



	ipDiagAlRouteIfc  OBJECT-TYPE

			SYNTAX  INTEGER{

					notChecked(-1),

					ethernet1(0),

					serial1(1),

					isdn1-B1(2),

					isdn1-D(3),

					serial2(4),

					serial3(5),

					serial4(6),

					ethernet2(7),

					ethernet3(8),

					ethernet4(9),

					cpci(10),

					ethernet5(11),

					isdn1-B2(12),

					isdn1-B(13),

					ethernet6(14)

					}

			ACCESS  read-only

			STATUS  mandatory

		DESCRIPTION

			"Interface."

		::= { ipDiagAlRouteEntry 7 }



	ipDiagAlRouteTcpProt  OBJECT-TYPE

			SYNTAX  INTEGER{

					notChecked(0),

					checked(1)

					}

			ACCESS  read-only

			STATUS  mandatory

		DESCRIPTION

			"Check on Tcp protocol checked- not checked."

		::= { ipDiagAlRouteEntry 8 }



	ipDiagAlRouteTcpPort  OBJECT-TYPE

			SYNTAX  INTEGER{

					notChecked(0)

					}

			ACCESS  read-only

			STATUS  mandatory

		DESCRIPTION

			"Tcp port."

		::= { ipDiagAlRouteEntry 9 }



	ipDiagAlRoutePConnSt  OBJECT-TYPE

			SYNTAX  INTEGER{

					enabled(1),

					disabled(0)

					}

			ACCESS  read-only

			STATUS  mandatory

		DESCRIPTION

			"Check on connection state enabled-disabled."

		::= { ipDiagAlRouteEntry 10 }



	ipDiagAlRouteUdpProt  OBJECT-TYPE

			SYNTAX  INTEGER{

					notChecked(0),

					checked(1)

					}

			ACCESS  read-only

			STATUS  mandatory

		DESCRIPTION

			" Check on Udp protocol enabled-disabled."

		::= { ipDiagAlRouteEntry 11 }



	ipDiagAlRouteUdpPort  OBJECT-TYPE

			SYNTAX  INTEGER{

					notChecked(0)

					}

			ACCESS  read-only

			STATUS  mandatory

		DESCRIPTION

			"Udp port."

		::= { ipDiagAlRouteEntry 12 }



	ipDiagAlRouteIcmpProt  OBJECT-TYPE

			SYNTAX  INTEGER{

					notChecked(0),

					checked(1)

					}

			ACCESS  read-only

			STATUS  mandatory

		DESCRIPTION

			" Check on Icmp protocol enabled-disabled."

		::= { ipDiagAlRouteEntry 13 }



	ipDiagAlRouteAhProt  OBJECT-TYPE

			SYNTAX  INTEGER{

					notChecked(0),

					checked(1)

					}

			ACCESS  read-only

			STATUS  mandatory

		DESCRIPTION

			" Check on Ah protocol enabled-disabled."

		::= { ipDiagAlRouteEntry 14 }



	ipDiagAlRouteEspProt  OBJECT-TYPE

			SYNTAX  INTEGER{

					notChecked(0),

					checked(1)

					}

			ACCESS  read-only

			STATUS  mandatory

		DESCRIPTION

			" Check on Esp protocol enabled-disabled."

		::= { ipDiagAlRouteEntry 15 }







-- ------------------------------------------------------------------------------------------------------------------------------

--     NODE IpSec

--				 : diagnosis of the security system based on the IP protocol     

--     AUTHOR : Antonio Tosi

--     DATE : 04-05-98

--     OBJECTS :

--      IpSecCardInOut

--      IpSecTc (TABLE)

--      IpSecTcFlash (TABLE)

--      IpSecNumEntry

--      IpSecTcIp (TABLE)

--      IpSecTrap (NODE)

--      IpSecPermit 	(TABLE)			10.1.2001 Tab. PERMIT per disabiltare traffico cifrato

--      IpSecPermitCnf					11.1.2001 gruppo PERMIT Conf. per Ins/Del. Permit SNMP

-- ------------------------------------------------------------------------------------------------------------------------------





ipSecTrap               OBJECT IDENTIFIER ::= { ipSec 6 }



-- ------------------------------------------------------------------------------------------------------------------------

--     VARIABLE IpSecCardInOut    

--                                               CryptoCard IN - CryptoCard OUT

-- ------------------------------------------------------------------------------------------------------------------------

	ipSecCardInOut     OBJECT-TYPE

			SYNTAX  INTEGER

			ACCESS  read-only

			STATUS  mandatory

		DESCRIPTION

			"SystemInfo AgPresent field."

			::= { ipSec 1 }



-- ------------------------------------------------------------------------------------------------------------------------

--     TABLE  IpSecTc    

--                                               ICR module's Cryptography table 

-- ------------------------------------------------------------------------------------------------------------------------



ipSecTcTable       OBJECT-TYPE

		SYNTAX  SEQUENCE OF IpSecTcEntry

		ACCESS  read-only

		STATUS  mandatory

	DESCRIPTION

		"This table provides informations about chypering gateways and configured

		security services."

	::= { ipSec 2 }





	ipSecTcEntry OBJECT-TYPE

			SYNTAX  IpSecTcEntry

			ACCESS  read-only

			STATUS  mandatory

		DESCRIPTION

			"Cryptography table entry. "

			INDEX { ipSecTcGtw }

		::= { ipSecTcTable 1 }



	IpSecTcEntry ::= SEQUENCE {

		ipSecTcGtw   IpAddress,

		ipSecTcCypher   INTEGER,

		ipSecTcChain   INTEGER,

		ipSecTcIntegr   INTEGER,

		ipSecTcSignt    INTEGER,

		ipSecTcAuth  INTEGER,

		ipSecTcAccessctrl       INTEGER,

		ipSecTcAuthStatus    INTEGER,

		ipSecTcAuthTaut      INTEGER,

		ipSecTcAuthTmax     INTEGER,

		ipSecTcAuthNmax     INTEGER

		}



	ipSecTcGtw   OBJECT-TYPE

			SYNTAX  IpAddress

			ACCESS  read-only

			STATUS  mandatory

		DESCRIPTION

			"Addressee chypering gateway."

		::= { ipSecTcEntry 1 }



	ipSecTcCypher   OBJECT-TYPE

			SYNTAX  INTEGER{

					enabled(1),

					disabled(0)

					}

			ACCESS  read-only

			STATUS  mandatory

		DESCRIPTION

			"Cyphering service ON/OFF."

		::= { ipSecTcEntry 2 }



	ipSecTcIntegr  OBJECT-TYPE

			SYNTAX  INTEGER{

					enabled(1),

					disabled(0)

					}

			ACCESS  read-only

			STATUS  mandatory

		DESCRIPTION

			"Integrity service ON/OFF."

		::= { ipSecTcEntry 4 }



	ipSecTcChain  OBJECT-TYPE

			SYNTAX  INTEGER{

					enabled(1),

					disabled(0)

					}

			ACCESS  read-only

			STATUS  mandatory

		DESCRIPTION

			"Chaining service ON/OFF."

		::= { ipSecTcEntry 3 }



	ipSecTcSignt   OBJECT-TYPE

			SYNTAX  INTEGER{

					enabled(1),

					disabled(0)

					}

			ACCESS  read-only

			STATUS  mandatory

		DESCRIPTION

			"Electronic sign (authentication of the sender) ON/OFF."

		::= { ipSecTcEntry 5 }



	ipSecTcAuth  OBJECT-TYPE

			SYNTAX  INTEGER{

					enabled(1),

					disabled(0)

					}

			ACCESS  read-only

			STATUS  mandatory

		DESCRIPTION

			"Authentication service ON/OFF."

		::= { ipSecTcEntry 6 }



	ipSecTcAccessctrl  OBJECT-TYPE

			SYNTAX  INTEGER{

					enabled(1),

					disabled(0)

					}

			ACCESS  read-only

			STATUS  mandatory

		DESCRIPTION

			"Check on accesses service ON/OFF."

		::= { ipSecTcEntry 7 }



	ipSecTcAuthStatus  OBJECT-TYPE

			SYNTAX  INTEGER

			ACCESS  read-only

			STATUS  mandatory

		DESCRIPTION

			"Gateway authentication status."

		::= { ipSecTcEntry 8 }



	ipSecTcAuthTaut  OBJECT-TYPE

			SYNTAX  INTEGER

			ACCESS  read-only

			STATUS  mandatory

		DESCRIPTION

			"Average time beetwen authentication requests."

		::= { ipSecTcEntry 9 }



	ipSecTcAuthTmax  OBJECT-TYPE

			SYNTAX  INTEGER

			ACCESS  read-only

			STATUS  mandatory

		DESCRIPTION

			"Maximum waiting time for authentication replies. "

		::= { ipSecTcEntry 10 }



	ipSecTcAuthNmax  OBJECT-TYPE

			SYNTAX  INTEGER

			ACCESS  read-only

			STATUS  mandatory

		DESCRIPTION

			"Maximum number of authentication requests before fail."

		::= { ipSecTcEntry 11 }







-- ------------------------------------------------------------------------------------------------------------------------

--     TABELLA  IpSecTcFlash    

--                                               ICR module cryptography table (in the flash memory)

--                                               NOTE: often referred as "agenda".

-- ------------------------------------------------------------------------------------------------------------------------



ipSecTcFlashTable       OBJECT-TYPE

		SYNTAX  SEQUENCE OF IpSecTcFlashEntry

		ACCESS  read-only

		STATUS  mandatory

	DESCRIPTION

		" This table provides informations about chypering gateways and configured

		security services reading data directly in the flash memory (often referred as                  agenda)."

	::= { ipSec 3 }





	ipSecTcFlashEntry OBJECT-TYPE

			SYNTAX  IpSecTcFlashEntry

			ACCESS  read-only

			STATUS  mandatory

		DESCRIPTION

			" Cryptography table entry. "

			INDEX { ipSecTcFlashGtw }

		::= { ipSecTcFlashTable 1 }



	IpSecTcFlashEntry ::= SEQUENCE {

		ipSecTcFlashGtw   IpAddress,

		ipSecTcFlashCypher   INTEGER,

		ipSecTcFlashChain   INTEGER,

		ipSecTcFlashIntegr   INTEGER,

		ipSecTcFlashSignt    INTEGER,

		ipSecTcFlashAuth  INTEGER,

		ipSecTcFlashAccessctrl       INTEGER,

		ipSecTcFlashNotaio  IpAddress,

		ipSecTcFlashValiditySince  DisplayString,

		ipSecTcFlashValidityUntil  DisplayString,

		ipSecTcFlashInfo  DisplayString

		}



	ipSecTcFlashGtw   OBJECT-TYPE

			SYNTAX  IpAddress

			ACCESS  read-only

			STATUS  mandatory

		DESCRIPTION

			" Addressee chypering gateway. "

		::= { ipSecTcFlashEntry 1 }



	ipSecTcFlashCypher   OBJECT-TYPE

			SYNTAX  INTEGER{

					enabled(1),

					disabled(0)

					}

			ACCESS  read-only

			STATUS  mandatory

		DESCRIPTION

			" Cyphering service ON/OFF. "

		::= { ipSecTcFlashEntry 2 }



	ipSecTcFlashIntegr  OBJECT-TYPE

			SYNTAX  INTEGER{

					enabled(1),

					disabled(0)

					}

			ACCESS  read-only

			STATUS  mandatory

		DESCRIPTION

			"Integrity service ON/OFF"

		::= { ipSecTcFlashEntry 4 }



	ipSecTcFlashChain  OBJECT-TYPE

			SYNTAX  INTEGER{

					enabled(1),

					disabled(0)

					}

			ACCESS  read-only

			STATUS  mandatory

		DESCRIPTION

			"Chaining service ON/OFF."

		::= { ipSecTcFlashEntry 3 }



	ipSecTcFlashSignt   OBJECT-TYPE

			SYNTAX  INTEGER{

					enabled(1),

					disabled(0)

					}

			ACCESS  read-only

			STATUS  mandatory

		DESCRIPTION

			"Electronic sign (authentication of the sender) ON/OFF."

		::= { ipSecTcFlashEntry 5 }



	ipSecTcFlashAuth  OBJECT-TYPE

			SYNTAX  INTEGER{

					enabled(1),

					disabled(0)

					}

			ACCESS  read-only

			STATUS  mandatory

		DESCRIPTION

			"Authentication service ON/OFF"

		::= { ipSecTcFlashEntry 6 }



	ipSecTcFlashAccessctrl  OBJECT-TYPE

			SYNTAX  INTEGER{

					enabled(1),

					disabled(0)

					}

			ACCESS  read-only

			STATUS  mandatory

		DESCRIPTION

			"Check on accesses service ON/OFF."

		::= { ipSecTcFlashEntry 7 }



	ipSecTcFlashNotaio  OBJECT-TYPE

			SYNTAX  IpAddress

			ACCESS  read-only

			STATUS  mandatory

		DESCRIPTION

			"Certifying Notary IP address. "

		::= { ipSecTcFlashEntry 8 }



	ipSecTcFlashValiditySince  OBJECT-TYPE

			SYNTAX  DisplayString

			ACCESS  read-only

			STATUS  mandatory

		DESCRIPTION

			"Validity begin date."

		::= { ipSecTcFlashEntry 9 }



	ipSecTcFlashValidityUntil  OBJECT-TYPE

			SYNTAX  DisplayString 

			ACCESS  read-only

			STATUS  mandatory

		DESCRIPTION

			"Validity end date."

		::= { ipSecTcFlashEntry 10 }



	ipSecTcFlashInfo  OBJECT-TYPE

			SYNTAX  DisplayString 

			ACCESS  read-only

			STATUS  mandatory

		DESCRIPTION

			"Entry's info field."

		::= { ipSecTcFlashEntry 11 }



-- ------------------------------------------------------------------------------------------------------------------------

--     VARIABLE IpSecNumEntry    

--                                               Number of entries in agenda

-- ------------------------------------------------------------------------------------------------------------------------





	ipSecNumEntry     OBJECT-TYPE

			SYNTAX  INTEGER

			ACCESS  read-only

			STATUS  mandatory

		DESCRIPTION

			"Number of entries in agenda."

			::= { ipSec 4 }



-- ------------------------------------------------------------------------------------------------------------------------

--     TABLE  IpSecTcIp    

--                                               IP module cryptogrphy table

-- ------------------------------------------------------------------------------------------------------------------------

ipSecTcIpTable       OBJECT-TYPE

		SYNTAX  SEQUENCE OF IpSecTcIpEntry

		ACCESS  read-only

		STATUS  mandatory

	DESCRIPTION

		"This table provides informations about which gateways

		have cryptography services configured for frames destined to them."

	::= { ipSec 5 }





	ipSecTcIpEntry OBJECT-TYPE

			SYNTAX  IpSecTcIpEntry

			ACCESS  read-only

			STATUS  mandatory

		DESCRIPTION

			" Cryptography table entry. "

			INDEX { ipSecTcIpIpDst }

		::= { ipSecTcIpTable 1 }



	IpSecTcIpEntry ::= SEQUENCE {

		ipSecTcIpIpDst   IpAddress,

		ipSecTcIpMaskDst   IpAddress,

		ipSecTcIpGtwDst  IpAddress

		}



	ipSecTcIpIpDst   OBJECT-TYPE

			SYNTAX  IpAddress

			ACCESS  read-only

			STATUS  mandatory

		DESCRIPTION

			"Addressee IP address."

		::= { ipSecTcIpEntry 1 }



	ipSecTcIpMaskDst   OBJECT-TYPE

			SYNTAX  IpAddress

			ACCESS  read-only

			STATUS  mandatory

		DESCRIPTION

			"Addressee IP mask."

		::= { ipSecTcIpEntry 2 }



	ipSecTcIpGtwDst   OBJECT-TYPE

			SYNTAX  IpAddress

			ACCESS  read-only

			STATUS  mandatory

		DESCRIPTION

			"Cyphering gateway. "

		::= { ipSecTcIpEntry 3 }







-- ------------------------------------------------------------------------------------------------------------------------

--     NODO IpSecTrap    

--                           Useful informations related to the sending of an alarm

-- ------------------------------------------------------------------------------------------------------------------------



-- ------------------------------------------------------------------------------------------------------------------------

--     VARIABILE IpSecTrapIndIp    

--                                              IP address of the gateway that caused the alarm to be sent

-- ------------------------------------------------------------------------------------------------------------------------

	ipSecTrapIndIp     OBJECT-TYPE

			SYNTAX  IpAddress

			ACCESS  read-only

			STATUS  mandatory

		DESCRIPTION

			" IP address of the gateway that caused the alarm to be sent."

			::= { ipSecTrap 1 }



-- ------------------------------------------------------------------------------------------------------------------------

--     VARIABILE IpSecTrapKeyp    

--                                              Used public key

-- ------------------------------------------------------------------------------------------------------------------------

	ipSecTrapKeyp     OBJECT-TYPE

			SYNTAX OCTET STRING 

			ACCESS  read-only

			STATUS  mandatory

		DESCRIPTION

			" Public key which caused the alarm to be sent."

			::= { ipSecTrap 2 }



-- ------------------------------------------------------------------------------------------------------------------------

--     VARIABILE IpSecTrapCode    

--                                              Alarm code

-- ------------------------------------------------------------------------------------------------------------------------

	ipSecTrapCode     OBJECT-TYPE

			SYNTAX  INTEGER

			ACCESS  read-only

			STATUS  mandatory

		DESCRIPTION

			" Specific trap sent: 38144-bad agend; 36864-authentication failed; 36868-gateway not responding."

			::= { ipSecTrap 3 }





-- ------------------------------------------------------------------------------------------------------------------------

--     VARIABILE IpSecTrapDataValid    

--                                              States weather data are accessible or not

-- ------------------------------------------------------------------------------------------------------------------------

	ipSecTrapDataValid     OBJECT-TYPE

			SYNTAX  INTEGER{

					keyNotValid(2),

					valid(1),

					notValid(0)

					}

			ACCESS  read-only

			STATUS  mandatory

		DESCRIPTION

			" States weather data are accessible or not."

			::= { ipSecTrap 4 }









-- *****************************************************************************

-- Gruppo 802.2

--        Ha le seguenti ramificazioni:

--        - i802Diag    - i802IfcCnfTab     (TABELLA)

--                      - i802LinkCnfTab    (TABELLA)

--                      - i802OpTab         (TABELLA)

--                      - i802StatTab       (TABELLA)

--

-- Nell'analisi delle variabili tenere presente la seguente considerazione:

-- 802.2 e' costituito da 2 Unita' Logiche denominate " Wan Station Component

-- (WSC)" e "Lan Station Component(LSC)".

--      - WSC gestisce la linea X25 con controllo logico QLLC sia su un PVC

--        che su un SVC.

--      - LSC gestisce l'accesso Lan con LLC IEE 802.2 utilizzando i SAP di

--        indirizzo 04, 08, 0C per la conversione QLLC.

-- *****************************************************************************



i802Diag        OBJECT IDENTIFIER ::= { i802-2 2 }





-- -------------------------------------------------------------------------

--     TABELLA i802IfcCnfTab     

--                                               TABELLA CONFIGURAZIONE IFC I802

-- -------------------------------------------------------------------------



i802IfcCnfTable   OBJECT-TYPE

		SYNTAX  SEQUENCE OF I802IfcCnfEntry

		ACCESS  not-accessible

		STATUS  mandatory

	DESCRIPTION

		"Questa tabella raccoglie le informazioni di

		 configurazione 802.2 relative ad un'interfaccia."

	::= { i802Diag 1 }





	i802IfcCnfEntry OBJECT-TYPE

			SYNTAX  I802IfcCnfEntry

			ACCESS  not-accessible

			STATUS  mandatory

		DESCRIPTION

			"Entry configurazione 802.2 ifc"

			INDEX { i802IfcCnfInd }

		::= { i802IfcCnfTable 1 }

	I802IfcCnfEntry ::= SEQUENCE {

		i802IfcCnfInd   INTEGER,

		i802IfcNLink    INTEGER,

		i802IfcCrin     INTEGER,

		i802IfcLenCrin  INTEGER

		}





	i802IfcCnfInd   OBJECT-TYPE

			SYNTAX  INTEGER

			ACCESS  read-only

			STATUS  mandatory

		DESCRIPTION

			"Indice relativo all'interfaccia 802.2,

			 corrisponde a ifIndex della MIB II."

		::= { i802IfcCnfEntry 1 }





	i802IfcNLink    OBJECT-TYPE

			SYNTAX  INTEGER

			ACCESS  read-only

			STATUS  mandatory

		DESCRIPTION

			"Numero di link 802.2 configurati sull'

			 interfaccia (per la definizione di LINK

			 vedi tabella i802LinkCnfTab)."

		::= { i802IfcCnfEntry 2 }





	i802IfcCrin     OBJECT-TYPE

			SYNTAX  INTEGER{

				criterio-NUALEN (1),

				criterio-SUBLEN (2),

				criterio-NONE (3)

				}

			ACCESS  read-only

			STATUS  mandatory

		DESCRIPTION

			"Definisce la modalita' di instradamento 

			(vedi manuale configurazione GAIA)."

		::= { i802IfcCnfEntry 3 }





	i802IfcLenCrin  OBJECT-TYPE

			SYNTAX  INTEGER

			ACCESS  read-only

			STATUS  mandatory

		DESCRIPTION

			"Lunghezza utilizzata dal criterio di instradamento:

			 Valori ammessi: 0 se i802IfcCrin = NONE,

			 da 1...15 se i802IfcCrin = NUALEN e SUBLEN"

		::= { i802IfcCnfEntry 4 }



-- -------------------------------------------------------------------------

--     TABELLA i802LinkCnfTab     

--                                               TABELLA CONFIGURAZIONE LINK I802

-- -------------------------------------------------------------------------



i802LinkCnfTable  OBJECT-TYPE

		SYNTAX  SEQUENCE OF I802LinkCnfEntry

		ACCESS  not-accessible

		STATUS  mandatory

	DESCRIPTION

		"Questa tabella riporta tutte le informazioni

		 di configurazione relative al singolo LINK 802.2

		 dell'interfaccia specificata."

	::= { i802Diag 2 }





	i802LinkCnfEntry        OBJECT-TYPE

			SYNTAX  I802LinkCnfEntry

			ACCESS  not-accessible

			STATUS  mandatory

		DESCRIPTION

			"Entry configurazione 802.2 link"

			INDEX { i802LinkIfc,

				i802LinkInd }

		::= { i802LinkCnfTable 1 }

	I802LinkCnfEntry ::= SEQUENCE {

		i802LinkIfc     INTEGER,

		i802LinkInd     INTEGER,

		i802LinkT200    INTEGER,

		i802LinkTmng    INTEGER,

		i802LinkT203    INTEGER,

		i802LinkN200    INTEGER,

		i802LinkN201    INTEGER,

		i802LinkK       INTEGER,

		i802LinkEthDst  OCTET STRING,

		i802LinkEthSrc  OCTET STRING,

		i802LinkNuaDst  OCTET STRING,

		i802LinkSsap    INTEGER,

		i802LinkDsap    INTEGER

		}





	i802LinkIfc     OBJECT-TYPE

			SYNTAX  INTEGER

			ACCESS  read-only

			STATUS  mandatory

		DESCRIPTION

			"Indice dell'interfaccia, corrisponde a ifIndex

			 della MIB II."

		::= { i802LinkCnfEntry 1 }





	i802LinkInd     OBJECT-TYPE

			SYNTAX  INTEGER

			ACCESS  read-only

			STATUS  mandatory

		DESCRIPTION

			"Indice del link 802.2 con numerazione

			 a partire da 1."

		::= { i802LinkCnfEntry 2 }





	i802LinkT200    OBJECT-TYPE

			SYNTAX  INTEGER

			ACCESS  read-only

			STATUS  mandatory

		DESCRIPTION

			"Valore del timer T200.

			 Valori ammessi 5...200 espressi in ms."

		::= { i802LinkCnfEntry 3 }





	i802LinkTmng    OBJECT-TYPE

			SYNTAX  INTEGER

			ACCESS  read-only

			STATUS  mandatory

		DESCRIPTION

			"Timer trascorso il quale l'apparato inizia

			 la procedura di richiesta connessione con la

			 trama di contatto TEST.

			 Valori ammessi da 10.... 600."

		::= { i802LinkCnfEntry 4 }





	i802LinkT203    OBJECT-TYPE

			SYNTAX  INTEGER

			ACCESS  read-only

			STATUS  mandatory

		DESCRIPTION

			"Configurazione timer T203.

			 Valori ammessi da 10....600."

		::= { i802LinkCnfEntry 5 }





	i802LinkN200    OBJECT-TYPE

			SYNTAX  INTEGER

			ACCESS  read-only

			STATUS  mandatory

		DESCRIPTION

			"Valore parametro N200.

			 Valori ammessi da 1...10."

		::= { i802LinkCnfEntry 6 }





	i802LinkN201    OBJECT-TYPE

			SYNTAX  INTEGER

			ACCESS  read-only

			STATUS  mandatory

		DESCRIPTION

			"Valore parametro N201."

		::= { i802LinkCnfEntry 7 }





	i802LinkK       OBJECT-TYPE

			SYNTAX  INTEGER

			ACCESS  read-only

			STATUS  mandatory

		DESCRIPTION

			"Valore parametro K.

			 Valore ammessi da 1...127."

		::= { i802LinkCnfEntry 8 }





	i802LinkEthDst  OBJECT-TYPE

			SYNTAX  OCTET STRING (SIZE(6))

			ACCESS  read-only

			STATUS  mandatory

		DESCRIPTION

			"Indirizzo MAC destinatario"

		::= { i802LinkCnfEntry 9 }





	i802LinkEthSrc  OBJECT-TYPE

			SYNTAX  OCTET STRING (SIZE(6))

			ACCESS  read-only

			STATUS  mandatory

		DESCRIPTION

			"Indirizzo MAC sorgente"

		::= { i802LinkCnfEntry 10 }





	i802LinkNuaDst  OBJECT-TYPE

			SYNTAX  DisplayString

			ACCESS  read-only

			STATUS  mandatory

		DESCRIPTION

			"Nua destinatario utilizzato dal link X25

			 connesso."

		::= { i802LinkCnfEntry 11 }





	i802LinkSsap    OBJECT-TYPE

			SYNTAX  INTEGER

			ACCESS  read-only

			STATUS  mandatory

		DESCRIPTION

			"SAP sorgente.

			 Valori ammessi 04, 08, 0C."

		::= { i802LinkCnfEntry 12 }





	i802LinkDsap    OBJECT-TYPE

			SYNTAX  INTEGER

			ACCESS  read-only

			STATUS  mandatory

		DESCRIPTION

			"SAP destinatario.

			 Valori ammessi 04, 08, 0C."

		::= { i802LinkCnfEntry 13 }



-- -------------------------------------------------------------------------

--     TABELLA i802OpTab     

--                                               TABELLA OPERATIVA I802

-- -------------------------------------------------------------------------



i802OpTable       OBJECT-TYPE

		SYNTAX  SEQUENCE OF I802OpEntry

		ACCESS  not-accessible

		STATUS  mandatory

	DESCRIPTION

		"Questa tabella indicizzata sull'interfaccia e sul 

		 link 802.2 riassume le principali informazioni sullo

		 stato operativo del link."

	::= { i802Diag 3 }





	i802OpEntry     OBJECT-TYPE

			SYNTAX  I802OpEntry

			ACCESS  not-accessible

			STATUS  mandatory

		DESCRIPTION

			"Entry Operativa 802.2"

			INDEX { i802OpIfc,

				i802OpLink }

		::= { i802OpTable 1 }

	I802OpEntry ::= SEQUENCE {

		i802OpIfc       INTEGER,

		i802OpLink      INTEGER,

		i802OpLanMode   INTEGER,

		i802OpLanState  INTEGER,

		i802OpWanState  INTEGER,

	     -- i802OpModeStart INTEGER,

		i802OpIdbIdnRx  OCTET STRING,

		i802OpIdbIdnTx  OCTET STRING

		}





	i802OpIfc       OBJECT-TYPE

			SYNTAX  INTEGER

			ACCESS  read-only

			STATUS  mandatory

		DESCRIPTION

			"Indice dell'interfaccia 802.2 corrisponde

			 a ifIndex della MIB II."

		::= { i802OpEntry 1 }





	i802OpLink      OBJECT-TYPE

			SYNTAX  INTEGER

			ACCESS  read-only

			STATUS  mandatory

		DESCRIPTION

			"Numero del link relativo all'interfaccia

			 specificata."

		::= { i802OpEntry 2 }





	i802OpLanMode   OBJECT-TYPE

			SYNTAX  INTEGER {

				modalita-802-3 (1),

				modalita-ETHERNET (2)

				}

			ACCESS  read-only

			STATUS  mandatory

		DESCRIPTION

			"Modalita` lavoro a livello MAC:

			 802.3 / Ethernet."

		::= { i802OpEntry 3 }





	i802OpLanState  OBJECT-TYPE

			SYNTAX  INTEGER {

				 disconnected (3),

				 await-Est    (4),

				 await-Rel    (5),

				 established  (6),

				 broadcast    (8),

				 rej-sent     (9),

				 remote-busy  (10),

				 local-busy   (11),

				 busy-TXRX    (12)

				}

			ACCESS  read-only

			STATUS  mandatory

		DESCRIPTION

			"Stato corrente del protocollo 802.2 

			 lato interfaccia Lan."

		::= { i802OpEntry 4 }





	i802OpWanState  OBJECT-TYPE

			SYNTAX  INTEGER {

				no-CONNECTIONS        (0),

				up-EST                (1),

				low-AWAITS-CONN       (2),

				up-LOW-EST            (3),

				low-AWAITS-DISC       (4),

				up-DISC-LOW-NOT-YET   (5),

				up-D-LOW-WCNT         (6),

				up-WCON-LOW-CNT       (7),

				up-WDISC-LOW-DISC     (8),

				up-WCON-LOW-DISC      (9)

				}

			ACCESS  read-only

			STATUS  mandatory

		DESCRIPTION

			"Stato corrente della connessione 

			 lato interfaccia Wan"

		::= { i802OpEntry 5 }





	i802OpIdbIdnRx  OBJECT-TYPE

			SYNTAX  OCTET STRING (SIZE(4))

			ACCESS  read-only

			STATUS  mandatory

		DESCRIPTION

			"IdBlock IdNumber relativi all'ultima

			 trama XID ricevuta da Lan.

			 Valore 0xffffffff all'inizializzazione o

			 alla chiusura di sessione."

		::= { i802OpEntry 6 }





	i802OpIdbIdnTx  OBJECT-TYPE

			SYNTAX  OCTET STRING (SIZE(4))

			ACCESS  read-only

			STATUS  mandatory

		DESCRIPTION

			"Riporta i valori dei campiIdBlock IdNumber

			 presenti nell'ultima trama XID trasmessa sull'

			 interfaccia Lan.

			 Valore 0xffffffff all'inizializzazione o

			 alla chiusura di sessione."

		::= { i802OpEntry 7 }





-- -------------------------------------------------------------------------

--     TABELLA i802StatTab     

--                                               TABELLA STATISTICHE I802

-- -------------------------------------------------------------------------



i802StatTable     OBJECT-TYPE

		SYNTAX  SEQUENCE OF I802StatEntry

		ACCESS  not-accessible

		STATUS  mandatory

	DESCRIPTION

		"Questa tabella indicizzata per interfaccia e link

		 riporta contatori statistici relativi al link 802.2.

		 La tabella viene azzerata in seguito a errori di

		 protocollo irreversibili (es: ricezione DM non sol-

		 lecitato etc)."

	::= { i802Diag 4 }





	i802StatEntry   OBJECT-TYPE

			SYNTAX  I802StatEntry

			ACCESS  not-accessible

			STATUS  mandatory

		DESCRIPTION

			"Entry statistiche 802.2"

			INDEX { i802StatIfc, 

				i802StatLink }

		::= { i802StatTable 1 }

	I802StatEntry ::= SEQUENCE {

		i802StatIfc     INTEGER,

		i802StatLink    INTEGER,

		i802InfoTx      Counter,

		i802RnrTx       Counter,

		i802RejTx       Counter,

		i802SabmeTx     Counter,

		i802DiscTx      Counter,

		i802XidTx       Counter,

		i802TestTx      Counter,

		i802UiTx        Counter,

		i802FrmrTx      Counter,

		i802RnrTxTime   TimeTicks,

		i802NRitr       Counter,

		i802InfoRx      Counter,

		i802RnrRx       Counter,

		i802RejRx       Counter,

		i802SabmeRx     Counter,

		i802DiscRx      Counter,

		i802XidRx       Counter,

		i802TestRx      Counter,

		i802UiRx        Counter,

		i802FrmrRx      Counter,

		i802RnrRxTime   TimeTicks

		}





	i802StatIfc     OBJECT-TYPE

			SYNTAX  INTEGER

			ACCESS  read-only

			STATUS  mandatory

		DESCRIPTION

			"Indice dell'interfaccia 802.2, corrisponde

			 a ifIndex della MIB II."

		::= { i802StatEntry 1 }

				



	i802StatLink    OBJECT-TYPE

			SYNTAX  INTEGER

			ACCESS  read-only

			STATUS  mandatory

		DESCRIPTION

			"Numero del Link 802.2."

		::= { i802StatEntry 2 }





	i802InfoTx      OBJECT-TYPE

			SYNTAX  Counter

			ACCESS  read-only

			STATUS  mandatory

		DESCRIPTION

			"Contatore delle Info trasmesse"

		::= { i802StatEntry 3 }





	i802RnrTx       OBJECT-TYPE

			SYNTAX  Counter

			ACCESS  read-only

			STATUS  mandatory

		DESCRIPTION

			"Contatore RNR trasmessi."

		::= { i802StatEntry 4 }





	i802RejTx       OBJECT-TYPE

			SYNTAX  Counter

			ACCESS  read-only

			STATUS  mandatory

		DESCRIPTION

			"Contatore REJ trasmessi."

		::= { i802StatEntry 5 }





	i802SabmeTx     OBJECT-TYPE

			SYNTAX  Counter

			ACCESS  read-only

			STATUS  mandatory

		DESCRIPTION

			"Contatore SABME trasmessi."

		::= { i802StatEntry 6 }





	i802DiscTx      OBJECT-TYPE

			SYNTAX  Counter

			ACCESS  read-only

			STATUS  mandatory

		DESCRIPTION

			"Contatore DISC trasmessi."

		::= { i802StatEntry 7 }





	i802XidTx       OBJECT-TYPE

			SYNTAX  Counter

			ACCESS  read-only

			STATUS  mandatory

		DESCRIPTION

			"Contatore XID trasmessi."

		::= { i802StatEntry 8 }





	i802TestTx      OBJECT-TYPE

			SYNTAX  Counter

			ACCESS  read-only

			STATUS  mandatory

		DESCRIPTION

			"Contatore TEST trasmessi."

		::= { i802StatEntry 9 }





	i802UiTx        OBJECT-TYPE

			SYNTAX  Counter

			ACCESS  read-only

			STATUS  mandatory

		DESCRIPTION

			"Contatore UI trasmessi."

		::= { i802StatEntry 10 }





	i802FrmrTx      OBJECT-TYPE

			SYNTAX  Counter

			ACCESS  read-only

			STATUS  mandatory

		DESCRIPTION

			"Contatore FRMR trasmessi."

		::= { i802StatEntry 11 }





	i802RnrTxTime   OBJECT-TYPE

			SYNTAX  TimeTicks

			ACCESS  read-only

			STATUS  mandatory

		DESCRIPTION

			"Tempo di sistema relativo all'ultima trama

			 RNR trasmessa."

		::= { i802StatEntry 12 }





	i802NRitr       OBJECT-TYPE

			SYNTAX  Counter

			ACCESS  read-only

			STATUS  mandatory

		DESCRIPTION

			"Contatore numero ritrasmissioni."

		::= { i802StatEntry 13 }





	i802InfoRx      OBJECT-TYPE

			SYNTAX  Counter

			ACCESS  read-only

			STATUS  mandatory

		DESCRIPTION

			"Contatore delle Info ricevute"

		::= { i802StatEntry 14 }





	i802RnrRx       OBJECT-TYPE

			SYNTAX  Counter

			ACCESS  read-only

			STATUS  mandatory

		DESCRIPTION

			"Contatore RNR ricevuti."

		::= { i802StatEntry 15 }





	i802RejRx       OBJECT-TYPE

			SYNTAX  Counter

			ACCESS  read-only

			STATUS  mandatory

		DESCRIPTION

			"Contatore REJ ricevuti."

		::= { i802StatEntry 16 }





	i802SabmeRx     OBJECT-TYPE

			SYNTAX  Counter

			ACCESS  read-only

			STATUS  mandatory

		DESCRIPTION

			"Contatore SABME ricevuti."

		::= { i802StatEntry 17 }





	i802DiscRx      OBJECT-TYPE

			SYNTAX  Counter

			ACCESS  read-only

			STATUS  mandatory

		DESCRIPTION

			"Contatore DISC ricevuti."

		::= { i802StatEntry 18 }





	i802XidRx       OBJECT-TYPE

			SYNTAX  Counter

			ACCESS  read-only

			STATUS  mandatory

		DESCRIPTION

			"Contatore XID ricevuti."

		::= { i802StatEntry 19 }





	i802TestRx      OBJECT-TYPE

			SYNTAX  Counter

			ACCESS  read-only

			STATUS  mandatory

		DESCRIPTION

			"Contatore TEST ricevuti."

		::= { i802StatEntry 20 }





	i802UiRx        OBJECT-TYPE

			SYNTAX  Counter

			ACCESS  read-only

			STATUS  mandatory

		DESCRIPTION

			"Contatore UI ricevuti."

		::= { i802StatEntry 21 }





	i802FrmrRx      OBJECT-TYPE

			SYNTAX  Counter

			ACCESS  read-only

			STATUS  mandatory

		DESCRIPTION

			"Contatore FRMR ricevuti."

		::= { i802StatEntry 22 }





	i802RnrRxTime   OBJECT-TYPE

			SYNTAX  TimeTicks

			ACCESS  read-only

			STATUS  mandatory

		DESCRIPTION

			"Tempo di sistema relativa all'ultime trama

			 RNR ricevuta."

		::= { i802StatEntry 23 }







-- *****************************************************************************

-- Gruppo X28

--        Ha le seguenti ramificazioni:

--        - X28Diag     - X28CnfTab     (TABELLA)

--                      - X28OpTab      (TABELLA)

-- *****************************************************************************



x28Diag OBJECT IDENTIFIER ::= { x28 2 }







-- -------------------------------------------------------------------------

--     TABELLA X28CnfTab     

--                                               TABELLA CONFIGURAZIONE X28

-- -------------------------------------------------------------------------



x28CnfTable       OBJECT-TYPE

		SYNTAX  SEQUENCE OF X28CnfEntry

		ACCESS  not-accessible

		STATUS  mandatory

	DESCRIPTION

		"Questa tabella riassume i parametri di	configurazione

		 X28 di un'interfaccia."

	::= { x28Diag 1 }



	x28CnfEntry     OBJECT-TYPE

			SYNTAX  X28CnfEntry

			ACCESS  not-accessible

			STATUS  mandatory

		DESCRIPTION

			"Entry tabella X28CnfTab"

			INDEX   { x28CnfIfc }

		::= { x28CnfTable 1 }



	X28CnfEntry ::= SEQUENCE {

		x28CnfIfc               INTEGER,

		x28CnfPar1              INTEGER,

		x28CnfPar2              INTEGER,

		x28CnfPar3              INTEGER,

		x28CnfPar4              INTEGER,

		x28CnfPar5              INTEGER,

		x28CnfPar6              INTEGER,

		x28CnfPar7              INTEGER,

		x28CnfPar8              INTEGER,

		x28CnfPar9              INTEGER,

		x28CnfPar10             INTEGER,

		x28CnfPar11             INTEGER,

		x28CnfPar12             INTEGER,

		x28CnfPar13             INTEGER,

		x28CnfPar14             INTEGER,

		x28CnfPar15             INTEGER,

		x28CnfPar16             INTEGER,

		x28CnfPar17             INTEGER,

		x28CnfPar18             INTEGER,

		x28CnfPar19             INTEGER,

		x28CnfPar20             INTEGER,

		x28CnfPar21             INTEGER,

		x28CnfPar22             INTEGER,

		x28CnfParity            INTEGER

		}





	x28CnfIfc       OBJECT-TYPE

			SYNTAX  INTEGER

			ACCESS  read-only

			STATUS  mandatory

		DESCRIPTION

			"Indice dell'interfaccia su cui e` configurata

			 l'entita` X28. corrisponde a ifIndex della

			 MIB II."

		::= { x28CnfEntry 1 }





	x28CnfPar1      OBJECT-TYPE

			SYNTAX  INTEGER

			ACCESS  read-only

			STATUS  mandatory

		DESCRIPTION

			"Parametro 1 profilo X28"

		::= { x28CnfEntry 2 }



	x28CnfPar2      OBJECT-TYPE

			SYNTAX  INTEGER

			ACCESS  read-only

			STATUS  mandatory

		DESCRIPTION

			"Parametro 2 profilo X28"

		::= { x28CnfEntry 3 }



	x28CnfPar3      OBJECT-TYPE

			SYNTAX  INTEGER

			ACCESS  read-only

			STATUS  mandatory

		DESCRIPTION

			"Parametro 3 profilo X28"

		::= { x28CnfEntry 4 }



	x28CnfPar4      OBJECT-TYPE

			SYNTAX  INTEGER

			ACCESS  read-only

			STATUS  mandatory

		DESCRIPTION

			"Parametro 4 profilo X28"

		::= { x28CnfEntry 5 }



	x28CnfPar5      OBJECT-TYPE

			SYNTAX  INTEGER

			ACCESS  read-only

			STATUS  mandatory

		DESCRIPTION

			"Parametro 5 profilo X28"

		::= { x28CnfEntry 6 }



	x28CnfPar6      OBJECT-TYPE

			SYNTAX  INTEGER

			ACCESS  read-only

			STATUS  mandatory

		DESCRIPTION

			"Parametro 6 profilo X28"

		::= { x28CnfEntry 7 }



	x28CnfPar7      OBJECT-TYPE

			SYNTAX  INTEGER

			ACCESS  read-only

			STATUS  mandatory

		DESCRIPTION

			"Parametro 7 profilo X28"

		::= { x28CnfEntry 8 }



	x28CnfPar8      OBJECT-TYPE

			SYNTAX  INTEGER

			ACCESS  read-only

			STATUS  mandatory

		DESCRIPTION

			"Parametro 8 profilo X28"

		::= { x28CnfEntry 9 }



	x28CnfPar9      OBJECT-TYPE

			SYNTAX  INTEGER

			ACCESS  read-only

			STATUS  mandatory

		DESCRIPTION

			"Parametro 9 profilo X28"

		::= { x28CnfEntry 10 }



	x28CnfPar10     OBJECT-TYPE

			SYNTAX  INTEGER

			ACCESS  read-only

			STATUS  mandatory

		DESCRIPTION

			"Parametro 10 profilo X28"

		::= { x28CnfEntry 11 }



	x28CnfPar11     OBJECT-TYPE

			SYNTAX  INTEGER

			ACCESS  read-only

			STATUS  mandatory

		DESCRIPTION

			"Parametro 11 profilo X28"

		::= { x28CnfEntry 12 }



	x28CnfPar12     OBJECT-TYPE

			SYNTAX  INTEGER

			ACCESS  read-only

			STATUS  mandatory

		DESCRIPTION

			"Parametro 12 profilo X28"

		::= { x28CnfEntry 13 }



	x28CnfPar13     OBJECT-TYPE

			SYNTAX  INTEGER

			ACCESS  read-only

			STATUS  mandatory

		DESCRIPTION

			"Parametro 13 profilo X28"

		::= { x28CnfEntry 14 }



	x28CnfPar14     OBJECT-TYPE

			SYNTAX  INTEGER

			ACCESS  read-only

			STATUS  mandatory

		DESCRIPTION

			"Parametro 14 profilo X28"

		::= { x28CnfEntry 15 }



	x28CnfPar15     OBJECT-TYPE

			SYNTAX  INTEGER

			ACCESS  read-only

			STATUS  mandatory

		DESCRIPTION

			"Parametro 15 profilo X28"

		::= { x28CnfEntry 16 }



	x28CnfPar16     OBJECT-TYPE

			SYNTAX  INTEGER

			ACCESS  read-only

			STATUS  mandatory

		DESCRIPTION

			"Parametro 16 profilo X28"

		::= { x28CnfEntry 17 }



	x28CnfPar17     OBJECT-TYPE

			SYNTAX  INTEGER

			ACCESS  read-only

			STATUS  mandatory

		DESCRIPTION

			"Parametro 17 profilo X28"

		::= { x28CnfEntry 18 }



	x28CnfPar18     OBJECT-TYPE

			SYNTAX  INTEGER

			ACCESS  read-only

			STATUS  mandatory

		DESCRIPTION

			"Parametro 18 profilo X28"

		::= { x28CnfEntry 19 }



	x28CnfPar19     OBJECT-TYPE

			SYNTAX  INTEGER

			ACCESS  read-only

			STATUS  mandatory

		DESCRIPTION

			"Parametro 19 profilo X28"

		::= { x28CnfEntry 20 }



	x28CnfPar20     OBJECT-TYPE

			SYNTAX  INTEGER

			ACCESS  read-only

			STATUS  mandatory

		DESCRIPTION

			"Parametro 20 profilo X28"

		::= { x28CnfEntry 21 }



	x28CnfPar21     OBJECT-TYPE

			SYNTAX  INTEGER

			ACCESS  read-only

			STATUS  mandatory

		DESCRIPTION

			"Parametro 21 profilo X28"

		::= { x28CnfEntry 22 }



	x28CnfPar22     OBJECT-TYPE

			SYNTAX  INTEGER

			ACCESS  read-only

			STATUS  mandatory

		DESCRIPTION

			"Parametro 22 profilo X28"

		::= { x28CnfEntry 23 }



	x28CnfParity    OBJECT-TYPE

			SYNTAX  INTEGER{

					even  (0),

					odd   (1),

					mark  (2),

					space (3)

			}

			ACCESS  read-only

			STATUS  mandatory

		DESCRIPTION

			"Parita' X28 configurata"

		::= { x28CnfEntry 24 }





-- -------------------------------------------------------------------------

--     TABELLA X28OpTab     

--                                               TABELLA OPERATIVA X28

-- -------------------------------------------------------------------------



x28OpTable        OBJECT-TYPE

		SYNTAX  SEQUENCE OF X28OpEntry

		ACCESS  not-accessible

		STATUS  mandatory

	DESCRIPTION

		"Tabella dei parametri operativi su una

		 interfaccia X28."

	::= { x28Diag 2 }



	x28OpEntry      OBJECT-TYPE

			SYNTAX  X28OpEntry

			ACCESS  not-accessible

			STATUS  mandatory

		DESCRIPTION

			"Entry tabella X28OpTab"

			INDEX   { x28OpIfc }

		::= { x28OpTable 1 }



	X28OpEntry ::= SEQUENCE {

		x28OpIfc                INTEGER,

		x28OpPar1               INTEGER,

		x28OpPar2               INTEGER,

		x28OpPar3               INTEGER,

		x28OpPar4               INTEGER,

		x28OpPar5               INTEGER,

		x28OpPar6               INTEGER,

		x28OpPar7               INTEGER,

		x28OpPar8               INTEGER,

		x28OpPar9               INTEGER,

		x28OpPar10              INTEGER,

		x28OpPar11              INTEGER,

		x28OpPar12              INTEGER,

		x28OpPar13              INTEGER,

		x28OpPar14              INTEGER,

		x28OpPar15              INTEGER,

		x28OpPar16              INTEGER,

		x28OpPar17              INTEGER,

		x28OpPar18              INTEGER,

		x28OpPar19              INTEGER,

		x28OpPar20              INTEGER,

		x28OpPar21              INTEGER,

		x28OpPar22              INTEGER,

		x28OpParity             INTEGER,

		x28OpState              INTEGER,

		x28OpParityErr          Counter,

		x28OpIfcDest            INTEGER



		}





	x28OpIfc        OBJECT-TYPE

			SYNTAX  INTEGER

			ACCESS  read-only

			STATUS  mandatory

		DESCRIPTION

			"Indice dell'interfaccia su cui e` configurata

			 l'entita` X28, corrisponde a ifIndex della

			 MIB II."

		::= { x28OpEntry 1 }





	x28OpPar1       OBJECT-TYPE

			SYNTAX  INTEGER

			ACCESS  read-only

			STATUS  mandatory

		DESCRIPTION

			"Parametro 1 profilo X28"

		::= { x28OpEntry 2 }



	x28OpPar2       OBJECT-TYPE

			SYNTAX  INTEGER

			ACCESS  read-only

			STATUS  mandatory

		DESCRIPTION

			"Parametro 2 profilo X28"

		::= { x28OpEntry 3 }



	x28OpPar3       OBJECT-TYPE

			SYNTAX  INTEGER

			ACCESS  read-only

			STATUS  mandatory

		DESCRIPTION

			"Parametro 3 profilo X28"

		::= { x28OpEntry 4 }



	x28OpPar4       OBJECT-TYPE

			SYNTAX  INTEGER

			ACCESS  read-only

			STATUS  mandatory

		DESCRIPTION

			"Parametro 4 profilo X28"

		::= { x28OpEntry 5 }



	x28OpPar5       OBJECT-TYPE

			SYNTAX  INTEGER

			ACCESS  read-only

			STATUS  mandatory

		DESCRIPTION

			"Parametro 5 profilo X28"

		::= { x28OpEntry 6 }



	x28OpPar6       OBJECT-TYPE

			SYNTAX  INTEGER

			ACCESS  read-only

			STATUS  mandatory

		DESCRIPTION

			"Parametro 6 profilo X28"

		::= { x28OpEntry 7 }



	x28OpPar7       OBJECT-TYPE

			SYNTAX  INTEGER

			ACCESS  read-only

			STATUS  mandatory

		DESCRIPTION

			"Parametro 7 profilo X28"

		::= { x28OpEntry 8 }



	x28OpPar8       OBJECT-TYPE

			SYNTAX  INTEGER

			ACCESS  read-only

			STATUS  mandatory

		DESCRIPTION

			"Parametro 8 profilo X28"

		::= { x28OpEntry 9 }



	x28OpPar9       OBJECT-TYPE

			SYNTAX  INTEGER

			ACCESS  read-only

			STATUS  mandatory

		DESCRIPTION

			"Parametro 9 profilo X28"

		::= { x28OpEntry 10 }



	x28OpPar10      OBJECT-TYPE

			SYNTAX  INTEGER

			ACCESS  read-only

			STATUS  mandatory

		DESCRIPTION

			"Parametro 10 profilo X28"

		::= { x28OpEntry 11 }



	x28OpPar11      OBJECT-TYPE

			SYNTAX  INTEGER

			ACCESS  read-only

			STATUS  mandatory

		DESCRIPTION

			"Parametro 11 profilo X28"

		::= { x28OpEntry 12 }



	x28OpPar12      OBJECT-TYPE

			SYNTAX  INTEGER

			ACCESS  read-only

			STATUS  mandatory

		DESCRIPTION

			"Parametro 12 profilo X28"

		::= { x28OpEntry 13 }



	x28OpPar13      OBJECT-TYPE

			SYNTAX  INTEGER

			ACCESS  read-only

			STATUS  mandatory

		DESCRIPTION

			"Parametro 13 profilo X28"

		::= { x28OpEntry 14 }



	x28OpPar14      OBJECT-TYPE

			SYNTAX  INTEGER

			ACCESS  read-only

			STATUS  mandatory

		DESCRIPTION

			"Parametro 14 profilo X28"

		::= { x28OpEntry 15 }



	x28OpPar15      OBJECT-TYPE

			SYNTAX  INTEGER

			ACCESS  read-only

			STATUS  mandatory

		DESCRIPTION

			"Parametro 15 profilo X28"

		::= { x28OpEntry 16 }



	x28OpPar16      OBJECT-TYPE

			SYNTAX  INTEGER

			ACCESS  read-only

			STATUS  mandatory

		DESCRIPTION

			"Parametro 16 profilo X28"

		::= { x28OpEntry 17 }



	x28OpPar17      OBJECT-TYPE

			SYNTAX  INTEGER

			ACCESS  read-only

			STATUS  mandatory

		DESCRIPTION

			"Parametro 17 profilo X28"

		::= { x28OpEntry 18 }



	x28OpPar18      OBJECT-TYPE

			SYNTAX  INTEGER

			ACCESS  read-only

			STATUS  mandatory

		DESCRIPTION

			"Parametro 18 profilo X28"

		::= { x28OpEntry 19 }



	x28OpPar19      OBJECT-TYPE

			SYNTAX  INTEGER

			ACCESS  read-only

			STATUS  mandatory

		DESCRIPTION

			"Parametro 19 profilo X28"

		::= { x28OpEntry 20 }



	x28OpPar20      OBJECT-TYPE

			SYNTAX  INTEGER

			ACCESS  read-only

			STATUS  mandatory

		DESCRIPTION

			"Parametro 20 profilo X28"

		::= { x28OpEntry 21 }



	x28OpPar21      OBJECT-TYPE

			SYNTAX  INTEGER

			ACCESS  read-only

			STATUS  mandatory

		DESCRIPTION

			"Parametro 21 profilo X28"

		::= { x28OpEntry 22 }



	x28OpPar22      OBJECT-TYPE

			SYNTAX  INTEGER

			ACCESS  read-only

			STATUS  mandatory

		DESCRIPTION

			"Parametro 22 profilo X28"

		::= { x28OpEntry 23 }



	x28OpParity     OBJECT-TYPE

			SYNTAX  INTEGER{

					even  (0),

					odd   (1),

					mark  (2),

					space (3)

			}

			ACCESS  read-only

			STATUS  mandatory

		DESCRIPTION

			"Parita' X28 configurata"

		::= { x28OpEntry 24 }



	x28OpState      OBJECT-TYPE

			SYNTAX  INTEGER {

				 pad-Waiting                  (0),

				 connection-in-Progress       (1),

				 waiting-Command              (2),

				 data-Transfer                (3),

				 disconnection-in-Progress    (4)

				}

			ACCESS  read-only

			STATUS  mandatory

		DESCRIPTION

			"Stato interfaccia"

		::= { x28OpEntry 25 }



	x28OpParityErr  OBJECT-TYPE

			SYNTAX  Counter

			ACCESS  read-only

			STATUS  mandatory

		DESCRIPTION

			"Contatore errori parita'"

		::= { x28OpEntry 26 }



	x28OpIfcDest    OBJECT-TYPE

			SYNTAX  INTEGER

			ACCESS  read-only

			STATUS  mandatory

		DESCRIPTION

			"Indice (ifIndex) interfaccia connessa"

		::= { x28OpEntry 27 }





-- *****************************************************************************

-- Gruppo FRY

--        Ha le seguenti ramificazioni:

-- *****************************************************************************



   fryDiag         OBJECT IDENTIFIER ::= { fry 2}



-- -------------------------------------------------------------------------

--     TABELLA Frame Relay     

--                 TABELLA configurazione ifc FRY Standard RFC 1315

-- -------------------------------------------------------------------------



     frDlcmiTable OBJECT-TYPE

	 SYNTAX   SEQUENCE OF FrDlcmiEntry

	 ACCESS   not-accessible

	 STATUS   mandatory

	 DESCRIPTION

	    "The Parameters for the Data Link Connection Management

	    Interface for the frame relay service on this

	    interface."

	::= { fryDiag 1 }



	frDlcmiEntry OBJECT-TYPE

	SYNTAX   FrDlcmiEntry

	ACCESS   not-accessible

	STATUS   mandatory

	DESCRIPTION

		"The Parameters for a particular Data Link Con-

			nection Management Interface."

	INDEX { frDlcmiIfIndex }

	::= { frDlcmiTable 1 }



	 FrDlcmiEntry ::=

	     SEQUENCE {

		 frDlcmiIfIndex                 INTEGER,

		 frDlcmiState                   INTEGER,

		 frDlcmiAddress                 INTEGER,

		 frDlcmiAddressLen              INTEGER,

		 frDlcmiPollingInterval INTEGER,

		 frDlcmiFullEnquiryInterval     INTEGER,

		 frDlcmiErrorThreshold          INTEGER,

		 frDlcmiMonitoredEvents INTEGER,

		 frDlcmiMaxSupportedVCs INTEGER,

		 frDlcmiMulticast                       INTEGER

	 }



	 frDlcmiIfIndex OBJECT-TYPE

	     SYNTAX   INTEGER

	     ACCESS   read-only

	     STATUS   mandatory

	     DESCRIPTION

		"The ifIndex value of the  corresponding  ifEn-

		try."

	    ::= { frDlcmiEntry 1 }



	 frDlcmiState OBJECT-TYPE

	     SYNTAX INTEGER {

		 noLmiConfigured        (1),

		 lmiRev1                (2),

		 ansiT1-617-D   (3),            -- ANSI T1.617 Annex D

		 ansiT1-617-B   (4),            -- ANSI T1.617 Annex B

		 itutX36                (5)    -- CCITT Q933 Annex A modifica rispetto standard

	     }

	     ACCESS   read-only         --standard: read-write

	     STATUS   mandatory

	     DESCRIPTION

		"This variable states which Data  Link  Connec-

		tion Management scheme is active (and by impli-

		cation, what DLCI it uses) on the  Frame  Relay

		interface."

	    REFERENCE

	       "Draft American National Standard T1.617-1991"

	   ::= { frDlcmiEntry 2 }



	 frDlcmiAddress OBJECT-TYPE

	     SYNTAX      INTEGER {

			 q921           (1),  -- 13 bit DLCI

			 q922March90    (2),  -- 11 bit DLCI

			 q922November90 (3),  -- 10 bit DLCI

			 q922           (4)   -- Final Standard

	     }

	     ACCESS  read-only          --standard: read-write

	     STATUS  mandatory

	     DESCRIPTION

		"This variable states which address  format  is

		in use on the Frame Relay interface."

	    ::= { frDlcmiEntry 3 }



	 frDlcmiAddressLen OBJECT-TYPE

	     SYNTAX  INTEGER {

		     two-octets (2),

		     three-octets (3),

		     four-octets (4)

	     }

	     ACCESS  read-only          --standard: read-write

	     STATUS  mandatory

	     DESCRIPTION

		"This variable states which address  length  in

		octets.  In the case of Q922 format, the length

		indicates the entire length of the address  in-

		cluding the control portion."

	    ::= { frDlcmiEntry 4 }



	 frDlcmiPollingInterval OBJECT-TYPE

	     SYNTAX   INTEGER (5..30)

	     ACCESS   read-write

	     STATUS   mandatory

	     DESCRIPTION

		"This is the number of seconds between  succes-

		sive status enquiry messages."

	    REFERENCE

	       "Draft American National  Standard  T1.617-1991,

	       Section D.7 Timer T391."

--           DEFVAL { 10 }

	   ::= { frDlcmiEntry 5 }





	 frDlcmiFullEnquiryInterval OBJECT-TYPE

	     SYNTAX   INTEGER (1..255)

	     ACCESS   read-write

	     STATUS   mandatory

	     DESCRIPTION

		"Number of status enquiry intervals  that  pass

		before  issuance  of a full status enquiry mes-

		sage."

	    REFERENCE

	       "Draft American National  Standard  T1.617-1991,

	       Section D.7 Counter N391."

--           DEFVAL { 6 }

	   ::= { frDlcmiEntry 6 }







	 frDlcmiErrorThreshold OBJECT-TYPE

	     SYNTAX   INTEGER (1..10)

	     ACCESS   read-write

	     STATUS   mandatory

	     DESCRIPTION

		"This  is  the  maximum  number  of  unanswered

		Status Enquiries the equipment shall accept be-

		fore declaring the interface down."

	    REFERENCE

	       "Draft American National  Standard  T1.617-1991,

	       Section D.5.1 Counter N392."

--           DEFVAL { 3 }

	   ::= { frDlcmiEntry 7 }



	 frDlcmiMonitoredEvents OBJECT-TYPE

	     SYNTAX   INTEGER (1..10)

	     ACCESS   read-write

	     STATUS   mandatory

	     DESCRIPTION

		"This is the number of status polling intervals

		over which the error threshold is counted.  For

		example, if within 'MonitoredEvents' number  of

		events  the  station  receives 'ErrorThreshold'

		number of errors, the interface  is  marked  as

		down."

	    REFERENCE

	       "Draft American National  Standard  T1.617-1991,

	       Section D.5.2 Counter N393."

--           DEFVAL { 4 }

	   ::= { frDlcmiEntry 8 }







	 frDlcmiMaxSupportedVCs OBJECT-TYPE

	     SYNTAX   INTEGER

	     ACCESS   read-only --standard: read-write

	     STATUS   mandatory

	     DESCRIPTION

		"The maximum number of Virtual Circuits allowed

		for  this  interface.   Usually dictated by the

		Frame Relay network.



		In response to a SET, if a value less than zero

		or  higher  than the agent's maximal capability

		is configured, the agent  should  respond  bad-

		Value"

	    ::= { frDlcmiEntry 9 }





	 frDlcmiMulticast OBJECT-TYPE

	     SYNTAX   INTEGER {

			 nonBroadcast (1),

			 broadcast (2)

			 }

	     ACCESS   read-only --standard: read-write

	     STATUS   mandatory

	     DESCRIPTION

		"This indicates whether the Frame Relay  inter-

		face is using a multicast service."

	    ::= { frDlcmiEntry 10 }



-- -------------------------------------------------------------------------

--     TABELLA Frame Relay     

--                 TABELLA configurazione dlci FRY Standard RFC 1315

-- -------------------------------------------------------------------------



     frCircuitTable OBJECT-TYPE

	 SYNTAX   SEQUENCE OF FrCircuitEntry

	 ACCESS   not-accessible

	 STATUS   mandatory

	 DESCRIPTION

	    "A table containing information about specific Data

	    Link Connection Identifiers and corresponding virtual

	    circuits."

	 ::= { fryDiag 2 }



	 frCircuitEntry OBJECT-TYPE

	     SYNTAX   FrCircuitEntry

	     ACCESS   not-accessible

	     STATUS   mandatory

	     DESCRIPTION

		"The information regarding a single  Data  Link

		Connection Identifier."

	    INDEX { frCircuitIfIndex, frCircuitDlci }

	    ::= { frCircuitTable 1 }



	 FrCircuitEntry ::=

	     SEQUENCE {

		 frCircuitIfIndex         INTEGER,

		 frCircuitDlci            INTEGER,

		 frCircuitState           INTEGER,

		 frCircuitReceivedFECNs   INTEGER,

		 frCircuitReceivedBECNs   INTEGER,

		 frCircuitSentFrames      INTEGER,

		 frCircuitSentOctets      INTEGER,

		 frCircuitReceivedFrames  INTEGER,

		 frCircuitReceivedOctets  INTEGER,

		 frCircuitCreationTime    INTEGER,

		 frCircuitLastTimeChange  INTEGER,

		 frCircuitCommittedBurst  INTEGER,

		 frCircuitExcessBurst     INTEGER,

		 frCircuitThroughput      INTEGER

	 }



	 frCircuitIfIndex OBJECT-TYPE

	     SYNTAX   INTEGER

	     ACCESS   read-only

	     STATUS   mandatory

	     DESCRIPTION

		"The ifIndex Value of the ifEntry this  virtual

		circuit is layered onto."

	    ::= { frCircuitEntry 1 }





	 frCircuitDlci OBJECT-TYPE

	     SYNTAX   INTEGER

	     ACCESS   read-only

	     STATUS   mandatory

	     DESCRIPTION

		"The Data Link Connection Identifier  for  this

		virtual circuit."

	    REFERENCE

	       "Draft American National  Standard  T1.618-1991,

	       Section 3.3.6"

	   ::= { frCircuitEntry 2 }



	 frCircuitState OBJECT-TYPE

	     SYNTAX   INTEGER {

			 invalid (1),

			 active (2),

			 inactive (3)

		      }

	     ACCESS   read-only --standard: read-write

	     STATUS   mandatory

	     DESCRIPTION

		"Indicates whether the particular virtual  cir-

		cuit  is operational.  In the absence of a Data

		Link Connection Management  Interface,  virtual

		circuit  entries  (rows) may be created by set-

		ting virtual  circuit  state  to  'active',  or

		deleted by changing Circuit state to 'invalid'.

		Whether or not the row actually  disappears  is

		left  to the implementation, so this object may

		actually read as 'invalid' for  some  arbitrary

		length  of  time.   It is also legal to set the

		state of a virtual  circuit  to  'inactive'  to

		temporarily disable a given circuit."

--            DEFVAL { active }

	    ::= { frCircuitEntry 3 }





	 frCircuitReceivedFECNs OBJECT-TYPE

	     SYNTAX   INTEGER

	     ACCESS   read-only

	     STATUS   mandatory

	     DESCRIPTION

		"Number of frames received from the network in-

		dicating  forward  congestion since the virtual

		circuit was created."

	    REFERENCE

	       "Draft American National  Standard  T1.618-1991,

	       Section 3.3.3"

	   ::= { frCircuitEntry 4 }







	 frCircuitReceivedBECNs OBJECT-TYPE

	     SYNTAX   INTEGER

	     ACCESS   read-only

	     STATUS   mandatory

	     DESCRIPTION

		"Number of frames received from the network in-

		dicating  backward congestion since the virtual

		circuit was created."

	    REFERENCE

	       "Draft American National  Standard  T1.618-1991,

	       Section 3.3.4"

	   ::= { frCircuitEntry 5 }







	 frCircuitSentFrames OBJECT-TYPE

	     SYNTAX   INTEGER

	     ACCESS   read-only

	     STATUS   mandatory

	     DESCRIPTION

		"The number of frames sent  from  this  virtual

		circuit since it was created."

	    ::= { frCircuitEntry 6 }



	 frCircuitSentOctets OBJECT-TYPE

	     SYNTAX   INTEGER

	     ACCESS   read-only

	     STATUS   mandatory

	     DESCRIPTION

		"The number of octets sent  from  this  virtual

		circuit since it was created."

	    ::= { frCircuitEntry 7 }



	 frCircuitReceivedFrames OBJECT-TYPE

	     SYNTAX   INTEGER

	     ACCESS   read-only

	     STATUS   mandatory

	     DESCRIPTION

		"Number of frames received  over  this  virtual

		circuit since it was created."

	    ::= { frCircuitEntry 8 }



	 frCircuitReceivedOctets OBJECT-TYPE

	     SYNTAX   INTEGER

	     ACCESS   read-only

	     STATUS   mandatory

	     DESCRIPTION

		"Number of octets received  over  this  virtual

		circuit since it was created."

	    ::= { frCircuitEntry 9 }



	 frCircuitCreationTime OBJECT-TYPE

	     SYNTAX   INTEGER

	     ACCESS   read-only

	     STATUS   mandatory

	     DESCRIPTION

		"The value of sysUpTime when the  virtual  cir-

		cuit was created, whether by the Data Link Con-

		nection Management Interface  or  by  a  SetRe-

		quest."

	    ::= { frCircuitEntry 10 }



	 frCircuitLastTimeChange OBJECT-TYPE

	     SYNTAX   INTEGER

	     ACCESS   read-only

	     STATUS   mandatory

	     DESCRIPTION

		"The value of sysUpTime when last there  was  a

		change in the virtual circuit state"

	    ::= { frCircuitEntry 11 }



	 frCircuitCommittedBurst OBJECT-TYPE

	     SYNTAX   INTEGER

	     ACCESS   read-write

	     STATUS   mandatory

	     DESCRIPTION

		"This variable indicates the maximum amount  of

		data,  in  bits,  that  the  network  agrees to

		transfer under normal  conditions,  during  the

		measurement interval."

	    REFERENCE

	       "Draft American National  Standard  T1.617-1991,

	       Section 6.5.19"

--           DEFVAL   { 0 }  the default indicates no commitment

	   ::= { frCircuitEntry 12 }



	 frCircuitExcessBurst OBJECT-TYPE

	     SYNTAX   INTEGER

	     ACCESS   read-write

	     STATUS   mandatory

	     DESCRIPTION

		"This variable indicates the maximum amount  of

		uncommitted data bits that the network will at-

		tempt to deliver over the measurement interval.



		By default, if not configured when creating the

		entry, the Excess Information Burst Size is set

		to the value of ifSpeed."

	    REFERENCE

	       "Draft American National  Standard  T1.617-1991,

	       Section 6.5.19"

		   ::= { frCircuitEntry 13 }



	 frCircuitThroughput OBJECT-TYPE

	     SYNTAX   INTEGER

	     ACCESS   read-write

	     STATUS   mandatory

	     DESCRIPTION

		"Throughput is the average number of 'Frame Re-

		lay  Information  Field'  bits  transferred per

		second across a user network interface  in  one

		direction, measured over the measurement inter-

		val.



		If the  configured  committed  burst  rate  and

		throughput  are  both non-zero, the measurement

		interval

		T=frCircuitCommittedBurst/frCircuitThroughput.



		If the  configured  committed  burst  rate  and

		throughput  are  both zero, the measurement in-

		terval

		       T=frCircuitExcessBurst/ifSpeed."

	    REFERENCE

	       "Draft American National  Standard  T1.617-1991,

	       Section 6.5.19"

--           DEFVAL {0}   the default value of Throughput is

		       -- "no commitment".

	   ::= { frCircuitEntry 14 }



-- -------------------------------------------------------------------------

--     TABELLA Frame Relay     

--                 TABELLA errori per ogni interfaccia FRY Standard RFC 1315

-- -------------------------------------------------------------------------



     frErrTable OBJECT-TYPE

	 SYNTAX   SEQUENCE OF FrErrEntry

	 ACCESS   not-accessible

	 STATUS   mandatory

	 DESCRIPTION

	    "A table containing information about Errors on the

	    Frame Relay interface."

	 ::= { fryDiag 3 }



	 frErrEntry OBJECT-TYPE

	     SYNTAX   FrErrEntry

	     ACCESS   not-accessible

	     STATUS   mandatory

	     DESCRIPTION

		"The error information for a single frame relay

		interface."

	    INDEX { frErrIfIndex }

	    ::= { frErrTable 1 }





	 FrErrEntry ::=

	     SEQUENCE {

		 frErrIfIndex  INTEGER,

		 frErrType     INTEGER,

		 frErrData     DisplayString,

		 frErrTime     TimeTicks

	 }



	 frErrIfIndex OBJECT-TYPE

	     SYNTAX   INTEGER

	     ACCESS   read-only

	     STATUS   mandatory

	     DESCRIPTION

		"The ifIndex Value of the  corresponding  ifEn-

		try."

	    ::= { frErrEntry 1 }



	 frErrType OBJECT-TYPE

	     SYNTAX   INTEGER {

			 unknownError(1),

			 receiveShort(2),

			 receiveLong(3),

			 illegalDLCI(4),

			 unknownDLCI(5),

			 dlcmiProtoErr(6),

			 dlcmiUnknownIE(7),

			 dlcmiSequenceErr(8),

			 dlcmiUnknownRpt(9),

			 noErrorSinceReset(10)

		      }

	     ACCESS   read-only

	     STATUS   mandatory

	     DESCRIPTION

		"The type of error that was last seen  on  this

		interface."

	    ::= { frErrEntry 2 }



	 frErrData OBJECT-TYPE

	     SYNTAX   DisplayString

	     ACCESS   read-only

	     STATUS   mandatory

	     DESCRIPTION

		"An octet string containing as much of the  er-

		ror  packet as possible.  As a minimum, it must

		contain the Q.922 Address or  as  much  as  was

		delivered.   It is desirable to include all in-

		formation up to the PDU."

	    ::= { frErrEntry 3 }





	 frErrTime OBJECT-TYPE

	     SYNTAX   TimeTicks

	     ACCESS   read-only

	     STATUS   mandatory

	     DESCRIPTION

		"The value of sysUpTime at which the error  was

		detected."

	    ::= { frErrEntry 4 }



-- ------------------------------------------------------------------------------------------------------------------------

--     VARIABILE FRY-ABILTRAP

--                              definisce se il modulo e abilitato all'invio di trap

-- ------------------------------------------------------------------------------------------------------------------------



	 frTrapState OBJECT-TYPE

	     SYNTAX  INTEGER { enabled(1), disabled(2) }

	     ACCESS   read-write

	     STATUS   mandatory

	     DESCRIPTION

		"This variable  indicates  whether  the  system

		produces the frDLCIStatusChange trap."

	    DEFVAL { disabled }

	    ::= { fryDiag 4 }



-- -------------------------------------------------------------------------

--     TABELLA Frame Relay     

--                 TABELLA STATO interfaccia FRY non standard

-- -------------------------------------------------------------------------



     frDlcmiProprTable OBJECT-TYPE

	 SYNTAX   SEQUENCE OF FrDlcmiProprEntry

	 ACCESS   not-accessible

	 STATUS   mandatory

	 DESCRIPTION

	    "Stato dell'interfaccia Frame Relay relativamente a configurazioni

	     opzionali quali modalita asincrona e bidirezionale"

	::= { fryDiag 5 }



	frDlcmiProprEntry OBJECT-TYPE

	SYNTAX   FrDlcmiProprEntry

	ACCESS   not-accessible

	STATUS   mandatory

	DESCRIPTION

		"Parametri per una data interfaccia (configurazioni opzionali)"

	INDEX { frDlcmiPrIfIndex }

	::= { frDlcmiProprTable 1 }



	 FrDlcmiProprEntry ::=

	     SEQUENCE {

		 frDlcmiPrIfIndex               INTEGER,

		 frDlcmiPrType                  INTEGER,

		 frDlcmiPrStatus                        INTEGER,

		 frDlcmiPrModFun                        INTEGER,

		 frDlcmiPrAsyncr                        INTEGER,

		 frDlcmiPrBidir                 INTEGER,

		 frDlcmiPrBidSt                 INTEGER,

		 frDlcmiPrBidPollIntCtr INTEGER,

		 frDlcmiPrBidFullEnqInt INTEGER,

		 frDlcmiPrBidErrThres           INTEGER,

		 frDlcmiPrBidMonEv              INTEGER,

		 frDlcmiPrNumDlciColl           INTEGER

	 }



	 frDlcmiPrIfIndex OBJECT-TYPE

	     SYNTAX   INTEGER

	     ACCESS   read-only

	     STATUS   mandatory

	     DESCRIPTION

		"Indice dell'interfaccia su cui insiste quella logica 

			di cui si presentano le caratteristiche."

	    ::= { frDlcmiProprEntry 1 }



	 frDlcmiPrType OBJECT-TYPE

	     SYNTAX   INTEGER {

					serial1(1),

					serial2(4)

				}

	     ACCESS   read-only

	     STATUS   mandatory

	     DESCRIPTION

		"Tipo di interfaccia fisica su cui insiste quella logica."

	    ::= { frDlcmiProprEntry 2 }



	 frDlcmiPrStatus OBJECT-TYPE

	     SYNTAX   INTEGER {

					service-IN(1),

					service-OUT(2)

				}

	     ACCESS   read-only

	     STATUS   mandatory

	     DESCRIPTION

		"Stato dell'interfaccia."

	    ::= { frDlcmiProprEntry 3 }



	 frDlcmiPrModFun OBJECT-TYPE

	     SYNTAX   INTEGER {

				mod-DTE(1),

				mod-DEBUG(2),

				mod-TEST(3)

			}

	     ACCESS   read-only

	     STATUS   mandatory

	     DESCRIPTION

		"Modalita` di funzionamento del DTE:

			DTE:            modalita` tipica;

			DEBUG:  simulazione rete (non completa solo scopo debug);

			TEST:           senza polling."

	    ::= { frDlcmiProprEntry 4 }



	 frDlcmiPrAsyncr OBJECT-TYPE

	     SYNTAX   INTEGER {

				asincrono-OFF(1),

				asincrono-ON(2)

			}

	     ACCESS   read-only

	     STATUS   mandatory

	     DESCRIPTION

		"Abilitazione o disabilitazione della 

			procedura di polling asincrono."

	    ::= { frDlcmiProprEntry 5 }



	 frDlcmiPrBidir OBJECT-TYPE

	     SYNTAX   INTEGER {

				bidirezionale-OFF(1),

				bidirezionale-ON(2)

			}

	     ACCESS   read-only

	     STATUS   mandatory

	     DESCRIPTION

		"Abilitazione o disabilitazione della 

			procedura di polling bidirezionale."

	    ::= { frDlcmiProprEntry 6 }



	 frDlcmiPrBidSt OBJECT-TYPE

	     SYNTAX   INTEGER {

				bid-Service-IN(1),

				bid-Service-OUT(2)

			}

	     ACCESS   read-only

	     STATUS   mandatory

	     DESCRIPTION

		"Stato dell'interfaccia per quanto concerne il 

			polling in modalita` DCE."

	    ::= { frDlcmiProprEntry 7 }



	 frDlcmiPrBidPollIntCtr OBJECT-TYPE

	     SYNTAX   INTEGER

	     ACCESS   read-write

	     STATUS   mandatory

	     DESCRIPTION

		"Secondi che il DTE attende prima di considerare come non 

			giunto il messaggio di enquiry dal DCE (modalita` 

			bidirezionale)."

	    ::= { frDlcmiProprEntry 8 }

	 

	 frDlcmiPrBidFullEnqInt OBJECT-TYPE

	     SYNTAX   INTEGER

	     ACCESS   read-write

	     STATUS   mandatory

	     DESCRIPTION

		"Numero di messaggi di Status che il DTE si aspetta ricevere

			dal DCE (modalita` bidirezionale) prima di un Full Status."

	    ::= { frDlcmiProprEntry 9 }



	 frDlcmiPrBidErrThres OBJECT-TYPE

	     SYNTAX   INTEGER

	     ACCESS   read-write

	     STATUS   mandatory

	     DESCRIPTION

		"Numero di eventi di polling modalita` bidirezionale che il DTE

			attende prima di dichiarare down o up l'interfaccia."

	    ::= { frDlcmiProprEntry 10 }

	 

	 frDlcmiPrBidMonEv OBJECT-TYPE

	     SYNTAX   INTEGER

	     ACCESS   read-write

	     STATUS   mandatory

	     DESCRIPTION

		"Numero di eventi di polling modalita` bidirezionale in

			cui vengono monitorati gli errori."

	    ::= { frDlcmiProprEntry 11 }



	 frDlcmiPrNumDlciColl OBJECT-TYPE

	     SYNTAX   INTEGER

	     ACCESS   read-only

	     STATUS   mandatory

	     DESCRIPTION

		"Numero di DLCI che insistono sull'interfaccia."

	    ::= { frDlcmiProprEntry 12 }



-- -------------------------------------------------------------------------

--     TABELLA Frame Relay     

--                 TABELLA configurazione dlci FRY non Standard

-- -------------------------------------------------------------------------



     frCircuitProprTable OBJECT-TYPE

	 SYNTAX   SEQUENCE OF FrCircuitProprEntry

	 ACCESS   not-accessible

	 STATUS   mandatory

	 DESCRIPTION

	    "Tabella con informazioni aggiuntive sul singolo DLCI."

	 ::= { fryDiag 6 }



	 frCircuitProprEntry OBJECT-TYPE

	     SYNTAX   FrCircuitProprEntry

	     ACCESS   not-accessible

	     STATUS   mandatory

	     DESCRIPTION

		"Informazioni riguardanti un singolo DLCI."

	    INDEX { frCircPrIfIndex, frCircPrDlci }

	    ::= { frCircuitProprTable 1 }



	 FrCircuitProprEntry ::=

	     SEQUENCE {

		 frCircPrIfIndex                INTEGER,

		 frCircPrDlci                   INTEGER,

		 frCircPrMaxLunTrama            INTEGER,

		 frCircPrStatoBusy              INTEGER,

		 frCircPrVelInvio               INTEGER

		}



	 frCircPrIfIndex OBJECT-TYPE

	     SYNTAX   INTEGER

	     ACCESS   read-only

	     STATUS   mandatory

	     DESCRIPTION

		"Valore dell'indice dell'interfaccia in cui il DLCI e`

		configurato."

	    ::= { frCircuitProprEntry 1 }



	 frCircPrDlci OBJECT-TYPE

	     SYNTAX   INTEGER

	     ACCESS   read-only

	     STATUS   mandatory

	     DESCRIPTION

		"Valore del DLCI a cui i dati si riferiscono."

	    ::= { frCircuitProprEntry 2 }



	 frCircPrMaxLunTrama OBJECT-TYPE

	     SYNTAX   INTEGER

	     ACCESS   read-write

	     STATUS   mandatory

	     DESCRIPTION

		"Massima lunghezza della trama accettata 

		(Tra 1600 e 4096 byte)."

	    ::= { frCircuitProprEntry 3 }



	 frCircPrStatoBusy OBJECT-TYPE

	     SYNTAX   INTEGER {

			noCong(1),

			congRete(2),

			congDr(3),

			congDrRete(4)

		}

	     ACCESS   read-only

	     STATUS   mandatory

	     DESCRIPTION

		"Mostra se il sistema ha condizioni di congestione in atto: 

			NoCong: Nessuna Congestione; 

			CongRete: Congestione della rete;

			CongDr: Congestione del Driver del Router;

			CongDr&Rete Congestione del Driver e della rete."

	    ::= { frCircuitProprEntry 4 }



	 frCircPrVelInvio OBJECT-TYPE

	     SYNTAX   INTEGER

	     ACCESS   read-only

	     STATUS   mandatory

	     DESCRIPTION

		"Valore della velocita` di invio (Kbit/s) al momento."

	    ::= { frCircuitProprEntry 5 }





-- *****************************************************************************

-- Gruppo PPP

--        Ha le seguenti ramificazioni:

-- *****************************************************************************





	 pppLcp OBJECT IDENTIFIER ::= { ppp 1}



	       -- The individual groups within the PPP-LCP-MIB



	       pppLink      OBJECT IDENTIFIER ::= { pppLcp 1 }

--             pppLqr       OBJECT IDENTIFIER ::= { pppLcp 2 }

--             pppTests     OBJECT IDENTIFIER ::= { pppLcp 3 }



	  --  PPP Link Group





	  --

	  -- The PPP Link Group. Implementation of this

	  -- group is mandatory for all PPP entities.

	  --



	  -- The following object reflect the values of the option

	  -- parameters used in the PPP Link Control Protocol

	  --   pppLinkStatusLocalMRU

	  --   pppLinkStatusRemoteMRU

	  --   pppLinkStatusLocalToPeerACCMap

	  --   pppLinkStatusPeerToLocalACCMap

	  --   pppLinkStatusLocalToRemoteProtocolCompression

	  --   pppLinkStatusRemoteToLocalProtocolCompression

	  --   pppLinkStatusLocalToRemoteACCompression

	  --   pppLinkStatusRemoteToLocalACCompression

	  --   pppLinkStatusTransmitFcsSize

	  --   pppLinkStatusReceiveFcsSize

	  --

	  -- These values are not available until after the PPP Option

	  -- negotiation has completed, which is indicated by the link

	  -- reaching the open state (i.e., ifOperStatus is set to

	  -- up).

	  --

	  -- Therefore, when ifOperStatus is not up

	  -- the contents of these objects is undefined. The value

	  -- returned when accessing the objects is an implementation

	  -- dependent issue.





	  pppLinkStatusTable   OBJECT-TYPE

	       SYNTAX    SEQUENCE OF PppLinkStatusEntry

	       ACCESS    not-accessible

	       STATUS    mandatory

	       DESCRIPTION

			 "A table containing PPP-link specific variables

			 for this PPP implementation."

	       ::= { pppLink 1 }





	  pppLinkStatusEntry   OBJECT-TYPE

	       SYNTAX    PppLinkStatusEntry

	       ACCESS    not-accessible

	       STATUS    mandatory

	       DESCRIPTION

			 "Management information about a particular PPP

			 Link."

	       INDEX     { ifIndex }

	       ::= { pppLinkStatusTable 1 }





	  PppLinkStatusEntry ::= SEQUENCE {

	       pppLinkStatusPhysicalIndex

		    INTEGER,

	       pppLinkStatusBadAddresses

		    Counter,

	       pppLinkStatusBadControls

		    Counter,

	       pppLinkStatusPacketTooLongs

		    Counter,

	       pppLinkStatusBadFCSs

		    Counter,

	       pppLinkStatusLocalMRU

		    INTEGER,

	       pppLinkStatusRemoteMRU

		    INTEGER,

	       pppLinkStatusLocalToPeerACCMap

		    OCTET STRING,

	       pppLinkStatusPeerToLocalACCMap

		    OCTET STRING,

	       pppLinkStatusLocalToRemoteProtocolCompression

		    INTEGER,

	       pppLinkStatusRemoteToLocalProtocolCompression

		    INTEGER,

	       pppLinkStatusLocalToRemoteACCompression

		    INTEGER,

	       pppLinkStatusRemoteToLocalACCompression

		    INTEGER,

	       pppLinkStatusTransmitFcsSize

		    INTEGER,

	       pppLinkStatusReceiveFcsSize

		    INTEGER

	       }

	  pppLinkStatusPhysicalIndex   OBJECT-TYPE

	       SYNTAX    INTEGER(0..2147483647)

	       ACCESS    read-only

	       STATUS    mandatory

	       DESCRIPTION

			 "The value of ifIndex that identifies the

			 lower-level interface over which this PPP Link

			 is operating. This interface would usually be

			 an HDLC or RS-232 type of interface. If there

			 is no lower-layer interface element, or there

			 is no ifEntry for the element, or the element

			 can not be identified, then the value of this

			 object is 0.  For example, suppose that PPP is

			 operating over a serial port. This would use

			 two entries in the ifTable. The PPP could be

			 running over `interface' number 123 and the

			 serial port could be running over `interface'

			 number 987.  Therefore, ifSpecific.123 would

			 contain the OBJECT IDENTIFIER ppp

			 pppLinkStatusPhysicalIndex.123 would contain

			 987, and ifSpecific.987 would contain the

			 OBJECT IDENTIFIER for the serial-port's media-

			 specific MIB."

	       ::= { pppLinkStatusEntry 1 }





	  pppLinkStatusBadAddresses   OBJECT-TYPE

	       SYNTAX    Counter

	       ACCESS    read-only

	       STATUS    mandatory

	       DESCRIPTION

			 "The number of packets received with an

			 incorrect Address Field. This Counter is a

			 component of the ifInErrors variable that is

			 associated with the interface that represents

			 this PPP Link."

	       REFERENCE

			 "Section 3.1, Address Field, of RFC1331."

	       ::= { pppLinkStatusEntry 2 }





	  pppLinkStatusBadControls   OBJECT-TYPE

	       SYNTAX    Counter

	       ACCESS    read-only

	       STATUS    mandatory

	       DESCRIPTION

			 "The number of packets received on this link

			 with an incorrect Control Field. This Counter

			 is a component of the ifInErrors variable that

			 is associated with the interface that

			 represents this PPP Link."

	       REFERENCE

			 "Section 3.1, Control Field, of RFC1331."

	       ::= { pppLinkStatusEntry 3 }





	  pppLinkStatusPacketTooLongs   OBJECT-TYPE

	       SYNTAX    Counter

	       ACCESS    read-only

	       STATUS    mandatory

	       DESCRIPTION

			 "The number of received packets that have been

			 discarded because their length exceeded the

			 MRU. This Counter is a component of the

			 ifInErrors variable that is associated with the

			 interface that represents this PPP Link. NOTE,

			 packets which are longer than the MRU but which

			 are successfully received and processed are NOT

			 included in this count."

	       ::= { pppLinkStatusEntry 4 }





	  pppLinkStatusBadFCSs   OBJECT-TYPE

	       SYNTAX    Counter

	       ACCESS    read-only

	       STATUS    mandatory

	       DESCRIPTION

			 "The number of received packets that have been

			 discarded due to having an incorrect FCS. This

			 Counter is a component of the ifInErrors

			 variable that is associated with the interface

			 that represents this PPP Link."

	       ::= { pppLinkStatusEntry 5 }





	  pppLinkStatusLocalMRU   OBJECT-TYPE

	       SYNTAX    INTEGER(1..2147483648)

	       ACCESS    read-only

	       STATUS    mandatory

	       DESCRIPTION

			 "The current value of the MRU for the local PPP

			 Entity. This value is the MRU that the remote

			 entity is using when sending packets to the

			 local PPP entity. The value of this object is

			 meaningful only when the link has reached the

			 open state (ifOperStatus is up)."

	       ::= { pppLinkStatusEntry 6 }





	  pppLinkStatusRemoteMRU   OBJECT-TYPE

	       SYNTAX    INTEGER(1..2147483648)

	       ACCESS    read-only

	       STATUS    mandatory

	       DESCRIPTION

			 "The current value of the MRU for the remote

			 PPP Entity. This value is the MRU that the

			 local entity is using when sending packets to

			 the remote PPP entity. The value of this object

			 is meaningful only when the link has reached

			 the open state (ifOperStatus is up)."

	       ::= { pppLinkStatusEntry 7 }





	  pppLinkStatusLocalToPeerACCMap   OBJECT-TYPE

	       SYNTAX    OCTET STRING (SIZE (4))

	       ACCESS    read-only

	       STATUS    mandatory

	       DESCRIPTION

			 "The current value of the ACC Map used for

			 sending packets from the local PPP entity to

			 the remote PPP entity. The value of this object

			 is meaningful only when the link has reached

			 the open state (ifOperStatus is up)."

	       ::= { pppLinkStatusEntry 8 }





	  pppLinkStatusPeerToLocalACCMap   OBJECT-TYPE

	       SYNTAX    OCTET STRING (SIZE (4))

	       ACCESS    read-only

	       STATUS    mandatory

	       DESCRIPTION

			 "The ACC Map used by the remote PPP entity when

			 transmitting packets to the local PPP entity.

			 The value of this object is meaningful only

			 when the link has reached the open state

			 (ifOperStatus is up)."

	       ::= { pppLinkStatusEntry 9 }





	  pppLinkStatusLocalToRemoteProtocolCompression

	       OBJECT-TYPE

	       SYNTAX    INTEGER 

	       ACCESS    read-only

	       STATUS    mandatory

	       DESCRIPTION

			 "Indicates whether the local PPP entity will

			 use Protocol Compression when transmitting

			 packets to the remote PPP entity. The value of

			 this object is meaningful only when the link

			 has reached the open state (ifOperStatus is

			 up)."

	       ::= { pppLinkStatusEntry 10 }





	  pppLinkStatusRemoteToLocalProtocolCompression

	       OBJECT-TYPE

	       SYNTAX    INTEGER 

	       ACCESS    read-only

	       STATUS    mandatory

	       DESCRIPTION

			 "Indicates whether the remote PPP entity will

			 use Protocol Compression when transmitting

			 packets to the local PPP entity. The value of

			 this object is meaningful only when the link

			 has reached the open state (ifOperStatus is

			 up)."

	       ::= { pppLinkStatusEntry 11 }





	  pppLinkStatusLocalToRemoteACCompression   OBJECT-TYPE

	       SYNTAX    INTEGER 

	       ACCESS    read-only

	       STATUS    mandatory

	       DESCRIPTION

			 "Indicates whether the local PPP entity will

			 use Address and Control Compression when

			 transmitting packets to the remote PPP entity.

			 The value of this object is meaningful only

			 when the link has reached the open state

			 (ifOperStatus is up)."

	       ::= { pppLinkStatusEntry 12 }





	  pppLinkStatusRemoteToLocalACCompression   OBJECT-TYPE

	       SYNTAX    INTEGER 

	       ACCESS    read-only

	       STATUS    mandatory

	       DESCRIPTION

			 "Indicates whether the remote PPP entity will

			 use Address and Control Compression when

			 transmitting packets to the local PPP entity.

			 The value of this object is meaningful only

			 when the link has reached the open state

			 (ifOperStatus is up)."

	       ::= { pppLinkStatusEntry 13 }





	  pppLinkStatusTransmitFcsSize   OBJECT-TYPE

	       SYNTAX    INTEGER (0..128)

	       ACCESS    read-only

	       STATUS    mandatory

	       DESCRIPTION

			 "The size of the Frame Check Sequence (FCS) in

			 bits that the local node will generate when

			 sending packets to the remote node. The value

			 of this object is meaningful only when the link

			 has reached the open state (ifOperStatus is

			 up)."

	       ::= { pppLinkStatusEntry 14 }





	  pppLinkStatusReceiveFcsSize   OBJECT-TYPE

	       SYNTAX    INTEGER (0..128)

	       ACCESS    read-only

	       STATUS    mandatory

	       DESCRIPTION

			 "The size of the Frame Check Sequence (FCS) in

			 bits that the remote node will generate when

			 sending packets to the local node. The value of

			 this object is meaningful only when the link

			 has reached the open state (ifOperStatus is

			 up)."

	       ::= { pppLinkStatusEntry 15 }





	  pppLinkConfigTable   OBJECT-TYPE

	       SYNTAX    SEQUENCE OF PppLinkConfigEntry

	       ACCESS    not-accessible

	       STATUS    mandatory

	       DESCRIPTION

			 "A table containing the LCP configuration

			 parameters for this PPP Link. These variables

			 represent the initial configuration of the PPP

			 Link. The actual values of the parameters may

			 be changed when the link is brought up via the

			 LCP options negotiation mechanism."

	       ::= { pppLink 2 }





	  pppLinkConfigEntry   OBJECT-TYPE

	       SYNTAX    PppLinkConfigEntry

	       ACCESS    not-accessible

	       STATUS    mandatory

	       DESCRIPTION

			 "Configuration information about a particular

			 PPP Link."

	       INDEX     { ifIndex }

	       ::= { pppLinkConfigTable 1 }





	  PppLinkConfigEntry ::= SEQUENCE {

	       pppLinkConfigInitialMRU

		    INTEGER,

	       pppLinkConfigReceiveACCMap

		    OCTET STRING,

	       pppLinkConfigTransmitACCMap

		    OCTET STRING,

	       pppLinkConfigMagicNumber

		    INTEGER,

	       pppLinkConfigFcsSize

		    INTEGER

	       }



	  pppLinkConfigInitialMRU   OBJECT-TYPE

	       SYNTAX    INTEGER(0..2147483647)

	       ACCESS    read-write

	       STATUS    mandatory

	       DESCRIPTION

			 "The initial Maximum Receive Unit (MRU) that

			 the local PPP entity will advertise to the

			 remote entity. If the value of this variable is

			 0 then the local PPP entity will not advertise

			 any MRU to the remote entity and the default

			 MRU will be assumed. Changing this object will

			 have effect when the link is next restarted."

	       REFERENCE

			 "Section 7.2, Maximum Receive Unit of RFC1331."

	       DEFVAL    { 1500 }

	       ::= { pppLinkConfigEntry 1 }





	  pppLinkConfigReceiveACCMap   OBJECT-TYPE

	       SYNTAX    OCTET STRING (SIZE (4))

	       ACCESS    read-write

	       STATUS    mandatory

	       DESCRIPTION

			 "The Asynchronous-Control-Character-Map (ACC)

			 that the local PPP entity requires for use on

			 its receive side. In effect, this is the ACC

			 Map that is required in order to ensure that

			 the local modem will successfully receive all

			 characters. The actual ACC map used on the

			 receive side of the link will be a combination

			 of the local node's pppLinkConfigReceiveACCMap

			 and the remote node's

			 pppLinkConfigTransmitACCMap. Changing this

			 object will have effect when the link is next

			 restarted."

	       REFERENCE

			 "Section 7.3, page 4, Async-Control-Character-

			 Map of RFC1331."

	       DEFVAL   { 'ffffffff'h }

	       ::= { pppLinkConfigEntry 2 }





	  pppLinkConfigTransmitACCMap   OBJECT-TYPE

	       SYNTAX    OCTET STRING ( SIZE(4))

	       ACCESS    read-write

	       STATUS    mandatory

	       DESCRIPTION

			 "The Asynchronous-Control-Character-Map (ACC)

			 that the local PPP entity requires for use on

			 its transmit side. In effect, this is the ACC

			 Map that is required in order to ensure that

			 all characters can be successfully transmitted

			 through the local modem.  The actual ACC map

			 used on the transmit side of the link will be a

			 combination of the local node's

			 pppLinkConfigTransmitACCMap and the remote

			 node's pppLinkConfigReceiveACCMap. Changing

			 this object will have effect when the link is

			 next restarted."

	       REFERENCE

			 "Section 7.3, page 4, Async-Control-Character-

			 Map of RFC1331."

	       DEFVAL   { 'ffffffff'h }

	       ::= { pppLinkConfigEntry 3 }





	  pppLinkConfigMagicNumber   OBJECT-TYPE

	       SYNTAX    INTEGER 

	       ACCESS    read-write

	       STATUS    mandatory

	       DESCRIPTION

			 "If true(2) then the local node will attempt to

			 perform Magic Number negotiation with the

			 remote node. If false(1) then this negotiation

			 is not performed. In any event, the local node

			 will comply with any magic number negotiations

			 attempted by the remote node, per the PPP

			 specification. Changing this object will have

			 effect when the link is next restarted."

	       REFERENCE

			 "Section 7.6, Magic Number, of RFC1331."

	       DEFVAL   { false }

	       ::= { pppLinkConfigEntry 4 }





	  pppLinkConfigFcsSize   OBJECT-TYPE

	       SYNTAX    INTEGER (0..128)

	       ACCESS    read-write

	       STATUS    mandatory

	       DESCRIPTION

			 "The size of the FCS, in bits, the local node

			 will attempt to negotiate for use with the

			 remote node. Regardless of the value of this

			 object, the local node will comply with any FCS

			 size negotiations initiated by the remote node,

			 per the PPP specification. Changing this object

			 will have effect when the link is next

			 restarted."

		DEFVAL  { 16 }

	       ::= { pppLinkConfigEntry 5 }







	  -- 

	  -- The PPPsecurity GROUP

	  -- 



	  pppSecurity OBJECT IDENTIFIER ::= { ppp 2 }



--        pppSecurityProtocols OBJECT IDENTIFIER ::= { pppSecurity 1 }



	  -- The following uniquely identify the various protocols

	  -- used by PPP security. These OBJECT IDENTIFIERS are

	  -- used in the pppSecurityConfigProtocol and

	  -- pppSecuritySecretsProtocol objects to identify to which

	  -- protocols the table entries apply.



--             pppSecurityPapProtocol OBJECT IDENTIFIER ::=

--                         { pppSecurityProtocols 1 }

--             pppSecurityChapMD5Protocol OBJECT IDENTIFIER ::=

--                         { pppSecurityProtocols 2 }



	  -- PPP Security Group

	  -- Implementation of this group is optional.



	  -- This table allows the network manager to configure

	  -- which security protocols are to be used on which

	  -- link and in what order of preference each is to be tried





	  pppSecurityConfigTable   OBJECT-TYPE

	       SYNTAX    SEQUENCE OF PppSecurityConfigEntry

	       ACCESS    not-accessible

	       STATUS    mandatory

	       DESCRIPTION

			 "Table containing the configuration and

			 preference parameters for PPP Security."

	       ::= { pppSecurity 2 }





	  pppSecurityConfigEntry   OBJECT-TYPE

	       SYNTAX    PppSecurityConfigEntry

	       ACCESS    not-accessible

	       STATUS    mandatory

	       DESCRIPTION

			 "Security configuration information for a

			 particular PPP link."

	       INDEX     { pppSecurityConfigLink,

			 pppSecurityConfigPreference }

	       ::= { pppSecurityConfigTable 1 }





	  PppSecurityConfigEntry ::= SEQUENCE {

	       pppSecurityConfigLink

		    INTEGER,

	       pppSecurityConfigPreference

		    INTEGER,

	       pppSecurityConfigProtocol

		    OBJECT IDENTIFIER,

	       pppSecurityConfigStatus

		    INTEGER

	       }





	  pppSecurityConfigLink   OBJECT-TYPE

	       SYNTAX    INTEGER(0..2147483647)

	       ACCESS    read-write

	       STATUS    mandatory

	       DESCRIPTION

			 "The value of ifIndex that identifies the entry

			 in the interface table that is associated with

			 the local PPP entity's link for which this

			 particular security algorithm shall be

			 attempted. A value of 0 indicates the default

			 algorithm - i.e., this entry applies to all

			 links for which explicit entries in the table

			 do not exist."

	       ::= { pppSecurityConfigEntry 1 }





	  pppSecurityConfigPreference   OBJECT-TYPE

	       SYNTAX    INTEGER(0..2147483647)

	       ACCESS    read-write

	       STATUS    mandatory

	       DESCRIPTION

			 "The relative preference of the security

			 protocol identified by

			 pppSecurityConfigProtocol. Security protocols

			 with lower values of

			 pppSecurityConfigPreference are tried before

			 protocols with higher values of

			 pppSecurityConfigPreference."

	       ::= { pppSecurityConfigEntry 2 }





	  pppSecurityConfigProtocol   OBJECT-TYPE

	       SYNTAX    OBJECT IDENTIFIER

	       ACCESS    read-write

	       STATUS    mandatory

	       DESCRIPTION

			 "Identifies the security protocol to be

			 attempted on the link identified by

			 pppSecurityConfigLink at the preference level

			 identified by pppSecurityConfigPreference. "

	       ::= { pppSecurityConfigEntry 3 }





	  pppSecurityConfigStatus   OBJECT-TYPE

	       SYNTAX    INTEGER  {

			 invalid(1),

			 valid(2)

		    }

	       ACCESS    read-write

	       STATUS    mandatory

	       DESCRIPTION

			 "Setting this object to the value invalid(1)

			 has the effect of invalidating the

			 corresponding entry in the

			 pppSecurityConfigTable. It is an

			 implementation-specific matter as to whether

			 the agent removes an invalidated entry from the

			 table.  Accordingly, management stations must

			 be prepared to receive tabular information from

			 agents that corresponds to entries not

			 currently in use.  Proper interpretation of

			 such entries requires examination of the

			 relevant pppSecurityConfigStatus object."

	       DEFVAL    { valid }

	       ::= { pppSecurityConfigEntry 4 }





	  -- This table contains all of the ID/Secret pair information.





	  pppSecuritySecretsTable   OBJECT-TYPE

	       SYNTAX    SEQUENCE OF PppSecuritySecretsEntry

	       ACCESS    not-accessible

	       STATUS    mandatory

	       DESCRIPTION

			 "Table containing the identities and secrets

			 used by the PPP authentication protocols.  As

			 this table contains secret information, it is

			 expected that access to this table be limited

			 to those SNMP Party-Pairs for which a privacy

			 protocol is in use for all SNMP messages that

			 the parties exchange.  This table contains both

			 the ID and secret pair(s) that the local PPP

			 entity will advertise to the remote entity and

			 the pair(s) that the local entity will expect

			 from the remote entity.  This table allows for

			 multiple id/secret password pairs to be

			 specified for a particular link by using the

			 pppSecuritySecretsIdIndex object."

	       ::= { pppSecurity 3 }





	  pppSecuritySecretsEntry   OBJECT-TYPE

	       SYNTAX    PppSecuritySecretsEntry

	       ACCESS    not-accessible

	       STATUS    mandatory

	       DESCRIPTION

			 "Secret information."

	       INDEX     { pppSecuritySecretsLink,

			 pppSecuritySecretsIdIndex }

	       ::= { pppSecuritySecretsTable 1 }





	  PppSecuritySecretsEntry ::= SEQUENCE {

	       pppSecuritySecretsLink

		    INTEGER,

	       pppSecuritySecretsIdIndex

		    INTEGER,

	       pppSecuritySecretsDirection

		    INTEGER,

	       pppSecuritySecretsProtocol

		    OBJECT IDENTIFIER,

	       pppSecuritySecretsIdentity

		    OCTET STRING,

	       pppSecuritySecretsSecret

		    OCTET STRING,

	       pppSecuritySecretsStatus

		    INTEGER

	  }



	  pppSecuritySecretsLink   OBJECT-TYPE

	       SYNTAX    INTEGER(0..2147483647)

	       ACCESS    read-only

	       STATUS    mandatory

	       DESCRIPTION

			 "The link to which this ID/Secret pair applies.

			 By convention, if the value of this object is 0

			 then the ID/Secret pair applies to all links."

	       ::= { pppSecuritySecretsEntry 1 }





	  pppSecuritySecretsIdIndex   OBJECT-TYPE

	       SYNTAX    INTEGER(0..2147483647)

	       ACCESS    read-only

	       STATUS    mandatory

	       DESCRIPTION

			 "A unique value for each ID/Secret pair that

			 has been defined for use on this link.  This

			 allows multiple ID/Secret pairs to be defined

			 for each link.  How the local entity selects

			 which pair to use is a local implementation

			 decision."

	       ::= { pppSecuritySecretsEntry 2 }





	  pppSecuritySecretsDirection   OBJECT-TYPE

	       SYNTAX    INTEGER  {

			 local-to-remote(1),

			 remote-to-local(2)

		    }

	       ACCESS    read-write

	       STATUS    mandatory

	       DESCRIPTION

			 "This object defines the direction in which a

			 particular ID/Secret pair is valid.  If this

			 object is local-to-remote then the local PPP

			 entity will use the ID/Secret pair when

			 attempting to authenticate the local PPP entity

			 to the remote PPP entity.  If this object is

			 remote-to-local then the local PPP entity will

			 expect the ID/Secret pair to be used by the

			 remote PPP entity when the remote PPP entity

			 attempts to authenticate itself to the local

			 PPP entity."

	       ::= { pppSecuritySecretsEntry 3 }





	  pppSecuritySecretsProtocol   OBJECT-TYPE

	       SYNTAX    OBJECT IDENTIFIER

	       ACCESS    read-write

	       STATUS    mandatory

	       DESCRIPTION

			 "The security protocol (e.g. CHAP or PAP) to

			 which this ID/Secret pair applies."

	       ::= { pppSecuritySecretsEntry 4 }





	  pppSecuritySecretsIdentity   OBJECT-TYPE

	       SYNTAX    OCTET STRING (SIZE(0..255))

	       ACCESS    read-write

	       STATUS    mandatory

	       DESCRIPTION

			 "The Identity of the ID/Secret pair.  The

			 actual format, semantics, and use of

			 pppSecuritySecretsIdentity depends on the

			 actual security protocol used.  For example, if

			 pppSecuritySecretsProtocol is

			 pppSecurityPapProtocol then this object will

			 contain a PAP Peer-ID. If

			 pppSecuritySecretsProtocol is

			 pppSecurityChapMD5Protocol then this object

			 would contain the CHAP NAME parameter."

	       ::= { pppSecuritySecretsEntry 5 }





	  pppSecuritySecretsSecret   OBJECT-TYPE

	       SYNTAX    OCTET STRING (SIZE(0..255))

	       ACCESS    read-write

	       STATUS    mandatory

	       DESCRIPTION

			 "The secret of the ID/Secret pair.  The actual

			 format, semantics, and use of

			 pppSecuritySecretsSecret depends on the actual

			 security protocol used.  For example, if

			 pppSecuritySecretsProtocol is

			 pppSecurityPapProtocol then this object will

			 contain a PAP Password. If

			 pppSecuritySecretsProtocol is

			 pppSecurityChapMD5Protocol then this object

			 would contain the CHAP MD5 Secret."

	       ::= { pppSecuritySecretsEntry 6 }





	  pppSecuritySecretsStatus   OBJECT-TYPE

	       SYNTAX    INTEGER  {

			 invalid(1),

			 valid(2)

		    }

	       ACCESS    read-write

	       STATUS    mandatory

	       DESCRIPTION

			 "Setting this object to the value invalid(1)

			 has the effect of invalidating the

			 corresponding entry in the

			 pppSecuritySecretsTable. It is an

			 implementation-specific matter as to whether

			 the agent removes an invalidated entry from the

			 table.  Accordingly, management stations must

			 be prepared to receive tabular information from

			 agents that corresponds to entries not

			 currently in use.  Proper interpretation of

			 such entries requires examination of the

			 relevant pppSecuritySecretsStatus object."

	       DEFVAL    { valid }

	       ::= { pppSecuritySecretsEntry 7 }







	 -- The PPP IP Group.

	 -- Implementation of this group is mandatory for all

	 -- PPP implementations that support operating IP over PPP.



	 pppIp OBJECT IDENTIFIER ::= { ppp 3 }





	  pppIpTable   OBJECT-TYPE

	       SYNTAX    SEQUENCE OF PppIpEntry

	       ACCESS    not-accessible

	       STATUS    mandatory

	       DESCRIPTION

			 "Table containing the IP parameters and

			 statistics for the local PPP entity."

	       ::= { pppIp 1 }





	  pppIpEntry   OBJECT-TYPE

	       SYNTAX    PppIpEntry

	       ACCESS    not-accessible

	       STATUS    mandatory

	       DESCRIPTION

			 "IPCP status information for a particular PPP

			 link."

	       INDEX     { ifIndex }

	       ::= { pppIpTable 1 }





	  PppIpEntry ::= SEQUENCE {

	       pppIpOperStatus

		    INTEGER,

	       pppIpLocalToRemoteCompressionProtocol

		    INTEGER,

	       pppIpRemoteToLocalCompressionProtocol

		    INTEGER,

	       pppIpRemoteMaxSlotId

		    INTEGER,

	       pppIpLocalMaxSlotId

		    INTEGER

	  }





	  -- The following object reflect the values of the option

	  -- parameters used in the PPP IP Control Protocol

	  --   pppIpLocalToRemoteCompressionProtocol

	  --   pppIpRemoteToLocalCompressionProtocol

	  --   pppIpRemoteMaxSlotId

	  --   pppIpLocalMaxSlotId

	  -- These values are not available until after the PPP Option

	  -- negotiation has completed, which is indicated by the link

	  -- reaching the open state (i.e., pppIpOperStatus is set to

	  -- opened).

	  --

	  -- Therefore, when pppIpOperStatus is not opened

	  -- the contents of these objects is undefined. The value

	  -- returned when accessing the objects is an implementation

	  -- dependent issue.





	  pppIpOperStatus   OBJECT-TYPE

	       SYNTAX    INTEGER {opened(1), not-opened(2)}

	       ACCESS    read-only

	       STATUS    mandatory

	       DESCRIPTION

			 "The operational status of the IP network

			 protocol. If the value of this object is up

			 then the finite state machine for the IP

			 network protocol has reached the Opened state."

	       ::= { pppIpEntry 1 }





	  pppIpLocalToRemoteCompressionProtocol   OBJECT-TYPE

	       SYNTAX    INTEGER {

			 none(1),

			 vj-tcp(2)

		    }

	       ACCESS    read-only

	       STATUS    mandatory

	       DESCRIPTION

			 "The IP compression protocol that the local

			 PPP-IP entity uses when sending packets to the

			 remote PPP-IP entity. The value of this object

			 is meaningful only when the link has reached

			 the open state (pppIpOperStatus is opened)."

	       ::= { pppIpEntry 2 }





	  pppIpRemoteToLocalCompressionProtocol   OBJECT-TYPE

	       SYNTAX    INTEGER {

			 none(1),

			 vj-tcp(2)

		    }

	       ACCESS    read-only

	       STATUS    mandatory

	       DESCRIPTION

			 "The IP compression protocol that the remote

			 PPP-IP entity uses when sending packets to the

			 local PPP-IP entity. The value of this object

			 is meaningful only when the link has reached

			 the open state (pppIpOperStatus is opened)."

	       ::= { pppIpEntry 3 }



	  pppIpRemoteMaxSlotId   OBJECT-TYPE

	       SYNTAX    INTEGER(0..255)

	       ACCESS    read-only

	       STATUS    mandatory

	       DESCRIPTION

			 "The Max-Slot-Id parameter that the remote node

			 has advertised and that is in use on the link.

			 If vj-tcp header compression is not in use on

			 the link then the value of this object shall be

			 0. The value of this object is meaningful only

			 when the link has reached the open state

			 (pppIpOperStatus is opened)."

	       ::= { pppIpEntry 4 }





	  pppIpLocalMaxSlotId   OBJECT-TYPE

	       SYNTAX    INTEGER(0..255)

	       ACCESS    read-only

	       STATUS    mandatory

	       DESCRIPTION

			 "The Max-Slot-Id parameter that the local node

			 has advertised and that is in use on the link.

			 If vj-tcp header compression is not in use on

			 the link then the value of this object shall be

			 0. The value of this object is meaningful only

			 when the link has reached the open state

			 (pppIpOperStatus is opened)."

	       ::= { pppIpEntry 5 }





	  --

	  -- The PPP IP Configuration table.

	  -- This is a separate table in order to facilitate

	  -- placing these variables in a separate MIB view.

	  --



	  pppIpConfigTable   OBJECT-TYPE

	       SYNTAX    SEQUENCE OF PppIpConfigEntry

	       ACCESS    not-accessible

	       STATUS    mandatory

	       DESCRIPTION

			 "Table containing configuration variables for

			 the IPCP for the local PPP entity."

	       ::= { pppIp 2 }





	  pppIpConfigEntry   OBJECT-TYPE

	       SYNTAX    PppIpConfigEntry

	       ACCESS    not-accessible

	       STATUS    mandatory

	       DESCRIPTION

			 "IPCP information for a particular PPP link."

	       INDEX     { ifIndex }

	       ::= { pppIpConfigTable 1 }





	  PppIpConfigEntry ::= SEQUENCE {

	       pppIpConfigAdminStatus

		    INTEGER,

	       pppIpConfigCompression

		    INTEGER

	  }



	  pppIpConfigAdminStatus   OBJECT-TYPE

	       SYNTAX    INTEGER {open(1), close(2)}

	       ACCESS    read-write

	       STATUS    mandatory

	       DESCRIPTION

			 "The immediate desired status of the IP network

			 protocol. Setting this object to open will

			 inject an administrative open event into the IP

			 network protocol's finite state machine.

			 Setting this object to close will inject an

			 administrative close event into the IP network

			 protocol's finite state machine."

	       ::= { pppIpConfigEntry 1 }





	  pppIpConfigCompression   OBJECT-TYPE

	       SYNTAX    INTEGER {

			 none(1),

			 vj-tcp(2)

		    }

	       ACCESS    read-write

	       STATUS    mandatory

	       DESCRIPTION

			 "If none(1) then the local node will not

			 attempt to negotiate any IP Compression option.

			 Otherwise, the local node will attempt to

			 negotiate compression mode indicated by the

			 enumerated value. Changing this object will

			 have effect when the link is next restarted."

	       REFERENCE

			 "Section 4.0, Van Jacobson TCP/IP Header

			 Compression of RFC1332."

	       DEFVAL    { none }

	       ::= { pppIpConfigEntry 2 }





		 

-- *****************************************************************************

--  GRUPPO GENERAL-CONFIGURATION

--          Questo gruppo contiene una ramificazione per la gestione di parametri

--              di configurazione non relativi ad un protocollo ben definito. 

--          

-- *****************************************************************************



profile     OBJECT IDENTIFIER ::= { general-configuration 1 }



profileConf     OBJECT IDENTIFIER ::= { profile 1 }

profileOp	    OBJECT IDENTIFIER ::= { profile 2 }





profileTable   OBJECT-TYPE

		SYNTAX  SEQUENCE OF ProfileEntry

		ACCESS  not-accessible

		STATUS  mandatory

	DESCRIPTION

		" Questa tabella contiene i parametri di configurazione

		  dei profili."

	::= { profileConf 1 }



	profileEntry     OBJECT-TYPE

			SYNTAX  ProfileEntry

			ACCESS  not-accessible

			STATUS  mandatory

		DESCRIPTION

			"Entry tabella ProfileTab"

			INDEX   { profileId }

		::= { profileTable 1 }

	ProfileEntry ::= SEQUENCE {

		profileId                       INTEGER,

		profileName                     DisplayString,

		profileISDNPhone1               DisplayString,

		profileISDNPhone2               DisplayString,

		profileISDNPhone3               DisplayString,

		profileISDNPhone4               DisplayString,

		profileISDNPhone5               DisplayString,

		profileGatewayIP               IpAddress,

		profileAutUsername      DisplayString,

		profileAutPassword      DisplayString,

		profileAutPeerUsername  DisplayString,

		profileAutPeerPassword  DisplayString,

		profileAutPAP           INTEGER,

		profileAutCHAP          INTEGER,

		profileRemoteMASK               IpAddress,

		profileDefault          INTEGER,

		profileDynamic          INTEGER,

		profileCallbackType     INTEGER,

		profileUnnumbered       INTEGER,

		profileCalled           INTEGER,

		profileCalling          INTEGER,

		profileDefgtw           INTEGER,

		profileNat                      INTEGER,

		profileCallbackReq      INTEGER,

		profileCallbackAccept   INTEGER,

		profileRemoteMaskAuto   INTEGER,

		profileDynamicRemoteNet INTEGER,

		profileMPP              INTEGER,

		-- ProfileMPPSecondCh      INTEGER,

		profileCallbackTimer    INTEGER,

		profileRemoteIp			IpAddress,

		profileRemotePool		DisplayString,

		profileCounterCallIn	INTEGER,

		profileCounterCallOut	INTEGER,

		profileLastCallDirection DisplayString,

		profileLastCallTimeOpen	 DisplayString,

		profileLastCallTimeClose DisplayString,

		profileStatus			 DisplayString

		

	}



	profileId       OBJECT-TYPE

			SYNTAX  INTEGER

			ACCESS  read-only

			STATUS  mandatory

		DESCRIPTION

			"Profile Index." 

		::= { profileEntry 1 }



	profileName     OBJECT-TYPE

			SYNTAX  DisplayString

			ACCESS  read-only

			STATUS  mandatory

		DESCRIPTION

			"Profile Name." 

		::= { profileEntry 2 }



	profileISDNPhone1     OBJECT-TYPE

			SYNTAX  DisplayString

			ACCESS  read-only

			STATUS  mandatory

		DESCRIPTION

			"ISDN Phone Number 1." 

		::= { profileEntry 3 }



	profileISDNPhone2     OBJECT-TYPE

			SYNTAX  DisplayString

			ACCESS  read-only

			STATUS  mandatory

		DESCRIPTION

			"ISDN Phone Number 2." 

		::= { profileEntry 4 }



	profileISDNPhone3     OBJECT-TYPE

			SYNTAX  DisplayString

			ACCESS  read-only

			STATUS  mandatory

		DESCRIPTION

			"ISDN Phone Number 3." 

		::= { profileEntry 5 }



	profileISDNPhone4     OBJECT-TYPE

			SYNTAX  DisplayString

			ACCESS  read-only

			STATUS  mandatory

		DESCRIPTION

			"ISDN Phone Number 4." 

		::= { profileEntry 6 }



	profileISDNPhone5     OBJECT-TYPE

			SYNTAX  DisplayString

			ACCESS  read-only

			STATUS  mandatory

		DESCRIPTION

			"ISDN Phone Number 5." 

		::= { profileEntry 7 }



	profileGatewayIP       OBJECT-TYPE

			SYNTAX  IpAddress

			ACCESS  read-only

			STATUS  mandatory

		DESCRIPTION

			"Profile IP Gateway." 

		::= { profileEntry 8 }





	profileAutUsername  OBJECT-TYPE

			SYNTAX  DisplayString

			ACCESS  read-only

			STATUS  mandatory

		DESCRIPTION

			"Profile Chap/Pap Username." 

		::= { profileEntry 9 }



	profileAutPassword  OBJECT-TYPE

			SYNTAX  DisplayString

			ACCESS  read-only

			STATUS  mandatory

		DESCRIPTION

			"Profile Chap/Pap Password." 

		::= { profileEntry 10 }



	profileAutPeerUsername  OBJECT-TYPE

			SYNTAX  DisplayString

			ACCESS  read-only

			STATUS  mandatory

		DESCRIPTION

			"Profile Chap/Pap PeerUsername." 

		::= { profileEntry 11 }



	profileAutPeerPassword  OBJECT-TYPE

			SYNTAX  DisplayString

			ACCESS  read-only

			STATUS  mandatory

		DESCRIPTION

			"Profile Chap/Pap Peer Password." 

		::= { profileEntry 12 }



	profileAutPAP      OBJECT-TYPE

			SYNTAX  INTEGER  {

			 authentication-PAP-OFF(0),

			 authentication-PAP-ON(1)

			}

			ACCESS  read-only

			STATUS  mandatory

		DESCRIPTION

			"Profile PAP protocol status" 

		::= { profileEntry 13 }



	profileAutCHAP      OBJECT-TYPE

			SYNTAX  INTEGER  {

			 authentication-CHAP-OFF(0),

			 authentication-CHAP-ON(1)

			}

			ACCESS  read-only

			STATUS  mandatory

		DESCRIPTION

			"Profile Chap protocol status" 

		::= { profileEntry 14 }



	profileRemoteMASK       OBJECT-TYPE

			SYNTAX  IpAddress

			ACCESS  read-only

			STATUS  mandatory

		DESCRIPTION

			"Profile IP Remote Mask." 

		::= { profileEntry 15 }



	profileDefault      OBJECT-TYPE

			SYNTAX  INTEGER  {

			 default-Profile-Off(0),

			 default-Profile-On(1)

			}

			ACCESS  read-only

			STATUS  mandatory

		DESCRIPTION

			"Default Profile" 

		::= { profileEntry 16 }



	profileDynamic   OBJECT-TYPE

			 SYNTAX  INTEGER  {

			 dynamic-Off(0),

			 dynamic-On(1)

			}

			ACCESS  read-only

			STATUS  mandatory

		DESCRIPTION

			"Dynamic IP Profile" 

		::= { profileEntry 17 }



	profileCallbackType    OBJECT-TYPE

			SYNTAX  INTEGER  {

			 ppp-type(0),

			 isdn-type(1)

			}

			ACCESS  read-only

			STATUS  mandatory

		DESCRIPTION

			"Profile Callback Type" 

		::= { profileEntry 18 }



	profileUnnumbered   OBJECT-TYPE

			SYNTAX  INTEGER  {

			 unnumbered-Off(0),

			 unnumbered-On(1)

			}

			ACCESS  read-only

			STATUS  mandatory

		DESCRIPTION

			"Unnumbered Profile" 

		::= { profileEntry 19 }





	profileCalled    OBJECT-TYPE

			SYNTAX  INTEGER  {

			 called-Off(0),

			 called-On(1)

			}

			ACCESS  read-only

			STATUS  mandatory

		DESCRIPTION

			"Called Profile" 

		::= { profileEntry 20 }



	profileCalling  OBJECT-TYPE

			SYNTAX  INTEGER  {

			 calling-Off(0),

			 calling-On(1)

			}

			ACCESS  read-only

			STATUS  mandatory

		DESCRIPTION

			"Calling Profile" 

		::= { profileEntry 21 }



	profileDefgtw   OBJECT-TYPE

			SYNTAX  INTEGER  {

			 connection-to-defgtw-Off(0),

			 connection-to-defgtw-On(1)

			}

			ACCESS  read-only

			STATUS  mandatory

		DESCRIPTION

			"Default gateway connection Profile" 

		::= { profileEntry 22 }



	profileNat    OBJECT-TYPE

			SYNTAX  INTEGER  {

			 nat-Off(0),

			 nat-On(1)

			}

			ACCESS  read-only

			STATUS  mandatory

		DESCRIPTION

			"Nat function on Profile" 

		::= { profileEntry 23 }



	profileCallbackReq   OBJECT-TYPE

			SYNTAX  INTEGER  {

			 callback-Request-Off(0),

			 callback-Request-On(1)

			}

			ACCESS  read-only

			STATUS  mandatory

		DESCRIPTION

			"Callback request status on Profile" 

		::= { profileEntry 24 }

	

	profileCallbackAccept  OBJECT-TYPE

			SYNTAX  INTEGER  {

			 callback-Accept-Off(0),

			 callback-Accept-On(1)

			}

			ACCESS  read-only

			STATUS  mandatory

		DESCRIPTION

			"Callback Accept status on Profile" 

		::= { profileEntry 25 }



	profileRemoteMaskAuto  OBJECT-TYPE

			SYNTAX  INTEGER  {

			 remoteMask-Auto-Off(0),

			 remoteMask-Auto-On(1)

			}

			ACCESS  read-write

			STATUS  mandatory

		DESCRIPTION

			"Automatic Remote Mask acquisition status" 

		::= { profileEntry 26 }



	profileDynamicRemoteNet  OBJECT-TYPE

			SYNTAX  INTEGER  {

			 remote-Network-acquisition-Off(0),

			 remote-Network-acquisition-On(1)

			}

			ACCESS  read-only

			STATUS  mandatory

		DESCRIPTION

			"Automatic Remote Network acquisition status" 

		::= { profileEntry 27 }



	profileMPP  OBJECT-TYPE

			SYNTAX  INTEGER  {

			 mPP-Off(0),

			 mPP-On(1)

			}

			ACCESS  read-only

			STATUS  mandatory

		DESCRIPTION

			"Multilink PPP status on profile" 

		::= { profileEntry 28 }



   --	ProfileMPPSecondCh  OBJECT-TYPE

   --			SYNTAX  INTEGER  {

   --			 MPP-2 CH-Off(0),

   --			 MPP-2 CH-On(1)

	--		}

   --			ACCESS  read-only

   --			STATUS  mandatory

   --		DESCRIPTION

   --			"Multilink PPP (Second channel) status on profile" 

   --		::= { profileEntry 29 }



	profileCallbackTimer  OBJECT-TYPE

			SYNTAX  INTEGER

			ACCESS  read-only

			STATUS  mandatory

		DESCRIPTION

			"Callback Timer on profile" 

		::= { profileEntry 29 }



	profileRemoteIp       OBJECT-TYPE

			SYNTAX  IpAddress

			ACCESS  read-only

			STATUS  mandatory

		DESCRIPTION

			"Profile remote ip." 

		::= { profileEntry 30 }

	

	profileRemotePool  OBJECT-TYPE

			SYNTAX  DisplayString

			ACCESS  read-only

			STATUS  mandatory

		DESCRIPTION

			"Profile remote pool." 

		::= { profileEntry 31 }

		

	profileCounterCallIn  OBJECT-TYPE

			SYNTAX  INTEGER

			ACCESS  read-only

			STATUS  mandatory

		DESCRIPTION

			"Counter call incoming on profile" 

		::= { profileEntry 32 }



	profileCounterCallOut  OBJECT-TYPE

			SYNTAX  INTEGER

			ACCESS  read-only

			STATUS  mandatory

		DESCRIPTION

			"Counter call outgoing on profile" 

		::= { profileEntry 33 }



	profileLastCallDirection  OBJECT-TYPE

			SYNTAX  DisplayString

			ACCESS  read-only

			STATUS  mandatory

		DESCRIPTION

			"Profile last call direction." 

		::= { profileEntry 34 }



	profileLastCallTimeOpen  OBJECT-TYPE

			SYNTAX  DisplayString

			ACCESS  read-only

			STATUS  mandatory

		DESCRIPTION

			"Profile last call time open." 

		::= { profileEntry 35 }

	

	profileLastCallTimeClose  OBJECT-TYPE

			SYNTAX  DisplayString

			ACCESS  read-only

			STATUS  mandatory

		DESCRIPTION

			"Profile last call time close." 

		::= { profileEntry 36 }



	profileStatus	  OBJECT-TYPE

			SYNTAX  DisplayString

			ACCESS  read-only

			STATUS  mandatory

		DESCRIPTION

			"Profile status." 

		::= { profileEntry 37 }

--

profileRunTable   OBJECT-TYPE

		SYNTAX  SEQUENCE OF ProfileRunEntry

		ACCESS  not-accessible

		STATUS  mandatory

	DESCRIPTION

		" Questa tabella contiene i parametri run

		  dei profili."

	::= { profileOp 1 }



	profileRunEntry     OBJECT-TYPE

			SYNTAX  ProfileRunEntry

			ACCESS  not-accessible

			STATUS  mandatory

		DESCRIPTION

			"Entry tabella ProfileTabRun"

			INDEX   { profileIdRun }

		::= { profileRunTable 1 }

	ProfileRunEntry ::= SEQUENCE {

		profileIdRun                       	INTEGER,

		profileIdFather						INTEGER,

		profileFatherName                   DisplayString,

		profileISDNPhoneUsed               	DisplayString,

		profileIPGateway                	IpAddress,

		profileNumberChannelActive      	INTEGER,

		profileIndexChannelActive			DisplayString,

		profileConnectionTimeForChannel		DisplayString

	}



	profileIdRun       OBJECT-TYPE

			SYNTAX  INTEGER

			ACCESS  read-only

			STATUS  mandatory

		DESCRIPTION

			"Profile Run Index." 

		::= { profileRunEntry 1 }



	profileIdFather	  OBJECT-TYPE

			SYNTAX  INTEGER

			ACCESS  read-only

			STATUS  mandatory

		DESCRIPTION

			"IndexFather of Profile Run." 

		::= { profileRunEntry 2 }



	profileFatherName     OBJECT-TYPE

			SYNTAX  DisplayString

			ACCESS  read-only

			STATUS  mandatory

		DESCRIPTION

			"NameFather of Profile Run." 

		::= { profileRunEntry 3 }



	profileISDNPhoneUsed     OBJECT-TYPE

			SYNTAX  DisplayString

			ACCESS  read-only

			STATUS  mandatory

		DESCRIPTION

			"ISDN Phone Number Used." 

		::= { profileRunEntry 4 }



	profileIPGateway       OBJECT-TYPE

			SYNTAX  IpAddress

			ACCESS  read-only

			STATUS  mandatory

		DESCRIPTION

			"Profile Run IP Gateway." 

		::= { profileRunEntry 5 }



	profileNumberChannelActive  OBJECT-TYPE

			SYNTAX  INTEGER  

			ACCESS  read-only

			STATUS  mandatory

		DESCRIPTION

			"Number of channels active on profile run" 

		::= { profileRunEntry 6 }



	

	profileIndexChannelActive  OBJECT-TYPE

			SYNTAX  DisplayString

			ACCESS  read-only

			STATUS  mandatory

		DESCRIPTION

			"Index of channels actived on profile run." 

		::= { profileRunEntry 7 }

		

	profileConnectionTimeForChannel  OBJECT-TYPE

			SYNTAX  DisplayString

			ACCESS  read-only

			STATUS  mandatory

		DESCRIPTION

			"Connection Time on channel actived on profile run." 

		::= { profileRunEntry 8 }





-- This part of the MIB module defines the traps that AMTEC Services issue.

-- It is split into sections for each Service component.





-- Security Traps



authTrap	TRAP-TYPE

		ENTERPRISE  amtec

--		VARIABLES  {}

		DESCRIPTION

			"Viene inviata da un apparato nel caso in cui fallisca la

			 procedura di autenticazione con un entita di pari livello."



		-- #TEXTSTRING ""

		-- #SYMBOL AUTH-TRAP 0x9000

		::= 36864



signTrap	TRAP-TYPE

		ENTERPRISE  amtec

--		VARIABLES  {}

		DESCRIPTION

			"Viene inviata da un apparato che implementa il servizio di

			 firma nel caso in cui fallisca il controllo della firma in

			 un pacchetto ricevuto."



		-- #TEXTSTRING ""

		-- #SYMBOL SIGN-TRAP 0x9100

		::= 37120



accessTrap	TRAP-TYPE

		ENTERPRISE  amtec

--		VARIABLES  {}

		DESCRIPTION

			"Viene inviata da un apparato quando c'e un tentativo di

			 accesso non autorizzato."



		-- #TEXTSTRING ""

		-- #SYMBOL ACCESS-TRAP 0x9200

		::= 37376



badCRCTrap	TRAP-TYPE

		ENTERPRISE  amtec

--		VARIABLES  {}

		DESCRIPTION

			"Se implementato il servizio di integrita dei dati viene

			 inviata nel caso in cui il segmento decifrato abbia un 

			 CRC errato."



		-- #TEXTSTRING ""

		-- #SYMBOL BADCRC-TRAP 0x9300

		::= 37632



badChainTrap TRAP-TYPE

		 ENTERPRISE  amtec

--		 VARIABLES  {}

		 DESCRIPTION

			"Se implementato il servizio di concatenazione dei segmenti 

			 cifrati viene inviata nel caso in cui un segmento decifrato 

			 abbia un numero di sequenza errato."



		 -- #TEXTSTRING ""

		 -- #SYMBOL BADCHAIN-TRAP 0x9400

		 ::= 37888



badAgendTrap TRAP-TYPE

		 ENTERPRISE  amtec

--		 VARIABLES  {}

		 DESCRIPTION

			"Viene inviata nel caso in cui l'agenda delle chiavi pubbliche

			 non sia integra (ad esempio fallisce il controllo del CRC sul

			 file agenda."



		 -- #TEXTSTRING ""

		 -- #SYMBOL BADAGEND-TRAP 0x9500

		 ::= 38144



rxRstTrap 	 TRAP-TYPE

		 ENTERPRISE  amtec

--		 VARIABLES  {}

		 DESCRIPTION

			"Viene inviata da un apparato che riceva un RESET su un circuito 

			 virtuale X.25 di tipo switched su cui sia configurata la 

			 sicurezza X.25."



		 -- #TEXTSTRING ""

		 -- #SYMBOL RXRST-TRAP 0x9700

		 ::= 38656



cGSAccessTrap 	 TRAP-TYPE

		 ENTERPRISE  amtec

--		 VARIABLES  {}

		 DESCRIPTION

			"Viene inviata da un apparato che abbia ricevuto un tentativo

			 di accesso da un apparato identificato come gestore."



		 -- #TEXTSTRING ""

		 -- #SYMBOL CGSACCESS-TRAP 0x9800

		 ::= 38912



keyGoodTrap TRAP-TYPE

		ENTERPRISE  amtec

--		VARIABLES  {}

		DESCRIPTION

			"Viene inviata da un apparato che ha generato una nuova chiave

			 RSA."



		-- #TEXTSTRING ""

		-- #SYMBOL KEYGOOD-TRAP 0x9A00

		::= 39424



keyBadTrap 	TRAP-TYPE

		ENTERPRISE  amtec

--		VARIABLES  {}

		DESCRIPTION

			"Viene inviata da un apparato quando fallisce il processo di

			 generazione di una nuova chiave RSA."



		-- #TEXTSTRING ""

		-- #SYMBOL KEYBAD-TRAP 0x9B00

		::= 39680



keyNotWriteTrap 	 TRAP-TYPE

		ENTERPRISE  amtec

--		VARIABLES  {}

		DESCRIPTION

			"Viene inviata da un apparato quando fallisce la scrittura

			 di una nuova chiave RSA precedentemente generata sulla

			 flash dell'apparato medesimo."



		-- #TEXTSTRING ""

		-- #SYMBOL KEYNOTWRITE-TRAP 0x9C00

		::= 39936



keyWriteTrap	TRAP-TYPE

		ENTERPRISE  amtec

--		VARIABLES  {}

		DESCRIPTION

			"Viene inviata da un apparato quando ha portato a

			 termine la scrittura di una nuova chiave RSA in Flash."



		-- #TEXTSTRING ""

		-- #SYMBOL KEYWRITE-TRAP 0x9D00

		::= 40192



agNotAvailTrap 	 TRAP-TYPE

		ENTERPRISE  amtec

--		VARIABLES  {}

		DESCRIPTION

			"Viene inviata da un apparato quando e richiesta una

			 operazione di accesso alla flash ma tale operazione

			 non e al momento consentita (ad esempio e in corso

			 una operazione di scrittura in flash)."



		-- #TEXTSTRING ""

		-- #SYMBOL KEYAGNOTAVAIL-TRAP 0x9E00

		::= 40448



keyPubReqTrap 	 TRAP-TYPE

		ENTERPRISE  amtec

--		VARIABLES  {}

		DESCRIPTION

			"Viene inviata da un apparato che deve aprire una

			 connessione con un altro apparato in modo sicuro ma

			 non conosce la chiave pubblica da usare e ne fa

			 richiesta al gestore."



		-- #TEXTSTRING ""

		-- #SYMBOL KEYPUBREQ-TRAP 0x9F00

		::= 40704



alarmsDownTrap 	 TRAP-TYPE

		ENTERPRISE  amtec

--		VARIABLES  {}

		DESCRIPTION

			"Viene inviata a tempo da un apparato che dopo tre tentativi

			 di invio di una delle trap precedetenti non ha ricevuto

			 risposta dal gestore (il gestore alla ricezione di una trap

			 deve settare la variabile LTC dell'apparato mittente)."



		-- #TEXTSTRING ""

		-- #SYMBOL ALARMSDOWN-TRAP 0x8900

		::= 35072



noiseGenTrap 	 TRAP-TYPE

		ENTERPRISE  amtec

--		VARIABLES  {}

		DESCRIPTION

			"Viene inviata da un apparato che abbia riscontrato un non

			 perfetto funzionamento del generatore di rumore hardware

			 presente sulla scheda."



		-- #TEXTSTRING ""

		-- #SYMBOL KEYNOISEGEN-TRAP 0x8A00

		::= 35328



gtwNotRespTrap 	 TRAP-TYPE

		ENTERPRISE  amtec

--		VARIABLES  {}

		DESCRIPTION

			"Viene inviata nel caso in cui un gateway di sicurezza non

			 abbia risposto ad una richiesta di autenticazione inviata

			 dall'apparato."



		-- #TEXTSTRING ""

		-- #SYMBOL GTWNOTRESP-TRAP 0x9004

		::= 36868



gtwCertExpTrap 	 TRAP-TYPE

		ENTERPRISE  amtec

--		VARIABLES  {}

		DESCRIPTION

			"Viene inviata quando il certificato del gateway e' in scadenza."



		-- #TEXTSTRING ""

		-- #SYMBOL GTWCERTEXP-TRAP 0x9013

		::= 36883



-- Frame Relay Traps

fryLinkVarTrap 	 TRAP-TYPE

		ENTERPRISE  amtec

		VARIABLES  {frCircuitIfIndex, 

				frCircuitDlci,

				frCircuitState}

		DESCRIPTION

			"Viene inviata quando si verifica una variazione di stato 

			 (Attivo-Disattivo) su un DLCI; la trap riporta le variabili

			 della MIB proprietaria che danno informazioni aggiuntive

			 relativamente al DLCI in questione ed al suo stato."



		-- #TEXTSTRING ""

		-- #SYMBOL FRYLINKVAR-TRAP 0x7000

		::= 28672



-- Application Trap



modifiedConfTrap 	 TRAP-TYPE

		ENTERPRISE  amtec

--		VARIABLES  {}

		--&ACTIONS {log,minor}

		--&MESG "Configuration Modified"

		DESCRIPTION

			"Viene utilizzata dalle applicazioni del centro di gestione per comunicare l'avvenuta modifica della configurazione di un apparato."



		-- #TEXTSTRING ""

		-- #SYMBOL MODCONF-TRAP 0x

		::= 11111





-- FINE TRAP



--"AMTEC-MIB|IpSecPermitIpAddrIndex"	ALTNAME	"Peer address"

--"AMTEC-MIB|IpSecPermitIpMask"		ALTNAME	"Peer net mask"

--"AMTEC-MIB|IpSecPermitTime"		ALTNAME	"Remaining time (minutes)"



END



-- *****************************************************************************

-- Gruppo IKE/IPSEC 	(1.3.6.1.4.1.1.1954.3.10)  

--

-- *****************************************************************************

-- MIB per IKE/IPSEC: 

-- rfc2851-inet-addr-mib ()

-- ipsec-isakmp-ike-doi-tc ()

-- ipsec-mib (1.3.6.1.4.1.1.1954.3.10.1)  

-- mib-Isakmp (1.3.6.1.4.1.1.1954.3.10.2)  

-- ike-mib (1.3.6.1.4.1.1.1954.3.10.3)






-- *****************************************************************************

-- MIB           IPSEC-SA-MON-MIB (ipsec-mib.mib)



-- *****************************************************************************
