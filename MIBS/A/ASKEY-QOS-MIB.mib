ASKEY-QOS-MIB DEFINITIONS ::= BEGIN

IMPORTS
    MODULE-IDENTITY,
    OBJECT-TYPE                FROM SNMPv2-SMI
    ipDslam                    FROM ASKEY-DSLAM-MIB
    ifIndex                    FROM IF-MIB
    SnmpAdminString            FROM SNMP-FRAMEWORK-MIB
    askeyCosQueueMapping8021p  FROM ASKEY-SYSTEM-MIB
    RowStatus                  FROM SNMPv2-TC
;


askeyQoSMIB MODULE-IDENTITY
    LAST-UPDATED    "200605300000Z"  -- May 30, 2006
    ORGANIZATION    "ASKEY Inc."
    CONTACT-INFO    "ASKEY Inc.
                    E-mail: zarsus.kuo@askey.com.tw"

    DESCRIPTION     "ASKEY QoS MIB OID defines and documentation."
    ::= { ipDslam 16 }


--
-- 1. Line port table
--
askeyQoSLineMIBObjects OBJECT IDENTIFIER ::= { askeyQoSMIB 1 }

askeyQoSLineTable OBJECT-TYPE
    SYNTAX  SEQUENCE OF AskeyQoSLineEntry
    MAX-ACCESS  not-accessible
    STATUS  current
    DESCRIPTION
            "A list of line port QoS entries."
    ::= { askeyQoSLineMIBObjects 1 }

askeyQoSLineEntry OBJECT-TYPE
    SYNTAX  AskeyQoSLineEntry
    MAX-ACCESS  not-accessible
    STATUS  current
    DESCRIPTION
            "A QoS information entry containing objects for each line port."
    INDEX  { ifIndex }
    ::= { askeyQoSLineTable 1 }

AskeyQoSLineEntry ::= SEQUENCE {
    askeyQoSLineTrafficPolicing     SnmpAdminString
}

askeyQoSLineTrafficPolicing OBJECT-TYPE
    SYNTAX  SnmpAdminString (SIZE(1..32))
    MAX-ACCESS  read-write
    STATUS  current
    DESCRIPTION
            "The value of this object identifies the row in the
            Askey QoS Traffic Policing Table, (trafficPolicingTable),
            which applies for this line, and channels if applicable."
    ::= { askeyQoSLineEntry 1 }


--
-- 2. DiffServ
--
askeyQoSDiffServMIBObjects OBJECT IDENTIFIER ::= { askeyQoSMIB 2 }

diffServAdminStatus OBJECT-TYPE
    SYNTAX  INTEGER {
                enabled(1),
                disabled(2)
            }
    MAX-ACCESS  read-write
    STATUS  current
    DESCRIPTION
            "Enable or disable DiffServ function."
    ::= { askeyQoSDiffServMIBObjects 1 }

diffServMappingTable OBJECT-TYPE
    SYNTAX  SEQUENCE OF DiffServMappingEntry
    MAX-ACCESS  not-accessible
    STATUS  current
    DESCRIPTION
            "A table indicates mapping between 802.1p CoS and DSCP."
    ::= { askeyQoSDiffServMIBObjects 2 }

diffServMappingEntry OBJECT-TYPE
    SYNTAX  DiffServMappingEntry
    MAX-ACCESS  not-accessible
    STATUS  current
    DESCRIPTION
            "Mapping between 802.1p CoS and DSCP."
    INDEX { askeyCosQueueMapping8021p }
    ::= { diffServMappingTable 1 }

DiffServMappingEntry ::= SEQUENCE {
    diffServDSCP    INTEGER
}

diffServDSCP OBJECT-TYPE
    SYNTAX  INTEGER {
                be(0),
                af11(1),
                af12(2),
                af13(3),
                af21(4),
                af22(5),
                af23(6),
                af31(7),
                af32(8),
                af33(9),
                af41(10),
                af42(11),
                af43(12),
                ef(13)
            }
    MAX-ACCESS  read-write
    STATUS  current
    DESCRIPTION
            "DSCP value."
    ::= { diffServMappingEntry 1 }


--
-- 3. Traffic policing
--
askeyQoSTrafficPolicingMIBObjects OBJECT IDENTIFIER ::= { askeyQoSMIB 3 }

trafficPolicingTable OBJECT-TYPE
    SYNTAX  SEQUENCE OF TrafficPolicingEntry
    MAX-ACCESS  not-accessible
    STATUS  current
    DESCRIPTION
            "This table contains information on the line configuration.
            One entry in this table reflects a QoS profile defined by a
            manager which can be used to configure the line port QoS."
    ::= { askeyQoSTrafficPolicingMIBObjects 1}

trafficPolicingEntry OBJECT-TYPE
    SYNTAX  TrafficPolicingEntry
    MAX-ACCESS  not-accessible
    STATUS  current
    DESCRIPTION
            "Each entry consists of a list of parameters that represents the
            QoS configuration of a line."
    INDEX { IMPLIED trafficPolicingName }
    ::= { trafficPolicingTable 1}

TrafficPolicingEntry ::= SEQUENCE {
    trafficPolicingName         SnmpAdminString,
    trafficPolicingCIR          INTEGER,
--    trafficPolicingPIR          INTEGER,
    trafficPolicingAction       INTEGER,
    trafficPolicingRowStatus    RowStatus
}

trafficPolicingName OBJECT-TYPE
    SYNTAX  SnmpAdminString (SIZE (1..32))
    MAX-ACCESS  not-accessible
    STATUS  current
    DESCRIPTION
            "This object is used by the traffic policing table in order to
            identify a row of this table."
    ::= { trafficPolicingEntry 1 }

trafficPolicingCIR OBJECT-TYPE
    SYNTAX  INTEGER (0..1000)
    MAX-ACCESS  read-create
    STATUS  current
    DESCRIPTION
            "This value is CIR (Committed Information Rate) on this profile.
            Its unit is mbps (MBit per second)"
    ::= { trafficPolicingEntry 2 }

-- trafficPolicingPIR OBJECT-TYPE
--    SYNTAX  INTEGER (0..1000)
--    MAX-ACCESS  read-create
--    STATUS  current
--    DESCRIPTION
--            "This value is PIR (Peak Information Rate) on this profile.
--            Its unit is mbps (MBit per second)"
--    ::= { trafficPolicingEntry 3 }

trafficPolicingAction OBJECT-TYPE
    SYNTAX  INTEGER {
                noAction(0),
                drop(1),
                be(2),
                af11(3),
                af12(4),
                af13(5),
                af21(6),
                af22(7),
                af23(8),
                af31(9),
                af32(10),
                af33(11),
                af41(12),
                af42(13),
                af43(14),
                ef(15)
            }
    MAX-ACCESS  read-create
    STATUS  current
    DESCRIPTION
            "The action when traffic is over CIR. The actions include drop(0)
            the packets or do nothing to pass(1). Other actions will sign DSCP
            value into packets for QoS futher uses."
    ::= { trafficPolicingEntry 4 }

trafficPolicingRowStatus OBJECT-TYPE
    SYNTAX  RowStatus
    MAX-ACCESS  read-create
    STATUS  current
    DESCRIPTION
            "This object is used to create a new row or modify or delete
            an existing row in this table.

            A profile activated by setting this object to 'active'.  When
            'active' is set, the system will validate the profile.

            Before a profile can be deleted or taken out of service,
            (by setting this object to 'destroy' or 'outOfService')
            it must be first unreferenced from all associated lines."
    ::= { trafficPolicingEntry 5 }


END
