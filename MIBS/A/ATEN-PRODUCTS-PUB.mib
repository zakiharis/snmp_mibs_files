-- MIB created 09/13/2005 15:29:57, by
-- ATEN International Co., Ltd.

ATEN-PRODUCTS-PUB	DEFINITIONS ::= BEGIN

IMPORTS
    DisplayString
       		FROM SNMPv2-TC
	OBJECT-TYPE FROM SNMPv2-SMI
    public 	
			FROM ATEN-PRODUCTS-MIB;

email OBJECT-TYPE
       SYNTAX SEQUENCE OF UsrcfgEntry
       MAX-ACCESS not-accessible
       STATUS current
       DESCRIPTION
           "A list of email information.  The number of user is
           given by the value of usrcfgNumber."
       ::= { public 1 }

subject OBJECT-TYPE
      SYNTAX  DisplayString
      ACCESS  read-only
      STATUS  mandatory
      DESCRIPTION
              "A textual string containing subject of the email."
       ::= { email 1 }

message	OBJECT-TYPE
       SYNTAX DisplayString
       MAX-ACCESS read-only
       STATUS current
       DESCRIPTION
           "A textual string containing messsage(content) of the email."
       ::= { email 2 }	

to	OBJECT-TYPE
       SYNTAX DisplayString
       MAX-ACCESS read-only
       STATUS current
       DESCRIPTION
           "the email address of this email sending to"
       ::= { email 3 }	

cc	OBJECT-TYPE
       SYNTAX DisplayString
       MAX-ACCESS read-only
       STATUS current
       DESCRIPTION
           "the CC address of this email sending to"
       ::= { email 4 }	

log OBJECT-TYPE
       SYNTAX DisplayString
       MAX-ACCESS read-only
       STATUS current
       DESCRIPTION
           "the content of log"
       ::= { public 2 }	

trap	OBJECT-TYPE
       SYNTAX DisplayString
       MAX-ACCESS read-only
       STATUS current
       DESCRIPTION
           "this is the entrance of specific type(subtype) 
           classification in enterprise type, see 'ATEN-PRODUCTS-PUB-TRAP.txt'
           for details"
       ::= { public 3 }	

END
