-------------------------------------------------------------------------------
-- ACMEPACKET-SIP.txt:  Acme Packet SIP Application MIB
--
-- March 2012
--
-- Copyright (c) by Acme Packet, Inc.
-- All rights reserved.
-------------------------------------------------------------------------------

APSIP-MIB DEFINITIONS ::= BEGIN

IMPORTS
        MODULE-IDENTITY, OBJECT-TYPE, NOTIFICATION-TYPE,
        Gauge32, Integer32, Unsigned32
                FROM SNMPv2-SMI
        TEXTUAL-CONVENTION, DisplayString, TruthValue
                FROM SNMPv2-TC
        MODULE-COMPLIANCE, OBJECT-GROUP, NOTIFICATION-GROUP
                FROM SNMPv2-CONF
        InetAddress, InetAddressType
            FROM INET-ADDRESS-MIB
        acmepacketMgmt
                FROM ACMEPACKET-SMI
        ApHardwareModuleFamily, ApRedundancyState, ApPhyPortType,
        ApPresence, ApServerStatus
            FROM ACMEPACKET-TC;

apSipModule   MODULE-IDENTITY
               LAST-UPDATED     "201207130000Z"
               ORGANIZATION     "Acme Packet, Inc"
               CONTACT-INFO
                        "       Customer Service
                        Postal: Acme Packet, Inc
                                100 Crosby Drive
                                Bedford, MA 01730
                                US
                        Tel:    1-781-328-4400
                        E-mail: support@acmepacket.com"
       
                DESCRIPTION
                        "SIP MIB for Acme Packet."
                REVISION        "201207130000Z"
                DESCRIPTION
                        "Updated contact info."
                REVISION        "201203070000Z"
                DESCRIPTION
                        "Initial version."
                ::= { acmepacketMgmt 15 }


apSipMIBObjects OBJECT IDENTIFIER ::= { apSipModule 1 }
apSipMIBGeneralObjects OBJECT IDENTIFIER ::= {apSipMIBObjects 1}
apSipMIBTabularObjects OBJECT IDENTIFIER ::= {apSipMIBObjects 2}

apSipNotificationObjects OBJECT IDENTIFIER ::= { apSipModule 2 }

-- conformance information

apSipConformance OBJECT IDENTIFIER ::= { apSipModule 3 }
apSipObjectGroups OBJECT IDENTIFIER ::= { apSipConformance 1 }
apSipNotificationGroups OBJECT IDENTIFIER ::= { apSipConformance 2 }

apSipSecInterfaceObjects       OBJECT IDENTIFIER ::= {apSipMIBGeneralObjects 1}
apSipSecInterfaceNotifications OBJECT IDENTIFIER ::= { apSipNotificationObjects 1}
apSipSecIntfNotifObjects       OBJECT IDENTIFIER ::= { apSipSecInterfaceNotifications 1 }
apSipSecIntfNotifPrefix        OBJECT IDENTIFIER ::= { apSipSecInterfaceNotifications 2 }
apSipSecIntfNotifications      OBJECT IDENTIFIER ::= { apSipSecIntfNotifPrefix 0 }

apSipSecInterfaceTotalRegistrations OBJECT-TYPE
        SYNTAX                  Unsigned32
        MAX-ACCESS              read-only
        STATUS                  current
        DESCRIPTION
                "The total number of registrations on all secondary SIP interfaces."
        ::= { apSipSecInterfaceObjects 1 }

apSipSecInterfaceRegThreshold OBJECT-TYPE
        SYNTAX                  Unsigned32
        MAX-ACCESS              read-only
        STATUS                  current
        DESCRIPTION
                "The max threshold for registrations on all secondary SIP interfaces
                 beyond which trap and alarm will be raised."
        ::= { apSipSecInterfaceObjects 2 }

apSipSecInterfaceClearThreshold OBJECT-TYPE
        SYNTAX                  Unsigned32
        MAX-ACCESS              read-only
        STATUS                  current
        DESCRIPTION
                "The threshold for registrations on all secondary SIP interfaces
                 below which if alarm was raised before, it will be cleared."
        ::= { apSipSecInterfaceObjects 3 }

apSipSecInterfaceRegThresholdExceededTrap           NOTIFICATION-TYPE
        OBJECTS         { apSipSecInterfaceTotalRegistrations,
                          apSipSecInterfaceRegThreshold }
        STATUS          current
        DESCRIPTION
        " The trap will be generated if the total number of registrations
          on all secondary SIP interfaces exceed threshold."
        ::= { apSipSecIntfNotifications 1 }

apSipSecInterfaceRegThresholdClearTrap           NOTIFICATION-TYPE
        OBJECTS         { apSipSecInterfaceTotalRegistrations,
                          apSipSecInterfaceClearThreshold }
        STATUS          current
        DESCRIPTION
        " The trap will be generated if the total number of registrations
          on all secondary SIP interfaces go below clear threshold."
        ::= { apSipSecIntfNotifications 2 }


apSipSecInterfaceRegNotificationsGroup NOTIFICATION-GROUP
      NOTIFICATIONS {
                        apSipSecInterfaceRegThresholdExceededTrap,
                        apSipSecInterfaceRegThresholdClearTrap
                    }
                STATUS          current
                DESCRIPTION
                "A collection of traps to extend reporting capabilities."
      ::= {  apSipNotificationGroups 1 }

apSipSecInterfaceRegObjectsGroup OBJECT-GROUP
      OBJECTS {
                        apSipSecInterfaceTotalRegistrations,
                        apSipSecInterfaceRegThreshold,
                        apSipSecInterfaceClearThreshold                           
              }
      STATUS            current
      DESCRIPTION
                "A collection of objects providing the SIP MIB
                for Secondary Interface Registrations."
      ::= { apSipObjectGroups 1 }

END
