ASKEY-DSLAM-MIB DEFINITIONS ::= BEGIN

IMPORTS
    MODULE-IDENTITY, enterprises              FROM SNMPv2-SMI
    
    TEXTUAL-CONVENTION                        FROM SNMPv2-TC;

    askey MODULE-IDENTITY
        LAST-UPDATED    "200311250000Z"  -- november 25, 2003
        ORGANIZATION    "ASKEY Inc."
        CONTACT-INFO    "ASKEY Inc.
                         E-mail: cwfu@askey.com.tw"

        DESCRIPTION     "ASKEY DSLAM MIB OID defines and documentation."

        ::= { enterprises 3646 }

-- Textual Conventions
AskeyVendorTypeEnum ::= TEXTUAL-CONVENTION
    STATUS          current
    DESCRIPTION
            "Defines the enumeration of Askey vendor types."
    SYNTAX      INTEGER  {
        noEntity(1),                -- not such entity
        other(2),                   -- not defined vendor type
    
    -- AM0031 specificed
        am0031Chassis(3),           -- Chassis of AM0031, 1 CPU Slot/4 Line Slots
                                    --       /2 Power Slots/1 Fan Slot
                                    --       /1 Alarm Relay (In*4, Out*4)
        am0031BackPlane(4),         -- Backplane of AM0031(GE)
        genericEmptySlot(5),        -- Generic empty slot
        cpuSlot(6),                 -- Slot for CPU module
        lineCardSlot(7),            -- Slot for line card
        powerSlot(8),               -- Slot for power module
        fanSlot(9),                 -- Slot for Fan module
        am0031CpuModule(10),        -- CPU(PPC)/Switching(569x) module of AM0031
        am0031AdslModule(11),       -- ADSL(BCM6430F, 48 ports) module of AM0031
        am0031PowerModule(12),      -- Power module of AM0031
        am0031FanModule(13),        -- Fan module of AM0031
        genericAdslPort(14),        -- Generic ADSL ports
        bcm6430fAdslPort(15),       -- ADSL ports of BCM6430F
        gePort(16),                 -- GE port of CPU module
        alarmRelayModule(17),       -- Alarm relay module
        alarmRelayPort(18),         -- Alarm relay input port
        am0031VdslModule(19),       -- 
        am0031ShdslModule(20),      -- SHDSL(Conexant, 48 ports) module of AM0031
        am0031ShdslPort(21),        -- Conexant SHDSL ports
        

    -- AM0021 specificed, ((7 << 16) + n + 4)
        am0021Chassis(458759),            -- Chassis of AM0021, 2 CPU Slot/14 Line Slots
                                          --       /0 Power Slots/1 Fan Slot
                                          --       /1 Alarm Relay (In*4, Out*4)
        am0021CpuModuleX2GE(458762),      -- CPU(PPC)/Switching(569x) module with 2 GE ports
        am0021AdslModule(458763),         -- ADSL(BCM6430F, 48 ports) module of AM0021
        am0021PowerModule(458764),        -- Power module of AM0021
        am0021FanModule(458765),          -- Fan module of AM0021
        am0021AdslPort(458767),           -- ADSL ports of BCM6430F
        am0021GePort(458768),             -- GE port of CPU module
        am0021AlarmRelayModule(458769),   -- Alarm relay module
        am0021AlarmRelayPort(458770),     -- Alarm relay input port
        am0021VdslModule(458771),         -- 
        am0021ShdslModule(458772),        -- SHDSL(Conexant, 48 ports) module of AM0031
        am0021ShdslPort(458773),          -- Conexant SHDSL ports
        am0021CpuModuleX4GE(458774)       -- CPU(PPC)/Switching(565xx) module with 4 GE ports
    

    }
        
-- D300
    asd300          OBJECT IDENTIFIER ::= { askey 1300 }

-- D300 products' sysObjectID
    swv011          OBJECT IDENTIFIER ::= { askey 1300 300 1}
    swt011          OBJECT IDENTIFIER ::= { askey 1300 300 2}
    swv031          OBJECT IDENTIFIER ::= { askey 1300 300 3}
    swf011          OBJECT IDENTIFIER ::= { askey 1300 300 4}
    swt012          OBJECT IDENTIFIER ::= { askey 1300 300 5}
    am0031          OBJECT IDENTIFIER ::= { askey 1300 300 6}
    am0021          OBJECT IDENTIFIER ::= { askey 1300 300 7}
    ama1011         OBJECT IDENTIFIER ::= { askey 1300 300 8}
    ams1011         OBJECT IDENTIFIER ::= { askey 1300 300 9}

    unDefinedDevice OBJECT IDENTIFIER ::= { askey 1300 300 999}

-- IPDSLAM
    ipDslam         OBJECT IDENTIFIER ::= { asd300 2 }
    
-- DSLAM Ethernet Over ATM
--    askeySystemMib                   MODULE-IDENTITY ::= { ipDslam 1 }   work
--    askeyADSLMib                     MODULE-IDENTITY ::= { ipDslam 2 }   work
--    askeyIgmpSnoopMib                MODULE-IDENTITY ::= { ipDslam 3 }   work
--    askeyRfc2684Mib                  MODULE-IDENTITY ::= { ipDslam 4 }   obsolute
--    askeyProfileMib                  MODULE-IDENTITY ::= { ipDslam 5 }   obsolute
--    askeyMcastMib                    MODULE-IDENTITY ::= { ipDslam 5 }   work
--    askeyIpoaMib                     MODULE-IDENTITY ::= { ipDslam 6 }   work
--    askeyDslamVcVlanMIB              MODULE-IDENTITY ::= { ipDslam 11 }  work
--    askeyEntityAlarmMIB              MODULE-IDENTITY ::= { ipDslam 12 }  work
--    askeyLacpMib        	           MODULE-IDENTITY ::= { ipDslam 13 }  work

--
-- END of ASKEY-DSLAM-MIB
--

END
