ACC-MIB DEFINITIONS ::= BEGIN

-- Title:	ACC MIB
-- Date:	April 2, 1990
-- By:		Chris VandenBerg/ACC <chris@salt.acc.com>

IMPORTS
	enterprises, OBJECT-TYPE, Counter, Gauge, TimeTicks, IpAddress,
	NetworkAddress
		FROM RFC1065-SMI;

IfIndex ::= TEXTUAL-CONVENTION
  STATUS  current
  DESCRIPTION
    "The value of this object identifies the
    interface for which this entry contains
    management information.  The value of this
    object for a particular interface has the same
    value as the ifIndex object, defined in RFC
    1213, for the same interface."
  SYNTAX INTEGER
  
SmdsAddress ::= TEXTUAL-CONVENTION
    DISPLAY-HINT "1h:"
    STATUS       current
    DESCRIPTION
        "The 60-bit SMDS address,
         preceded by 4 bits with the following values:
         1100 when representing an individual address
         1110 when representing a group address."
    SYNTAX  OCTET STRING (SIZE (8))
	 
acc			OBJECT IDENTIFIER ::= { enterprises 5 }
  accSBAR		OBJECT IDENTIFIER ::= { acc 1 }
    accBRG		OBJECT IDENTIFIER ::= { accSBAR 1 }
	 
  accSBEngr		OBJECT IDENTIFIER ::= { acc 1 }
    sbe4000 		OBJECT IDENTIFIER ::= { accSBEngr 1 }

      sbeSystem 	OBJECT IDENTIFIER ::= { sbe4000 1 }
	sbeSysInfo 	OBJECT IDENTIFIER ::= { sbeSystem 1 }
	  sbeUnitName 	OBJECT-TYPE   --oUnitName
			SYNTAX	OCTET STRING
			ACCESS	read-write
			STATUS	mandatory
	DESCRIPTION ""
			::= { sbeSysInfo 1 }
	  sbeRomId 	OBJECT-TYPE   --oRomId
			SYNTAX	OCTET STRING
			ACCESS	read-only
			STATUS	mandatory
	DESCRIPTION ""
			::= { sbeSysInfo 2 }
	  sbeSwVersion 	OBJECT-TYPE   --oSoftwareVersion
			SYNTAX	OCTET STRING
			ACCESS	read-only
			STATUS	mandatory
	DESCRIPTION ""
			::= { sbeSysInfo 3 }
	  sbeReset 	OBJECT-TYPE   --oReset
			SYNTAX	INTEGER
			ACCESS	write-only
			STATUS	mandatory
	DESCRIPTION ""
			::= { sbeSysInfo 4 }
          sbeMemory    OBJECT IDENTIFIER ::= { sbeSysInfo 5 }
            sbeMemBlkEntSize   OBJECT-TYPE  --oMemBlkEntSize
                        SYNTAX  INTEGER
                        ACCESS  read-only
                        STATUS  mandatory
		DESCRIPTION ""
                        ::=  { sbeMemory 1 }
            sbeMemBlkEntTotal   OBJECT-TYPE  --oMemBlkEntTotal
                        SYNTAX  INTEGER
                        ACCESS  read-only
                        STATUS  mandatory
		DESCRIPTION ""
                        ::=  { sbeMemory 2 }
            sbeMemBlkEntMax   OBJECT-TYPE  --oMemBlkEntMax
                        SYNTAX  Counter
                        ACCESS  read-only
                        STATUS  mandatory
		DESCRIPTION ""
                        ::=  { sbeMemory 3 }
            sbeMemBlkEntInUse   OBJECT-TYPE  --oMemBlkEntInUse
                        SYNTAX  Gauge
                        ACCESS  read-only
                        STATUS  mandatory
		DESCRIPTION ""
                        ::=  { sbeMemory 4 }
            sbeMemBlkEntFails   OBJECT-TYPE  --oMemBlkEntFails
                        SYNTAX  Counter
                        ACCESS  read-only
                        STATUS  mandatory
		DESCRIPTION ""
                        ::=  { sbeMemory 5 }

	sbeSessionCtrl	OBJECT IDENTIFIER ::= { sbeSystem 2 }
	  sbeLogin 	OBJECT-TYPE   --oLogin
			SYNTAX	OCTET STRING
			ACCESS	read-write
			STATUS	mandatory
		DESCRIPTION ""
			::= { sbeSessionCtrl 1 }
	  sbeLogout	OBJECT-TYPE   --oLogout
			SYNTAX	OCTET STRING
			ACCESS	read-only
			STATUS	mandatory
		DESCRIPTION ""
			::= { sbeSessionCtrl 2 }
          sbeLoginTimeout  OBJECT-TYPE  --oLoginTimeout
                        SYNTAX TimeTicks 
                        ACCESS read-write
                        STATUS mandatory
		DESCRIPTION ""
                        ::= { sbeSessionCtrl 3 }
                        -- Session inactivity timer.
                        -- Zero disables timer (no timeout)
                        -- Default value is zero
                        -- Range is 0-86400 seconds

	sbeTrapTable 	OBJECT-TYPE 
                        SYNTAX  SEQUENCE OF SbeTrapEntry
                        ACCESS  read-write
                        STATUS  mandatory
		DESCRIPTION ""
                        ::= { sbeSystem 3 }
          sbeTrapEntry  OBJECT-TYPE
                        SYNTAX  SbeTrapEntry
                        ACCESS  read-write
                        STATUS  mandatory
		DESCRIPTION ""
                        ::= { sbeTrapTable 1 }
          SbeTrapEntry  ::= SEQUENCE {
                        sbeTrapAddr
                           IpAddress,
                        sbeTrapSeverity
                           INTEGER
                        } 
	    sbeTrapAddr OBJECT-TYPE   --oTrapAddr
			SYNTAX	IpAddress
			ACCESS	read-write
			STATUS	mandatory
		DESCRIPTION ""
			::= { sbeTrapEntry 1 }
	    sbeTrapSeverity 	OBJECT-TYPE   --oTrapSeverity
			SYNTAX	INTEGER (1..7)
			ACCESS	read-write
			STATUS	mandatory
		DESCRIPTION ""
			::= { sbeTrapEntry 2 }
	sbeClock 	OBJECT IDENTIFIER ::= { sbeSystem 4 }
	  sbeDate 	OBJECT-TYPE   --oDate
			SYNTAX	OCTET STRING
			ACCESS	read-write
			STATUS	mandatory
		DESCRIPTION ""
			::= { sbeClock 1 }
	  sbeUToffset 	OBJECT-TYPE   --oUToffset
			SYNTAX	OCTET STRING
			ACCESS	read-write
			STATUS	mandatory
		DESCRIPTION ""
			::= { sbeClock 2 }
                        -- 3-byte date string, HH MM SS
	  sbeSysBootTime  OBJECT-TYPE   --oSysBootTime
			SYNTAX	OCTET STRING
			ACCESS	read-write
			STATUS	mandatory
		DESCRIPTION ""
			::= { sbeClock 3 }
                        -- 3-byte date string, HH MM SS
       sbeAccessTable 	OBJECT-TYPE
                        SYNTAX  SEQUENCE OF  SbeAccessCmty
                        ACCESS  read-write
                        STATUS  mandatory
		DESCRIPTION ""
			::= { sbeSystem 6 }
         sbeAccessEnt   OBJECT-TYPE
                        SYNTAX  SbeAccessCmty
                        ACCESS  read-write
                        STATUS  mandatory
		DESCRIPTION ""
 			::= { sbeAccessTable 1 }
         SbeAccessCmty  ::= SEQUENCE {
                              sbeAccessCmty
                                OCTET STRING,
                              sbeAccessAddr
                                IpAddress,
                              sbeAccessNetMask
                                IpAddress,
                              sbeAccessUdpPort
                                INTEGER
                              }
	   sbeAccessCmty  	OBJECT-TYPE   --oAccessEntCommunity
			SYNTAX	OCTET STRING
			ACCESS	read-write
			STATUS	mandatory
		DESCRIPTION ""
			::= { sbeAccessEnt 1 }

	   sbeAccessAddr  	OBJECT-TYPE   --oAccessEntAddr
			SYNTAX	IpAddress
			ACCESS	read-write
			STATUS	mandatory
		DESCRIPTION ""
			::= { sbeAccessEnt 2 }

	   sbeAccessNetMask 	OBJECT-TYPE   --oAccessEntNetMask
			SYNTAX	IpAddress
			ACCESS	read-write
			STATUS	mandatory
		DESCRIPTION ""
			::= { sbeAccessEnt 3 }

	   sbeAccessUdpPort 	OBJECT-TYPE   --oAccessEntUdpPort
			SYNTAX	INTEGER
			ACCESS	read-write
			STATUS	mandatory
		DESCRIPTION ""
			::= { sbeAccessEnt 4 }
     sbeStp 		OBJECT IDENTIFIER ::= { sbe4000 2 }
	sbeStpPriority 	OBJECT-TYPE   --oStpPriority
			SYNTAX	INTEGER (0..255)
			ACCESS	read-write
			STATUS	mandatory
		DESCRIPTION ""
			::= { sbeStp 1 }
	sbeStpId 	OBJECT-TYPE   --oStpId
			SYNTAX	OCTET STRING
			ACCESS	read-only
			STATUS	mandatory
		DESCRIPTION ""
			::= { sbeStp 2 }
	sbeStpBrAddr 	OBJECT-TYPE   --oStpBrAddr
			SYNTAX	OCTET STRING
			ACCESS	read-only
			STATUS	mandatory
		DESCRIPTION ""
			::= { sbeStp 3 }
	sbeStpMode 	OBJECT-TYPE   --oStpMode
			SYNTAX	INTEGER {
				off(0),
				on(1)
				}
			ACCESS	read-write
			STATUS	mandatory
		DESCRIPTION ""
			::= { sbeStp 4 }
	sbeStpFilterTime 	OBJECT-TYPE   --oStpFilterTime
			SYNTAX	TimeTicks
			ACCESS	read-only
			STATUS	mandatory
		DESCRIPTION ""
			::= { sbeStp 5 }
	sbeStpMcastAddr 	OBJECT-TYPE   --oStpMultiCast
			SYNTAX	OCTET STRING
			ACCESS	read-write
			STATUS	mandatory
		DESCRIPTION ""
			::= { sbeStp 6 }
	sbeStpTopChangeDet 	OBJECT-TYPE   --oStpTopChangeDet
			SYNTAX	INTEGER {
				no(0),
				yes(1)
				}
			ACCESS	read-only
			STATUS	mandatory
		DESCRIPTION ""
			::= { sbeStp 7 }
	sbeStpTopChange 	OBJECT-TYPE   --oStpTopChange
			SYNTAX	INTEGER {
				no(0),
				yes(1)
				}
			ACCESS	read-only
			STATUS	mandatory
		DESCRIPTION ""
			::= { sbeStp 8 }
	sbeStpTopChangeTimer 	OBJECT-TYPE   --oStpTopChangeTime
			SYNTAX	TimeTicks
			ACCESS	read-only
			STATUS	mandatory
		DESCRIPTION ""
			::= { sbeStp 9 }
	sbeStpDesRoot 	OBJECT-TYPE   --oStpDesRoot
			SYNTAX	OCTET STRING
			ACCESS	read-only
			STATUS	mandatory
		DESCRIPTION ""
			::= { sbeStp 10 }
	sbeStpRootPathCost 	OBJECT-TYPE   --oStpRootPathCost
			SYNTAX	INTEGER
			ACCESS	read-only
			STATUS	mandatory
		DESCRIPTION ""
			::= { sbeStp 11 }
	sbeStpRootPort 	OBJECT-TYPE   --oStpRootPort
			SYNTAX	OCTET STRING
			ACCESS	read-only
			STATUS	mandatory
		DESCRIPTION ""
			::= { sbeStp 12 }
	sbeStpMaxAge 	OBJECT-TYPE   --oStpMaxAge
			SYNTAX	INTEGER (4..3600)
			ACCESS	read-write
			STATUS	mandatory
		DESCRIPTION ""
			::= { sbeStp 13 }
	sbeStpHelloTime 	OBJECT-TYPE   --oStpHelloTime
			SYNTAX	INTEGER (2..1800)
			ACCESS	read-write
			STATUS	mandatory
		DESCRIPTION ""
			::= { sbeStp 14 }
	sbeStpForwardDelay 	OBJECT-TYPE   --oStpForwardDelay
			SYNTAX	INTEGER (5..3600)
			ACCESS	read-write
			STATUS	mandatory
		DESCRIPTION ""
			::= { sbeStp 15 }
	sbeStpUpTime 	OBJECT-TYPE   --oStpUpTime
			SYNTAX	TimeTicks
			ACCESS	read-write
			STATUS	mandatory
		DESCRIPTION ""
			::= { sbeStp 16 }
	sbeStpTopChangeCnt 	OBJECT-TYPE   --oStpTopChangeCnt
			SYNTAX	Counter
			ACCESS	read-only
			STATUS	mandatory
		DESCRIPTION ""
			::= { sbeStp 17 }
      sbeBrPort 	OBJECT IDENTIFIER ::= { sbe4000 3 }
	sbeBrPortTable 	OBJECT IDENTIFIER ::= { sbeBrPort 1 }
	  sbeBrPortStats OBJECT IDENTIFIER ::= { sbeBrPortTable 1 }
	    sbeBrPortInNUcastPkts 	OBJECT-TYPE   --oPortInNUcastPkts
			SYNTAX	Counter
			ACCESS	read-only
			STATUS	mandatory
		DESCRIPTION ""
			::= { sbeBrPortStats 1 }
	    sbeBrPortInUcastPkts 	OBJECT-TYPE   --oPortInUcastPkts
			SYNTAX	Counter
			ACCESS	read-only
			STATUS	mandatory
		DESCRIPTION ""
			::= { sbeBrPortStats 2 }
	    sbeBrPortInDupPkts 	OBJECT-TYPE   --oPortInDupPkts
			SYNTAX	Counter
			ACCESS	read-only
			STATUS	mandatory
		DESCRIPTION ""
			::= { sbeBrPortStats 3 }
	    sbeBrPortOutNUcastPkts 	OBJECT-TYPE   --oPortOutNUcastPkts
			SYNTAX	Counter
			ACCESS	read-only
			STATUS	mandatory
		DESCRIPTION ""
			::= { sbeBrPortStats 4 }
	    sbeBrPortOutUcastPkts 	OBJECT-TYPE   --oPortOutUcastPkts
			SYNTAX	Counter
			ACCESS	read-only
			STATUS	mandatory
		DESCRIPTION ""
			::= { sbeBrPortStats 5 }
	    sbeBrPortStpInPkts 	OBJECT-TYPE   --oPortInStpPkts
			SYNTAX	Counter
			ACCESS	read-only
			STATUS	mandatory
		DESCRIPTION ""
			::= { sbeBrPortStats 6 }
	    sbeBrPortStpOutPkts 	OBJECT-TYPE   --oPortOUtStpPkts
			SYNTAX	Counter
			ACCESS	read-only
			STATUS	mandatory
		DESCRIPTION ""
			::= { sbeBrPortStats 7 }
	    sbeBrPortOutDelayDiscPkts 	OBJECT-TYPE   --oPortOutDelayDiscPkts
			SYNTAX	Counter
			ACCESS	read-only
			STATUS	mandatory
		DESCRIPTION ""
			::= { sbeBrPortStats 8 }
	    sbeBrPortOutPrioDiscPkts 	OBJECT-TYPE   --oPortOutPrioDiscPkts
			SYNTAX	Counter
			ACCESS	read-only
			STATUS	mandatory
		DESCRIPTION ""
			::= { sbeBrPortStats 9 }
	    sbeBrPortOutQLen 	OBJECT-TYPE   --oPortOutQLen
			SYNTAX	Gauge
			ACCESS	read-only
			STATUS	mandatory
		DESCRIPTION ""
			::= { sbeBrPortStats 10 }
	    sbeBrPortInDiscPkts 	OBJECT-TYPE   --oPortInDiscPkts
			SYNTAX	Counter
			ACCESS	read-only
			STATUS	mandatory
		DESCRIPTION ""
			::= { sbeBrPortStats 11 }
	  sbeBrPortStpPriority 	OBJECT-TYPE   --oPortPriority
			SYNTAX	INTEGER (0..255)
			ACCESS	read-write
			STATUS	mandatory
		DESCRIPTION ""
			::= { sbeBrPortTable 2 }
	  sbeBrPortId 	OBJECT-TYPE   --oPortId
			SYNTAX	OCTET STRING
			ACCESS	read-only
			STATUS	mandatory
		DESCRIPTION ""
			::= { sbeBrPortTable 3 }
	  sbeBrPortState 	OBJECT-TYPE   --oPortState
			SYNTAX	INTEGER {
				disabled(0),
				blocking(1),
				listening(2),
				learning(3),
				forwarding(4)
				}
			ACCESS	read-write
			STATUS	mandatory
		DESCRIPTION ""
			::= { sbeBrPortTable 5 }
	  sbeBrPortStpPathCost 	OBJECT-TYPE   --oPortPathCost
			SYNTAX	INTEGER (0..65535)
			ACCESS	read-write
			STATUS	mandatory
		DESCRIPTION ""
			::= { sbeBrPortTable 6 }
	  sbeBrPortStpDesRoot 	OBJECT-TYPE   --oPortDesRoot
			SYNTAX	OCTET STRING
			ACCESS	read-only
			STATUS	mandatory
		DESCRIPTION ""
			::= { sbeBrPortTable 7 }
	  sbeBrPortStpDesCost 	OBJECT-TYPE   --oPortDesCost
			SYNTAX	INTEGER (0..65535)
			ACCESS	read-write
			STATUS	mandatory
		DESCRIPTION ""
			::= { sbeBrPortTable 8 }
	  sbeBrPortStpDesBridge 	OBJECT-TYPE   --oPortDesBridge
			SYNTAX	OCTET STRING
			ACCESS	read-only
			STATUS	mandatory
		DESCRIPTION ""
			::= { sbeBrPortTable 9 }
	  sbeBrPortStpDesPort 	OBJECT-TYPE   --oPortDesPort
			SYNTAX	OCTET STRING
			ACCESS	read-only
			STATUS	mandatory
		DESCRIPTION ""
			::= { sbeBrPortTable 10 }

      sbeBridge 	OBJECT IDENTIFIER ::= { sbe4000 4 }
	sbeBrFdbTimeout 	OBJECT-TYPE   --oFdbTimeout
			SYNTAX	INTEGER (10..65535)
			ACCESS	read-write
			STATUS	mandatory
		DESCRIPTION ""
			::= { sbeBridge 1 }
	sbeBrFdbLearnMde 	OBJECT-TYPE   --oFdbLearnMode
			SYNTAX	INTEGER {
				off(0),
				on(1)
				}
			ACCESS	read-write
			STATUS	mandatory
		DESCRIPTION ""
			::= { sbeBridge 2 }
	sbeBrFdbRamCurrSize 	OBJECT-TYPE   --oFdbRamCurrSize
			SYNTAX	INTEGER
			ACCESS	read-only
			STATUS	mandatory
		DESCRIPTION ""
			::= { sbeBridge 3 }
	sbeBrFdbRamMaxSize 	OBJECT-TYPE   --oFdbRamMaxSize
			SYNTAX	INTEGER (64..1024)
			ACCESS	read-write
			STATUS	mandatory
		DESCRIPTION ""
			::= { sbeBridge 5 }
	sbeBrFdbNvmMaxSize 	OBJECT-TYPE   --oFdbNvmMaxSize
			SYNTAX	INTEGER
			ACCESS	read-only
			STATUS	mandatory
		DESCRIPTION ""
			::= { sbeBridge 6 }
	sbeBrFdbTable 	OBJECT IDENTIFIER ::= { sbeBridge 7 }
	  sbeBrFdbEntry OBJECT IDENTIFIER ::= { sbeBrFdbTable 1 }
	    sbeBrFdbEntMacAddr 	OBJECT-TYPE   --oFdbEntMacAddr
			SYNTAX	OCTET STRING
			ACCESS	read-write
			STATUS	mandatory
		DESCRIPTION ""
			::= { sbeBrFdbEntry 1 }
	    sbeBrFdbEntDisp 	OBJECT-TYPE   --oFdbEndDisp
			SYNTAX	INTEGER {
				forward(0),
				flood(1),
				discard(2)
				}
			ACCESS	read-write
			STATUS	mandatory
		DESCRIPTION ""
			::= { sbeBrFdbEntry 2 }
	    sbeBrFdbEntPort 	OBJECT-TYPE   --oFdbEntPort
			SYNTAX	INTEGER
			ACCESS	read-write
			STATUS	mandatory
		DESCRIPTION ""
			::= { sbeBrFdbEntry 3 }
	    sbeBrFdbEntTimer 	OBJECT-TYPE   --oFdbEntTimer
			SYNTAX	INTEGER
			ACCESS	read-write
			STATUS	mandatory
		DESCRIPTION ""
			::= { sbeBrFdbEntry 4 }
	sbeBrFpTable 	OBJECT IDENTIFIER ::= { sbeBridge 8 }
	  sbeBrFpEntry 	OBJECT IDENTIFIER ::= { sbeBrFpTable 1 }
	    sbeBrFpIndex OBJECT-TYPE   --oFPEindex
			SYNTAX	INTEGER 
			ACCESS	read-write
			STATUS	mandatory
		DESCRIPTION ""
			::= { sbeBrFpEntry 1 }
                        --port number
	    sbeBrFpProt OBJECT-TYPE   --oFPEprotId
			SYNTAX	INTEGER (0..65535)
			ACCESS	read-write
			STATUS	mandatory
		DESCRIPTION ""
			::= { sbeBrFpEntry 2 }
                        -- protocol type
	    sbeBrFpPrio OBJECT-TYPE   --oFPEpriority
			SYNTAX	INTEGER {
				discard(0),
				low(1),
				normal(2),
				high(3)
				}
			ACCESS	read-write
			STATUS	mandatory
		DESCRIPTION ""
			::= { sbeBrFpEntry 3 }
                        -- priority
	sbeBrFpPriDefault 	OBJECT-TYPE   --oFPEpriDef
			SYNTAX	INTEGER {
				discard(0),
				low(1),
				normal(2),
				high(3)
				}
			ACCESS	read-write
			STATUS	mandatory
		DESCRIPTION ""
			::= { sbeBridge 9 }

      sbeSlot 	OBJECT IDENTIFIER ::= { sbe4000 5 }
	sbeSlotTable 	OBJECT IDENTIFIER ::= { sbeSlot 2 }
	  sbeSlotEntry 	OBJECT IDENTIFIER ::= { sbeSlotTable 1 }
	    sbeSlotLastChange 	OBJECT-TYPE   --oSlotLastChange
			SYNTAX	OCTET STRING
			ACCESS	read-only
			STATUS	mandatory
		DESCRIPTION ""
			::= { sbeSlotEntry 9 }
	    sbeSlotInPkts 	OBJECT-TYPE   --oSlotInPkts
			SYNTAX	Counter
			ACCESS	read-only
			STATUS	mandatory
		DESCRIPTION ""
			::= { sbeSlotEntry 11 }
	    sbeSlotOutPkts 	OBJECT-TYPE   --oSlotOutPkts
			SYNTAX	Counter
			ACCESS	read-only
			STATUS	mandatory
		DESCRIPTION ""
			::= { sbeSlotEntry 17 }
	    sbeSlotNumChanges 	OBJECT-TYPE   --oSlotNumChange
			SYNTAX	Counter
			ACCESS	read-only
			STATUS	mandatory
		DESCRIPTION ""
			::= { sbeSlotEntry 21 }
            sbeSlotProtocol     OBJECT-TYPE   --oSlotProtocol
                        SYNTAX  INTEGER  {
                                enet(1),
                                x25(2),
                                lapb(3)
                                }
                        ACCESS  read-write
                        STATUS  mandatory
		DESCRIPTION ""
                        ::= { sbeSlotEntry 22 }

      sbeLapb 	OBJECT IDENTIFIER ::= { sbe4000 7 }

	sbeLapbNum 	OBJECT-TYPE   --oHdlcNumber
			SYNTAX	INTEGER
			ACCESS	read-only
			STATUS	mandatory
		DESCRIPTION ""
			::= { sbeLapb 1 }
			-- Number of HDLC ports

	sbeLapbParmTable 	OBJECT-TYPE
			SYNTAX	SEQUENCE OF SbeLapbParmEntry
			ACCESS	read-write
			STATUS	mandatory
		DESCRIPTION ""
			::= { sbeLapb 2 }
			-- HDLC LAPB port parameters

	  sbeLapbParmEntry 	OBJECT-TYPE 
			SYNTAX	SbeLapbParmEntry
			ACCESS	read-write
			STATUS	mandatory
		DESCRIPTION ""
			::= { sbeLapbParmTable 1 }

			SbeLapbParmEntry ::= SEQUENCE {
			    sbeLapbIndex	INTEGER,
			    sbeLapbType		INTEGER,
			    sbeLapbT1Timer	INTEGER,
			    sbeLapbN2Count	INTEGER,
			    sbeLapbFrameWindow	INTEGER
			    }
			-- LAPB parameters for a port.
			-- The instance of an entry is the port number.

	    sbeLapbIndex 	OBJECT-TYPE   --oHdlcIndex
			SYNTAX	INTEGER
			ACCESS	read-only
			STATUS	mandatory
		DESCRIPTION ""
			::= { sbeLapbParmEntry 1 }
			-- Physical port number of this interface.

	    sbeLapbType 	OBJECT-TYPE   --oHdlcType
			SYNTAX	INTEGER {
				dte(0),
				dce(1)
				}
			ACCESS	read-write
			STATUS	mandatory
		DESCRIPTION ""
			::= { sbeLapbParmEntry 2 }
			-- LAPB station type for this interface.

	    sbeLapbT1timer 	OBJECT-TYPE   --oHdlcT1timer
			SYNTAX	INTEGER (1..32000)
			ACCESS	read-write
			STATUS	mandatory
		DESCRIPTION ""
			::= { sbeLapbParmEntry 3 }
			-- T1 timer value (in milliseconds) for this
			-- interface.

	    sbeLapbN2count 	OBJECT-TYPE   --oHdlcN2count
			SYNTAX	INTEGER (2..20)
			ACCESS	read-write
			STATUS	mandatory
		DESCRIPTION ""
			::= { sbeLapbParmEntry 4 }
			-- N2 counter (retry counter) for this interface.

	    sbeLapbFrameWindow 	OBJECT-TYPE   --oHdlcFrameWindow
			SYNTAX	INTEGER (1..127)
			ACCESS	read-write
			STATUS	mandatory
		DESCRIPTION ""
			::= { sbeLapbParmEntry 5 }
			-- LAPB frame window.  If a value greater than
			-- 7 is specified, modulo-128 sequencing is used
			-- instead of modulo-8 sequencing.

	sbeLapbStatTable    OBJECT IDENTIFIER ::= { sbeLapb 3 }
          sbeLapbStatEntry  OBJECT IDENTIFIER ::= { sbeLapbStatTable 1 }
            sbeLapbStatIndex  OBJECT-TYPE    --oHdlcStatIndex
                        SYNTAX  INTEGER
                        ACCESS  read-only
                        STATUS  mandatory
		DESCRIPTION ""
                        ::= { sbeLapbStatEntry 1 }

            sbeLapbStatBadFCSIns  OBJECT-TYPE  --oHdlcStatBadFCSIns
                        SYNTAX  Counter
                        ACCESS  read-only
                        STATUS  mandatory
		DESCRIPTION ""
                        ::= { sbeLapbStatEntry 2 }

            sbeLapbStatFRMRIns  OBJECT-TYPE  --oHdlcStatFRMRIns
                        SYNTAX  Counter
                        ACCESS  read-only
                        STATUS  mandatory
		DESCRIPTION ""
                        ::= { sbeLapbStatEntry 3 }

            sbeLapbStatT1Timeouts  OBJECT-TYPE  --oHdlcStatT1Timeouts
                        SYNTAX  Counter
                        ACCESS  read-only
                        STATUS  mandatory
		DESCRIPTION ""
                        ::= { sbeLapbStatEntry 4 }
            sbeLapbStatREJIns  OBJECT-TYPE  --oHdlcStatREJIns
                        SYNTAX  Counter
                        ACCESS  read-only
                        STATUS  mandatory
		DESCRIPTION ""
                        ::= { sbeLapbStatEntry 5 }
            sbeLapbStatREJOuts  OBJECT-TYPE  --oHdlcStatREJOuts
                        SYNTAX  Counter
                        ACCESS  read-only
                        STATUS  mandatory
		DESCRIPTION ""
                        ::= { sbeLapbStatEntry 6 }
            sbeLapbStatShortIns  OBJECT-TYPE  --oHdlcStatShortIns
                        SYNTAX  Counter
                        ACCESS  read-only
                        STATUS  mandatory
		DESCRIPTION ""
                        ::= { sbeLapbStatEntry 7 }

      sbeEthernet      	OBJECT IDENTIFIER ::= { sbe4000 8 }
	sbeEthernetNum 	OBJECT-TYPE   --oEthNumber
			SYNTAX	INTEGER
			ACCESS	read-only
			STATUS	mandatory
		DESCRIPTION ""
			::= { sbeEthernet 1 }
	sbeEthernetParmTable 	OBJECT IDENTIFIER ::= { sbeEthernet 2 }
	  sbeEthernetParmEntry 	OBJECT IDENTIFIER ::= { sbeEthernetParmTable 1 }
	    sbeEthernetIndex 	OBJECT-TYPE   --oEthIndex
			SYNTAX	INTEGER
			ACCESS	read-only
			STATUS	mandatory
		DESCRIPTION ""
			::= { sbeEthernetParmEntry 1 }
	sbeEnetStatTable 	OBJECT IDENTIFIER ::= { sbeEthernet 3 }
	  sbeEnetStatEntry 	OBJECT IDENTIFIER ::= { sbeEnetStatTable 1 }
	    sbeEnetIndex 	OBJECT-TYPE   --oEthIndex
			SYNTAX	INTEGER
			ACCESS	read-only
			STATUS	mandatory
		DESCRIPTION ""
			::= { sbeEnetStatEntry 1 }
            sbeEnetStatCRCErrs  OBJECT-TYPE --oEthStatCRCErrs
                        SYNTAX  Counter
                        ACCESS  read-only
                        STATUS  mandatory
		DESCRIPTION ""
                        ::= { sbeEnetStatEntry 2 }
            sbeEnetStatAlignErrs  OBJECT-TYPE --oEthStatAlignErrs
                        SYNTAX  Counter
                        ACCESS  read-only
                        STATUS  mandatory
		DESCRIPTION ""
                        ::= { sbeEnetStatEntry 3 }
            sbeEnetStatOutColls  OBJECT-TYPE --oEthStatOutColls
                        SYNTAX  Counter
                        ACCESS  read-only
                        STATUS  mandatory
		DESCRIPTION ""
                        ::= { sbeEnetStatEntry 4 }
            sbeEnetStatJabberConds  OBJECT-TYPE --oEthStatJabberConds
                        SYNTAX  Counter
                        ACCESS  read-only
                        STATUS  mandatory
		DESCRIPTION ""
                        ::= { sbeEnetStatEntry 5 }
            sbeEnetStatCarrierLosts  OBJECT-TYPE --oEthStatCarrierLosts
                        SYNTAX  Counter
                        ACCESS  read-only
                        STATUS  mandatory
		DESCRIPTION ""
                        ::= { sbeEnetStatEntry 6 }
            sbeEnetStatHeartbeatErrs  OBJECT-TYPE --oEthStatHeartBeatErrs
                        SYNTAX  Counter
                        ACCESS  read-only
                        STATUS  mandatory
		DESCRIPTION ""
                        ::= { sbeEnetStatEntry 7 }
            sbeEnetStatGiants  OBJECT-TYPE --oEthStatGiants
                        SYNTAX  Counter
                        ACCESS  read-only
                        STATUS  mandatory
		DESCRIPTION ""
                        ::= { sbeEnetStatEntry 8 }
            sbeEnetStatOneRetrys  OBJECT-TYPE --oEthStatOneRetrys
                        SYNTAX  Counter
                        ACCESS  read-only
                        STATUS  mandatory
		DESCRIPTION ""
                        ::= { sbeEnetStatEntry 9 }
            sbeEnetStatMultRetrys  OBJECT-TYPE --oEthStatMultRetrys
                        SYNTAX  Counter
                        ACCESS  read-only
                        STATUS  mandatory
		DESCRIPTION ""
                        ::= { sbeEnetStatEntry 10 }
            sbeEnetStatLateColls  OBJECT-TYPE --oEthStatLateColls
                        SYNTAX  Counter
                        ACCESS  read-only
                        STATUS  mandatory
		DESCRIPTION ""
                        ::= { sbeEnetStatEntry 11 }

      sbeMultilink 	OBJECT IDENTIFIER ::= { sbe4000 9 }
	sbeMlTable 	OBJECT IDENTIFIER ::= { sbeMultilink 2 }
	  sbeMlEntry 	OBJECT IDENTIFIER ::= { sbeMlTable 1 }
	    sbeMlAdminStatus 	OBJECT-TYPE   --oMlAdminStatus
			SYNTAX	INTEGER {
				on(1),
				off(2),
				undefined(3)
				}
			ACCESS	read-write
			STATUS	mandatory
		DESCRIPTION ""
			::= { sbeMlEntry 7 }

      sbeAsPort	 	OBJECT IDENTIFIER ::= { sbe4000 10 }
	sbeAsPortTable	OBJECT IDENTIFIER ::= { sbeAsPort 2 }
	sbeAsPortEntry 	OBJECT IDENTIFIER ::= { sbeAsPortTable 1 }
	  sbeAsPortSpeed 	OBJECT-TYPE   --oAsSpeed
			SYNTAX	INTEGER
			ACCESS	read-write
			STATUS	mandatory
		DESCRIPTION ""
			::= { sbeAsPortEntry 5 }

      sbeArp 	OBJECT IDENTIFIER ::= { sbe4000 11 }
	sbeArpTimeout 	OBJECT-TYPE   --oArpTimeout
			SYNTAX	INTEGER (1..1440)
			ACCESS	read-write
			STATUS	mandatory
		DESCRIPTION ""
			::= { sbeArp 1 }
	sbeArpTable 	OBJECT IDENTIFIER ::= { sbeArp 2 }
	  sbeArpEntry 	OBJECT IDENTIFIER ::= { sbeArpTable 1 }
	    sbeArpPhysAddress 	OBJECT-TYPE   --oArpPhysAddress
			SYNTAX	OCTET STRING
			ACCESS	read-only
			STATUS	mandatory
		DESCRIPTION ""
			::= { sbeArpEntry 1  }
	    sbeArpNetAddress 	OBJECT-TYPE   --oArpNetAddress
			SYNTAX	IpAddress
			ACCESS	read-only
			STATUS	mandatory
		DESCRIPTION ""
			::= { sbeArpEntry 2 }
	    sbeArpEntStatus 	OBJECT-TYPE   --oArpStatus
			SYNTAX	INTEGER {
				pending(1),
				dynamic(2),
				permanent(4)
				}
			ACCESS	read-only
			STATUS	mandatory
		DESCRIPTION ""
			::= { sbeArpEntry 3 }
	sbeArpType 	OBJECT-TYPE   --oArpType
			SYNTAX	INTEGER {
				normal(1),
				proxy(2)
				}
			ACCESS	read-write
			STATUS	mandatory
		DESCRIPTION ""
			::= { sbeArp 3 }
	sbeArpReqRcvd 	OBJECT-TYPE   --oArpReqRcvd
			SYNTAX	Counter
			ACCESS	read-only
			STATUS	mandatory
		DESCRIPTION ""
			::= { sbeArp 4 }
	sbeArpReqSent 	OBJECT-TYPE   --oArpReqSent
			SYNTAX	Counter
			ACCESS	read-only
			STATUS	mandatory
		DESCRIPTION ""
			::= { sbeArp 5 }
	sbeArpRspRcvd 	OBJECT-TYPE   --oArpRspRcvd
			SYNTAX	Counter
			ACCESS	read-only
			STATUS	mandatory
		DESCRIPTION ""
			::= { sbeArp 6 }
	sbeArpRspSent 	OBJECT-TYPE   --oArpRspSent
			SYNTAX	Counter
			ACCESS	read-only
			STATUS	mandatory
		DESCRIPTION ""
			::= { sbeArp 7 }
	sbeArpInErrs 	OBJECT-TYPE   --oArpInErrs
			SYNTAX	Counter
			ACCESS	read-only
			STATUS	mandatory
		DESCRIPTION ""
			::= { sbeArp 8 }
	sbeArpOutErrs 	OBJECT-TYPE   --oArpOutErrs
			SYNTAX	Counter
			ACCESS	read-only
			STATUS	mandatory
		DESCRIPTION ""
			::= { sbeArp 9 }
	sbeArpUnknownProtos 	OBJECT-TYPE   --oArpUnknownProtos
			SYNTAX	Counter
			ACCESS	read-only
			STATUS	mandatory
		DESCRIPTION ""
			::= { sbeArp 10 }

      sbeIpRoutingTable	OBJECT IDENTIFIER ::= { sbe4000 12 }
	sbeIpRouteEntry	OBJECT IDENTIFIER ::= { sbeIpRoutingTable 1 }
	  sbeIpRouteDestSubnet 	OBJECT-TYPE   --oIpRouteDestSubnet
			SYNTAX	IpAddress
			ACCESS	read-write
			STATUS	mandatory
		DESCRIPTION ""
			::= { sbeIpRouteEntry 2 }

      sbeProbe 	OBJECT IDENTIFIER ::= { sbe4000 13 }
	sbeProbeAddr 	OBJECT-TYPE   --oProbeAddress
			SYNTAX	OCTET STRING
			ACCESS	read-write
			STATUS	mandatory
		DESCRIPTION ""
			::= { sbeProbe 1 }
	sbeProbeData 	OBJECT-TYPE   --oProbeData
			SYNTAX	INTEGER
			ACCESS	read-write
			STATUS	mandatory
		DESCRIPTION ""
			::= { sbeProbe 2 }

      sbeIpAddrTable 	OBJECT IDENTIFIER ::= { sbe4000 14 }
	sbeIpAddrEntry 	OBJECT IDENTIFIER ::= { sbeIpAddrTable 1 }
	  sbeIpAddrMtu 	OBJECT-TYPE   --oIpAdEntMtu
			SYNTAX	INTEGER
			ACCESS	read-write
			STATUS	mandatory
		DESCRIPTION ""
			::= { sbeIpAddrEntry 1 }
	  sbeIpAddrSecurityType OBJECT-TYPE   --oIpAdEntSecurityType
			SYNTAX	INTEGER {
				none(1),
				basic(2)
				}
			ACCESS	read-write
			STATUS	mandatory
		DESCRIPTION ""
			::= { sbeIpAddrEntry 2 }
	  sbeIpAddrSecurityClass OBJECT-TYPE   --oIpAdEntSecurityClass
			SYNTAX	INTEGER
			ACCESS	read-write
			STATUS	mandatory
		DESCRIPTION ""
			::= { sbeIpAddrEntry 3 }
	  sbeIpAddrSecurityAuth OBJECT-TYPE   --oIpAdEntSecurityAuth
			SYNTAX	OCTET STRING
			ACCESS	read-write
			STATUS	mandatory
		DESCRIPTION ""
			::= { sbeIpAddrEntry 4 }
	  sbeIpAddrBcastAddr 	OBJECT-TYPE   --oIpAdEntBcastAddr
			SYNTAX	IpAddress
			ACCESS	read-write
			STATUS	mandatory
		DESCRIPTION ""
			::= { sbeIpAddrEntry 5 }
          sbeIpAdEntMetric      OBJECT-TYPE   --oIpAdEntMetric
                        SYNTAX  INTEGER (0..16)
                        ACCESS  read-write
                        STATUS  mandatory
		DESCRIPTION ""
                        ::= { sbeIpAddrEntry 6 }

      sbeEgp 	OBJECT IDENTIFIER ::= { sbe4000 15 }
	sbeEgpNeighTable OBJECT IDENTIFIER ::= { sbeEgp 1 }
	  sbeEgpNeighEntry OBJECT IDENTIFIER ::= { sbeEgpNeighTable 1 }
	    sbeEgpUptime OBJECT-TYPE   --oEgpUptime
			SYNTAX	TimeTicks
			ACCESS	read-only
			STATUS	mandatory
		DESCRIPTION ""
			::= { sbeEgpNeighEntry 1 }
	    sbeEgpFAS 	OBJECT-TYPE   --oEgpFAS
			SYNTAX	INTEGER
			ACCESS	read-only
			STATUS	mandatory
		DESCRIPTION ""
			::= { sbeEgpNeighEntry 2 }
	    sbeEgpSndSeq 	OBJECT-TYPE   --oEgpSndSeq
			SYNTAX	Counter
			ACCESS	read-only
			STATUS	mandatory
		DESCRIPTION ""
			::= { sbeEgpNeighEntry 3 }
	    sbeEgpRcvSeq 	OBJECT-TYPE   --oEgpRcvSeq
			SYNTAX	Counter
			ACCESS	read-only
			STATUS	mandatory
		DESCRIPTION ""
			::= { sbeEgpNeighEntry 4 }
	sbeEgpAdminStatus 	OBJECT-TYPE   --oEgpAdminStatus
			SYNTAX	INTEGER {
				off(1),
				on(2)
				}
			ACCESS	read-write
			STATUS	mandatory
		DESCRIPTION ""
			::= { sbeEgp 2 }
	sbeEgpASNumber 	OBJECT-TYPE   --oEgpASNumber
			SYNTAX	INTEGER (0..65535)
			ACCESS	read-write
			STATUS	mandatory
		DESCRIPTION ""
			::= { sbeEgp 3 }
	sbeEgpMetric 	OBJECT-TYPE   --oEgpMetric
			SYNTAX	INTEGER (0..255)
			ACCESS	read-write
			STATUS	mandatory
		DESCRIPTION ""
			::= { sbeEgp 4 }
	sbeEgpInErrMsgs 	OBJECT-TYPE   --oEgpInErrMsgs
			SYNTAX	Counter
			ACCESS	read-only
			STATUS	mandatory
		DESCRIPTION ""
			::= { sbeEgp 5 }
	sbeEgpOutErrMsgs 	OBJECT-TYPE   --oEgpOutErrMsgs
			SYNTAX	Counter
			ACCESS	read-only
			STATUS	mandatory
		DESCRIPTION ""
			::= { sbeEgp 6 }
	sbeEgpStateChanges 	OBJECT-TYPE   --oEgpStateChanges
			SYNTAX	Counter
			ACCESS	read-only
			STATUS	mandatory
		DESCRIPTION ""
			::= { sbeEgp 7 }
	sbeEgpLastChange 	OBJECT-TYPE   --oEgpLastChange
			SYNTAX	OCTET STRING
			ACCESS	read-only
			STATUS	mandatory
		DESCRIPTION ""
			::= { sbeEgp 8 }

      sbeRip 	OBJECT IDENTIFIER ::= { sbe4000 16 }
	sbeRipAdminStatus 	OBJECT-TYPE   --oRipAdminStatus
			SYNTAX	INTEGER {
				on(1),
				off(2)
				}
			ACCESS	read-write
			STATUS	mandatory
		DESCRIPTION ""
			::= { sbeRip 1 }
	sbeRipUpdateTimer 	OBJECT-TYPE   --oRipUpdateTime
			SYNTAX	TimeTicks
			ACCESS	read-write
			STATUS	mandatory
		DESCRIPTION ""
			::= { sbeRip 2 }
	sbeRipGateway 	OBJECT-TYPE   --oRipGateway
			SYNTAX	INTEGER {
				on(1),
				off(2)
				}
			ACCESS	read-write
			STATUS	mandatory
		DESCRIPTION ""
			::= { sbeRip 3 }
	sbeRipMetric 	OBJECT-TYPE   --oRipMetric
			SYNTAX	INTEGER (0..15)
			ACCESS	read-write
			STATUS	mandatory
		DESCRIPTION ""
			::= { sbeRip 4 }
	sbeRipNeighborTable	OBJECT IDENTIFIER ::= { sbeRip 5 }
	  sbeRipNeighborEntry 	OBJECT IDENTIFIER ::= { sbeRipNeighborTable 1 }
	    sbeRipNeighbor 	OBJECT-TYPE   --oRipNeighbor
			SYNTAX	IpAddress
			ACCESS	read-write
			STATUS	mandatory
		DESCRIPTION ""
			::= { sbeRipNeighborEntry 1 }
	sbeRipInCmdCnt	OBJECT-TYPE   --oRipInCmdCnt
			SYNTAX	Counter
			ACCESS	read-only
			STATUS	mandatory
		DESCRIPTION ""
			::= { sbeRip 6 }
	sbeRipInRspCnt	OBJECT-TYPE   --oRipInRspCnt
			SYNTAX	Counter
			ACCESS	read-only
			STATUS	mandatory
		DESCRIPTION ""
			::= { sbeRip 7 }
	sbeRipInErrors	OBJECT-TYPE   --oRipInErrors
			SYNTAX	Counter
			ACCESS	read-only
			STATUS	mandatory
		DESCRIPTION ""
			::= { sbeRip 8 }
	sbeRipOutCmdCnt	OBJECT-TYPE   --oRipOutCmdCnt
			SYNTAX	Counter
			ACCESS	read-only
			STATUS	mandatory
		DESCRIPTION ""
			::= { sbeRip 9 }
	sbeRipOutRspCount	OBJECT-TYPE   --oRipOutCmdCount
			SYNTAX	Counter
			ACCESS	read-only
			STATUS	mandatory
		DESCRIPTION ""
			::= { sbeRip 10 }

      sbeX25 		OBJECT IDENTIFIER ::= { sbe4000 17 }
-- X.25 addresses are represented as variable-length ASCII strings (length is
-- between 0 and 15, inclusive).

	sbeX25AtTable	OBJECT-TYPE
			SYNTAX	SEQUENCE OF Sbex25atentry
			ACCESS  read-write
			STATUS  mandatory
		DESCRIPTION ""
			::= { sbeX25 1  }
			-- Address translation table for X.25 interfaces.
			-- This is a superset of the standard address
			-- translation table; we keep two X.25 addresses
			-- per host because incoming and outgoing X.25
			-- addresses are not always the same.

	  sbeX25AtEntry	OBJECT-TYPE
			SYNTAX	SbeX25AtEntry
			ACCESS	read-write
			STATUS	mandatory
		DESCRIPTION ""
			::= { sbeX25AtTable 1 }

			SbeX25AtEntry ::= SEQUENCE {
			    sbeX25AtIfIndex	INTEGER,
			    sbeX25IpAddress	NetworkAddress,
			    sbeX25NetAddress1	OCTET STRING,
			    sbeX25NetAddress2	OCTET STRING
			    }
			-- Address translation entry for X.25 interfaces.
			-- The instance of an entry is the concatenation of
			-- the sbeX25AtIfIndex, the digit '1', and
			-- sbeX25IpAddress.

	  sbeX25AtIfIndex	OBJECT-TYPE   --oX25AtPort
			SYNTAX  INTEGER
			ACCESS  read-write
			STATUS  mandatory
		DESCRIPTION ""
			::= { sbeX25AtEntry 1 }
			-- Interface number (ifIndex) for which this 
			-- translation entry is valid.

	  sbeX25AtIpAddress OBJECT-TYPE   --oX25IpAddress
			SYNTAX  NetworkAddress
			ACCESS  read-write
			STATUS  mandatory
		DESCRIPTION ""
			::= { sbeX25AtEntry 2 }

	  sbeX25AtNetAddress1 OBJECT-TYPE   --oX25NetAddress1
			SYNTAX  OCTET STRING
			ACCESS  read-write
			STATUS  mandatory
		DESCRIPTION ""
			::= { sbeX25AtEntry 3 }
			-- X.25 address to use when calling this destination.
			-- (both X.25 addresses are checked when mapping an
			-- X.25 address to an IP address)

	  sbeX25AtNetAddress2 OBJECT-TYPE   --oX25NetAddress2
			SYNTAX  OCTET STRING
			ACCESS  read-write
			STATUS  mandatory
		DESCRIPTION ""
			::= { sbeX25AtEntry 4 }
			-- Alternate X.25 address to check when mapping an
			-- X.25 address to an IP address
	sbeX25SubnetParmTable	OBJECT-TYPE
			SYNTAX	SEQUENCE OF SbeX25SubnetParmEntry
			ACCESS  read-write
			STATUS  mandatory
		DESCRIPTION ""
			::= { sbeX25 2 }
			-- Per-network parameters for IP networks attached
			-- via X.25 interface.

	  sbeX25SubnetParmEntry	OBJECT-TYPE
			SYNTAX	SbeX25SubnetParmEntry
			ACCESS	read-write
			STATUS	mandatory
		DESCRIPTION ""
			::= { sbeX25SubnetParmTable 1 }

			SbeX25SubnetParmEntry ::= SEQUENCE {
			    sbeX25SubnetAddr	IpAddress,
			    sbeX25Facility	INTEGER,
			    sbeX25PktNegot	INTEGER,
			    sbeX25WindowNegot	INTEGER
			    }
			-- X.25-specific parameters for this IP network.
			-- The instance of an entry is the IP network
			-- (or subnet) number: the host part of the IP
			-- address is all zeroes.

	    sbeX25SubnetAddr 	OBJECT-TYPE   --oX25SubnetAddr
			SYNTAX	IpAddress
			ACCESS	read-write
			STATUS	mandatory
		DESCRIPTION ""
			::= { sbeX25SubnetParmEntry 1 }
			-- Network/subnet number of IP network.

	    sbeX25Facility 	OBJECT-TYPE   --oX25Facility
			SYNTAX	INTEGER {
				none(1),
				ddn-standard(2)
				}
			ACCESS	read-write
			STATUS	mandatory
		DESCRIPTION ""
			::= { sbeX25SubnetParmEntry 2 }
			-- selects whether DDN Standard Mode facility is
			-- included in call requests.

	    sbeX25PktNegot 	OBJECT-TYPE   --oX25PktNegot
			SYNTAX	INTEGER
			ACCESS	read-write
			STATUS	mandatory
		DESCRIPTION ""
			::= { sbeX25SubnetParmEntry 3 }
			-- specifies value for Packet Size Negotiation Facility
			-- (power of 2 between 16 and 1024), or zero if Packet
			-- Size Negotiation Facility is not to be used.

	    sbeX25WindowNegot 	OBJECT-TYPE   --oX25WindowNegot
			SYNTAX	INTEGER
			ACCESS	read-write
			STATUS	mandatory
		DESCRIPTION ""
			::= { sbeX25SubnetParmEntry 4 }
			-- specifies value for Window Size Negotiation Facility
			-- (between 1 and 127 inclusive), or zero if Window
			-- Size Negotiation Facility is not to be used.

	sbeX25PortParmTable	OBJECT-TYPE
			SYNTAX	SEQUENCE OF SbeX25PortParmEntry
			ACCESS  read-write
			STATUS  mandatory
		DESCRIPTION ""
			::= { sbeX25 3 }
			-- Per-port parameters for X.25 interfaces.

	  sbeX25PortParmEntry	OBJECT-TYPE
			SYNTAX	SbeX25PortParmEntry
			ACCESS	read-write
			STATUS	mandatory
		DESCRIPTION ""
			::= { sbeX25PortParmTable 1 }

			SbeX25PortParmEntry ::= SEQUENCE {
			    sbeX25PortParmIndex	INTEGER,
			    sbeX25AddrMode	INTEGER,
			    sbeX25PktSize	INTEGER,
			    sbeX25PktWind	INTEGER,
			    sbeX25SvcNumber	INTEGER,
			    sbeX25SvcBase	INTEGER,
			    sbeX25ExtendClr	INTEGER,
			    sbeX25ExtendSeq	INTEGER,
			    sbeX25IdleMin	TimeTicks,
			    sbeX25IdleMax	TimeTicks,
			    sbeX25IdleScale	TimeTicks
			    }
			-- X.25 (packet level) parameters for an X.25 interface.
			-- The instance of an entry is the port number.

	    sbeX25PortParmIndex 	OBJECT-TYPE   --oX25PortParmIndex
			SYNTAX	INTEGER
			ACCESS	read-only
			STATUS	mandatory
		DESCRIPTION ""
			::= { sbeX25PortParmEntry 1 }

	    sbeX25AddrMode 	OBJECT-TYPE   --oX25AddrMode
			SYNTAX	INTEGER {
				table(1),	-- use translation table
						-- (sbeX25AtTable)
				ddn(2),		-- use DDN mapping algorithm
				bfe(3)		-- use Blacker algorithm
				}
			ACCESS	read-write
			STATUS	mandatory
		DESCRIPTION ""
			::= { sbeX25PortParmEntry 2 }
			-- specifies address translation technique.

	    sbeX25PktSize 	OBJECT-TYPE   --oX25PktSize
			SYNTAX	INTEGER
			ACCESS	read-write
			STATUS	mandatory
		DESCRIPTION ""
			::= { sbeX25PortParmEntry 3 }
			-- specifies default data packet size for this port.

	    sbeX25PktWind 	OBJECT-TYPE   --oX25PktWindow
			SYNTAX	INTEGER
			ACCESS	read-write
			STATUS	mandatory
		DESCRIPTION ""
			::= { sbeX25PortParmEntry 4 }
			-- specifies default packet window size for this port.

	    sbeX25SvcNumber 	OBJECT-TYPE   --oX25SvcNumber
			SYNTAX	INTEGER
			ACCESS	read-write
			STATUS	mandatory
		DESCRIPTION ""
			::= { sbeX25PortParmEntry 5 }
			-- specifies maximum number of switched virtual
			-- circuits to be used on this port.

	    sbeX25SvcBase 	OBJECT-TYPE   --oX25SvcBase
			SYNTAX	INTEGER
			ACCESS	read-write
			STATUS	mandatory
		DESCRIPTION ""
			::= { sbeX25PortParmEntry 6 }
			-- specifies lowest Logical Channel Identifier
			-- to be used for switched virtual circuits.

	    sbeX25ExtendClr 	OBJECT-TYPE   --oX25ExtendClr
			SYNTAX	INTEGER {
				on(1),	-- use/accept extended clear format
				off(2)	-- disallow extended clear format
				}
			ACCESS	read-write
			STATUS	mandatory
		DESCRIPTION ""
			::= { sbeX25PortParmEntry 7 }
			-- specifies whether extended format for call clearing
			-- packets (as defined by X.25-1984) is permitted

	    sbeX25ExtendSeq 	OBJECT-TYPE   --oX25ExtendSeq
			SYNTAX	INTEGER {
				normal(1),	-- modulo-8 sequence numbers
				extended(2)	-- modulo-128 sequence numbers
				}
			ACCESS	read-write
			STATUS	mandatory
		DESCRIPTION ""
			::= { sbeX25PortParmEntry 8 }

	    sbeX25IdleMin 	OBJECT-TYPE   --oX25IdleMin
			SYNTAX	TimeTicks
			ACCESS	read-write
			STATUS	mandatory
		DESCRIPTION ""
			::= { sbeX25PortParmEntry 9 }
			-- minimum idle time for closing circuits; a circuit
			-- will not be cleared until it has been idle (no data
			-- has been sent or received) for at least this amount
			-- of time.

	    sbeX25IdleMax 	OBJECT-TYPE   --oX25IdleMax
			SYNTAX	TimeTicks
			ACCESS	read-write
			STATUS	mandatory
		DESCRIPTION ""
			::= { sbeX25PortParmEntry 10 }
			-- maximum idle time for closing circuits; a circuit
			-- will be cleared when its idle time exceeds this
			-- value.

	    sbeX25IdleScale 	OBJECT-TYPE   --oX25IdleScale
			SYNTAX	TimeTicks
			ACCESS	read-write
			STATUS	mandatory
		DESCRIPTION ""
			::= { sbeX25PortParmEntry 11 }
			-- scale factor for idle timeout: a circuit will
			-- be cleared when it has been idle for sbeX25IdleMin
			-- plus sbeX25IdleScale times the number of available
			-- circuits.

	sbeX25PktStatTable	OBJECT-TYPE
			SYNTAX	SEQUENCE OF SbeX25PktStatEntry
			ACCESS  read-only
			STATUS  mandatory
		DESCRIPTION ""
			::= { sbeX25 4 }
			-- Per-port packet statistics for X.25 interfaces.

	  sbeX25PktStatEntry	OBJECT-TYPE
			SYNTAX	SbeX25PktStatEntry
			ACCESS	read-write
			STATUS	mandatory
		DESCRIPTION ""
			::= { sbeX25PktStatTable 1 }
			-- X.25 packet level statistics for an X.25 interface.
			-- The instance of an entry is the port number.

			SbeX25PktStatEntry ::= SEQUENCE {
			    sbeX25PktIndex	INTEGER,
			    sbeX25RcvDiag 	Counter,
			    sbeX25RcvRestartReq Counter,
			    sbeX25RcvRestartConf Counter,
			    sbeX25RcvCallReq 	Counter,
			    sbeX25RcvCallAcc 	Counter,
			    sbeX25RcvClrReq	Counter,
			    sbeX25RcvClrConf 	Counter,
			    sbeX25RcvResetReq 	Counter,
			    sbeX25RcvResetConf 	Counter,
			    sbeX25RcvInt 	Counter,
			    sbeX25RcvIntConf 	Counter,
			    sbeX25RcvRR 	Counter,
			    sbeX25RcvRNR 	Counter,
			    sbeX25RcvData 	Counter,
			    sbeX25XmtDiag 	Counter,
			    sbeX25XmtRestartReq Counter,
			    sbeX25XmtRestartConf Counter,
			    sbeX25XmtCallReq 	Counter,
			    sbeX25XmtCallAcc 	Counter,
			    sbeX25XmtClrReq	Counter,
			    sbeX25XmtClrConf 	Counter,
			    sbeX25XmtResetReq 	Counter,
			    sbeX25XmtResetConf 	Counter,
			    sbeX25XmtInt 	Counter,
			    sbeX25XmtIntConf 	Counter,
			    sbeX25XmtRR 	Counter,
			    sbeX25XmtRNR 	Counter,
			    sbeX25XmtData 	Counter
			    }
	    sbeX25PktIndex 	OBJECT-TYPE   --oX25PktIndex
			SYNTAX	INTEGER
			ACCESS	read-only
			STATUS	mandatory
		DESCRIPTION ""
			::= { sbeX25PktStatEntry 1 }
			-- Port number of this X.25 interface.

	    sbeX25RcvDiag 	OBJECT-TYPE   --oX25RcvDiag
			SYNTAX	Counter
			ACCESS	read-only
			STATUS	mandatory
		DESCRIPTION ""
			::= { sbeX25PktStatEntry 2 }
			-- Number of Diagnostic packets received on this port.

	    sbeX25RcvRestartReq 	OBJECT-TYPE   --oX25RcvRestartReq
			SYNTAX	Counter
			ACCESS	read-only
			STATUS	mandatory
		DESCRIPTION ""
			::= { sbeX25PktStatEntry 3 }
			-- Number of Restart Request (Restart Indication)
			-- packets received on this port.

	    sbeX25RcvRestartConf 	OBJECT-TYPE   --oX25RcvRestartConf
			SYNTAX	Counter
			ACCESS	read-only
			STATUS	mandatory
		DESCRIPTION ""
			::= { sbeX25PktStatEntry 4 }
			-- Number of Restart Confirmation packets received
			-- on this port.

	    sbeX25RcvCallReq 	OBJECT-TYPE   --oX25RcvCallReq
			SYNTAX	Counter
			ACCESS	read-only
			STATUS	mandatory
		DESCRIPTION ""
			::= { sbeX25PktStatEntry 5 }
			-- Number of Call Request (Incoming Call) packets
			-- received on this port.

	    sbeX25RcvCallAcc 	OBJECT-TYPE   --oX25RcvCallAcc
			SYNTAX	Counter
			ACCESS	read-only
			STATUS	mandatory
		DESCRIPTION ""
			::= { sbeX25PktStatEntry 6 }
			-- Number of Call Accepted (Call Connected) packets
			-- received on this port.

	    sbeX25RcvClrReq	OBJECT-TYPE   --oX25RcvClrReq
			SYNTAX	Counter
			ACCESS	read-only
			STATUS	mandatory
		DESCRIPTION ""
			::= { sbeX25PktStatEntry 7 }
			-- Number of Clear Request (Clear Indication) packets
			-- received on this port.

	    sbeX25RcvClrConf 	OBJECT-TYPE   --oX25RcvClrConf
			SYNTAX	Counter
			ACCESS	read-only
			STATUS	mandatory
		DESCRIPTION ""
			::= { sbeX25PktStatEntry 8 }
			-- Number of Clear Confirmation packets received on
			-- this port.

	    sbeX25RcvResetReq 	OBJECT-TYPE   --oX25RcvResetReq
			SYNTAX	Counter
			ACCESS	read-only
			STATUS	mandatory
		DESCRIPTION ""
			::= { sbeX25PktStatEntry 9 }
			-- Number of Reset Request (Reset Indication) packets
			-- received on this port.

	    sbeX25RcvResetConf 	OBJECT-TYPE   --oX25RcvResetConf
			SYNTAX	Counter
			ACCESS	read-only
			STATUS	mandatory
		DESCRIPTION ""
			::= { sbeX25PktStatEntry 10 }
			-- Number of Reset Confirmation packets received on
			-- this port.

	    sbeX25RcvInt 	OBJECT-TYPE   --oX25RcvInt
			SYNTAX	Counter
			ACCESS	read-only
			STATUS	mandatory
		DESCRIPTION ""
			::= { sbeX25PktStatEntry 11 }
			-- Number of Interrupt packets received on this port.

	    sbeX25RcvIntConf 	OBJECT-TYPE   --oX25RcvIntConf
			SYNTAX	Counter
			ACCESS	read-only
			STATUS	mandatory
		DESCRIPTION ""
			::= { sbeX25PktStatEntry 12 }
			-- Number of Interrupt COnfirmation packets received
			-- on this port.

	    sbeX25RcvRR 	OBJECT-TYPE   --oX25RcvRR
			SYNTAX	Counter
			ACCESS	read-only
			STATUS	mandatory
		DESCRIPTION ""
			::= { sbeX25PktStatEntry 13 }
			-- Number of RR [Receive Ready] packets received on
			-- this port.

	    sbeX25RcvRNR 	OBJECT-TYPE   --oX25RcvRNR
			SYNTAX	Counter
			ACCESS	read-only
			STATUS	mandatory
		DESCRIPTION ""
			::= { sbeX25PktStatEntry 14 }
			-- Number of RNR [Receive Not Ready] packets received
			-- on this port.

	    sbeX25RcvData 	OBJECT-TYPE   --oX25RcvData
			SYNTAX	Counter
			ACCESS	read-only
			STATUS	mandatory
		DESCRIPTION ""
			::= { sbeX25PktStatEntry 15 }
			-- Number of Data packets received on this port.

	    sbeX25XmtDiag 	OBJECT-TYPE   --oX25XmtDiag
			SYNTAX	Counter
			ACCESS	read-only
			STATUS	mandatory
		DESCRIPTION ""
			::= { sbeX25PktStatEntry 16 }
			-- Number of Diagnostic packets transmitted on this
			-- port.

	    sbeX25XmtRestartReq 	OBJECT-TYPE   --oX25XmtRestartReq
			SYNTAX	Counter
			ACCESS	read-only
			STATUS	mandatory
		DESCRIPTION ""
			::= { sbeX25PktStatEntry 17 }
			-- Number of Restart Request (Restart Indication)
			-- packets transmitted on this port.

	    sbeX25XmtRestartConf 	OBJECT-TYPE   --oX25XmtRestartConf
			SYNTAX	Counter
			ACCESS	read-only
			STATUS	mandatory
		DESCRIPTION ""
			::= { sbeX25PktStatEntry 18 }
			-- Number of Restart Confirmation packets transmitted
			-- on this port.

	    sbeX25XmtCallReq 	OBJECT-TYPE   --oX25XmtCallReq
			SYNTAX	Counter
			ACCESS	read-only
			STATUS	mandatory
		DESCRIPTION ""
			::= { sbeX25PktStatEntry 19 }
			-- Number of Call Request (Incoming Call) packets
			-- transmitted on this port.

	    sbeX25XmtCallAcc 	OBJECT-TYPE   --oX25XmtCallAcc
			SYNTAX	Counter
			ACCESS	read-only
			STATUS	mandatory
		DESCRIPTION ""
			::= { sbeX25PktStatEntry 20 }
			-- Number of Call Accepted (Call Connected) packets
			-- transmitted on this port.

	    sbeX25XmtClrReq	OBJECT-TYPE   --oX25XmtClrReq
			SYNTAX	Counter
			ACCESS	read-only
			STATUS	mandatory
		DESCRIPTION ""
			::= { sbeX25PktStatEntry 21 }
			-- Number of Clear Request (Clear Indication) packets
			-- transmitted on this port.

	    sbeX25XmtClrConf 	OBJECT-TYPE   --oX25XmtClrConf
			SYNTAX	Counter
			ACCESS	read-only
			STATUS	mandatory
		DESCRIPTION ""
			::= { sbeX25PktStatEntry 22 }
			-- Number of Clear Confirmation packets transmitted
			-- on this port.

	    sbeX25XmtResetReq 	OBJECT-TYPE   --oX25XmtResetReq
			SYNTAX	Counter
			ACCESS	read-only
			STATUS	mandatory
		DESCRIPTION ""
			::= { sbeX25PktStatEntry 23 }
			-- Number of Reset Request (Reset Indication) packets
			-- transmitted on this port.

	    sbeX25XmtResetConf 	OBJECT-TYPE   --oX25XmtResetConf
			SYNTAX	Counter
			ACCESS	read-only
			STATUS	mandatory
		DESCRIPTION ""
			::= { sbeX25PktStatEntry 24 }
			-- Number of Reset Confirmation packets transmitted
			-- on this port.

	    sbeX25XmtInt 	OBJECT-TYPE   --oX25XmtInt
			SYNTAX	Counter
			ACCESS	read-only
			STATUS	mandatory
		DESCRIPTION ""
			::= { sbeX25PktStatEntry 25 }
			-- Number of Interrupt packets transmitted on this
			-- port.

	    sbeX25XmtIntConf 	OBJECT-TYPE   --oX25XmtIntConf
			SYNTAX	Counter
			ACCESS	read-only
			STATUS	mandatory
		DESCRIPTION ""
			::= { sbeX25PktStatEntry 26 }
			-- Number of Interrupt COnfirmation packets
			-- transmitted on this port.

	    sbeX25XmtRR 	OBJECT-TYPE   --oX25XmtRR
			SYNTAX	Counter
			ACCESS	read-only
			STATUS	mandatory
		DESCRIPTION ""
			::= { sbeX25PktStatEntry 27 }
			-- Number of RR [Receive Ready] packets transmitted
			-- on this port.

	    sbeX25XmtRNR 	OBJECT-TYPE   --oX25XmtRNR
			SYNTAX	Counter
			ACCESS	read-only
			STATUS	mandatory
		DESCRIPTION ""
			::= { sbeX25PktStatEntry 28 }
			-- Number of RNR [Receive Not Ready] packets
			-- transmitted on this port.

	    sbeX25XmtData 	OBJECT-TYPE   --oX25XmtData
			SYNTAX	Counter
			ACCESS	read-only
			STATUS	mandatory
		DESCRIPTION ""
			::= { sbeX25PktStatEntry 29 }
			-- Number of Data packets transmitted on this port.

      sbeIp 		OBJECT IDENTIFIER ::= { sbe4000 18 }
        sbeIpSrcRouting  OBJECT-TYPE   --oIpSrcRouting
			SYNTAX  INTEGER {
                           on(1),  --
                           off(2)  -- Discard source-routed IP packets
                        }
                        ACCESS read-write
                        STATUS  mandatory
		DESCRIPTION ""
                        ::= { sbeIp 1 }
        sbeIpFiltTable  OBJECT IDENTIFIER ::= { sbeIp 2 }
          sbeIpFiltEntry  OBJECT IDENTIFIER ::= { sbeIpFiltTable 1 }
            sbeIpFiltDAddr  OBJECT-TYPE  --oIpFiltEntDAddr
                        SYNTAX  IpAddress
                        ACCESS  read-write
                        STATUS  mandatory
		DESCRIPTION ""
                        ::= { sbeIpFiltEntry 1 }
                        -- Destination Address
            sbeIpFiltDNetMask  OBJECT-TYPE  --oIpFiltEntDNetMask
                        SYNTAX  IpAddress
                        ACCESS  read-write
                        STATUS  mandatory
		DESCRIPTION ""
                        ::= { sbeIpFiltEntry 2 }
                        -- Destination Network Mask
            sbeIpFiltSAddr  OBJECT-TYPE  --oIpFiltEntSAddr
                        SYNTAX  IpAddress
                        ACCESS  read-write
                        STATUS  mandatory
		DESCRIPTION ""
                        ::= { sbeIpFiltEntry 3 }
                        -- Source Address
            sbeIpFiltSNetMask  OBJECT-TYPE  --oIpFiltEntSNetMask
                        SYNTAX  IpAddress
                        ACCESS  read-write
                        STATUS  mandatory
		DESCRIPTION ""
                        ::= { sbeIpFiltEntry 4 }
                        -- Source Network Mask
            sbeIpFiltParm  OBJECT-TYPE  --oIpFiltEntParm
                        SYNTAX  OCTET STRING
                        ACCESS  read-write
                        STATUS  mandatory
		DESCRIPTION ""
                        ::= { sbeIpFiltEntry 5 }
                        -- Filter parameters;
                          -- Byte 0 is Operation 1
                             -- [0,1,2] = [None, !,=]
                          --Bytes 1,2 is Protocol
                          --Byte 3 is Operation 2
                             -- [0,1,2,3,4] = [None, !, <, >, =]
                          -- Bytes 4,5 is port number
            sbeIpFiltDisp  OBJECT-TYPE  --oIpFiltEntDisp
                        SYNTAX  INTEGER {
                                 drop(1),  -- Discard
                                 forward(2)  -- Keep it
                                }
                        ACCESS  read-write
                        STATUS  mandatory
		DESCRIPTION ""
                        ::= { sbeIpFiltEntry 6 }
                        -- Destination Address
      sbeDn 		OBJECT IDENTIFIER ::= { sbe4000 19 }
	sbeDnNumber	OBJECT-TYPE  --oDnNumCirc
			SYNTAX  INTEGER
			ACCESS read-only
			STATUS mandatory
		DESCRIPTION ""
                        ::= { sbeDn 1 }
			-- Number of DECNET circuits

	sbeDnID		OBJECT-TYPE  --oDnID
			SYNTAX  INTEGER
			ACCESS read-write
			STATUS mandatory
		DESCRIPTION ""
                        ::= { sbeDn 2 }
			-- Node ID;  Least 10 bits identify the node,
			-- six bits above that identify the area.

	sbeDnMaxNode	OBJECT-TYPE  --oDnNN
			SYNTAX  INTEGER (1..1023)
			ACCESS read-write
			STATUS mandatory
		DESCRIPTION ""
                        ::= { sbeDn 3 }
			-- Maximum node number permitted in the local area


	sbeDnMaxArea	OBJECT-TYPE  --oDnNA
			SYNTAX  INTEGER (1..63)
			ACCESS read-write
			STATUS mandatory
		DESCRIPTION ""
                        ::= { sbeDn 4 }
			-- Maximum area number permitted

	sbeDnMaxRtr	OBJECT-TYPE  --oDnNBRA
			SYNTAX  INTEGER (1..64)
			ACCESS read-write
			STATUS mandatory
		DESCRIPTION ""
                        ::= { sbeDn 5 }
			-- Maximum number of adjacent routers 

	sbeDnMaxEndNode	OBJECT-TYPE  --oDnNBEA
			SYNTAX  INTEGER (1..1023)
			ACCESS read-write
			STATUS mandatory
		DESCRIPTION ""
                        ::= { sbeDn 6 }
			-- Maximum number of broadcast endnode adjacencies

	sbeDnMaxLocHop	OBJECT-TYPE  --oDnMaxh
			SYNTAX  INTEGER (1..30)
			ACCESS read-write
			STATUS mandatory
		DESCRIPTION ""
                        ::= { sbeDn 7 }
			-- Maximum number of hops allowed within this area

	sbeDnMaxLocCost	OBJECT-TYPE  --oDnMaxc
			SYNTAX  INTEGER (1..1022)
			ACCESS read-write
			STATUS mandatory
		DESCRIPTION ""
                        ::= { sbeDn 8 }
			-- Maximum cost allowed on a path within this area

	sbeDnMaxVisit	OBJECT-TYPE  --oDnMaxv
			SYNTAX  INTEGER (1..63)
			ACCESS read-write
			STATUS mandatory
		DESCRIPTION ""
                        ::= { sbeDn 9 }
			-- Maximum number of node visits allowed for a packet

	sbeDnMaxForHop	OBJECT-TYPE  --oDnAMaxh
			SYNTAX  INTEGER (1..30)
			ACCESS read-write
			STATUS mandatory
		DESCRIPTION ""
                        ::= { sbeDn 10 }
			-- Maximum number of hops allowed to another area

	sbeDnMaxForCost	OBJECT-TYPE  --oDnAMaxc
			SYNTAX  INTEGER (1..1022)
			ACCESS read-write
			STATUS mandatory
		DESCRIPTION ""
                        ::= { sbeDn 11 }
			-- Maximum cost allowed on a path to another area

	sbeDnBCT1		OBJECT-TYPE  --oDnBCT1
			SYNTAX  TimeTicks
			ACCESS read-write
			STATUS mandatory
		DESCRIPTION ""
                        ::= { sbeDn 12 }
			-- Interval between retranmissions of routing
			-- database updates on Broadcast Address

	sbeDnT1		OBJECT-TYPE  --oDnT1
			SYNTAX  TimeTicks
			ACCESS read-write
			STATUS mandatory
		DESCRIPTION ""
                        ::= { sbeDn 13 }
			-- Interval between retranmissions of routing
			-- database updates  non-broadcast

        sbeDnMsgLev     OBJECT-TYPE  --oDnMsgLevel
			SYNTAX  INTEGER (1..7)
			ACCESS read-write
			STATUS mandatory
		DESCRIPTION ""
			::= { sbeDn 14 }
			-- Message level for generation of trap messages
			-- describing DECNET operational phenonomena
			-- See "Trap level" for description

	sbeDnNodeState	OBJECT-TYPE  --oDnNodeState
			SYNTAX  INTEGER {
			off(1),
			level1(2),
			level2(3)
			}
			ACCESS read-write
			STATUS mandatory
		DESCRIPTION ""
                        ::= { sbeDn 15 }
			-- Operational state of the node 

	sbeDnUnreach	OBJECT-TYPE  --oDnNodeUnreach
			SYNTAX  Counter
			ACCESS read-only
			STATUS mandatory
		DESCRIPTION ""
                        ::= { sbeDn 16 }
			-- Packets dropped due to node unreachable

	sbeDnVisitXcd	OBJECT-TYPE  --oDnVisitExceed
			SYNTAX  Counter
			ACCESS read-only
			STATUS mandatory
		DESCRIPTION ""
                        ::= { sbeDn 17 }
			-- Packets dropped due to visits exceeded

	sbeDnBadNode	OBJECT-TYPE  --oDnNodeNumIllegal
			SYNTAX  Counter
			ACCESS read-only
			STATUS mandatory
		DESCRIPTION ""
                        ::= { sbeDn 18 }
			-- Packets dropped due to illegal node number

	sbeDnPktOsize	OBJECT-TYPE  --oDnOversizePack
			SYNTAX  Counter
			ACCESS read-only
			STATUS mandatory
		DESCRIPTION ""
                        ::= { sbeDn 19 }
			-- Packets dropped due to oversize packet

	sbeDnFmtErr	OBJECT-TYPE  --oDnPackFormat
			SYNTAX  Counter
			ACCESS read-only
			STATUS mandatory
		DESCRIPTION ""
                        ::= { sbeDn 20 }
			-- Packets dropped due to packet format error

        sbeDnCktTable  OBJECT IDENTIFIER ::= { sbeDn 21 }
          sbeDnCktEntry  OBJECT IDENTIFIER ::= { sbeDnCktTable 1 }
            sbeDnCktIndex  OBJECT-TYPE  --oDnCircuitIndex
                        SYNTAX  INTEGER
                        ACCESS  read-only
                        STATUS  mandatory
		DESCRIPTION ""
                        ::= { sbeDnCktEntry 1 }
                        -- Circuit number

            sbeDnCktStatus  OBJECT-TYPE  --oDnAdmStatus
                        SYNTAX  INTEGER {
				on(1),
				off(2)
			}
                        ACCESS  read-write
                        STATUS  mandatory
		DESCRIPTION ""
                        ::= { sbeDnCktEntry 2 }
                        -- Administrative DECNET state of this circuit

            sbeDnCktState  OBJECT-TYPE  --oDnState
                        SYNTAX  INTEGER {
				up(1),
				down(2),
				shut(3),
				start(4),
				test(5)
			}
                        ACCESS  read-only
                        STATUS  mandatory
		DESCRIPTION ""
                        ::= { sbeDnCktEntry 3 }
                        -- Operational DECNET state of this circuit

            sbeDnCktCost  OBJECT-TYPE  --oDnCost
                        SYNTAX  INTEGER (1..1022)
                        ACCESS  read-write
                        STATUS  mandatory
		DESCRIPTION ""
                        ::= { sbeDnCktEntry 4 }
                        -- Administrative circuit cost

            sbeDnMaxRtr  OBJECT-TYPE  --oDnMaxRouters
                        SYNTAX  INTEGER (1..32)
                        ACCESS  read-write
                        STATUS  mandatory
		DESCRIPTION ""
                        ::= { sbeDnCktEntry 5 }
                        -- Maximum number of routers that can be
			-- communicated with over this circuit

            sbeDnHelloInt  OBJECT-TYPE  --oDnHelloInterval
                        SYNTAX  TimeTicks
                        ACCESS  read-write
                        STATUS  mandatory
		DESCRIPTION ""
                        ::= { sbeDnCktEntry 6 }
                        -- Interval between transmission of Router Hello
			-- messages to other DECNET routers on this circuit

            sbeDnRtrPriority  OBJECT-TYPE  --oDnRouterPrio
                        SYNTAX  INTEGER (0..255)
                        ACCESS  read-write
                        STATUS  mandatory
		DESCRIPTION ""
                        ::= { sbeDnCktEntry 7 }
                        -- Priority of this Decnet router to become
			-- designated router on this circuit.

            sbeDnDesRtrID  OBJECT-TYPE  --oDnDesRouterId
                        SYNTAX  INTEGER
                        ACCESS  read-write
                        STATUS  mandatory
		DESCRIPTION ""
                        ::= { sbeDnCktEntry 8 }
			-- ID of router which is designated router on
			-- this circuit.  Lower 10 bits is node number,
			-- six bits above that are area number.

            sbeDnDesRtrPrio  OBJECT-TYPE  --oDnDesRouterPrio
                        SYNTAX  INTEGER (0..255)
                        ACCESS  read-write
                        STATUS  mandatory
		DESCRIPTION ""
                        ::= { sbeDnCktEntry 9 }
			-- Priority of router which is designated router on
			-- this circuit.  

            sbeDnTrnPktRec  OBJECT-TYPE  --oDnTranPackRec
                        SYNTAX  Counter
                        ACCESS  read-only
                        STATUS  mandatory
		DESCRIPTION ""
                        ::= { sbeDnCktEntry 10 }
			-- Number of transit packets received on
			-- this circuit.

            sbeDnTrnPktSnd  OBJECT-TYPE  --oDnTranPackSnd
                        SYNTAX  Counter
                        ACCESS  read-only
                        STATUS  mandatory
		DESCRIPTION ""
                        ::= { sbeDnCktEntry 11 }
			-- Number of transit packets sent on
			-- this circuit.

            sbeDnEndNodePktRec  OBJECT-TYPE  --oDnEndNodePackRec
                        SYNTAX  Counter
                        ACCESS  read-only
                        STATUS  mandatory
		DESCRIPTION ""
                        ::= { sbeDnCktEntry 12 }
			-- Number of end-node packets received on
			-- this circuit.

            sbeDnEndNodePktSnd  OBJECT-TYPE  --oDnEndNodePackSnd
                        SYNTAX  Counter
                        ACCESS  read-only
                        STATUS  mandatory
		DESCRIPTION ""
                        ::= { sbeDnCktEntry 13 }
			-- Number of end-node packets sent on
			-- this circuit.

            sbeDnCktDown  OBJECT-TYPE  --oDnCircuitDown
                        SYNTAX  Counter
                        ACCESS  read-only
                        STATUS  mandatory
		DESCRIPTION ""
                        ::= { sbeDnCktEntry 14 }
			-- Number of "circuit down" events noted on
			-- this circuit.

END
