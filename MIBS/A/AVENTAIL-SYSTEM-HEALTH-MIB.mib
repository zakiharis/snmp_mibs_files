-- File Name : AVENTAIL-SYSTEM-HEALTH

AVENTAIL-SYSTEM-HEALTH-MIB	DEFINITIONS ::= BEGIN
	IMPORTS
		aventail
			FROM AVENTAIL-MIB
		OBJECT-TYPE, Integer32, NOTIFICATION-TYPE, enterprises, MODULE-IDENTITY
			FROM SNMPv2-SMI;

	aventailSystemHealth MODULE-IDENTITY
             LAST-UPDATED      "200409071432Z" 
             ORGANIZATION      "Aventail"
             CONTACT-INFO       "email:   support@aventail.com"
             DESCRIPTION     "This Aventail MIB provides System Health Info"
        	::= {aventail 2}

	authenticatedUsers	OBJECT IDENTIFIER
		::=  {  aventailSystemHealth  1  }

	connectionUtilization	OBJECT IDENTIFIER
		::=  {  aventailSystemHealth  2  }

	cpuUtilization	OBJECT-TYPE	
		SYNTAX			Integer32
		MAX-ACCESS	read-only
		STATUS			current
		DESCRIPTION	"The current CPU percent utilization of the sum of \
		                             CPUs on the single node."
		::=  {  aventailSystemHealth  3  }

	memoryTotalUtilization	OBJECT IDENTIFIER
		::=  {  aventailSystemHealth  4  }
		
	ramUtilization	OBJECT-TYPE	
		SYNTAX			Integer32
		MAX-ACCESS	read-only
		STATUS			current
		DESCRIPTION	"The current virtual memory (RAM )  percentage being utilized."
		::=  {  memoryTotalUtilization  1  }

	swapUtilization	OBJECT-TYPE	
		SYNTAX			Integer32
		MAX-ACCESS	read-only
		STATUS			current
		DESCRIPTION	"The current virtual memory (Swap) percentage  being utilized."
		::=  {  memoryTotalUtilization  2  }

	bandwidthUtilization	OBJECT IDENTIFIER
		::=  {  aventailSystemHealth  5  }

	cpuCapacityWarning	NOTIFICATION-TYPE
		STATUS			current
		DESCRIPTION	"The heuristically determined percentage of cpu capacity \
		                             utilization of a single node system has exceeded the 90% \
		                             of the cpu capacity. This capacity is the cpuCapacityUtilization \
		                             for single node systems. "
		::=  {  aventailSystemHealth  6  }

	memoryCapacityWarning	NOTIFICATION-TYPE
		STATUS			current
		DESCRIPTION	"The heuristically determined percentage of memory \
		                            capacity utilization of a single node system has exceeded \
		                            the 90% of the memory capacity. This capacity is the \
		                            memoryCapacityUtilization for single node systems."
		::=  {  aventailSystemHealth  7  }

	userLimitWarning	NOTIFICATION-TYPE
		STATUS			current
		DESCRIPTION	"Notification is generated if the concurrent number \
						of authenticated users on single node system has reached \
		                             the 90 % of the license capacity limit. "
		::=  {  aventailSystemHealth  8  }

	currentlyLoggedIn	OBJECT-TYPE	
		SYNTAX			Integer32
		MAX-ACCESS	read-only
		STATUS			current
		DESCRIPTION	"Number of currently authenticated users serviced \
		                            by AVPN , EW & NG"
		::=  {  authenticatedUsers  1  }

	peakLoggedIn	OBJECT-TYPE	
		SYNTAX			Integer32
		MAX-ACCESS	read-only
		STATUS			current
		DESCRIPTION	"The maximum number of concurrent users \
		                            serviced by AVPN , EW & NG this \
		                            system has had since the last reset interval; \
		                            where the reset interval is 24 hours."
		::=  {  authenticatedUsers  2  }
	

	maximumlicensedUsers	OBJECT-TYPE	
		SYNTAX			Integer32
		MAX-ACCESS	read-only
		STATUS			current
		DESCRIPTION	"The maximum number of concurrent users \
		                            this system is licensed for."
		::=  {  authenticatedUsers  3  }

	currentConnections	OBJECT-TYPE	
		SYNTAX			Integer32
		MAX-ACCESS	read-only
		STATUS			current
		DESCRIPTION	"The number concurrent connections being \
		                            serviced by AVPN , EW & NG."
		::=  {  connectionUtilization  1  }

	peakConnections	OBJECT-TYPE	
		SYNTAX			Integer32
		MAX-ACCESS	read-only
		STATUS			current
		DESCRIPTION	"The maximum number of concurrent connections \
		                            serviced by AVPN , EW & NG, this system has had \
		                            since the last reset interval; where reset interval is 24 hours."
		::=  {  connectionUtilization  2  }

	internalInterfaceCurrentThroughput	OBJECT-TYPE	
		SYNTAX			Integer32
		MAX-ACCESS	read-only
		STATUS			current
		DESCRIPTION	"The current SSL VPN throughput in Mega bits per \
		                            second as measured on the internal interface of the node \
		                            since the last reset interval; where reset interval is 24 hours."
		::=  {  bandwidthUtilization  1  }

	internalInterfacePeakThroughput	OBJECT-TYPE	

		SYNTAX			Integer32
		MAX-ACCESS	read-only
		STATUS			current
		DESCRIPTION	"The peak SSL VPN InternalInterface throughput in Mega \
		                             bits per second since the last reset interval; \
		                             where reset interval is 24 hours."
		::=  {  bandwidthUtilization  2  }

	externalInterfaceCurrentThroughput	OBJECT-TYPE	
		SYNTAX			Integer32
		MAX-ACCESS	read-only
		STATUS			current
		DESCRIPTION	"The current SSL VPN throughput in Mega bits per second \
		                             as measured on the external interface of the node since \
		                             the last reset interval; where reset interval is 24 hours."
		::=  {  bandwidthUtilization  3  }

	

	externalInterfacePeakThroughput	OBJECT-TYPE	

		SYNTAX			Integer32
		MAX-ACCESS	read-only
		STATUS			current
		DESCRIPTION	"The peak SSL VPN ExternalInterface throughput in \
		                             Mega bits per second since the last reset interval; \
		                             where reset interval is 24 hours."
		::=  {  bandwidthUtilization  4  }

	clusterlInterfaceCurrentThroughput	OBJECT-TYPE	

		SYNTAX			Integer32
		MAX-ACCESS	read-only
		STATUS			current
		DESCRIPTION	"The current SSL VPN ClusterInterface throughput in \
		                              Mega bits per second since the last reset interval; \
		                              where reset interval is 24 hours."
		::=  {  bandwidthUtilization  5  }

	clusterInterfacePeakThroughput	OBJECT-TYPE	

		SYNTAX			Integer32
		MAX-ACCESS	read-only
		STATUS			current
		DESCRIPTION	"The peak SSL VPN ClusterInterface throughput in \
		                            Mega bits per second since the last reset interval; \
		                            where reset interval is 24 hours."
		::=  {  bandwidthUtilization  6  }

	logUtilization	OBJECT-TYPE
		SYNTAX		        Integer32
		MAX-ACCESS	 read-only
		STATUS		        current
		DESCRIPTION	"Percent of log file partition being utilized"
		::= { aventailSystemHealth  9 }

	logCapacityWarning 	NOTIFICATION-TYPE
		STATUS			current
		DESCRIPTION	"The percentage of log file disk space of a single \
		                            node system has exceeded the 90% of the total \
		                            capacity. "
		::=  {  aventailSystemHealth 100  }

	userLimitReached	NOTIFICATION-TYPE
		STATUS			current
		DESCRIPTION	"The concurrent number of authenticated users on \
		                            a single node system has reached \
		                            the current license capacity limit for authorized users. \
		                            This capacity is the currentlyLoggedIn on the single node systems."
		::=  {  aventailSystemHealth  102  }

	userLimitExceeded	NOTIFICATION-TYPE
		STATUS			current
		DESCRIPTION	"The concurrent number of authenticated users on\
		                            a single node system has \
		                            reached the maximum of the license capacity limit \
		                            taking into account grace count for authorized users. \
		                            This capacity is the currentlyLoggedIn on the 
		                            single node systems."
               ::=  {  aventailSystemHealth  103  }


END
