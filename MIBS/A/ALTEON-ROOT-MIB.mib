-- COPYRIGHT NOTICE
-- Copyright (c) Radware Ltd. 2009
-- All rights reserved

ALTEON-ROOT-MIB DEFINITIONS ::= BEGIN

IMPORTS
	enterprises 
		FROM RFC1155-SMI;


alteon		        OBJECT IDENTIFIER ::= { enterprises 1872 }

-- textual conventions

-- groups in alteon

registration		OBJECT IDENTIFIER ::= { alteon 1 }
private-mibs		OBJECT IDENTIFIER ::= { alteon 2 }

--This only here because the Volera build requires it. 
--We want to obsolete it some day.
personalContentCache   	OBJECT IDENTIFIER ::= { alteon 3 }       
ics         		OBJECT IDENTIFIER ::= { personalContentCache  1 }
-- End of Volera hack :-(

switch 		        OBJECT IDENTIFIER ::= { private-mibs 1 }
gs-switch		OBJECT IDENTIFIER ::= { private-mibs 2 }
isd 	        	OBJECT IDENTIFIER ::= { private-mibs 3 }
switch-chassis  	OBJECT IDENTIFIER ::= { private-mibs 4 }
aws-switch		OBJECT IDENTIFIER ::= { private-mibs 5 }
virt-admin		OBJECT IDENTIFIER ::= { private-mibs 6 }

chassis-8600     	OBJECT IDENTIFIER ::= { switch-chassis 1 }
wsm4Traps		OBJECT IDENTIFIER ::= { chassis-8600 2 }

platform        	OBJECT IDENTIFIER ::= { isd 1 }
sslOffload      	OBJECT IDENTIFIER ::= { isd 2 }
firewall      	        OBJECT IDENTIFIER ::= { isd 3 }
contentDirector	        OBJECT IDENTIFIER ::= { isd 4 }

-- Alteon product object identification

-- TS AceSwitch Registration

-- AceSwitch 110 - 8 10/100 UTP and 2 1000 Fiber ports
aceswitch110 OBJECT IDENTIFIER ::= { registration 1 }

-- AceDirector (110 based) - 8 10/100 UTP ports
acedirector OBJECT IDENTIFIER ::= { registration 2 }

-- AceSwitch 180 - 8 10/100 UTP or 1000 Fiber, and 1 1000 Fiber ports
aceswitch180 OBJECT IDENTIFIER ::= { registration 3 }

-- AceDirector 2 (180 based) - 8 10/100 UTP ports
acedirector2 OBJECT IDENTIFIER ::= { registration 4 }

-- AceSwitch 180e - 8 10/100 UTP or 1000 Fiber, and 1 1000 Fiber ports
aceswitch180e OBJECT IDENTIFIER ::= { registration 5 }

-- AceDirector 3 - 8 10/100 UTP and 1 1000 Fiber ports
acedirector3 OBJECT IDENTIFIER ::= { registration 6 }

-- CacheDirector - 8 10/100 UTP ports
cachedirector OBJECT IDENTIFIER ::= { registration 7 }

-- GS AceSwitch Registration
gs-switches OBJECT IDENTIFIER ::= { registration 8 }

-- AceSwitch 184 - 8 10/100 UTP or 1000 Fiber, and 1 1000 Fiber ports
aceswitch184 OBJECT IDENTIFIER ::= { registration 9 }

-- AceDirector 4 - 8 10/100 UTP and 1 1000 Fiber ports
acedirector4 OBJECT IDENTIFIER ::= { registration 10 }

-- Integrated Service Director Registration
isd-reg OBJECT IDENTIFIER ::= { registration 11 }

-- Webswitch Module 4 10/100 UTP or 1000 Fiber
webswitch-module OBJECT IDENTIFIER ::= { registration 12 }

-- AWS series switches ( Cheetah )
aws-switches OBJECT IDENTIFIER ::= { registration 13 }

-- deprecated, do not use
-- Alteon Link Optimizer ( ALO )
alteonLinkOptimizer OBJECT IDENTIFIER ::= { registration 14 }

-- Web Switch Module for IBM BladeCenter
wsm-BladeCenter OBJECT IDENTIFIER ::= { registration 15 }

-- Alteon Link Optimizer ( ALO ) Series Registration
alteonLinkOptimizer143 OBJECT IDENTIFIER ::= { registration 16 }
alteonLinkOptimizer150 OBJECT IDENTIFIER ::= { registration 17 }

-- Web Switch Module for IBM L2/L3 BladeCenter 
ibm-BladeCenterL3 OBJECT IDENTIFIER ::= { registration 18 }
-- Zoe Copper,Fiber Modules 
copperModule OBJECT IDENTIFIER ::= { ibm-BladeCenterL3 1 }
fiberModule OBJECT IDENTIFIER ::= { ibm-BladeCenterL3 2 }


-- AWS 2000 series switches 4 Gig plus 24/48 FE
aws2000-switches OBJECT IDENTIFIER ::= { aws-switches 1 }

-- AWS 3000 series switches 4 Gig plus 8/16 Gig
aws3000-switches OBJECT IDENTIFIER ::= { aws-switches 2 }

-- Radware Alteon Application switches
radwarealteon-switches OBJECT IDENTIFIER ::= { aws-switches 3 }

-- AWS 2000 Series Registration
aws2424 OBJECT IDENTIFIER ::= { aws2000-switches 1 }
aws2448 OBJECT IDENTIFIER ::= { aws2000-switches 2 }
-- AWS 2200 series switches 2 Gig plus 24 FE
aws2224 OBJECT IDENTIFIER ::= { aws2000-switches 3 }
-- AWS2424 with SSL Acceleration
aas2424s OBJECT IDENTIFIER ::= { aws2000-switches 4 }
-- AAWS 2200 series switches 2 Gig plus 8 FE
aas2208 OBJECT IDENTIFIER ::= { aws2000-switches 5 }
-- AWS 2200 series switches 2 Gig plus 16 FE
aas2216 OBJECT IDENTIFIER ::= { aws2000-switches 6 }
-- AWS 2424E5 Series Registration
aws2424E5 OBJECT IDENTIFIER ::= { aws2000-switches 7 }
-- AWS2424 E5 with SSL Acceleration
aas2424sE5 OBJECT IDENTIFIER ::= { aws2000-switches 8 }
-- AAWS 2208 E5 series switches 2 Gig plus 8 FE
aas2208E5 OBJECT IDENTIFIER ::= { aws2000-switches 9 }
-- AWS 2216 E5 series switches 2 Gig plus 16 FE
aas2216E5 OBJECT IDENTIFIER ::= { aws2000-switches 10 }

-- AWS 3000 Series Registration
aws3408 OBJECT IDENTIFIER ::= { aws3000-switches 1 }
aws3416 OBJECT IDENTIFIER ::= { aws3000-switches 2 }
aws3408E5 OBJECT IDENTIFIER ::= { aws3000-switches 3 } 

-- Radware Alteon switches Series Registration
ods4416 OBJECT IDENTIFIER ::= { radwarealteon-switches 1 }
ods5412 OBJECT IDENTIFIER ::= { radwarealteon-switches 2 }
ods4408 OBJECT IDENTIFIER ::= { radwarealteon-switches 3 }
odsva OBJECT IDENTIFIER   ::= { radwarealteon-switches 4 }
ods5224 OBJECT IDENTIFIER ::= { radwarealteon-switches 5 }

-- Virtualization (AC & vADC)
ods-virt-ac   OBJECT IDENTIFIER ::= { ods5412 1 }
ods-virt-vadc OBJECT IDENTIFIER ::= { ods5412 2 }

-- GS AceSwitch Registration
-- Chassis Switches
chas-switch OBJECT IDENTIFIER ::= { gs-switches 1 }

-- Chassis Switch Registration
chas-switch-reg OBJECT IDENTIFIER ::= { chas-switch 1 }

-- Alteon 708 - Chassis with max. 64 FE or 16 GE ports
alteon708 OBJECT IDENTIFIER ::= { chas-switch-reg 1 }

-- skipping chas-switch-reg 2

-- Chassis Switch sub-component Registration
chas-switch-comp-reg OBJECT IDENTIFIER ::= { chas-switch 2 }

-- AC Power Supply 
alteonACPowerSupply7xx OBJECT IDENTIFIER ::= { chas-switch-comp-reg 1 }

-- DC Power Supply 
alteonDCPowerSupply7xx OBJECT IDENTIFIER ::= { chas-switch-comp-reg 2 }

-- Fan Tray with four Fans for Alteon 708
alteonFan708 OBJECT IDENTIFIER ::= { chas-switch-comp-reg 3 }

-- skipping chas-switch-comp-reg 4

-- Management Processor Module 
alteonModuleMP OBJECT IDENTIFIER ::= { chas-switch-comp-reg 5 }

-- Switching Fabric Module 
alteonModuleSF OBJECT IDENTIFIER ::= { chas-switch-comp-reg 6 }

-- MDA Module with 16 10/100 UTP ports
alteonModuleFE-UTP OBJECT IDENTIFIER ::= { chas-switch-comp-reg 7 }

-- Module with 4 1000SX ports
alteonModuleGE-SX OBJECT IDENTIFIER ::= { chas-switch-comp-reg 8 }

-- Module with 4 1000BT ports
alteonModuleGE-UTP OBJECT IDENTIFIER ::= { chas-switch-comp-reg 9 }


-- Integrated Service Director Registration
-- Alteon Content Director
alteonContentDirector OBJECT IDENTIFIER ::= { isd-reg 1 }

alteonSSLOffload 			OBJECT IDENTIFIER ::= { isd-reg 2 }

-- Personal Content Cache
alteonPersonalContentCache 	OBJECT IDENTIFIER ::= { isd-reg 3 }

-- Tungsten Firewall product ( awaiting the official name! )
alteonFirewall 	OBJECT IDENTIFIER ::= { isd-reg 4 }

-- Alteon WLAN Security Switch
alteonWSS	OBJECT IDENTIFIER ::= { isd-reg 5 }

END
