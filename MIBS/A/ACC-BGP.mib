ACC-BGP DEFINITIONS ::= BEGIN

    IMPORTS
	 OBJECT-TYPE, IpAddress FROM RFC1155-SMI
	 TRAP-TYPE FROM RFC-1215
	 bgpLocalAs, bgpPeerLocalAddr,bgpPeerRemoteAddr FROM BGP4-MIB
  	 accTrapLogSeqNum FROM ACC-SYSTEM
	accBRG, DisplayString, IfIndex, SmdsAddress
             FROM ACC-MIB
        bgpPeerState, --bgpLocalAddr, bgpRemoteAddr,
        bgpPeerHoldTimeConfigured, bgpPeerKeepAliveConfigured FROM BGP4-MIB
		RowStatus FROM SNMPv2-TC;

    -- ACC BGP branch
    accBgp 		OBJECT IDENTIFIER ::= { accBRG 51 }
    accBgpGeneral	OBJECT IDENTIFIER ::= { accBgp 1 }
    --
    --  ACC general BGP objects
    --
    accBgpAdminState OBJECT-TYPE
        SYNTAX 	INTEGER {
    		    enabled(1),
    		    disabled(2)
    		}
        ACCESS 	read-write
        STATUS  mandatory
	DESCRIPTION
	     "The administrative state of BGP."
	DEFVAL { disabled }
        ::= { accBgpGeneral 1 }
    accBgpMessageLevel OBJECT-TYPE
        SYNTAX  INTEGER (1..7)
        ACCESS  read-write
        STATUS  mandatory
        DESCRIPTION
             "The diagnostic and message level setting. A higher value
	      generates more detailed diagnostic feedback."
	DEFVAL { 1 }
        ::= { accBgpGeneral 2 }
    accBgpLocalAsFullMesh OBJECT-TYPE
        SYNTAX  INTEGER {
		    yes(1),
		    no(2)
		}
        ACCESS  read-write
        STATUS  mandatory
        DESCRIPTION
             "Configures the local AS to a full mesh."
        DEFVAL { no }
        ::= { accBgpGeneral 3 }
    --
    --		The BGP Peer Table
    --
    accBgpPeerTable OBJECT-TYPE
        SYNTAX  SEQUENCE OF AccBgpPeerEntry 
        ACCESS  	not-accessible
        STATUS  	mandatory
	DESCRIPTION
	     "Extensions to the bgpPeerTable defined in rfc1657."
    ::= { accBgp 2 }
    accBgpPeerEntry OBJECT-TYPE
        SYNTAX 	AccBgpPeerEntry
        ACCESS 	not-accessible
        STATUS  mandatory
        DESCRIPTION
	""
        INDEX   { accBgpPeerAddress }
        ::= { accBgpPeerTable  1 }
    AccBgpPeerEntry ::=
        SEQUENCE {
    	accBgpPeerAddress		IpAddress,
    	accBgpPeerVersionConfigured	INTEGER,
    	accBgpPeerDefaultImportPref	INTEGER,
    	accBgpPeerDefaultExportMetric	INTEGER,
    	accBgpPeerPassive		INTEGER,
    	accBgpPeerUseMed		INTEGER,
    	accBgpPeerMessageLevel		INTEGER,
    	accBgpPeerMultiHop		INTEGER,
    	accBgpPeerStatus		RowStatus
        }
    	accBgpPeerAddress OBJECT-TYPE
    	SYNTAX 	IpAddress
    	ACCESS 	read-only
    	STATUS  	mandatory
	DESCRIPTION
	     "The remote IP address of this entry's BGP peer."
    	::= { accBgpPeerEntry  1 }
    	accBgpPeerVersionConfigured OBJECT-TYPE
    	SYNTAX 	INTEGER {
		    bgp3(3),
		    bgp4(4)
		}
    	ACCESS 	read-write
    	STATUS  mandatory
	DESCRIPTION
	     "The configured version of this entry's BGP peer."	
        DEFVAL { bgp4 }
    	::= { accBgpPeerEntry  2 }
    	accBgpPeerDefaultImportPref OBJECT-TYPE
    	SYNTAX 	INTEGER (1..255)
    	ACCESS 	read-write
    	STATUS  mandatory
	DESCRIPTION
	     "The default import preference for this entry's BGP peer."
        DEFVAL { 144 }
    	::= { accBgpPeerEntry  3 }
    	accBgpPeerDefaultExportMetric OBJECT-TYPE
    	SYNTAX 	INTEGER (1..4294967295)
    	ACCESS 	read-write
    	STATUS  mandatory
	DESCRIPTION
	     "The default export metric for this entry's BGP peer. This value
	      is used as the MED when no other specific policy is configured."
        DEFVAL { 4294967295 }
    	::= { accBgpPeerEntry  4 }
    	accBgpPeerPassive OBJECT-TYPE
    	SYNTAX 	INTEGER {
    		    yes(1),
    		    no(2)
    		}
    	ACCESS 	read-write
    	STATUS  mandatory
	DESCRIPTION
	     "Determines whether or not the local BGP entity will initiate
	      a peer relationship with this BGP peer."
        DEFVAL { no }
    	::= { accBgpPeerEntry  5 }
    	accBgpPeerUseMed OBJECT-TYPE
    	SYNTAX 	INTEGER {
    		    yes(1),
    		    no(2)
    		}
    	ACCESS 	read-write
    	STATUS  mandatory
	DESCRIPTION
	     "Determines if this local BGP entity will include the MED path
	      attributes in announcements to this BGP peer."
        DEFVAL { yes }
    	::= { accBgpPeerEntry  6 }
        accBgpPeerMessageLevel OBJECT-TYPE
        SYNTAX  INTEGER (1..7)
        ACCESS  read-write
        STATUS  mandatory
        DESCRIPTION
             "The configured diagnostic level for this BGP peer. Setting this value to 1 
	      will enable the interface to generate critical diagnostic information. 
	      Increasing the value increases the diagnostic information. Level 7 is 
	      mostly informational."
        DEFVAL { 1 }
        ::= { accBgpPeerEntry  7 }
        accBgpPeerMultiHop OBJECT-TYPE
        SYNTAX  INTEGER {
                    yes(1),
                    no(2)
                }
        ACCESS  read-write
        STATUS  mandatory
        DESCRIPTION
             "Configures this BGP peer to be more than one hop away.
	      Used for external BGP peers only."
        DEFVAL { no }
        ::= { accBgpPeerEntry  8 }
    	accBgpPeerStatus OBJECT-TYPE
    	SYNTAX 	RowStatus
    	ACCESS 	read-write
    	STATUS  mandatory
	DESCRIPTION
	     "The current status of this protocol entry."
    	::= { accBgpPeerEntry  9 }
    --
    --		Obsoleted BGP Export Table
    --
    --		{ accBgp 3 }
    --
    --		The BGP Import Table
    --
    accBgpImportTable OBJECT-TYPE
        SYNTAX  SEQUENCE OF AccBgpImportEntry 
        ACCESS  not-accessible
        STATUS  mandatory
	DESCRIPTION
	     "This table lists the import policies used by this BGP
	      application. Import policies determine what NLRI from 
	      BGP peer announcements that will be accepted and added 
	      to the local forwarding table."
    ::= { accBgp 4 }
    accBgpImportEntry OBJECT-TYPE
        SYNTAX 	AccBgpImportEntry
        ACCESS 	not-accessible
        STATUS  mandatory
	DESCRIPTION
		" "
        INDEX   { accBgpImportNetwork, accBgpImportMask, 
    		  accBgpImportPeerAS, accBgpImportPeerAddress,
    		  accBgpImportHomeAS, accBgpImportOrigin
		}
        ::= { accBgpImportTable 1 }
    AccBgpImportEntry ::=
        SEQUENCE {
    	accBgpImportNetwork		IpAddress,
    	accBgpImportMask		IpAddress,
    	accBgpImportPeerAS		INTEGER,
    	accBgpImportPeerAddress		IpAddress,
    	accBgpImportHomeAS		INTEGER,
    	accBgpImportOrigin 		INTEGER,
    	accBgpImportPreference 		INTEGER,
    	accBgpImportAction 		INTEGER,
    	accBgpImportStatus		RowStatus
        }
    	accBgpImportNetwork OBJECT-TYPE
    	SYNTAX 	IpAddress
    	ACCESS 	read-only
    	STATUS  mandatory
	DESCRIPTION
	     "The import policies NLRI prefix."
    	::= { accBgpImportEntry  1 }
    	accBgpImportMask OBJECT-TYPE
    	SYNTAX 	IpAddress
    	ACCESS 	read-only
    	STATUS  	mandatory
	DESCRIPTION
	     "The mask to be used against BGP peer announcements NLRI and
	      compared to this policies network object value."
    	::= { accBgpImportEntry  2 }
    	accBgpImportPeerAS OBJECT-TYPE
    	SYNTAX 	INTEGER
    	ACCESS 	read-only
    	STATUS  mandatory
	DESCRIPTION
	     "The BGP peer's AS."
    	::= { accBgpImportEntry  3 }
    	accBgpImportPeerAddress OBJECT-TYPE
    	SYNTAX 	IpAddress
    	ACCESS 	read-only
    	STATUS  mandatory
	DESCRIPTION
	     "The BGP peer's IP address."
    	::= { accBgpImportEntry  4 }
    	accBgpImportHomeAS OBJECT-TYPE
    	SYNTAX 	INTEGER
    	ACCESS 	read-only
    	STATUS  mandatory
	DESCRIPTION
	     "The home AS of the NLRI in the announcement"
    	::= { accBgpImportEntry  5 }
    	accBgpImportOrigin OBJECT-TYPE
    	SYNTAX 	INTEGER {
    		    igp(1),
    		    egp(2),
    		    unknown(3)
    		}
    	ACCESS 	read-only
    	STATUS  mandatory
	DESCRIPTION
	     "The Origin code of the NLRI in the announcement."
    	::= { accBgpImportEntry  6 }
        accBgpImportAction OBJECT-TYPE
        SYNTAX  INTEGER {
                    import(1),
                    ignore(2)
                }
        ACCESS  read-write
        STATUS  mandatory
        DESCRIPTION
             "The action to be taken when a policy match is met."
        DEFVAL { import }
        ::= { accBgpImportEntry  7 }
    	accBgpImportPreference OBJECT-TYPE
    	SYNTAX 	INTEGER (0..255)
    	ACCESS 	read-write
    	STATUS  mandatory
	DESCRIPTION
	     "The import preference to be assigned the NLRI when a policy
	      match has been met."
	DEFVAL { 0 }
    	::= { accBgpImportEntry  8 }
    	accBgpImportStatus OBJECT-TYPE
    	SYNTAX 	RowStatus
    	ACCESS 	read-write
    	STATUS  mandatory
	DESCRIPTION
	     "The current status of this row entry."
    	::= { accBgpImportEntry  9 }
    --
    --		The BGP Autonomous System Weight Table
    --
    accBgpASWeightTable OBJECT-TYPE
        SYNTAX  SEQUENCE OF AccBgpASWeightEntry 
        ACCESS  not-accessible
        STATUS  mandatory
	DESCRIPTION
	     "The AS weight table. This table indicates how the
	      local BGP application is weighting Autonomous System
	      during path selection."
    ::= { accBgp 5 }
    accBgpASWeightEntry OBJECT-TYPE
        SYNTAX 	AccBgpASWeightEntry
        ACCESS 	not-accessible
        STATUS  mandatory
	DESCRIPTION
		" "
        INDEX   { accBgpASWeightAS } 
        ::= { accBgpASWeightTable 1 }
    AccBgpASWeightEntry ::=
        SEQUENCE {
    	accBgpASWeightAS 		INTEGER,
    	accBgpASWeight	 		INTEGER,
    	accBgpASWeightStatus		RowStatus
        }
    	accBgpASWeightAS  OBJECT-TYPE
    	SYNTAX 	INTEGER (0..65535)
    	ACCESS 	read-only
    	STATUS  mandatory
	DESCRIPTION
	     "The Autonomous System identifier."
    	::= { accBgpASWeightEntry  1 }
    	accBgpASWeight OBJECT-TYPE
    	SYNTAX 	INTEGER (0..255)
    	ACCESS 	read-write
    	STATUS  mandatory
	DESCRIPTION
	     "The AS weight to be applied. A value of 255 is equivalent
	      to infinity."
    	::= { accBgpASWeightEntry  2 }
    	accBgpASWeightStatus OBJECT-TYPE
    	SYNTAX 	RowStatus
    	ACCESS 	read-write
    	STATUS  mandatory
	DESCRIPTION
	     "The current status of this entry."
    	::= { accBgpASWeightEntry  3 }
    --
    --		The BGP Aggregate Table
    --
    accBgpAggregateTable OBJECT-TYPE
        SYNTAX  SEQUENCE OF AccBgpAggregateEntry 
        ACCESS  	not-accessible
        STATUS  	mandatory
	DESCRIPTION
	     "The BGP aggregation policy table. This table indicates
	      what the local BGP application will attempt to aggregate."
    ::= { accBgp 6 }
    accBgpAggregateEntry OBJECT-TYPE
        SYNTAX 	AccBgpAggregateEntry
        ACCESS 	not-accessible
        STATUS  mandatory
        DESCRIPTION
 		" "
        INDEX   { accBgpAggregateAddr, accBgpAggregateMask } 
        ::= { accBgpAggregateTable 1 }
    AccBgpAggregateEntry ::=
        SEQUENCE {
    	accBgpAggregateAddr		IpAddress,
    	accBgpAggregateMask 	 	IpAddress,
    	accBgpAggregateAdvertise	INTEGER,
    	accBgpAggregatePref	 	INTEGER,
    	accBgpAggregateComponents  	INTEGER,
    	accBgpAggregateActive  		INTEGER,
    	accBgpAggregateAdminStat  	INTEGER,
    	accBgpAggregateStatus		RowStatus
        }
    	accBgpAggregateAddr OBJECT-TYPE
    	SYNTAX 	IpAddress
    	ACCESS 	read-only
    	STATUS  mandatory
	DESCRIPTION
	     "The aggregate address to be made active when a aggregate
	      policy match is made."
    	::= { accBgpAggregateEntry  1 }
    	accBgpAggregateMask  OBJECT-TYPE
    	SYNTAX 	IpAddress
    	ACCESS 	read-only
    	STATUS  mandatory
	DESCRIPTION
	     "The mask to be included with the aggregate address when a
	      aggregate policy match is made."
    	::= { accBgpAggregateEntry  2 }
        accBgpAggregateAdvertise OBJECT-TYPE
        SYNTAX  INTEGER {
		    yes(1),
		    no(2)
		}
        ACCESS  read-write
        STATUS  mandatory
        DESCRIPTION
             "Determines whether or not the aggregate policy will be
	      suppressed when a aggregate policy match is made."
	DEFVAL { yes }
        ::= { accBgpAggregateEntry  3 }
    	accBgpAggregatePref OBJECT-TYPE
    	SYNTAX 	INTEGER (0..255)
    	ACCESS 	read-write
    	STATUS  mandatory
	DESCRIPTION
	     "The preference of the aggregate policy when a policy match
	      is made."
	DEFVAL { 144 }
    	::= { accBgpAggregateEntry  4 }
    	accBgpAggregateComponents   OBJECT-TYPE
    	SYNTAX 	INTEGER (0..10)
    	ACCESS 	read-write
    	STATUS  mandatory
	DESCRIPTION
	     "The number aggregate policy components that must be active
	      before this aggregate policy is made active."
	DEFVAL { 0 }
    	::= { accBgpAggregateEntry  5 }
        accBgpAggregateActive   OBJECT-TYPE
        SYNTAX  INTEGER {
		    yes(1),
		    no(2)
		}
        ACCESS  read-only
        STATUS  mandatory
        DESCRIPTION
             "Indicates whether this aggregate policy is currently
	      active."
        ::= { accBgpAggregateEntry  6 }
        accBgpAggregateAdminStat   OBJECT-TYPE
        SYNTAX  INTEGER {
                    enabled(1),
                    disabled(2)
                }
        ACCESS  read-write
        STATUS  mandatory
        DESCRIPTION
             "The administrative status of this aggregate policy."
        ::= { accBgpAggregateEntry  7 }
    	accBgpAggregateStatus  OBJECT-TYPE
    	SYNTAX 	RowStatus
    	ACCESS 	read-write
    	STATUS  mandatory
	DESCRIPTION
	     "The current status of this entry."
    	::= { accBgpAggregateEntry  8 }
    --
    --		The BGP Aggregate Component Table
    --
    accBgpAggrComponentTable OBJECT-TYPE
        SYNTAX  SEQUENCE OF AccBgpAggrComponentEntry 
        ACCESS  not-accessible
        STATUS  mandatory
	DESCRIPTION
	     "The BGP applications aggregate policy component table."
    ::= { accBgp 7 }
    accBgpAggrComponentEntry OBJECT-TYPE
        SYNTAX 	AccBgpAggrComponentEntry
        ACCESS 	not-accessible
        STATUS  mandatory
	DESCRIPTION
		" "
        INDEX   { accBgpAggrCompParentAddr, accBgpAggrCompParentMask,
    		  accBgpAggrComponentAddr,  accBgpAggrComponentMask
		} 
        ::= { accBgpAggrComponentTable 1 }
    AccBgpAggrComponentEntry ::=
        SEQUENCE {
    	accBgpAggrCompParentAddr	IpAddress,
    	accBgpAggrCompParentMask 	IpAddress,
    	accBgpAggrComponentAddr		IpAddress,
    	accBgpAggrComponentMask 	IpAddress,
    	accBgpAggrComponentProtocol	INTEGER,
    	accBgpAggrComponentActive	INTEGER,
    	accBgpAggrComponentStatus	RowStatus
        }
        accBgpAggrCompParentAddr OBJECT-TYPE
        SYNTAX  IpAddress
        ACCESS  read-only
        STATUS  mandatory
        DESCRIPTION
             "The components aggregate policy parent address."
        ::= { accBgpAggrComponentEntry  1 }
        accBgpAggrCompParentMask OBJECT-TYPE
        SYNTAX  IpAddress
        ACCESS  read-only
        STATUS  mandatory
        DESCRIPTION
             "The components aggregate policy parent mask."
        ::= { accBgpAggrComponentEntry  2 }
    	accBgpAggrComponentAddr OBJECT-TYPE
    	SYNTAX 	IpAddress
    	ACCESS 	read-only
    	STATUS  mandatory
	DESCRIPTION
	     "The components address."
    	::= { accBgpAggrComponentEntry  3 }
    	accBgpAggrComponentMask OBJECT-TYPE
    	SYNTAX 	IpAddress
    	ACCESS 	read-only
    	STATUS  mandatory
	DESCRIPTION
	     "The components mask."
    	::= { accBgpAggrComponentEntry  4 }
    	accBgpAggrComponentProtocol OBJECT-TYPE
    	SYNTAX 	INTEGER {
    		    any(1),
    		    static(2),
    		    ospf(3),
    		    rip(4),
    		    bgp(5) 
    		}
    	ACCESS 	read-write
    	STATUS  mandatory
	DESCRIPTION
	     "The route's protocol owner that will cause this aggregate
	      component to activate."
    	::= { accBgpAggrComponentEntry  5 }
        accBgpAggrComponentActive OBJECT-TYPE
        SYNTAX  INTEGER {
                    yes(1),
                    no(2)
                }
        ACCESS  read-only
        STATUS  mandatory
        DESCRIPTION
             "Indicates whether this aggregate component is currently
	      active."
        ::= { accBgpAggrComponentEntry  6 }
    	accBgpAggrComponentStatus OBJECT-TYPE
    	SYNTAX 	RowStatus
    	ACCESS 	read-write
    	STATUS  mandatory
	DESCRIPTION
	     "The current status of this entry."
    	::= { accBgpAggrComponentEntry  7 }
    --
    --          The BGP Export Table
    --
    accBgpExportTable OBJECT-TYPE
        SYNTAX  SEQUENCE OF AccBgpExportEntry
        ACCESS  not-accessible
        STATUS  mandatory
        DESCRIPTION
             "This table lists the export policies used by the local
              BGP routing application. Export policies determine what
              NLRI BGP will include in announcements to BGP peers."
    ::= { accBgp 8 }
    accBgpExportEntry OBJECT-TYPE
        SYNTAX  AccBgpExportEntry
        ACCESS  not-accessible
        STATUS  mandatory
        DESCRIPTION
                " "
        INDEX   { accBgpExportPeerAS, accBgpExportPeerAddress,
		  accBgpExportProtocol, accBgpExportSpecific2,
		  accBgpExportSpecific1, accBgpExportNetwork,
		  accBgpExportMask
		}
        ::= { accBgpExportTable 1 }
    AccBgpExportEntry ::=
        SEQUENCE {
        accBgpExportPeerAS              INTEGER,
        accBgpExportPeerAddress         IpAddress,
        accBgpExportProtocol            INTEGER,
        accBgpExportSpecific2           INTEGER,
        accBgpExportSpecific1           INTEGER,
        accBgpExportNetwork             IpAddress,
        accBgpExportMask                IpAddress,
        accBgpExportAction              INTEGER,
        accBgpExportMetric              INTEGER,
        accBgpExportStatus              RowStatus
        }
        accBgpExportPeerAS OBJECT-TYPE
        SYNTAX  INTEGER
        ACCESS  read-only
        STATUS  mandatory
        DESCRIPTION
             "The BGP peer's AS identifier."
        ::= { accBgpExportEntry  1 }
        accBgpExportPeerAddress OBJECT-TYPE
        SYNTAX  IpAddress
        ACCESS  read-only
        STATUS  mandatory
        DESCRIPTION
             "The BGP peer's address."
        ::= { accBgpExportEntry  2 }
        accBgpExportProtocol OBJECT-TYPE
        SYNTAX  INTEGER {
                    any(1),
                    local(2),
                    static(3),
                    iospf(4),
                    eospf(5),
                    rip(6),
                    ebgp(7),
                    ibgp(8),
                    aggr(9)
                }
        ACCESS  read-only
        STATUS  mandatory
        DESCRIPTION
             "The protocol owner of the NLRI."
        ::= { accBgpExportEntry  3 }
        accBgpExportSpecific2 OBJECT-TYPE
        SYNTAX  INTEGER
        ACCESS  read-only
        STATUS  mandatory
        DESCRIPTION
             "The secondary protocol specific value for this export
              policy."
        ::= { accBgpExportEntry  4 }
        accBgpExportSpecific1 OBJECT-TYPE
        SYNTAX  INTEGER
        ACCESS  read-only
        STATUS  mandatory
        DESCRIPTION
             "The protocol specific value for this export policy."
        ::= { accBgpExportEntry  5 }
        accBgpExportNetwork OBJECT-TYPE
        SYNTAX  IpAddress
        ACCESS  read-only
        STATUS  mandatory
        DESCRIPTION
             "The export policies NLRI prefix."
        ::= { accBgpExportEntry  6 }
        accBgpExportMask OBJECT-TYPE
        SYNTAX  IpAddress
        ACCESS  read-only
        STATUS  mandatory
        DESCRIPTION
             "The mask to be used against NLRI when performing a policy
              lookup. A match is considered met if the result is subsumable
              by the network object value."
        ::= { accBgpExportEntry  7 }
        accBgpExportAction OBJECT-TYPE
        SYNTAX  INTEGER {
                    export(1),
                    block(2)
                }
        ACCESS  read-write
        STATUS  mandatory
        DESCRIPTION
             "The action to be taken when a policy match is met."
        DEFVAL { export }
        ::= { accBgpExportEntry  8 }
        accBgpExportMetric OBJECT-TYPE
        SYNTAX  INTEGER (0..4294967295)
        ACCESS  read-write
        STATUS  mandatory
        DESCRIPTION
             "The metric (or MED) to be included in announcements to BGP
              peer's when a policy match is met."
        DEFVAL { 0 }
        ::= { accBgpExportEntry  9 }
        accBgpExportStatus OBJECT-TYPE
        SYNTAX  RowStatus
        ACCESS  read-write
        STATUS  mandatory
        DESCRIPTION
             "The current status of this entry."
        ::= { accBgpExportEntry  10 }
-- START CFG_TRAP_ENHANCEMENTS
-- Bgp Traps
        accBgpTraps OBJECT IDENTIFIER   ::= { accBgp 9 }
        accBgpTrapMsg   OBJECT-TYPE
        SYNTAX          DisplayString 
        ACCESS          read-write
        STATUS          mandatory
        DESCRIPTION
                "Enterprise Trap Message for Bgp."
        ::= { accBgpTraps 1 } 
-- END CFG_TRAP_ENHANCEMENTS

        accBgpPeerNotDisbldTrap TRAP-TYPE
        ENTERPRISE        accBgpTraps 
        VARIABLES       { accBgpTrapMsg,
                          accBgpPeerAddress ,
                           accTrapLogSeqNum}
        DESCRIPTION
                "Peer must be disabled before it has to be deleted. 
		 User tried to delete a peer without disabling it and 
		 hence the trap.
SEVERITY-DEFAULT: Warning 
EVENTTYPE-DEFAULT: 10 
ADDITIONAL-TEXT-VARIABLES: { accTrapLogSeqNum,accBgpTrapMsg }
PCAUSE-DEFAULT: 7 " 
 
        ::= 1 
        accBgpAddFltPolTrap TRAP-TYPE
        ENTERPRISE        accBgpTraps 
        VARIABLES       { accBgpTrapMsg,
                          accBgpImportNetwork,
                          accBgpImportMask ,
                           accTrapLogSeqNum}
        DESCRIPTION
                "Add BGP filter policy failed.
SEVERITY-DEFAULT: Warning 
EVENTTYPE-DEFAULT: 10 
ADDITIONAL-TEXT-VARIABLES: { accTrapLogSeqNum,accBgpTrapMsg }
PCAUSE-DEFAULT: 7 " 
 
        ::= 2 
        accBgpDelFltPolTrap TRAP-TYPE
        ENTERPRISE        accBgpTraps 
        VARIABLES       { accBgpTrapMsg,
                          accBgpImportNetwork,
                          accBgpImportMask ,
                           accTrapLogSeqNum}
        DESCRIPTION
                "It happens when the user tries to delete a filter 
		 policy that doesnt exist.
SEVERITY-DEFAULT: Warning 
EVENTTYPE-DEFAULT: 10 
ADDITIONAL-TEXT-VARIABLES: { accTrapLogSeqNum,accBgpTrapMsg }
PCAUSE-DEFAULT: 7 " 
 
        ::= 3 
        accBgpAddImpPolTrap TRAP-TYPE
        ENTERPRISE        accBgpTraps 
        VARIABLES       { accBgpTrapMsg,
                          accBgpExportNetwork,
                          accBgpExportMask ,
                           accTrapLogSeqNum}
        DESCRIPTION
                "Adding Import policy failed due to memory shortage.
SEVERITY-DEFAULT: Major 
EVENTTYPE-DEFAULT: 10 
ADDITIONAL-TEXT-VARIABLES: { accTrapLogSeqNum,accBgpTrapMsg }
PCAUSE-DEFAULT: 32 " 
 
        ::= 4 
        accBgpDelImpPolTrap TRAP-TYPE
        ENTERPRISE        accBgpTraps 
        VARIABLES       { accBgpTrapMsg,
                          accBgpExportNetwork,
                          accBgpExportMask ,
                           accTrapLogSeqNum}
        DESCRIPTION
                "It happens when the user tries to delete an Import 
		 policy that doesnt exist.
SEVERITY-DEFAULT: Warning 
EVENTTYPE-DEFAULT: 10 
ADDITIONAL-TEXT-VARIABLES: { accTrapLogSeqNum,accBgpTrapMsg }
PCAUSE-DEFAULT: 7 " 
 
        ::= 5
        accBgpAddAsWtPolTrap TRAP-TYPE
        ENTERPRISE        accBgpTraps 
        VARIABLES       { accBgpTrapMsg,
                          accBgpASWeightAS ,
                           accTrapLogSeqNum}
        DESCRIPTION
                "Adding AS weight policy failed due to memory shortage.
SEVERITY-DEFAULT: Major 
EVENTTYPE-DEFAULT: 10 
ADDITIONAL-TEXT-VARIABLES: { accTrapLogSeqNum,accBgpTrapMsg }
PCAUSE-DEFAULT: 32 " 
 
        ::= 6 
        accBgpDelAsWtPolTrap TRAP-TYPE
        ENTERPRISE        accBgpTraps 
        VARIABLES       { accBgpTrapMsg,
                          accBgpASWeightAS ,
                           accTrapLogSeqNum}
        DESCRIPTION
                "It happens when the user tries to delete an AS weight 
		 policy that doesnt exist.
SEVERITY-DEFAULT: Warning 
EVENTTYPE-DEFAULT: 10 
ADDITIONAL-TEXT-VARIABLES: { accTrapLogSeqNum,accBgpTrapMsg }
PCAUSE-DEFAULT: 7 " 
 
        ::= 7 
        accBgpNbrTrap TRAP-TYPE
        ENTERPRISE        accBgpTraps 
        VARIABLES       { accBgpTrapMsg,
                          accBgpPeerAddress ,
                           accTrapLogSeqNum}
        DESCRIPTION
                "Probably attempted to add ourselves as a peer.
SEVERITY-DEFAULT: Warning 
EVENTTYPE-DEFAULT: 10 
ADDITIONAL-TEXT-VARIABLES: { accTrapLogSeqNum,accBgpTrapMsg }
PCAUSE-DEFAULT: 7 " 
 
        ::= 8 
        accBgpInvHoldKeepAliveTrap TRAP-TYPE
        ENTERPRISE        accBgpTraps 
        VARIABLES       { accBgpTrapMsg,
                          bgpPeerHoldTimeConfigured,
                          bgpPeerKeepAliveConfigured ,
accTrapLogSeqNum}
        DESCRIPTION
                "Hold_time shouldnt be less than Keep_Alive time 
		 (it is recommended that keep_alive time be one-third 
		  of hold_time). Trap occured when the user tried 
		  configure Hold_time less than the Keep_Alive time.
SEVERITY-DEFAULT: Warning 
EVENTTYPE-DEFAULT: 10 
ADDITIONAL-TEXT-VARIABLES: { accTrapLogSeqNum,accBgpTrapMsg }
PCAUSE-DEFAULT: 7 " 
 
        ::= 9  
        accBgpIllegalLocalAsTrap TRAP-TYPE
        ENTERPRISE        accBgpTraps 
        VARIABLES       { accBgpTrapMsg,
                          bgpLocalAs ,
accTrapLogSeqNum}
        DESCRIPTION
                "Wont be allowed setting if local AS was not setup.
SEVERITY-DEFAULT: Warning 
EVENTTYPE-DEFAULT: 10 
ADDITIONAL-TEXT-VARIABLES: { accTrapLogSeqNum,accBgpTrapMsg }
PCAUSE-DEFAULT: 7 " 
 
        ::= 10
        accBgpIBGPPeerAddrTrap TRAP-TYPE
        ENTERPRISE        accBgpTraps 
        VARIABLES       { accBgpTrapMsg,
                          accBgpExportPeerAS,
                          accBgpExportPeerAddress ,
                           accTrapLogSeqNum}
        DESCRIPTION
                "Peer belongs to same AS. So trap indicates ignoring 
		 IBgp peer address.
SEVERITY-DEFAULT: Warning 
EVENTTYPE-DEFAULT: 10 
ADDITIONAL-TEXT-VARIABLES: { accTrapLogSeqNum,accBgpTrapMsg }
PCAUSE-DEFAULT: 7 " 
 
        ::= 11 
        accBgpPolPeerAddrTrap TRAP-TYPE
        ENTERPRISE        accBgpTraps 
        VARIABLES       { accBgpTrapMsg,
                          bgpLocalAs,
                          accBgpExportPeerAS,
                          accBgpExportPeerAddress ,
                           accTrapLogSeqNum}
        DESCRIPTION
                "Indiacates that Peer is not directly connected. It 
		 is probably IBGP peer, if we have not connected to 
		 him yet we cannot say for sure (multi-hop eBGP), trap 
		 warning the user.
SEVERITY-DEFAULT: Warning 
EVENTTYPE-DEFAULT: 10 
ADDITIONAL-TEXT-VARIABLES: { accTrapLogSeqNum,accBgpTrapMsg }
PCAUSE-DEFAULT: 7 " 
 
        ::= 12 
        accBgpPeerNotFndTrap TRAP-TYPE
        ENTERPRISE        accBgpTraps 
        VARIABLES       { accBgpTrapMsg,
                          accBgpExportPeerAddress  ,
                           accTrapLogSeqNum}
        DESCRIPTION
                "Peer in policy not found.
SEVERITY-DEFAULT: Warning 
EVENTTYPE-DEFAULT: 10 
ADDITIONAL-TEXT-VARIABLES: { accTrapLogSeqNum,accBgpTrapMsg }
PCAUSE-DEFAULT: 7 " 
 
        ::= 13
        accBgpPeerAllocTrap TRAP-TYPE
        ENTERPRISE        accBgpTraps 
        VARIABLES       { accBgpTrapMsg,
                          accBgpPeerAddress ,
                           accTrapLogSeqNum}
        DESCRIPTION
                "Could not allocate memory for Peer due to memory 
		 shortage.
SEVERITY-DEFAULT: Major 
EVENTTYPE-DEFAULT: 10 
ADDITIONAL-TEXT-VARIABLES: { accTrapLogSeqNum,accBgpTrapMsg }
PCAUSE-DEFAULT: 32 " 
 
        ::= 14
        accBgpRcvBfrAllocTrap TRAP-TYPE
        ENTERPRISE        accBgpTraps 
        VARIABLES       { accBgpTrapMsg,
                          accBgpPeerAddress ,
                           accTrapLogSeqNum}
        DESCRIPTION
                "Alloc rcv buffer failed due to memory shortage, hence 
		 the trap indicating the same.
SEVERITY-DEFAULT: Major 
EVENTTYPE-DEFAULT: 10 
ADDITIONAL-TEXT-VARIABLES: { accTrapLogSeqNum,accBgpTrapMsg }
PCAUSE-DEFAULT: 32 " 
 
        ::= 15   
        accBgpTmrAllocTrap TRAP-TYPE
        ENTERPRISE        accBgpTraps 
        VARIABLES       { accBgpTrapMsg,
                          accBgpPeerAddress ,
                           accTrapLogSeqNum}
        DESCRIPTION
                "Timer alloc failed due to memory shortage.
SEVERITY-DEFAULT: Major 
EVENTTYPE-DEFAULT: 10 
ADDITIONAL-TEXT-VARIABLES: { accTrapLogSeqNum,accBgpTrapMsg }
PCAUSE-DEFAULT: 32 " 
 
        ::= 16
        accBgpPeerEnableTmrAllocTrap TRAP-TYPE
        ENTERPRISE        accBgpTraps 
        VARIABLES       { accBgpTrapMsg,
                          accBgpPeerAddress ,
                           accTrapLogSeqNum}
        DESCRIPTION
                "Timer alloc failed due to memory shortage.
SEVERITY-DEFAULT: Major 
EVENTTYPE-DEFAULT: 10 
ADDITIONAL-TEXT-VARIABLES: { accTrapLogSeqNum,accBgpTrapMsg }
PCAUSE-DEFAULT: 32 " 
 
        ::= 17
        accBgpGrpAllocTrap TRAP-TYPE
        ENTERPRISE        accBgpTraps 
        VARIABLES       { accBgpTrapMsg ,
                           accTrapLogSeqNum}
        DESCRIPTION
         	"Could not allocate memory for BGP group due to 
		 memory shortage.
SEVERITY-DEFAULT: Major 
EVENTTYPE-DEFAULT: 10 
ADDITIONAL-TEXT-VARIABLES: { accTrapLogSeqNum,accBgpTrapMsg }
PCAUSE-DEFAULT: 32 " 
 
        ::= 18
        accBgpShutdownAllocTrap TRAP-TYPE
        ENTERPRISE        accBgpTraps 
        VARIABLES       { accBgpTrapMsg ,
                           accTrapLogSeqNum}
        DESCRIPTION
                "Shutdown alloc failed due to memory shortage.
SEVERITY-DEFAULT: Major 
EVENTTYPE-DEFAULT: 10 
ADDITIONAL-TEXT-VARIABLES: { accTrapLogSeqNum,accBgpTrapMsg }
PCAUSE-DEFAULT: 32 " 
 
        ::= 19  
       accBgpOrphanTrap TRAP-TYPE
        ENTERPRISE        accBgpTraps 
        VARIABLES       { accBgpTrapMsg,
                          bgpLocalAs ,
accTrapLogSeqNum}
        DESCRIPTION
                "Indicates that either parent doesnt exist; allocating 
		 memory for peer FSM timers or other peer timers failed 
		 due to memory shortage.
SEVERITY-DEFAULT: Major 
EVENTTYPE-DEFAULT: 10 
ADDITIONAL-TEXT-VARIABLES: { accTrapLogSeqNum,accBgpTrapMsg }
PCAUSE-DEFAULT: 32 " 
 
        ::= 20
        accBgpRtclAllocTrap TRAP-TYPE
        ENTERPRISE        accBgpTraps 
        VARIABLES       { accBgpTrapMsg ,
                           accTrapLogSeqNum}
        DESCRIPTION
                "Rtcl alloc failed due to memory shortage.
SEVERITY-DEFAULT: Major 
EVENTTYPE-DEFAULT: 10 
ADDITIONAL-TEXT-VARIABLES: { accTrapLogSeqNum,accBgpTrapMsg }
PCAUSE-DEFAULT: 32 " 
 
        ::= 21 
        accBgpAggrAllocTrap TRAP-TYPE
        ENTERPRISE        accBgpTraps 
        VARIABLES       { accBgpTrapMsg ,
                           accTrapLogSeqNum}
        DESCRIPTION
                "Aggregate policy alloc failed due to memory shortag.
SEVERITY-DEFAULT: Major 
EVENTTYPE-DEFAULT: 10 
ADDITIONAL-TEXT-VARIABLES: { accTrapLogSeqNum,accBgpTrapMsg }
PCAUSE-DEFAULT: 32 " 
 
        ::= 22 
        accBgpPolAllocTrap TRAP-TYPE
        ENTERPRISE        accBgpTraps 
        VARIABLES       { accBgpTrapMsg ,
                           accTrapLogSeqNum}
        DESCRIPTION
                "Policy alloc failed due to memory shortage.
SEVERITY-DEFAULT: Major 
EVENTTYPE-DEFAULT: 10 
ADDITIONAL-TEXT-VARIABLES: { accTrapLogSeqNum,accBgpTrapMsg }
PCAUSE-DEFAULT: 32 " 
 
        ::= 23
        accBgpAnnounceAllocTrap TRAP-TYPE
        ENTERPRISE        accBgpTraps 
        VARIABLES       { accBgpTrapMsg ,
                           accTrapLogSeqNum}
        DESCRIPTION
                "Announce alloc failed due to memory shortage.
SEVERITY-DEFAULT: Major 
EVENTTYPE-DEFAULT: 10 
ADDITIONAL-TEXT-VARIABLES: { accTrapLogSeqNum,accBgpTrapMsg }
PCAUSE-DEFAULT: 32 " 
 
        ::= 24
        accBgpAddNhTrap TRAP-TYPE
        ENTERPRISE        accBgpTraps 
        VARIABLES       { accBgpTrapMsg ,
                           accTrapLogSeqNum}
        DESCRIPTION
                "ip_add_nh Failed due to memory shortage.
SEVERITY-DEFAULT: Major 
EVENTTYPE-DEFAULT: 10 
ADDITIONAL-TEXT-VARIABLES: { accTrapLogSeqNum,accBgpTrapMsg }
PCAUSE-DEFAULT: 32 " 
 
        ::= 25
        accBgpNlriAllocTrap TRAP-TYPE
        ENTERPRISE        accBgpTraps 
        VARIABLES       { accBgpTrapMsg ,
                           accTrapLogSeqNum}
        DESCRIPTION
                "Alloc NLRI failed due to memory shortage.
SEVERITY-DEFAULT: Major 
EVENTTYPE-DEFAULT: 10 
ADDITIONAL-TEXT-VARIABLES: { accTrapLogSeqNum,accBgpTrapMsg }
PCAUSE-DEFAULT: 32 " 
 
        ::= 26  
        accBgpPeerRtAllocTrap TRAP-TYPE
        ENTERPRISE        accBgpTraps 
        VARIABLES       { accBgpTrapMsg ,
                           accTrapLogSeqNum}
        DESCRIPTION
                "Alloc route failed due to memory shortage.
SEVERITY-DEFAULT: Major 
EVENTTYPE-DEFAULT: 10 
ADDITIONAL-TEXT-VARIABLES: { accTrapLogSeqNum,accBgpTrapMsg }
PCAUSE-DEFAULT: 32 " 
 
        ::= 27 
        accBgpPeerRtEntryAllocTrap TRAP-TYPE
        ENTERPRISE        accBgpTraps 
        VARIABLES       { accBgpTrapMsg ,
                           accTrapLogSeqNum}
        DESCRIPTION
                "Alloc route entry failed due to memory shortage.
SEVERITY-DEFAULT: Major 
EVENTTYPE-DEFAULT: 10 
ADDITIONAL-TEXT-VARIABLES: { accTrapLogSeqNum,accBgpTrapMsg }
PCAUSE-DEFAULT: 32 " 
 
        ::= 28
        accBgpRtInfoAllocTrap TRAP-TYPE
        ENTERPRISE        accBgpTraps 
        VARIABLES       { accBgpTrapMsg ,
                           accTrapLogSeqNum}
        DESCRIPTION
                "Alloc BGP route info failed due to memory shortage.
SEVERITY-DEFAULT: Major 
EVENTTYPE-DEFAULT: 10 
ADDITIONAL-TEXT-VARIABLES: { accTrapLogSeqNum,accBgpTrapMsg }
PCAUSE-DEFAULT: 32 " 
 
        ::= 29
        accBgpEvntMemTrap TRAP-TYPE
        ENTERPRISE        accBgpTraps 
        VARIABLES       { accBgpTrapMsg,
                          bgpPeerLocalAddr,
                          bgpPeerRemoteAddr ,
accTrapLogSeqNum}
        DESCRIPTION
                "Allocation for event message failed due to memory 
		 shortage.
SEVERITY-DEFAULT: Major 
EVENTTYPE-DEFAULT: 10 
ADDITIONAL-TEXT-VARIABLES: { accTrapLogSeqNum,accBgpTrapMsg }
PCAUSE-DEFAULT: 32 " 
 
        ::= 30 
        accBgpPeerCBAllocTrap TRAP-TYPE
        ENTERPRISE        accBgpTraps 
        VARIABLES       { accBgpTrapMsg,
                          bgpPeerLocalAddr,
                          bgpPeerRemoteAddr ,
accTrapLogSeqNum}
        DESCRIPTION
                "Peer CB not allocated due to memory shortage.
SEVERITY-DEFAULT: Major 
EVENTTYPE-DEFAULT: 10 
ADDITIONAL-TEXT-VARIABLES: { accTrapLogSeqNum,accBgpTrapMsg }
PCAUSE-DEFAULT: 32 " 
 
        ::= 31
        accBgpRelEvntMemTrap TRAP-TYPE
        ENTERPRISE        accBgpTraps 
        VARIABLES       { accBgpTrapMsg,
                          bgpPeerLocalAddr,
                          bgpPeerRemoteAddr ,
accTrapLogSeqNum}
        DESCRIPTION
        	"Allocation for event message failed due to memory 
		 shortage.
SEVERITY-DEFAULT: Major 
EVENTTYPE-DEFAULT: 10 
ADDITIONAL-TEXT-VARIABLES: { accTrapLogSeqNum,accBgpTrapMsg }
PCAUSE-DEFAULT: 32 " 
 
        ::= 32
        accBgpConnectTrap TRAP-TYPE
        ENTERPRISE        accBgpTraps 
        VARIABLES       { accBgpTrapMsg,
                          bgpPeerLocalAddr,
                          bgpPeerRemoteAddr ,
accTrapLogSeqNum}
        DESCRIPTION
                "Indicates that creating a connection has failed.
SEVERITY-DEFAULT: Minor 
EVENTTYPE-DEFAULT: 2 
ADDITIONAL-TEXT-VARIABLES: { accTrapLogSeqNum,accBgpTrapMsg }
PCAUSE-DEFAULT: 5 " 
 
        ::= 33 
        accBgpPeerInvStateTrap TRAP-TYPE
        ENTERPRISE        accBgpTraps 
        VARIABLES       { accBgpTrapMsg,
                          bgpPeerRemoteAddr,
                          bgpPeerState ,
accTrapLogSeqNum}
        DESCRIPTION
                "Peer <REMOTE_ADDRESS> invalid state.
SEVERITY-DEFAULT: Minor 
EVENTTYPE-DEFAULT: 2 
ADDITIONAL-TEXT-VARIABLES: { accTrapLogSeqNum,accBgpTrapMsg }
PCAUSE-DEFAULT: 5 " 
 
        ::= 34
        accBgpAllocTrap TRAP-TYPE
        ENTERPRISE        accBgpTraps 
        VARIABLES       { accBgpTrapMsg,
                          accBgpPeerAddress ,
                           accTrapLogSeqNum}
        DESCRIPTION
                "Alloc failed due to memory shortage.
SEVERITY-DEFAULT: Major 
EVENTTYPE-DEFAULT: 10 
ADDITIONAL-TEXT-VARIABLES: { accTrapLogSeqNum,accBgpTrapMsg }
PCAUSE-DEFAULT: 32 " 
 
        ::= 35
        accBgpPeerNoTxBfrTrap TRAP-TYPE
        ENTERPRISE        accBgpTraps 
        VARIABLES       { accBgpTrapMsg,
                          accBgpPeerAddress ,
                           accTrapLogSeqNum}
        DESCRIPTION
        	"Allocation for transmit buffers failed due to memory 
		 shortage.
SEVERITY-DEFAULT: Minor 
EVENTTYPE-DEFAULT: 2 
ADDITIONAL-TEXT-VARIABLES: { accTrapLogSeqNum,accBgpTrapMsg }
PCAUSE-DEFAULT: 5 " 
 
        ::= 36
        accBgpPeerWriteTrap TRAP-TYPE
        ENTERPRISE        accBgpTraps 
        VARIABLES       { accBgpTrapMsg,
                          accBgpPeerAddress ,
                           accTrapLogSeqNum}
        DESCRIPTION
                "The peer has no valid control block; so any write 
		 operation will be rejected.
SEVERITY-DEFAULT: Minor 
EVENTTYPE-DEFAULT: 2 
ADDITIONAL-TEXT-VARIABLES: { accTrapLogSeqNum,accBgpTrapMsg }
PCAUSE-DEFAULT: 5 " 
 
        ::= 37 
        accBgpClosingConnTrap TRAP-TYPE
        ENTERPRISE        accBgpTraps 
        VARIABLES       { accBgpTrapMsg,
                          accBgpPeerAddress ,
                           accTrapLogSeqNum}
        DESCRIPTION
                "The peer has no valid control block; so any write 
		 operation will be rejected.
SEVERITY-DEFAULT: Minor 
EVENTTYPE-DEFAULT: 2 
ADDITIONAL-TEXT-VARIABLES: { accTrapLogSeqNum,accBgpTrapMsg }
PCAUSE-DEFAULT: 5 " 
 
        ::= 38
        accBgpSpoolBfrTrap TRAP-TYPE
        ENTERPRISE        accBgpTraps 
        VARIABLES       { accBgpTrapMsg,
                          accBgpPeerAddress ,
                           accTrapLogSeqNum}
        DESCRIPTION
                "Indicates that spool buffer for a peer is tried to 
		 create even though it has one already.
SEVERITY-DEFAULT: Major 
EVENTTYPE-DEFAULT: 10 
ADDITIONAL-TEXT-VARIABLES: { accTrapLogSeqNum,accBgpTrapMsg }
PCAUSE-DEFAULT: 32 " 
 
        ::= 39
        accBgpRtryCntTrap TRAP-TYPE
        ENTERPRISE        accBgpTraps 
        VARIABLES       { accBgpTrapMsg,
                          accBgpPeerAddress ,
                           accTrapLogSeqNum}
        DESCRIPTION
                "Peer <bgp_peeer> retry count exceeded, closing 
		 connection.
SEVERITY-DEFAULT: Minor 
EVENTTYPE-DEFAULT: 2 
ADDITIONAL-TEXT-VARIABLES: { accTrapLogSeqNum,accBgpTrapMsg }
PCAUSE-DEFAULT: 45 " 
 
        ::= 40
        accBgpPaAllocTrap TRAP-TYPE
        ENTERPRISE        accBgpTraps 
        VARIABLES       { accBgpTrapMsg ,
                           accTrapLogSeqNum}
        DESCRIPTION
                "Alloc PA failed due to memory shortage.
SEVERITY-DEFAULT: Major 
EVENTTYPE-DEFAULT: 10 
ADDITIONAL-TEXT-VARIABLES: { accTrapLogSeqNum,accBgpTrapMsg }
PCAUSE-DEFAULT: 32 " 
 
        ::= 41
        accBgpPSegAllocTrap TRAP-TYPE
        ENTERPRISE        accBgpTraps 
        VARIABLES       { accBgpTrapMsg ,
                           accTrapLogSeqNum}
        DESCRIPTION
                "Alloc PSeg failed due to memory shortage.
SEVERITY-DEFAULT: Major 
EVENTTYPE-DEFAULT: 10 
ADDITIONAL-TEXT-VARIABLES: { accTrapLogSeqNum,accBgpTrapMsg }
PCAUSE-DEFAULT: 32 " 
 
        ::= 42
        accBgpAddNxtHopTrap TRAP-TYPE
        ENTERPRISE        accBgpTraps 
        VARIABLES       { accBgpTrapMsg ,
                           accTrapLogSeqNum}
        DESCRIPTION
                "Adding nexthop failed due to memory shortage.
SEVERITY-DEFAULT: Warning 
EVENTTYPE-DEFAULT: 10 
ADDITIONAL-TEXT-VARIABLES: { accTrapLogSeqNum,accBgpTrapMsg }
PCAUSE-DEFAULT: 7 " 
 
        ::= 43
        accBgpRxBufAllocTrap TRAP-TYPE
        ENTERPRISE        accBgpTraps 
        VARIABLES       { accBgpTrapMsg,
                          accBgpPeerAddress ,
                           accTrapLogSeqNum}
        DESCRIPTION
                "Alloc receive buffer failed due to memory shortage.
SEVERITY-DEFAULT: Major 
EVENTTYPE-DEFAULT: 10 
ADDITIONAL-TEXT-VARIABLES: { accTrapLogSeqNum,accBgpTrapMsg }
PCAUSE-DEFAULT: 32 " 
 
        ::= 44
        accBgpPeerRcvBfrAllocTrap TRAP-TYPE
        ENTERPRISE        accBgpTraps 
        VARIABLES       { accBgpTrapMsg,
                          accBgpPeerAddress ,
                           accTrapLogSeqNum}
        DESCRIPTION
                "Alloc Message Receive Buffer failed due to memory 
		 shortage.
SEVERITY-DEFAULT: Major 
EVENTTYPE-DEFAULT: 10 
ADDITIONAL-TEXT-VARIABLES: { accTrapLogSeqNum,accBgpTrapMsg }
PCAUSE-DEFAULT: 32 " 
 
        ::= 45   
END
