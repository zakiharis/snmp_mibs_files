A3Com-Llc-r1-MIB DEFINITIONS ::= BEGIN

IMPORTS
    enterprises, Counter, Gauge, TimeTicks, IpAddress
        FROM RFC1155-SMI

    DisplayString
        FROM RFC1213-MIB

    ifIndex 
        FROM RFC1213-MIB

    OBJECT-TYPE
        FROM RFC-1212
	Integer32 FROM SNMPv2-SMI;

--
-- Represents an 802 MAC address represented in non-canonical format.  
-- That is, the most significant bit will be transmitted first.
--
   MacAddress ::= OCTET STRING (SIZE (6)) 

-- indistinguishable from INTEGER, but never needs more than
-- 32-bits for a two's complement representation
-- [Next line commented out by HP to work with 4.1 version of xnmloadmib]
-- Integer32 ::= INTEGER (-2147483648..2147483647)

--
--  The following data link controls are modelled in this MIB module:
--
--     1. LLC
--

a3com       OBJECT IDENTIFIER ::= { enterprises 43 }
brouterMIB  OBJECT IDENTIFIER ::= { a3com 2 }
llc         OBJECT IDENTIFIER ::= { brouterMIB 26 }

--
--  THE LLC GROUP
--  =============
--
--  The following resources are modelled in the LLC group of this MIB module:
--
--     1. Ports
--     2. Service Access Points
--     3. Connection Components
--     4. Tunnels

llcPortGroup     OBJECT IDENTIFIER ::= { llc 1 } -- Physical Ports
llcSapGroup      OBJECT IDENTIFIER ::= { llc 2 } -- Local SAPs
llcCcGroup       OBJECT IDENTIFIER ::= { llc 3 } -- Connection Components
llcTunnelGroup   OBJECT IDENTIFIER ::= { llc 4 } -- Tunnels

--
--  THE LLC PORT GROUP
--  ==================
--
--  The following classes of information are modelled for each LLC port:
--
--     1.  ADMINISTRATIVE ( read/write )
--     2.  OPERATIONAL    ( read-only  )
--     3.  STATISTICS     ( read-only  ) 

--  Information not found in this group is found in tables described in
--  the following RFCs:
--
--    1.  RFC1213  - MIB-II
--
--            TABLE                      INDEX
--            ====================       ====================
--        a.  ifTable                    ifIndex
--
--  *************************************************************
--  *                                                           *
--  *           THE LLC PORT ADMINISTRATIVE TABLE               *
--  *                                                           *
--  *************************************************************

llcPortAdminTable   OBJECT-TYPE
                    SYNTAX      SEQUENCE OF LlcPortAdminEntry
                    ACCESS      not-accessible
                    STATUS      mandatory
                    DESCRIPTION
                        "This table contains objects that can be
                        changed to manage an LLC port.    Changing one
                        of these parameters may take effect in the
                        operating port immediately or may wait until
                        the interface is restarted depending on the
                        details of the implementation.

                        The operating values may be different from
                        these configured values if  a configured
                        parameter was changed after the interface was
                        started."
                    ::= { llcPortGroup 1 }

llcPortAdminEntry   OBJECT-TYPE
                    SYNTAX      LlcPortAdminEntry
                    ACCESS      not-accessible
                    STATUS      mandatory
                    DESCRIPTION
                        "A list of configured values for an LLC port."
                    INDEX   { ifIndex }
                    ::= { llcPortAdminTable 1 }

LlcPortAdminEntry   ::= SEQUENCE
{
        llcPortAdminName                DisplayString,
        llcPortAdminMaxSaps             Gauge,
        llcPortAdminMaxCcs              Gauge,
        llcPortAdminMaxPDUOctets        Integer32,
        llcPortAdminMaxUnackedIPDUsSend INTEGER,
        llcPortAdminMaxUnackedIPDUsRcv  INTEGER,
        llcPortAdminMaxRetransmits      Integer32,
        llcPortAdminAckTimer            TimeTicks,
        llcPortAdminPbitTimer           TimeTicks,
        llcPortAdminRejTimer            TimeTicks,
        llcPortAdminBusyTimer           TimeTicks,
        llcPortAdminInactTimer          TimeTicks,
        llcPortAdminDelayAckCount       Integer32,
        llcPortAdminDelayAckTimer       TimeTicks,
        llcPortAdminNw                  Integer32
}

llcPortAdminName   OBJECT-TYPE
                    SYNTAX      DisplayString (SIZE (1..10))
                    ACCESS      read-only
                    STATUS      mandatory
                    DESCRIPTION
                        "An octet string that defines the physical port
                        to which this interface is assigned.  It has
                        implementation-specific significance. Its value
                        shall be unique within the administered
                        system.  It must contain only ASCII printable
                        characters."
                    ::= { llcPortAdminEntry 1 }

llcPortAdminMaxSaps OBJECT-TYPE
                    SYNTAX      Gauge
                    ACCESS      read-write
                    STATUS      mandatory
                    DESCRIPTION
                        "This parameter specifies the maximum number of
                        SAPs that can be defined for this port."
                    ::= { llcPortAdminEntry 2 }

llcPortAdminMaxCcs  OBJECT-TYPE
                    SYNTAX      Gauge
                    ACCESS      read-write
                    STATUS      mandatory
                    DESCRIPTION
                        "This parameter specifies the maximum number of
                        connection components that can be
                        administratively defined for this port."
                    ::= { llcPortAdminEntry 3 }

llcPortAdminMaxPDUOctets   OBJECT-TYPE
                    SYNTAX      Integer32
                    ACCESS      read-write
                    STATUS      mandatory
                    DESCRIPTION
                        "This object denotes the default maximum I PDU
                        size, in octets, that LLCs on this port may
                        send to and receive from their remote LLC
                        partners. This count is referred to as 'N1' in
                        the IEEE 802.2 specification [5].  This size
                        includes I-Frames, UI-Frames, XIDs, and TEST
                        frames.

                        The I PDU size includes all octets in a frame,
                        excluding framing characters, the MAC header,
                        and the LLC header."
                    ::= { llcPortAdminEntry 4 }

llcPortAdminMaxUnackedIPDUsSend OBJECT-TYPE
                    SYNTAX      INTEGER (1..127)
                    ACCESS      read-write
                    STATUS      mandatory
                    DESCRIPTION
                        "This object denotes the default maximum
                        consecutive unacknowledged I PDU frames that
                        LLCs on this port may send to their remote LLC
                        partners. This count is referred to as 'k' in
                        the IEEE 802.2 specification [5].

                        At connection setup, the remote LLC may send,
                        using an XID frame, the maximum number of
                        unacknowledged I PDUs which it is prepared to
                        receive. If so, an implementation may choose to
                        override the administered maximum number of
                        unacknowledged PDUs with the dynamically learned
                        value and should reflect this in the
                        llcCcOperMaxUnackedIPDUsSend object for the
                        connection component."
                    DEFVAL { 7 }
                    ::= { llcPortAdminEntry 5 }

llcPortAdminMaxUnackedIPDUsRcv  OBJECT-TYPE
                    SYNTAX      INTEGER (1..127)
                    ACCESS      read-write
                    STATUS      mandatory
                    DESCRIPTION
                        "This object denotes the default maximum number
                        of unacknowledged I PDUs that LLCs on this port
                        can expect to receive from their remote LLC
                        partners. This count is referred to as 'k' in
                        the IEEE 802.2 specification [5].

                        At connection setup, an implementation may
                        choose to send this value to the remote LLC,
                        using an XID frame."
                    DEFVAL { 7 }
                    ::= { llcPortAdminEntry 6 }

llcPortAdminMaxRetransmits      OBJECT-TYPE
                    SYNTAX      Integer32
                    ACCESS      read-write
                    STATUS      mandatory
                    DESCRIPTION
                       "This object denotes the default value for the
                       maximum number of times which LLCs on this port
                       shall retry a PDU following the expiration of
                       the acknowledgement timer, the P-bit timer or
                       the reject timer. When these retries are
                       exhausted, the link shall be declared inactive.
                       This count is referred to as 'N2' in the IEEE
                       802.2 specification [5]."
                    DEFVAL { 7 }
                    ::= { llcPortAdminEntry 7 }

llcPortAdminAckTimer            OBJECT-TYPE
                    SYNTAX      TimeTicks
                    ACCESS      read-write
                    STATUS      mandatory
                    DESCRIPTION
                       "This object denotes the default value for the
                       time interval during which the LLCs on this port
                       shall expect to receive either:

                       1) an acknowledgement to one or more outstanding
                       I PDUs.  or 2) a response PDU to an unnumbered
                       command PDU.

                       The expiration of this timer shall cause the
                       unacknowledged frames to be retransmitted
                       (up to N2 times).

                       For Implementations that only use a single
                       'T1' Value (ref. IBM Token-Ring Network
                       technical reference Chapter 11).  This object
                       will be used to control/read the value."
                    DEFVAL { 300 }
                    ::= { llcPortAdminEntry 8 }


llcPortAdminPbitTimer           OBJECT-TYPE
                    SYNTAX      TimeTicks
                    ACCESS      read-write
                    STATUS      mandatory
                    DESCRIPTION
                        "This object denotes the default value for the
                        time interval during which the LLCs on this
                        port shall expect to receive a PDU with the F
                        bit set to '1' in response to a Type 2 command
                        with the P bit set to '1'.

                        The expiration of this timer shall cause the
                        command with the poll bit to be retransmitted
                        (up to N2 times)."
                    DEFVAL { 300 }
                    ::= { llcPortAdminEntry 9 }

llcPortAdminRejTimer           OBJECT-TYPE
                    SYNTAX      TimeTicks
                    ACCESS      read-write
                    STATUS      mandatory
                    DESCRIPTION
                        "This object denotes the default value for the
                        time interval during which the LLCs on this
                        port shall expect to receive a reply to a REJ
                        PDU.

                        The expiration of this timer shall cause the
                        REJ PDU to be retransmitted (up to N2 times)."
                    DEFVAL { 300 }
                    ::= { llcPortAdminEntry 10 }

llcPortAdminBusyTimer           OBJECT-TYPE
                    SYNTAX      TimeTicks
                    ACCESS      read-write
                    STATUS      mandatory
                    DESCRIPTION
                        "This object denotes the default value for the
                        time interval during which the LLCs on this
                        port shall expect to receive an indication that
                        a busy condition at the remote LLC has
                        cleared.

                        The expiration of this timer causes the
                        adjacent connection component to be polled."
                    DEFVAL { 30000 }
                    ::= { llcPortAdminEntry 11 }

llcPortAdminInactTimer          OBJECT-TYPE
                    SYNTAX      TimeTicks
                    ACCESS      read-write
                    STATUS      mandatory
                    DESCRIPTION
                        "This object denotes the default value for the
                        time interval during which the LLCs on this
                        port shall expect to receive any PDU from the
                        remote LLC.  This function is not described in
                        the IEEE 802.2 specification [5].  It is listed
                        in the IBM Token-Ring Network Architecture [6]
                        Reference as the Ti parameter and is widely
                        implemented.

                        The expiration of this timer shall cause the
                        local LLC to send a PDU to the remote LLC with
                        the P bit set to '1'.

                        Any value for this object less than or equal to
                        the acknowledgement timer shall mean that the
                        timer is not used."
                    DEFVAL { 1500 }
                    ::= { llcPortAdminEntry 12 }

llcPortAdminDelayAckCount       OBJECT-TYPE
                    SYNTAX      Integer32
                    ACCESS      read-write
                    STATUS      mandatory
                    DESCRIPTION
                        "This object denotes the default value for the
                        maximum number of consecutive I PDUs which the
                        LLCs on this port shall receive during the
                        interval defined by llcCcOperDelayTimer
                        without sending an immediate acknowledgement.
                        This must be less than or equal to the value of
                        llcCcOperMaxUnackIPDUsRcv. This function is not
                        described in the IEEE 802.2 specification [5].
                        It is listed in the IBM Token-Ring Network
                        Architecture Reference [6] as the N3 parameter
                        and is widely implemented.

                        A value of one indicates that acknowledgments
                        will be sent immediately and that the value of
                        llcPortAdminDelayAckTimer shall be ignored."
                    DEFVAL { 1 }
                    ::= { llcPortAdminEntry 13 }

llcPortAdminDelayAckTimer       OBJECT-TYPE
                    SYNTAX      TimeTicks
                    ACCESS      read-write
                    STATUS      mandatory
                    DESCRIPTION
                        "This object denotes the default value for the
                        time interval during which the LLCs on this
                        port shall delay acknowledgment of one or more
                        I PDUs (up to the value of
                        llcCcOperDelayAckCount). This function is not
                        described in the IEEE 802.2 specification [5].

                        It is listed in the IBM Token-Ring Network
                        Architecture Reference [6] as the T2 parameter
                        and is widely implemented.

                        The expiration of this timer shall cause the
                        local LLC to acknowledge all unacknowledged I
                        PDUs.  A value of 0 means that an
                        acknowledgement will be sent immediately.

                        This object is associated with the
                        llcPortAdminDelayAckCount object and is only
                        defined if that object has a value greater than
                        one."
                    DEFVAL { 0 }
                    ::= { llcPortAdminEntry 14 }

llcPortAdminNw      OBJECT-TYPE
                    SYNTAX      Integer32
                    ACCESS      read-write
                    STATUS      mandatory
                    DESCRIPTION
                        "This object denotes the default value for the
                        number of IPDUs that must be acknowledged
                        before the working window size (Ww) can be
                        incremented by 1 when the working window is not
                        equal to the maximum transmit window size (TW).
                        It controls the gradual incrementing of Ww in
                        congestion situations.

                        This function is not described in the IEEE
                        802.2 specification [5].  However, it is listed
                        in the IBM Token-Ring Network Architecture
                        Reference [6] as the Nw parameter and is widely
                        implemented."
                    DEFVAL { 4 }
                    ::= { llcPortAdminEntry 15 }

--  *************************************************************
--  *                                                           *
--  *                THE LLC PORT OPERATIONAL TABLE             *
--  *                                                           *
--  *************************************************************

llcPortOperTable    OBJECT-TYPE
                    SYNTAX      SEQUENCE OF LlcPortOperEntry
                    ACCESS      not-accessible
                    STATUS      mandatory
                    DESCRIPTION
                        "This table contains current LLC port
                        parameters.  Many of these objects have
                        corresponding objects in the llcPortAdminTable."
                    ::= { llcPortGroup 2 }

llcPortOperEntry    OBJECT-TYPE
                    SYNTAX      LlcPortOperEntry
                    ACCESS      not-accessible
                    STATUS      mandatory
                    DESCRIPTION
                        "Currently set parameters for a specific LLC port."
                    INDEX   { ifIndex }
                    ::= { llcPortOperTable 1 }

LlcPortOperEntry   ::= SEQUENCE
{
        llcPortOperNumSaps              Gauge,
        llcPortOperSimRim               INTEGER,
        llcPortOperLastModifyTime       TimeTicks
}

llcPortOperNumSaps  OBJECT-TYPE
                    SYNTAX      Gauge
                    ACCESS      read-only
                    STATUS      mandatory
                    DESCRIPTION
                        "This object defines the number of SAPs on this
                        port that are currently enabled.  In other
                        words, this object is a count of the number of
                        instances of llcSapOperEntry that have a
                        llcSapOperStatus value of 'active(2)'."
                    ::= { llcPortOperEntry 1 }

llcPortOperSimRim   OBJECT-TYPE
                    SYNTAX      INTEGER
                    {
                         no   (1),
                         yes  (2)
                    }
                    ACCESS      read-only
                    STATUS      mandatory
                    DESCRIPTION
                        "This object reflects support for transmission
                        and receipt of SIM and RIM control frames for
                        this port.

                        SIM and RIM are not defined in the ANSI/IEEE
                        802.2 specification [5] nor in the IBM Token
                        Ring Architecture Reference [6].  These
                        control frames are used for the remote program
                        load of IBM communications processors."
                    DEFVAL { no }
                    ::= { llcPortOperEntry 2 }

llcPortOperLastModifyTime     OBJECT-TYPE
                    SYNTAX      TimeTicks
                    ACCESS      read-only
                    STATUS      mandatory
                    DESCRIPTION
                         "This object describes the value of sysUpTime
                         when this port definition was last modified.
                         If the port has not been modified, then this
                         value shall be zero."
                    ::= { llcPortOperEntry 3 }

--  *************************************************************
--  *                                                           *
--  *           THE LLC PORT STATISTICS TABLE                   *
--  *                                                           *
--  *************************************************************

-- llcPortStatsTable   OBJECT-TYPE
--                     SYNTAX      SEQUENCE OF LlcPortStatsEntry
--                     ACCESS      not-accessible
--                     STATUS      mandatory
--                     DESCRIPTION
--                         "Each entry in this table contains statistics
--                         for a specific LLC port."
--                      ::= { llcPortGroup 3 }

--  llcPortStatsEntry   OBJECT-TYPE
--                     SYNTAX      LlcPortStatsEntry
--                     ACCESS      not-accessible
--                     STATUS      mandatory
--                     DESCRIPTION
--                         "A list of statistics for an LLC port."
--                     INDEX   { ifIndex }
--                     ::= { llcPortStatsTable 1 }

--  LlcPortStatsEntry ::= SEQUENCE
--  {
--      The llcPortStatsTable does not contain any entries and remains
--      here merely as a placeholder.
--  }

--
--  THE LLC SAP GROUP
--  =================
--

--  The following classes of information are modelled for each local SAP:
--
--     1.  ADMINISTRATIVE ( read-only )
--     2.  OPERATIONAL    ( read-only )
--     3.  STATISTICS     ( read-only )

--  *************************************************************
--  *                                                           *
--  *           THE LLC SAP ADMINISTRATIVE TABLE                *
--  *                                                           *
--  *************************************************************

llcSapAdminTable    OBJECT-TYPE
                    SYNTAX      SEQUENCE OF LlcSapAdminEntry
                    ACCESS      not-accessible
                    STATUS      mandatory
                    DESCRIPTION
                        "This table contains objects that can be
                        changed to manage a local SAP.    Changing one
                        of these parameters may take effect in the
                        operating SAP immediately or may wait until the
                        interface is restarted depending on the details
                        of the implementation.

                        The operating values may be different from
                        these configured values if  a configured
                        parameter was changed after the interface was
                        started."
                     ::= { llcSapGroup 1 }

llcSapAdminEntry    OBJECT-TYPE
                    SYNTAX      LlcSapAdminEntry
                    ACCESS      not-accessible
                    STATUS      mandatory
                    DESCRIPTION
                        "A list of configured values for a local SAP."
                    INDEX   { ifIndex, llcSapNumber }
                    ::= { llcSapAdminTable 1 }

LlcSapAdminEntry   ::= SEQUENCE
{
--
--          3Com does not currently support SAP configuration;
--          if it does at a future date, the rest of the entries for
--          this table will be implemented.
--
        llcSapNumber                    INTEGER
}

llcSapNumber        OBJECT-TYPE
                    SYNTAX      INTEGER (1..254)
                    ACCESS      read-only
                    STATUS      mandatory
                    DESCRIPTION
                        "The address of this local SAP."
                    ::= { llcSapAdminEntry 1 }


--  *************************************************************
--  *                                                           *
--  *           THE LLC SAP OPERATIONAL TABLE                   *
--  *                                                           *
--  *************************************************************

llcSapOperTable     OBJECT-TYPE
                    SYNTAX      SEQUENCE OF LlcSapOperEntry
                    ACCESS      not-accessible
                    STATUS      mandatory
                    DESCRIPTION
                        "This table contains objects that reflect the
                        current operational parameters of a local SAP."
                     ::= { llcSapGroup 2 }

llcSapOperEntry     OBJECT-TYPE
                    SYNTAX      LlcSapOperEntry
                    ACCESS      not-accessible
                    STATUS      mandatory
                    DESCRIPTION
                        "A list of configured values for a local SAP."
                    INDEX   { ifIndex, llcSapNumber }
                    ::= { llcSapOperTable 1 }

LlcSapOperEntry   ::= SEQUENCE
{
        llcSapOperStatus                INTEGER,
        llcSapOperNumCcs                Integer32,
        llcSapOperLlc2Support           INTEGER
}

llcSapOperStatus    OBJECT-TYPE
                    SYNTAX      INTEGER
                    {
                         inactive  (1),
                         active    (2)
                    }
                    ACCESS      read-only
                    STATUS      mandatory
                    DESCRIPTION
                        "This parameter describes the actual state of
                        this local SAP."
                    ::= { llcSapOperEntry 1 }

llcSapOperNumCcs    OBJECT-TYPE
                    SYNTAX      Integer32
                    ACCESS      read-only
                    STATUS      mandatory
                    DESCRIPTION
                        "This object defines the number of connection
                        components on this SAP that are currently in
                        one of the 'connected' states.  In other words,
                        this object is a count of the number of
                        instances of llcCcOperEntry that have a
                        llcCcOperState value greater than or equal to
                        'normal(3)'."
                    ::= { llcSapOperEntry 2 }

llcSapOperLlc2Support OBJECT-TYPE
                    SYNTAX      INTEGER
                    {
                         no   (1),
                         yes  (2)
                    }
                    ACCESS      read-only
                    STATUS      mandatory
                    DESCRIPTION
                        "This parameter describes whether or not the
                        LLC implementation supports LLC2 connection
                        components."
                    ::= { llcSapOperEntry 3 }

--  *************************************************************
--  *                                                           *
--  *           THE LLC SAP STATISTICS TABLE                    *
--  *                                                           *
--  *************************************************************

llcSapStatsTable    OBJECT-TYPE
                    SYNTAX      SEQUENCE OF LlcSapStatsEntry
                    ACCESS      not-accessible
                    STATUS      mandatory
                    DESCRIPTION
                        "This table contains objects that reflect the
                        current operational statistics of a local SAP."
                     ::= { llcSapGroup 3 }

llcSapStatsEntry    OBJECT-TYPE
                    SYNTAX      LlcSapStatsEntry
                    ACCESS      not-accessible
                    STATUS      mandatory
                    DESCRIPTION
                        "A list of configured values for a local SAP."
                    INDEX   { ifIndex, llcSapNumber }
                    ::= { llcSapStatsTable 1 }

LlcSapStatsEntry   ::= SEQUENCE
{
        llcSapStatsLocalBusies          Counter,
        llcSapStatsRemoteBusies         Counter,
        llcSapStatsIFramesIn            Counter,
        llcSapStatsIFramesOut           Counter,
        llcSapStatsIOctetsIn            Counter,
        llcSapStatsIOctetsOut           Counter,
        llcSapStatsSFramesIn            Counter,
        llcSapStatsSFramesOut           Counter,
        llcSapStatsRetransmitsOut       Counter,
        llcSapStatsREJsIn               Counter,
        llcSapStatsREJsOut              Counter,
        llcSapStatsWwCount              Counter,
        llcSapStatsTESTCommandsIn       Counter,
        llcSapStatsTESTCommandsOut      Counter,
        llcSapStatsTESTResponsesIn      Counter,
        llcSapStatsTESTResponsesOut     Counter,
        llcSapStatsXIDCommandsIn        Counter,
        llcSapStatsXIDCommandsOut       Counter,
        llcSapStatsXIDResponsesIn       Counter,
        llcSapStatsXIDResponsesOut      Counter,
        llcSapStatsUIFramesIn           Counter,
        llcSapStatsUIFramesOut          Counter,
        llcSapStatsUIOctetsIn           Counter,
        llcSapStatsUIOctetsOut          Counter,
        llcSapStatsConnectOk            Counter,
        llcSapStatsConnectFail          Counter,
        llcSapStatsDisconnect           Counter,
        llcSapStatsDisconnectFRMRSend   Counter,
        llcSapStatsDisconnectFRMRRcv    Counter,
        llcSapStatsDisconnectTimer      Counter,
        llcSapStatsReset                Counter
}

llcSapStatsLocalBusies OBJECT-TYPE
                    SYNTAX      Counter
                    ACCESS      read-only
                    STATUS      mandatory
                    DESCRIPTION
                        "This object reflects the total number of times
                        that the local connection components on this
                        SAP have entered a busy state (RNR).  This
                        object is initialized to zero when the SAP is
                        created."
                    ::= { llcSapStatsEntry 1 }

llcSapStatsRemoteBusies OBJECT-TYPE
                    SYNTAX      Counter
                    ACCESS      read-only
                    STATUS      mandatory
                    DESCRIPTION
                        "This object reflects the total number of
                        times that the adjacent (i.e. remote) connection
                        components on this SAP have entered a busy
                        state (RNR).  This object is initialized to
                        zero when the SAP is created."
                    ::= { llcSapStatsEntry 2 }

llcSapStatsIFramesIn OBJECT-TYPE
                    SYNTAX      Counter
                    ACCESS      read-only
                    STATUS      mandatory
                    DESCRIPTION
                        "This object reflects the total number of
                        I-Frames that have been received by connection
                        components on this SAP.  This object is
                        initialized to zero when the SAP is created."
                    ::= { llcSapStatsEntry 3 }

llcSapStatsIFramesOut OBJECT-TYPE
                    SYNTAX      Counter
                    ACCESS      read-only
                    STATUS      mandatory
                    DESCRIPTION
                        "This object reflects the total number of
                        I-Frames that have been transmitted by connection
                        components on this SAP.  This object is
                        initialized to zero when the SAP is created."
                    ::= { llcSapStatsEntry 4 }

llcSapStatsIOctetsIn OBJECT-TYPE
                    SYNTAX      Counter
                    ACCESS      read-only
                    STATUS      mandatory
                    DESCRIPTION
                        "This object reflects the total octets received
                        from adjacent connection components on this
                        SAP.  This object covers the address, control,
                        and information field of I-Frames only.  This
                        object is initialized to zero when the SAP is
                        created."
                    ::= { llcSapStatsEntry 5 }

llcSapStatsIOctetsOut OBJECT-TYPE
                    SYNTAX      Counter
                    ACCESS      read-only
                    STATUS      mandatory
                    DESCRIPTION
                        "This object reflects the total octets
                        transmitted to adjacent connection components
                        on this SAP.  This object covers the address,
                        control, and information field of I-Frames
                        only.  This object is initialized to zero when
                        the SAP is created."
                    ::= { llcSapStatsEntry 6 }

llcSapStatsSFramesIn OBJECT-TYPE
                    SYNTAX      Counter
                    ACCESS      read-only
                    STATUS      mandatory
                    DESCRIPTION
                        "This object reflects the total number of
                        S-Frames that have been received by connection
                        components on this SAP.  This object is
                        initialized to zero when the SAP is created.

                        Note - the ratio of the number of I-Frames to
                        S-Frames might serve as a measure of link
                        efficiency and, for instance, could be used to
                        tune the acknowledgement timer."
                    ::= { llcSapStatsEntry 7 }

llcSapStatsSFramesOut OBJECT-TYPE
                    SYNTAX      Counter
                    ACCESS      read-only
                    STATUS      mandatory
                    DESCRIPTION
                        "This object reflects the total number of
                        S-Frames that have been transmitted by connection
                        components on this SAP.  This object is
                        initialized to zero when the SAP is created.

                        Note - the ratio of the number of I-Frames to
                        S-Frames might serve as a measure of link
                        efficiency and, for instance, could be used to
                        tune the acknowledgement timer."
                    ::= { llcSapStatsEntry 8 }

llcSapStatsRetransmitsOut OBJECT-TYPE
                    SYNTAX      Counter
                    ACCESS      read-only
                    STATUS      mandatory
                    DESCRIPTION
                        "This object reflects the total number of
                        I-Frames retransmitted by all local connection
                        components on this SAP.  This object is
                        initialized to zero when the SAP is created."
                    ::= { llcSapStatsEntry 9 }

llcSapStatsREJsIn    OBJECT-TYPE
                    SYNTAX      Counter
                    ACCESS      read-only
                    STATUS      mandatory
                    DESCRIPTION
                        "This object reflects the total REJ frames
                        received from all adjacent LLC connection
                        components on this SAP since it was created."
                    ::= { llcSapStatsEntry 10 }

llcSapStatsREJsOut   OBJECT-TYPE
                    SYNTAX      Counter
                    ACCESS      read-only
                    STATUS      mandatory
                    DESCRIPTION
                        "This object reflects the total REJ frames
                        transmitted to an adjacent LLC connection
                        components on this SAP since it was created."
                    ::= { llcSapStatsEntry 11 }

llcSapStatsWwCount   OBJECT-TYPE
                    SYNTAX      Counter
                    ACCESS      read-only
                    STATUS      mandatory
                    DESCRIPTION
                        "This object reflects the total number of
                        times, since this SAP was created, that the
                        dynamic window algorithm has been invoked to
                        reduce the value of Ww on any of the connection
                        components of this SAP.  This object is
                        initialized to zero when the SAP is created.

                        This function is not described in the IEEE 802.2
                        specification [5], but is widely implemented."
                    ::= { llcSapStatsEntry 12 }

llcSapStatsTESTCommandsIn     OBJECT-TYPE
                    SYNTAX      Counter
                    ACCESS      read-only
                    STATUS      mandatory
                    DESCRIPTION
                        "This object denotes the number of TEST
                        commands this SAP has received and is a measure
                        of the number of stations in the network trying
                        to connect up.

                        This object is initialized to zero when the SAP
                        is created."
                    ::= { llcSapStatsEntry 13 }

llcSapStatsTESTCommandsOut    OBJECT-TYPE
                    SYNTAX      Counter
                    ACCESS      read-only
                    STATUS      mandatory
                    DESCRIPTION
                        "This object denotes the number of TEST
                        commands this SAP has sent and is a measure of
                        the number of other stations we are trying to
                        connect to.

                        This object is initialized to zero when the SAP
                        is created."
                    ::= { llcSapStatsEntry 14 }

llcSapStatsTESTResponsesIn    OBJECT-TYPE
                    SYNTAX      Counter
                    ACCESS      read-only
                    STATUS      mandatory
                    DESCRIPTION
                        "This object denotes the number of TEST
                        responses this SAP has received and is a
                        measure of the number of stations in the
                        network responding to TEST commands this SAP
                        has sent.

                        This object is initialized to zero when the SAP
                        is created."
                    ::= { llcSapStatsEntry 15 }

llcSapStatsTESTResponsesOut   OBJECT-TYPE
                    SYNTAX      Counter
                    ACCESS      read-only
                    STATUS      mandatory
                    DESCRIPTION
                        "This object denotes the number of TEST
                        responses this SAP has sent and is a measure of
                        the number of other stations trying to connect
                        to this SAP.

                        This object is initialized to zero when the SAP
                        is created."
                    ::= { llcSapStatsEntry 16 }

llcSapStatsXIDCommandsIn     OBJECT-TYPE
                    SYNTAX      Counter
                    ACCESS      read-only
                    STATUS      mandatory
                    DESCRIPTION
                        "This object denotes the number of XID commands
                        this SAP has received and is a measure of the
                        number of stations in the network trying to
                        connect to this SAP.  This object is a count of
                        all XIDs, including SNA XID, IEEE XID, null
                        XID, and non-activation XIDs.

                        This object is initialized to zero when the SAP
                        is created."
                    ::= { llcSapStatsEntry 17 }

llcSapStatsXIDCommandsOut    OBJECT-TYPE
                    SYNTAX      Counter
                    ACCESS      read-only
                    STATUS      mandatory
                    DESCRIPTION
                        "This object denotes the number of XID commands
                        this SAP has sent and is a measure of the
                        number of other stations this SAP is trying to
                        connect to.  This object is a count of all
                        XIDs, including SNA XID, IEEE XID, null XID,
                        and non-activation XIDs.

                        This object is initialized to zero when the SAP
                        is created."
                    ::= { llcSapStatsEntry 18 }

llcSapStatsXIDResponsesIn    OBJECT-TYPE
                    SYNTAX      Counter
                    ACCESS      read-only
                    STATUS      mandatory
                    DESCRIPTION
                        "This object denotes the number of XID
                        responses this SAP has received and is a
                        measure of the number of stations in the
                        network responding to TEST commands this SAP
                        has sent.  This object is a count of all XIDs,
                        including SNA XID, IEEE XID, null XID, and
                        non-activation XIDs.

                        This object is initialized to zero when the SAP
                        is created."
                    ::= { llcSapStatsEntry 19 }

llcSapStatsXIDResponsesOut   OBJECT-TYPE
                    SYNTAX      Counter
                    ACCESS      read-only
                    STATUS      mandatory
                    DESCRIPTION
                        "This object denotes the number of XID
                        responses this SAP has sent and is a measure of
                        the number of other stations trying to connect
                        to this SAP.  This object is a count of all
                        XIDs, including SNA XID, IEEE XID, null XID,
                        and non-activation XIDs.

                        This object is initialized to zero when the SAP
                        is created."
                    ::= { llcSapStatsEntry 20 }

llcSapStatsUIFramesIn OBJECT-TYPE
                    SYNTAX      Counter
                    ACCESS      read-only
                    STATUS      mandatory
                    DESCRIPTION
                        "This object reflects the total number of
                        unnumbered information (UI) frames received on
                        a local SAP."
                    ::= { llcSapStatsEntry 21 }

llcSapStatsUIFramesOut OBJECT-TYPE
                    SYNTAX      Counter
                    ACCESS      read-only
                    STATUS      mandatory
                    DESCRIPTION
                        "This object reflects the total number of
                        unnumbered information (UI) frames sent on a
                        local SAP."
                    ::= { llcSapStatsEntry 22 }

llcSapStatsUIOctetsIn OBJECT-TYPE
                    SYNTAX      Counter
                    ACCESS      read-only
                    STATUS      mandatory
                    DESCRIPTION
                        "This object reflects the total octets received
                        from adjacent connection components on this
                        SAP.  This object covers the address, control,
                        and information field of UI-Frames only.  This
                        object is initialized to zero when the SAP is
                        created."
                    ::= { llcSapStatsEntry 23 }

llcSapStatsUIOctetsOut OBJECT-TYPE
                    SYNTAX      Counter
                    ACCESS      read-only
                    STATUS      mandatory
                    DESCRIPTION
                        "This object reflects the total octets
                        transmitted to adjacent connection components
                        on this SAP.  This object covers the address,
                        control, and information field of UI-Frames
                        only.  This object is initialized to zero when
                        the SAP is created."
                    ::= { llcSapStatsEntry 24 }

llcSapStatsConnectOk OBJECT-TYPE
                    SYNTAX      Counter
                    ACCESS      read-only
                    STATUS      mandatory
                    DESCRIPTION
                        "This object reflects the total number of
                        successful connections that have been
                        established on this SAP since the SAP was
                        created.

                        A successful connection is indicated by a
                        successful SABME/UA exchange."
                    ::= { llcSapStatsEntry 25 }

llcSapStatsConnectFail OBJECT-TYPE
                    SYNTAX      Counter
                    ACCESS      read-only
                    STATUS      mandatory
                    DESCRIPTION
                        "This object reflects the total number of
                        unsuccessful connections that have been
                        attempted on this SAP since the SAP was
                        created.

                        An unsuccessful connection attempt is indicated
                        by a SABME/DM exchange or a SABME/timeout."
                    ::= { llcSapStatsEntry 26 }

llcSapStatsDisconnect OBJECT-TYPE
                    SYNTAX      Counter
                    ACCESS      read-only
                    STATUS      mandatory
                    DESCRIPTION
                        "This object reflects the total number of
                        normal disconnections that have been
                        performed on this SAP since the SAP was
                        created.

                        A normal disconnection is indicated by a
                        successful DISC/UA exchange or merely a DISC
                        sent or received."
                    ::= { llcSapStatsEntry 27 }

llcSapStatsDisconnectFRMRSend OBJECT-TYPE
                    SYNTAX      Counter
                    ACCESS      read-only
                    STATUS      mandatory
                    DESCRIPTION
                        "This object reflects the total number of
                        abnormal disconnections (resulting from a FRMR
                        being sent) that have been performed on this
                        SAP since the SAP was created."
                    ::= { llcSapStatsEntry 28 }

llcSapStatsDisconnectFRMRRcv OBJECT-TYPE
                    SYNTAX      Counter
                    ACCESS      read-only
                    STATUS      mandatory
                    DESCRIPTION
                        "This object reflects the total number of
                        abnormal disconnections (resulting from a FRMR
                        being received) that have been performed on
                        this SAP since the SAP was created."
                    ::= { llcSapStatsEntry 29 }

llcSapStatsDisconnectTimer OBJECT-TYPE
                    SYNTAX      Counter
                    ACCESS      read-only
                    STATUS      mandatory
                    DESCRIPTION
                        "This object reflects the total number of
                        abnormal disconnections (resulting from a timer
                        expiration) that have been performed on this
                        SAP since the SAP was created."
                    ::= { llcSapStatsEntry 30 }

llcSapStatsReset    OBJECT-TYPE
                    SYNTAX      Counter
                    ACCESS      read-only
                    STATUS      mandatory
                    DESCRIPTION
                        "This object reflects the total number of
                        resets that have been performed on this SAP
                        since the SAP was created.

                        A reset is ... "

-- (++) From IETF-San Jose: DESCRIPTION to be completed by snix@metaplex.com.
                    ::= { llcSapStatsEntry 31 }


--
--  THE LLC CONNECTION COMPONENT GROUP
--  ==================================
--

--  The following classes of information are modelled for each LLC connection
--  component:
--
--     1.  ADMINISTRATIVE ( read-only )
--     2.  OPERATIONAL    ( read-only )
--     3.  STATISTICS     ( read-only )

--  *************************************************************
--  *                                                           *
--  *    THE LLC CONNECTION COMPONENT ADMINISTRATIVE TABLE      *
--  *                                                           *
--  *************************************************************

llcCcAdminTable   OBJECT-TYPE
                    SYNTAX      SEQUENCE OF LlcCcAdminEntry
                    ACCESS      not-accessible
                    STATUS      mandatory
                    DESCRIPTION
                        "This table contains objects that can be
                        changed to manage an LLC connection component.
                        Changing one of these parameters may take
                        effect in the operating link immediately or may
                        wait until the link is restarted depending on
                        the details of the implementation.

                        The operating values may be different from
                        these configured values if changed by XID
                        negotiation or if a configured parameter was
                        changed after the link was started."
                    ::= { llcCcGroup 1 }

llcCcAdminEntry     OBJECT-TYPE
                    SYNTAX      LlcCcAdminEntry
                    ACCESS      not-accessible
                    STATUS      mandatory
                    DESCRIPTION
                        "A list of configured values for an LLC connection
                        component."
                    INDEX   { ifIndex, llcCcLSap, llcCcRSap,
                              llcCcRMac, llcCcLMac }
                    ::= { llcCcAdminTable 1 }

LlcCcAdminEntry ::= SEQUENCE
{
--
--          3Com does not currently support connection component
--          configuration; if it does at a future date, the rest
--          of the entries for this table will be implemented.
--
        llcCcLSap                       INTEGER,
        llcCcRSap                       INTEGER,
        llcCcLMac                       OCTET STRING,
        llcCcRMac                       OCTET STRING
}

llcCcLSap           OBJECT-TYPE
                    SYNTAX      INTEGER (1..254)
                    ACCESS      read-only
                    STATUS      mandatory
                    DESCRIPTION
                        "This value is the address of the local SAP
                        for this Connection Component."
                    ::= { llcCcAdminEntry 1 }

llcCcRSap           OBJECT-TYPE
                    SYNTAX      INTEGER (1..254)
                    ACCESS      read-only
                    STATUS      mandatory
                    DESCRIPTION
                        "This value is the address of the remote SAP
                        for this Connection Component."
                    ::= { llcCcAdminEntry 2 }

llcCcLMac           OBJECT-TYPE
                    SYNTAX      OCTET STRING (SIZE (6))
                    ACCESS      read-only
                    STATUS      mandatory
                    DESCRIPTION
                        "This value is the local MAC address for this
                        Connection Component."
                    ::= { llcCcAdminEntry 3 }

llcCcRMac           OBJECT-TYPE
                    SYNTAX      OCTET STRING (SIZE (6))
                    ACCESS      read-only
                    STATUS      mandatory
                    DESCRIPTION
                        "This value is the remote MAC address for this
                        Connection Component."
                    ::= { llcCcAdminEntry 4 }

--  *************************************************************
--  *                                                           *
--  *      THE LLC CONNECTION COMPONENT OPERATIONAL TABLE       *
--  *                                                           *
--  *************************************************************

llcCcOperTable      OBJECT-TYPE
                    SYNTAX      SEQUENCE OF LlcCcOperEntry
                    ACCESS      not-accessible
                    STATUS      mandatory
                    DESCRIPTION
                        "This table contains current LLC link
                        parameters.  Many of these objects have
                        corresponding objects in the
                        llcCcAdminTable."
                    ::= { llcCcGroup 2 }

llcCcOperEntry      OBJECT-TYPE
                    SYNTAX      LlcCcOperEntry
                    ACCESS      not-accessible
                    STATUS      mandatory
                    DESCRIPTION
                        "A list of status and control values for an
                        LLC connection component."
                    INDEX   { ifIndex, llcCcLSap, llcCcRSap,
                              llcCcRMac, llcCcLMac }
                    ::= { llcCcOperTable 1 }

LlcCcOperEntry     ::= SEQUENCE
{
        llcCcOperState                  INTEGER,
        llcCcOperMaxIPDUOctetsSend      Integer32,
        llcCcOperMaxIPDUOctetsRcv       Integer32,
        llcCcOperMaxUnackedIPDUsSend    INTEGER,
        llcCcOperMaxUnackedIPDUsRcv     INTEGER,
        llcCcOperMaxRetransmits         Integer32,
        llcCcOperAckTimer               TimeTicks,
        llcCcOperPbitTimer              TimeTicks,
        llcCcOperRejTimer               TimeTicks,
        llcCcOperBusyTimer              TimeTicks,
        llcCcOperInactTimer             TimeTicks,
        llcCcOperDelayAckCount          Integer32,
        llcCcOperDelayAckTimer          TimeTicks,
        llcCcOperNw                     Integer32,
        llcCcOperWw                     INTEGER,
        llcCcOperCreateTime             TimeTicks,
        llcCcOperLastModifyTime         TimeTicks,
        llcCcOperLastFailTime           TimeTicks,
        llcCcOperLastFailCause          INTEGER,
        llcCcOperLastFailFRMRInfo       OCTET STRING,
        llcCcOperLastWwCause            INTEGER
}

llcCcOperState      OBJECT-TYPE
                    SYNTAX      INTEGER
                    {
                        aDM            (1),
                        setup          (2),
                        normal         (3),
                        busy           (4),
                        reject         (5),
                        await          (6),
                        awaitBusy      (7),
                        awaitReject    (8),
                        dConn          (9),
                        reset          (10),
                        error          (11),
                        conn           (12),
                        resetCheck     (13),
                        resetWait      (14)
                    }
                    ACCESS      read-only
                    STATUS      mandatory
                    DESCRIPTION
                        "This object describes the operational state of
                        the LLC connection.  If the connection
                        component is disabled, llcCcOperState will be
                        allowed to transition to aDM(1).  If the
                        connection component is enabled, llcCcOperState
                        will be allowed to transition to normal(3)."
                    ::= { llcCcOperEntry 1 }

llcCcOperMaxIPDUOctetsSend  OBJECT-TYPE
                    SYNTAX      Integer32
                    ACCESS      read-only
                    STATUS      mandatory
                    DESCRIPTION
                        "This object denotes the maximum I PDU size, in
                        octets, that this LLC SAP may send to its
                        remote connection component partner. This count
                        is referred to as 'N1' in the IEEE 802.2
                        specification [5].

                        At connection setup, the remote LLC may send,
                        using an XID frame, the maximum I PDU size
                        which it is prepared to receive. If so, an
                        implementation may choose to override the
                        administered maximum PDU size with the
                        dynamically learned value and should reflect
                        that in this object.

                        The I PDU size includes all octets in a frame,
                        excluding framing characters, the MAC header
                        and link header."
                    ::= { llcCcOperEntry 2 }

llcCcOperMaxIPDUOctetsRcv     OBJECT-TYPE
                    SYNTAX      Integer32
                    ACCESS      read-only
                    STATUS      mandatory
                    DESCRIPTION
                        "This object denotes the maximum I PDU size,in
                        octets, that this LLC can expect to receive
                        from its remote LLC partner. This count is
                        referred to as 'N1' in the IEEE 802.2
                        specification [5]

                        The I PDU size includes all octets in a frame
                        with the exception of the framing characters,
                        the MAC header and the link header."
                    ::= { llcCcOperEntry 3 }

llcCcOperMaxUnackedIPDUsSend   OBJECT-TYPE
                    SYNTAX      INTEGER (1..127)
                    ACCESS      read-only
                    STATUS      mandatory
                    DESCRIPTION
                        "This object denotes the maximum consecutive
                        unacknowledged I PDU frames that this LLC may
                        send to its remote LLC partner. This count is
                        referred to as 'k' in the IEEE 802.2
                        specification [5].

                        At connection setup, the remote LLC may send,
                        using an XID frame, the maximum number of
                        unacknowledged I PDUs which it is prepared to
                        receive. If so, an implementation may choose to
                        override the administered maximum number of
                        unacknowledged PDUs with the dynamically learned
                        value and should reflect that in this object."
                    ::= { llcCcOperEntry 4 }

llcCcOperMaxUnackedIPDUsRcv    OBJECT-TYPE
                    SYNTAX      INTEGER (1..127)
                    ACCESS      read-only
                    STATUS      mandatory
                    DESCRIPTION
                        "This object denotes the maximum number of
                        unacknowledged I PDUs that this LLC can expect
                        to receive from its remote LLC partner. This
                        count is referred to as 'k' in the IEEE 802.2
                        specification [5]."
                    ::= { llcCcOperEntry 5 }

llcCcOperMaxRetransmits      OBJECT-TYPE
                    SYNTAX      Integer32
                    ACCESS      read-only
                    STATUS      mandatory
                    DESCRIPTION
                        "This object denotes the value for the maximum
                        number of times that this LLC shall retry PDUs
                        following the expiration of the acknowledgement
                        timer, the P-bit timer or the reject timer.
                        When these retries are exhausted, the link
                        shall be declared inactive.  This count is
                        referred to as 'N2' in the IEEE 802.2
                        specification [5]."
                    ::= { llcCcOperEntry 6 }

llcCcOperAckTimer            OBJECT-TYPE
                    SYNTAX      TimeTicks
                    ACCESS      read-only
                    STATUS      mandatory
                    DESCRIPTION
                        "This object denotes the value for the time
                        interval during which this LLC shall expect to
                        receive either:

                        1) an acknowledgement to one or more
                        outstanding I PDUs.  or 2) a response PDU to an
                        unnumbered command PDU.

                        The expiration of this timer shall cause the
                        frame unacknowledged frames to be retransmitted
                        (up to N2 times)."
                    ::= { llcCcOperEntry 7 }

llcCcOperPbitTimer           OBJECT-TYPE
                    SYNTAX      TimeTicks
                    ACCESS      read-only
                    STATUS      mandatory
                    DESCRIPTION
                        "This object denotes the value for the time
                        interval during which this LLC shall expect to
                        receive a PDU with the F bit set to '1' in
                        response to a Type 2 command with the P bit set
                        to '1'.

                        The expiration of this timer shall cause the
                        REJ PDU to be retransmitted (up to N2 times)."
                    ::= { llcCcOperEntry 8 }

llcCcOperRejTimer           OBJECT-TYPE
                    SYNTAX      TimeTicks
                    ACCESS      read-only
                    STATUS      mandatory
                    DESCRIPTION
                        "This object denotes the value for the time
                        interval during which this LLC shall expect to
                        receive a reply to a REJ PDU.

                        The expiration of this timer shall cause the
                        REJ PDU to be retransmitted (up to N2 times)."
                    ::= { llcCcOperEntry 9 }

llcCcOperBusyTimer           OBJECT-TYPE
                    SYNTAX      TimeTicks
                    ACCESS      read-only
                    STATUS      mandatory
                    DESCRIPTION
                        "This object denotes the value for the time
                        interval during which this LLC shall expect to
                        receive an indication that a busy condition at
                        the remote LLC has cleared."
                    ::= { llcCcOperEntry 10 }

llcCcOperInactTimer          OBJECT-TYPE
                    SYNTAX      TimeTicks
                    ACCESS      read-only
                    STATUS      mandatory
                    DESCRIPTION
                        "This object denotes the value for the time
                        interval during which this LLC shall expect to
                        receive any PDU from the remote LLC.  This
                        function is not described in the IEEE 802.2
                        specification [5] but is widely implemented.

                        The expiration of this timer shall cause the
                        local LLC to send a PDU to the remote LLC with
                        the P bit set to '1'.

                        Any value for this object less than or equal to
                        the acknowledgement timer shall mean that the
                        timer is not used."
                    ::= { llcCcOperEntry 11 }

llcCcOperDelayAckCount OBJECT-TYPE
                    SYNTAX      Integer32
                    ACCESS      read-only
                    STATUS      mandatory
                    DESCRIPTION
                        "This object denotes the value for the maximum
                        number of consecutive I PDUs which this LLC
                        shall receive during the interval defined by
                        llcCcOperDelayTimer without sending an
                        immediate acknowledgement.  This must be less
                        than or equal to the value of
                        llcCcOperMaxUnackIPDUsRcv. This function is not
                        described in the IEEE 802.2 specification [5]
                        but is widely implemented.

                        A value of one indicates that acknowledgments
                        will be sent immediately and that the value of
                        llcCcOperDelayAckTimer should be ignored."
                    ::= { llcCcOperEntry 12 }

llcCcOperDelayAckTimer OBJECT-TYPE
                    SYNTAX      TimeTicks
                    ACCESS      read-only
                    STATUS      mandatory
                    DESCRIPTION
                        "This object denotes the value for the time
                        interval during which this LLC shall delay
                        acknowledgment of one or more I PDUs (up to the
                        value of llcCcOperDelayAckCount). This function
                        is not described in the IEEE 802.2
                        specification [5] but is widely implemented.

                        The expiration of this timer shall cause the
                        local LLC to acknowledge all unacknowledged I
                        PDUs.

                        This object is associated with the
                        llcCcOperDelayAckCount object and only has
                        meaning if that object has a value greater than
                        one."
                    ::= { llcCcOperEntry 13 }

llcCcOperNw         OBJECT-TYPE
                    SYNTAX      Integer32
                    ACCESS      read-only
                    STATUS      mandatory
                    DESCRIPTION
                        "This object denotes the value for the number
                        of IPDUs that must be acknowledged before the
                        working window size (Ww) can be incremented by
                        1 when the working window is not equal to the
                        maximum transmit window size (TW). It controls
                        the gradual incrementing of Ww in congestion
                        situations.

                        This function is not described in the IEEE
                        802.2 specification [5], but is widely
                        implemented."
                    ::= { llcCcOperEntry 14 }

llcCcOperWw         OBJECT-TYPE
                    SYNTAX      INTEGER (1..127)
                    ACCESS      read-only
                    STATUS      mandatory
                    DESCRIPTION
                        "Maximum number of sequentially numbered IPDUs
                        that the connection component may have
                        outstanding (unacknowledged) at any given time.
                        Ww is initialized to the value of
                        llcCcOperMaxUnackedIPDUsSend when the link is
                        established. When the dynamic window algorithm
                        is invoked, Ww varies from 1 up to
                        llcCcOperMaxUnackedIPDUsSend.

                        Each time the llcCcOperWw value is decreased,
                        the reason is recorded in llcCcOperLastWwCause,
                        and llcCcStatWwCount is incremented by 1.

                        This function is not described in the IEEE
                        802.2 specification [5], but is widely
                        implemented."
                    ::= { llcCcOperEntry 15 }

llcCcOperCreateTime OBJECT-TYPE
                    SYNTAX      TimeTicks
                    ACCESS      read-only
                    STATUS      mandatory
                    DESCRIPTION
                        "This object describes the value of sysUpTime
                         when this row was created."
                    ::= { llcCcOperEntry 16 }

llcCcOperLastModifyTime     OBJECT-TYPE
                    SYNTAX      TimeTicks
                    ACCESS      read-only
                    STATUS      mandatory
                    DESCRIPTION
                        "For administered connection components, this
                        object describes the value of sysUpTime the
                        last time this row was modified.  If the row
                        has not been modified, then this value shall be
                        zero.

                        For dynamic connection components, this object
                        identifies the time this connection component
                        was created."
                    ::= { llcCcOperEntry 17 }

llcCcOperLastFailTime     OBJECT-TYPE
                    SYNTAX      TimeTicks
                    ACCESS      read-only
                    STATUS      mandatory
                    DESCRIPTION
                        "This object describes the value of sysUpTime
                        the last time this connection component
                        failed.  Connection component failure is
                        defined as a transition to an llcCcOperState
                        value of aDM(1).  If the connection component
                        has not failed, then this value shall be zero."
                    ::= { llcCcOperEntry 18 }

llcCcOperLastFailCause     OBJECT-TYPE
                    SYNTAX      INTEGER
                    {
                        undefined         (1),
                        rxFRMR            (2),
                        txFRMR            (3),
                        discReceived      (4),
                        discSent          (5),
                        retriesExpired    (6),
                        forcedShutdown    (7)
                    }
                    ACCESS      read-only
                    STATUS      mandatory
                    DESCRIPTION
                        "This enumerated object reflects the cause of
                        the last failure of this LLC connection
                        component.  If the connection component has not
                        failed, then this object will have a value of
                        undefined(1)."
                    DEFVAL { undefined }
                    ::= { llcCcOperEntry 19 }

llcCcOperLastFailFRMRInfo   OBJECT-TYPE
                    SYNTAX      OCTET STRING (SIZE(5))
                    ACCESS      read-only
                    STATUS      mandatory
                    DESCRIPTION
                        "This object reflects the information field of
                        the FRMR frame if the last failure for this LLC
                        connection component was a result of an
                        invalid frame.  Otherwise, this field has no
                        meaning."
                    ::= { llcCcOperEntry 20 }

llcCcOperLastWwCause   OBJECT-TYPE
                    SYNTAX          INTEGER
                    {
                        neverInvoked         (1),
                        lostData             (2),
                        macLayerCongestion   (3),
                        other                (4)
                    }
                    ACCESS      read-only
                    STATUS      mandatory
                    DESCRIPTION
                        "This object indicates the reason that the llcCcOperWw
                        was reduced the last time this occurred."
                    ::= { llcCcOperEntry 21 }

--  *************************************************************
--  *                                                           *
--  *      THE LLC CONNECTION COMPONENT STATISTICS TABLE        *
--  *                                                           *
--  *************************************************************

llcCcStatsTable   OBJECT-TYPE
                    SYNTAX      SEQUENCE OF LlcCcStatsEntry
                    ACCESS      not-accessible
                    STATUS      mandatory
                    DESCRIPTION
                        "Each entry in this table contains statistics
                        for a specific LLC connection component."
                     ::= { llcCcGroup 3 }

llcCcStatsEntry   OBJECT-TYPE
                    SYNTAX      LlcCcStatsEntry
                    ACCESS      not-accessible
                    STATUS      mandatory
                    DESCRIPTION
                        "A list of statistics for an LLC connection
                        component."
                    INDEX   { ifIndex, llcCcLSap, llcCcRSap,
                              llcCcRMac, llcCcLMac }
                    ::= { llcCcStatsTable 1 }

LlcCcStatsEntry ::= SEQUENCE
{
        llcCcStatsLocalBusies           Counter,
        llcCcStatsRemoteBusies          Counter,
        llcCcStatsIFramesIn             Counter,
        llcCcStatsIFramesOut            Counter,
        llcCcStatsIOctetsIn             Counter,
        llcCcStatsIOctetsOut            Counter,
        llcCcStatsSFramesIn             Counter,
        llcCcStatsSFramesOut            Counter,
        llcCcStatsRetransmitsOut        Counter,
        llcCcStatsREJsIn                Counter,
        llcCcStatsREJsOut               Counter,
        llcCcStatsWwCount               Counter
}

-- (++) From IETF-San Jose: sberl@cisco.com to contribute an object for the
--      number of times T1 expires.

-- (++) From IETF-San Jose: fix the description to be in terms of
--      llcCcOperState values. sberl@cisco.com to contribute.

llcCcStatsLocalBusies OBJECT-TYPE
                    SYNTAX      Counter
                    ACCESS      read-only
                    STATUS      mandatory
                    DESCRIPTION
                        "This object reflects the total number of times
                        that the local connection component has entered
                        a busy state (RNR).  This object is initialized
                        to zero when the connection component is
                        created."
                    ::= { llcCcStatsEntry 1 }

-- (++) From IETF-San Jose: fix the description to be in terms of
--      llcCcOperState values. sberl@cisco.com to contribute.

llcCcStatsRemoteBusies OBJECT-TYPE
                    SYNTAX      Counter
                    ACCESS      read-only
                    STATUS      mandatory
                    DESCRIPTION
                        "This object reflects the total number of times
                        that the adjacent (i.e. remote) connection
                        component has entered a busy state (RNR).  This
                        object is initialized to zero when the
                        connection component is created."
                    ::= { llcCcStatsEntry 2 }

llcCcStatsIFramesIn OBJECT-TYPE
                    SYNTAX      Counter
                    ACCESS      read-only
                    STATUS      mandatory
                    DESCRIPTION
                        "This object reflects the total number of
                        I-Frames that have been received by the
                        connection component.  This object is
                        initialized to zero when the connection
                        component is created."
                    ::= { llcCcStatsEntry 3 }

llcCcStatsIFramesOut OBJECT-TYPE
                    SYNTAX      Counter
                    ACCESS      read-only
                    STATUS      mandatory
                    DESCRIPTION
                        "This object reflects the total number of
                        I-Frames that have been transmitted by this
                        connection component.  This object is
                        initialized to zero when the connection
                        component is created."
                    ::= { llcCcStatsEntry 4 }

llcCcStatsIOctetsIn OBJECT-TYPE
                    SYNTAX      Counter
                    ACCESS      read-only
                    STATUS      mandatory
                    DESCRIPTION
                        "This object reflects the total octets received
                        from the adjacent connection component.  This
                        object covers the address, control, and
                        information field of I-Frames only.  This
                        object is initialized to zero when the
                        connection component is created."
                    ::= { llcCcStatsEntry 5 }

llcCcStatsIOctetsOut OBJECT-TYPE
                    SYNTAX      Counter
                    ACCESS      read-only
                    STATUS      mandatory
                    DESCRIPTION
                        "This object reflects the total octets
                        transmitted to the adjacent connection
                        component.  This object covers the address,
                        control, and information field of I-Frames
                        only.  This object is initialized to zero when
                        the connection component is created."
                    ::= { llcCcStatsEntry 6 }

llcCcStatsSFramesIn OBJECT-TYPE
                    SYNTAX      Counter
                    ACCESS      read-only
                    STATUS      mandatory
                    DESCRIPTION
                        "This object reflects the total number of
                        S-Frames that have been received by this
                        connection component.  This object is
                        initialized to zero when the connection
                        component is created.

                        Note - the ratio of the number of I-Frames to
                        S-Frames might serve as a measure of link
                        efficiency and, for instance, could be used to
                        tune the acknowledgement timer."
                    ::= { llcCcStatsEntry 7 }

llcCcStatsSFramesOut OBJECT-TYPE
                    SYNTAX      Counter
                    ACCESS      read-only
                    STATUS      mandatory
                    DESCRIPTION
                        "This object reflects the total number of
                        S-Frames that have been transmitted by this
                        connection component.  This object is
                        initialized to zero when the connection
                        component is created.

                        Note - the ratio of the number of I-Frames to
                        S-Frames might serve as a measure of link
                        efficiency and, for instance, could be used to
                        tune the acknowledgement timer."
                    ::= { llcCcStatsEntry 8 }

llcCcStatsRetransmitsOut OBJECT-TYPE
                    SYNTAX      Counter
                    ACCESS      read-only
                    STATUS      mandatory
                    DESCRIPTION
                        "This object reflects the total number of
                        I-Frames retransmitted by the local connection
                        component.  This object is initialized to zero
                        when the connection component is created."
                    ::= { llcCcStatsEntry 9 }

llcCcStatsREJsIn    OBJECT-TYPE
                    SYNTAX      Counter
                    ACCESS      read-only
                    STATUS      mandatory
                    DESCRIPTION
                        "This object reflects the total REJ frames
                        received from an adjacent LLC connection
                        component since connection component startup."
                    ::= { llcCcStatsEntry 10 }

llcCcStatsREJsOut   OBJECT-TYPE
                    SYNTAX      Counter
                    ACCESS      read-only
                    STATUS      mandatory
                    DESCRIPTION
                        "This object reflects the total REJ frames
                        transmitted to an adjacent LLC connection
                        component since connection component startup."
                    ::= { llcCcStatsEntry 11 }

llcCcStatsWwCount   OBJECT-TYPE
                    SYNTAX      Counter
                    ACCESS      read-only
                    STATUS      mandatory
                    DESCRIPTION
                        "This object reflects the total number of times, since
                        connection component startup, that the dynamic window
                        algorithm has been invoked to reduce the value of Ww.
                        At connection component startup, this object must be
                        initialized to zero.

                        This function is not described in the IEEE 802.2
                        specification [5], but is widely implemented."
                    ::= { llcCcStatsEntry 12 }

--
--  THE LLC TUNNEL GROUP
--  ====================
--
--  +++++++++++++++++++++++++++++++++++++++++++++++++++++++++++++
--  +                                                           +
--  +              ADDITIONAL TABLES STORED IN                  +
--  +              COMPACT CONFIGURATION STORAGE                +
--  +                    3COM PROPRIETARY                       +
--  +                                                           +
--  +++++++++++++++++++++++++++++++++++++++++++++++++++++++++++++

--  The following items of information are provided for LLC tunnelling
--  and are kept in Compact Configuration Storage (CCS) files:
--
--     1.   Virtual Ring Number ( read/write )
--     2.   Tunnel Mode         ( read/write )
--     3.   Tunnel Priority     ( read/write )
--
--  The following tables of information are provided for each LLC tunnel
--  and are kept in Compact Configuration Storage (CCS) files:
--
--     1.   Participating Router Table ( read/write )
--     2.   Default Destination Table  ( read/write )
--

ccsLlcTunnelInfo                    OBJECT IDENTIFIER ::= { llcTunnelGroup 1 }

--
--	Virtual Ring Number 
--

        ccsLlcTunnelVirtualRing OBJECT-TYPE
	    SYNTAX  INTEGER ( 1..4095 )
	    ACCESS  read-write
	    STATUS  mandatory
	    DESCRIPTION
		    "This defines the number of the virtual
		    token ring used by Logical Link Control.

                    Changing this parameter may take effect for the
		    tunnel immediately or may wait until the tunnel
		    is restarted depending on the details of the
		    implementation."
	    ::= { ccsLlcTunnelInfo 1 }

--
--	Tunnel Mode: tunnel_mode
--

	ccsLlcTunnelMode 	OBJECT-TYPE
	    SYNTAX  INTEGER
	    {
		qTunnelEnable           (4),
		qTunnelDisable          (8),
		qTunnelSecure           (16),
		qTunnelEnableSecure     (20),
		qTunnelDisableSecure    (24),
		qTunnelNonSecure        (32),
		qTunnelEnableNonSecure  (36),
		qTunnelDisableNonSecure (40)
	    }
            ACCESS  read-write
            STATUS  mandatory
            DESCRIPTION
                "This allows one to enable tunneling on the box and
		describe the mode of operation i.e. Secure or NonSecure.
		Secure mode means that this box will only accept connection
		from partners listed in the tunnel peer list. In the non-
		Secure mode any incoming IP address is accepted.

                This parameter may combine one of qTunnelEnable and
		qTunnelDisable (Enable/Disable set) with one of
		qTunnelSecure and qTunnelNonSecure (Secure/Nonsecure set);
		e.g. qTunnelEnable and qTunnelSecure is a legal
		combination. If a member of one set is not supplied on a
		'write' operation, the value for that set remains unchanged.

                Changing this parameter may take effect for the tunnel
		immediately or may wait until the tunnel is restarted
		depending on the details of the implementation."
	    ::= { ccsLlcTunnelInfo 2 }


--
--	Tunnel Priority: tunnel_priority
--

	ccsLlcTunnelSNAPriority	OBJECT-TYPE
            SYNTAX  INTEGER
	    {
	        qPrioDefault	(1),
		qPrioHigh	(2),
		qPrioMedium	(3),
		qPrioLow	(4)
	    }
            ACCESS  read-write
            STATUS  mandatory
            DESCRIPTION
                "This determines the priority of the tunnel traffic
		on the Logical Link Control link.

                Changing this parameter may take effect for the tunnel
		immediately or may wait until the tunnel is restarted
		depending on the details of the implementation."
	    ::= { ccsLlcTunnelInfo 3 }

--  *************************************************************
--  *                                                           *
--  *         THE LLC TUNNEL PARTICIPATING ROUTER TABLE         *
--  *                                                           *
--  *************************************************************

	ccsLlcTunnelRouterTable OBJECT-TYPE
	    SYNTAX  SEQUENCE OF CcsLlcTunnelRouterEntry
	    ACCESS  not-accessible
	    STATUS  mandatory
            DESCRIPTION
                "A table of information regarding all routers
            	participating in Logical Link Control 2.

                Changing one of these parameters may take effect for
		the tunnel immediately or may wait until the tunnel
		is restarted depending on the details of the
		implementation."
	    ::= { llcTunnelGroup 2 }

	ccsLlcTunnelRouterEntry OBJECT-TYPE
	    SYNTAX  CcsLlcTunnelRouterEntry
	    ACCESS  not-accessible
            STATUS  mandatory
            DESCRIPTION
		"Information for a single participating router."
	    INDEX   { ccsLlcTunnelId }
    	    ::= { ccsLlcTunnelRouterTable 1 }

	CcsLlcTunnelRouterEntry ::=
    	    SEQUENCE {
        	ccsLlcPeerAddress             IpAddress,
        	ccsLlcLocalAddress            IpAddress,
		ccsLlcTunnelId                INTEGER,
		ccsLlcRouterEnable            INTEGER,
		ccsLlcRouterMode              INTEGER,
		ccsLlcRouterTunnelTransport   INTEGER,
		ccsLlcRouterTunnelPort        INTEGER,
       	        ccsLlcRouterPeerString        DisplayString 
    	    }

	ccsLlcPeerAddress OBJECT-TYPE
	    SYNTAX  IpAddress 
	    ACCESS  read-write
            STATUS  mandatory
            DESCRIPTION
                "The IP address of the Logical Link Control node's peer.
		The peer is at the remote end of the tunnel."
	    ::= { ccsLlcTunnelRouterEntry 1 }

	ccsLlcLocalAddress OBJECT-TYPE
	    SYNTAX  IpAddress 
	    ACCESS  read-write
            STATUS  mandatory
            DESCRIPTION
                "The IP address of the Logical Link Control node
		at the local end of the tunnel."
	    ::= { ccsLlcTunnelRouterEntry 2 }

	ccsLlcTunnelId OBJECT-TYPE
	    SYNTAX  INTEGER (0..63)
	    ACCESS  read-only
            STATUS  mandatory
            DESCRIPTION
                "The tunnel index. This is a unique identifier
		for the tunnel."
	    ::= { ccsLlcTunnelRouterEntry 3 }

	ccsLlcRouterEnable OBJECT-TYPE
	    SYNTAX  INTEGER
	    {
		qTunEnable  (1),
		qtunDisable (2)
	    }
	    ACCESS  read-write
            STATUS  mandatory
            DESCRIPTION
                "Allows tunnel peer to be enabled." 
	    ::= { ccsLlcTunnelRouterEntry 4 }

	ccsLlcRouterMode OBJECT-TYPE
	    SYNTAX  INTEGER
	    {
		qTransparent  (1),
		qSpecificTerm (2),
		qLocalTerm    (3)
	    }
	    ACCESS  read-write
            STATUS  mandatory
            DESCRIPTION
                "Mode of the peer." 
	    ::= { ccsLlcTunnelRouterEntry 5 }

	ccsLlcRouterTunnelTransport OBJECT-TYPE
	    SYNTAX  INTEGER
	    {
		qTcp (2)
	    }
	    ACCESS  read-write
            STATUS  mandatory
            DESCRIPTION
                "Type of transport protocol used for tunnelling." 
	    ::= { ccsLlcTunnelRouterEntry 6 }

	ccsLlcRouterTunnelPort OBJECT-TYPE
	    SYNTAX  INTEGER (0..32767)
	    ACCESS  read-write
            STATUS  mandatory
            DESCRIPTION
                "Port number if TCP is used for tunnelling." 
	    ::= { ccsLlcTunnelRouterEntry 7 }

	ccsLlcRouterPeerString OBJECT-TYPE
            SYNTAX  DisplayString (SIZE (1..16))
	    ACCESS  read-write
            STATUS  mandatory
            DESCRIPTION
                "The name of Logical Link Control node's peer."
	    ::= { ccsLlcTunnelRouterEntry 8 }

--  *************************************************************
--  *                                                           *
--  *       THE LLC TUNNEL DEFAULT DESTINATION TABLE            *
--  *                                                           *
--  *************************************************************

	ccsLlcTunnelDefaultDestTable OBJECT-TYPE
	    SYNTAX  SEQUENCE OF CcsLlcTunnelDefaultDestEntry
	    ACCESS  not-accessible
            STATUS  mandatory
            DESCRIPTION
                "Table of default routes for frames that arrive at this
		router. The route on which a particular frame is sent is
		determined from the frames's destination MAC address.

                Changing one of these parameters may take effect for the
		tunnel immediately or may wait until the tunnel is
		restarted depending on the details of the implementation."
	    ::= { llcTunnelGroup 3 }

	ccsLlcTunnelDefaultDestEntry OBJECT-TYPE
            SYNTAX  CcsLlcTunnelDefaultDestEntry
	    ACCESS  not-accessible
            STATUS  mandatory
            DESCRIPTION
                "Mapping of a MAC address to a destination router."
--	    INDEX  { INTEGER }
	    ::= { ccsLlcTunnelDefaultDestTable 1 } 

	CcsLlcTunnelDefaultDestEntry ::=
	    SEQUENCE {
		ccsLlcDestTunnelId          INTEGER,
		ccsLlcRemoteMacAddress      MacAddress,
		ccsLlcRemoteSap             INTEGER,
		ccsLlcRemoteSapLowRange     INTEGER,
		ccsLlcRemoteSapHighRange    INTEGER
	    }

	ccsLlcDestTunnelId OBJECT-TYPE
	    SYNTAX  INTEGER (0..63)
	    ACCESS  read-only
            STATUS  mandatory
            DESCRIPTION
                "The destination's llcTunnelId for it's associated
		ccsLlcTunnelRouterTable entry."
	    ::= { ccsLlcTunnelDefaultDestEntry 1 }

	ccsLlcRemoteMacAddress OBJECT-TYPE
            SYNTAX  MacAddress
	    ACCESS  read-write
            STATUS  mandatory
            DESCRIPTION
                "The MAC address used for reaching the remote router."
	    ::= { ccsLlcTunnelDefaultDestEntry 2 }

	ccsLlcRemoteSap OBJECT-TYPE
            SYNTAX  INTEGER (0..255)
	    ACCESS  read-write
            STATUS  mandatory
            DESCRIPTION
                "The current Service Access Port used for reaching the
		destination address."
	    ::= { ccsLlcTunnelDefaultDestEntry 3 }

	ccsLlcRemoteSapLowRange OBJECT-TYPE
            SYNTAX  INTEGER (0..255)
	    ACCESS  read-write
            STATUS  mandatory
            DESCRIPTION
                "The lowest Service Access Port that can be used to
		reach the destination address."
	    ::= { ccsLlcTunnelDefaultDestEntry 4 }

	ccsLlcRemoteSapHighRange OBJECT-TYPE
            SYNTAX  INTEGER (0..255)
	    ACCESS  read-write
            STATUS  mandatory
            DESCRIPTION
                "The highest Service Access Port that can be used to
		reach the destination address."
	    ::= { ccsLlcTunnelDefaultDestEntry 5 }

--  +++++++++++++++++++++++++++++++++++++++++++++++++++++++++++++
--  +                                                           +
--  +              END OF LLC TUNNEL GROUP                      +
--  +                 3COM PROPRIETARY                          +
--  +                                                           +
--  +++++++++++++++++++++++++++++++++++++++++++++++++++++++++++++

--
--  TRAP DEFINITIONS
--

--
--  No traps in this version
--

END
