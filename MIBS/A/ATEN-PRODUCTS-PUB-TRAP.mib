-- MIB created 09/13/2005 15:29:57, by
-- ATEN International Co., Ltd.
-- this file describes the specific type of trap
-- there must be only one layer under trap point because only leaf point can be accessed

-- this mib is not used for being generally accessed, it's just used for record
-- specific types in trap from ATEN's products

-- users (trap manager) can use this file as a reference
-- users can use "get" or "walk" to access this mib tree for the name of certain specific type
-- the value after "trap" in defination is value of specific type value( An interger )


ATEN-PRODUCTS-PUB-TRAP DEFINITIONS ::= BEGIN

IMPORTS
OBJECT-TYPE FROM SNMPv2-SMI

    DisplayString
   		FROM SNMPv2-TC
    public
    	FROM ATEN-PRODUCTS-MIB;

trap 		OBJECT IDENTIFIER ::= { public 3 }

email OBJECT-TYPE
       SYNTAX DisplayString
       MAX-ACCESS read-only
       STATUS current
       DESCRIPTION
           "Name of specific(subtype) of trap in enterprise type"
       ::= { trap 1 }

log	OBJECT-TYPE
       SYNTAX DisplayString
       MAX-ACCESS read-only
       STATUS current
       DESCRIPTION
           "Name of specific(subtype) of trap in enterprise type"
       ::= { trap 2 }	

login  OBJECT-TYPE
       SYNTAX DisplayString
       MAX-ACCESS read-only
       STATUS current
       DESCRIPTION
           "Name of specific(subtype) of 'user login event' in enterprise type"
       ::= { trap 3 }

logout  OBJECT-TYPE
		SYNTAX DisplayString
		MAX-ACCESS read-only
		STATUS current
		DESCRIPTION
		   "Name of specific(subtype) of 'user logout event' in enterprise type"
		::= { trap 4 }
END
