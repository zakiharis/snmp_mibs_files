AVPRODUCT-INFO-MIB DEFINITIONS ::= BEGIN

--	

IMPORTS
	MODULE-IDENTITY, OBJECT-TYPE, Integer32,
	NOTIFICATION-TYPE, Unsigned32, Counter64, Counter32
		FROM SNMPv2-SMI
	DateAndTime, DisplayString,TimeStamp
		FROM SNMPv2-TC
	SnmpAdminString
		FROM SNMP-FRAMEWORK-MIB
	statistics
		FROM KAV4FS-STATISTICS-MIB
;

avProductInfo MODULE-IDENTITY
	LAST-UPDATED "201602241200Z"
	ORGANIZATION "www.kaspersky.com"
	CONTACT-INFO "Kaspersky Lab"
	DESCRIPTION "Product Info"
	-- revisions
	REVISION "201602241200Z"
	DESCRIPTION  "Automatically generated."
 ::= { statistics 4 }


	avProductInfoAVProductName OBJECT-TYPE
	SYNTAX SnmpAdminString
	MAX-ACCESS read-only
	STATUS current
	DESCRIPTION
		""
	::= { avProductInfo 1 }

	avProductInfoAVProductVersion OBJECT-TYPE
	SYNTAX SnmpAdminString
	MAX-ACCESS read-only
	STATUS current
	DESCRIPTION
		""
	::= { avProductInfo 2 }

	avProductInfoAVProductInstallationDate OBJECT-TYPE
	SYNTAX DateAndTime
	MAX-ACCESS read-only
	STATUS current
	DESCRIPTION
		""
	::= { avProductInfo 3 }

	avProductInfoAVProductLicenseState OBJECT-TYPE
	SYNTAX DisplayString
	MAX-ACCESS read-only
	STATUS current
	DESCRIPTION
		""
	::= { avProductInfo 4 }

	avProductInfoAVProductLicenseExpireDate OBJECT-TYPE
	SYNTAX DateAndTime
	MAX-ACCESS read-only
	STATUS current
	DESCRIPTION
		""
	::= { avProductInfo 5 }


END
