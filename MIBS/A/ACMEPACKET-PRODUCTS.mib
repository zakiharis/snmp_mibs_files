----------------------------------------------------------------------
-- ACMEPACKET-PRODUCTS-MIB:  Acme packet Product Information
--
-- April 2007
--
-- Copyright by Acme Packet, Inc.
-- All rights reserved.
------------------------------------------------------------------------

ACMEPACKET-PRODUCTS DEFINITIONS ::= BEGIN

IMPORTS
        acmepacket
                FROM ACMEPACKET-SMI

	OBJECT-IDENTITY, MODULE-IDENTITY
		FROM SNMPv2-SMI;

acmepacketProducts MODULE-IDENTITY
	LAST-UPDATED "201207160000Z"
	ORGANIZATION "Acme Packet, Inc."
	CONTACT-INFO
			"           	Customer Service
		 	Postal:		Acme Packet, Inc
					100 Crosby Drive 
					Bedford, MA 01730
					US
		    	Tel:		1-781-328-4400
		 	E-mail:		support@acmepacket.com"
	DESCRIPTION
		"Products supported at Acme Packet."
        REVISION    "201207160000Z"
        DESCRIPTION "Updated contact info"
	REVISION      "200704031500Z"
	DESCRIPTION
		"Initial version of this MIB module."
	::= { acmepacket 1 }	-- assigned by IANA


apNetNet4000Series OBJECT-IDENTITY
	STATUS	current
	DESCRIPTION
		"This is subtree contains all product lines supported in
                 the Net-Net 4000 Series product line." 
	::= { acmepacketProducts 1 }

apNetNet4250 OBJECT-IDENTITY
	STATUS	current
	DESCRIPTION
		"The Net-Net 4250 product." 
	::= { apNetNet4000Series 1 }

apNetNet4500 OBJECT-IDENTITY
	STATUS	current
	DESCRIPTION
		"The Net-Net 4500 product." 
	::= { apNetNet4000Series 2 }

apNetNet9000Series OBJECT-IDENTITY
	STATUS	current
	DESCRIPTION
		"This is subtree contains all product lines supported in
                 the Net-Net 9000 Series product line." 
	::= { acmepacketProducts 2 }

apNetNet9200 OBJECT-IDENTITY
	STATUS	current
	DESCRIPTION
		"The Net-Net 9200 product." 
	::= { apNetNet9000Series 1 }

apNetNet3000Series OBJECT-IDENTITY
	STATUS	current
	DESCRIPTION
		"This is subtree contains all product lines supported in
                 the Net-Net 3000 Series product line." 
	::= { acmepacketProducts 3 }

apNetNet3800 OBJECT-IDENTITY
	STATUS	current
	DESCRIPTION
		"The Net-Net 3800 product." 
	::= { apNetNet3000Series 1 }

apNetNet3820 OBJECT-IDENTITY
	STATUS	current
	DESCRIPTION
		"The Net-Net 3820 product." 
	::= { apNetNet3000Series 2 }

apNetNetOSSeries OBJECT-IDENTITY
	STATUS	current
	DESCRIPTION
		"This is subtree contains all product lines supported in
                 the Net-Net OS Series product line." 
	::= { acmepacketProducts 4 }

apNetNetOS OBJECT-IDENTITY
	STATUS	current
	DESCRIPTION
		"The Net-Net OS running on third party hardware." 
	::= { apNetNetOSSeries 1 }

apNetNetOSVM OBJECT-IDENTITY
	STATUS	current
	DESCRIPTION
		"The Net-Net OS running in a virtual machine environment."
	::= { apNetNetOSSeries 2 }

apNetNet6000Series OBJECT-IDENTITY
	STATUS	current
	DESCRIPTION
		"This is subtree contains all product lines supported in
                 the Net-Net 6000 Series product line." 
	::= { acmepacketProducts 5 }

apNetNet6300 OBJECT-IDENTITY
	STATUS	current
	DESCRIPTION
		"The Net-Net 6300 product." 
	::= { apNetNet6000Series 1 }

END
