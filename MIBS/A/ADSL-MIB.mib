ADSL-MIB DEFINITIONS ::= BEGIN
	IMPORTS
          OBJECT-TYPE, MODULE-IDENTITY,
          Counter32, Integer32
                  FROM SNMPv2-SMI
          common, DisplayString , UsrConfigStatus
                  FROM USR-DEFINITIONS-MIB;
usrAdsl MODULE-IDENTITY
        LAST-UPDATED "200205051800Z"
        ORGANIZATION "CommWorks Corporation, a 3Com Company"
        CONTACT-INFO "Customer Support"
        DESCRIPTION
           "The commWorks enterprise defined MIB objects for ADSL"
--      REVISION  "200205051800Z"
--      DESCRIPTION "Converted to SNMPv2"
       ::= { common 26 }
   -- textual conventions
   -- 
   -- textual conventions are like pre-processor macro in 'C'
   --        (i.e. #define statements)
   -- Use them to define your own 'datatypes'
   -- Begin managed object definitions here...
	usrAdslXmitPower OBJECT-TYPE
         SYNTAX   Integer32(-15..-3)
         MAX-ACCESS   read-only
         STATUS       current
         DESCRIPTION
            "Transmit power of ADSL transceiver represented in dB."
         ::= { usrAdsl 1 }
	usrAdslRmtReqDwnConstStatus OBJECT-TYPE
         SYNTAX   Integer32 (0..128)
         MAX-ACCESS   read-write
         STATUS       current
         DESCRIPTION
            	"Value corresponds to the downstream constellation
                 requested."
         ::= { usrAdsl 2 }
	usrAdslActualDwnConstStatus OBJECT-TYPE
         SYNTAX   Integer32 (0..128)
         MAX-ACCESS   read-only
         STATUS       current
         DESCRIPTION
            	"Value corresponds to the actual downstream constellation
                 that was used, which may differ from the value requested."
         ::= { usrAdsl 3 }
	usrAdslRmtReqUpConstStatus OBJECT-TYPE
         SYNTAX   Integer32 (0..128)
         MAX-ACCESS   read-only
         STATUS       current
         DESCRIPTION
            "Value corresponds to the upstream constellation requested."
         ::= { usrAdsl 4 }
	usrAdslActualUpConstStatus OBJECT-TYPE
         SYNTAX   Integer32 (0..128)
         MAX-ACCESS   read-only
         STATUS       current
         DESCRIPTION
            "Value corresponds to the actual upstream constellation that
             was used, which may differ from the value requested."
         ::= { usrAdsl 5 }
	usrAdslFwRel OBJECT-TYPE
         SYNTAX   Integer32 (0..16777215)
         MAX-ACCESS   read-only
         STATUS       current
         DESCRIPTION
            "Firmware release number of the GTI supplied transceiver
             software module."
         ::= { usrAdsl 6 }
	usrAdslStartletVerson OBJECT-TYPE
         SYNTAX   Integer32 (0..4)
         MAX-ACCESS   read-only
         STATUS       current
         DESCRIPTION
            "Value is a number that corresponds to the version number of
             the STARLET VLSI in the transceiver."
         ::= { usrAdsl 7 }
	usrAdslMeanSqError OBJECT-TYPE
         SYNTAX   INTEGER {
                           minus50db(1),
                           plus50db(2)
                          }
         MAX-ACCESS   read-only
         STATUS       current
         DESCRIPTION
            "Received signal to noise ratio."
         ::= { usrAdsl 8 }
	usrAdslEqualization OBJECT-TYPE
         SYNTAX   Integer32  -- Range values are TBD
         MAX-ACCESS   read-only -- TBD
         STATUS       current
         DESCRIPTION
            "TBD"
         ::= { usrAdsl 9 }
	usrAdslReceiverGain OBJECT-TYPE
         SYNTAX   Integer32 -- Range values are TBD
         MAX-ACCESS   read-write
         STATUS       current
         DESCRIPTION
            "Total receiver gain measured in dB."
         ::= { usrAdsl 10 }
	usrAdslBytesErrCorrected OBJECT-TYPE
         SYNTAX   Integer32 (0..255)
         MAX-ACCESS   read-only
         STATUS       current
         DESCRIPTION
            "Number of bytes corrected by Reed-Solomon error correction
             algorithm in the STARLET."
         ::= { usrAdsl 11 }
	usrAdslBytesNotErrCorrected OBJECT-TYPE
         SYNTAX   Integer32 (0..255)
         MAX-ACCESS   read-only
         STATUS       current
         DESCRIPTION
            "Number of bytes not corrected by Reed-Solomon error correction
             algorithm in the STARLET."
         ::= { usrAdsl 12 }
	usrAdslOverflowCounter OBJECT-TYPE
         SYNTAX   Counter32
         MAX-ACCESS   read-only
         STATUS       current
         DESCRIPTION
            "Running counter for when usrAdslBytesErrorCorrected or 
             usrAdslBytesNotErrorCorrected overflows"
         ::= { usrAdsl 13 }
	usrAdslOpState OBJECT-TYPE
         SYNTAX   Integer32 (0..134)
         MAX-ACCESS   read-only
         STATUS       current
         DESCRIPTION
            "Defines the high level operating state of the transceiver.
             Used by the customer to determine whether the transceiver
             is in idle mode, data mode, test mode, or startup."
         ::= { usrAdsl 14 }
	usrAdslStartupProgress OBJECT-TYPE
         SYNTAX   Integer32 (0..191)
         MAX-ACCESS   read-only
         STATUS       current
         DESCRIPTION
            "Defines the current detailed startup state of the
             transceiver.  The LSB determines the major mode
             corresponding to startup in var usrAdslOpState."
         ::= { usrAdsl 15 }
	usrAdslLastFailedStatus OBJECT-TYPE
         SYNTAX   Integer32 (0..191)
         MAX-ACCESS   read-only
         STATUS       current
         DESCRIPTION
            "Defines the last detailed state reached in
             usrAdslStartupProgress before startup failed."
         ::= { usrAdsl 16 }
	usrAdslActualBaudDataRateDwn OBJECT-TYPE
         SYNTAX   Integer32 (340..952)
         MAX-ACCESS   read-only
         STATUS       current
         DESCRIPTION
            "Actual downstream rate of kilobytes per second."
         ::= { usrAdsl 17 }
	usrAdslActualBaudDataRateDwnMar OBJECT-TYPE
         SYNTAX   Integer32 -- Range values are TBD
         MAX-ACCESS   read-only
         STATUS       current
         DESCRIPTION
            "TBD"
         ::= { usrAdsl 18 }
	usrAdslActualBaudDataRateUp OBJECT-TYPE
         SYNTAX   Integer32
         MAX-ACCESS   read-only
         STATUS       current
         DESCRIPTION
            "Actual upstream rate of kilobytes per second."
         ::= { usrAdsl 19 }
	usrAdslActualBaudDataRateUpMarg OBJECT-TYPE
         SYNTAX   Integer32 -- Range values are TBD
         MAX-ACCESS   read-only
         STATUS       current
         DESCRIPTION
            "TBD"
         ::= { usrAdsl 20 }
        usrAdslCFMStatusFlag OBJECT-TYPE
         SYNTAX  UsrConfigStatus
         MAX-ACCESS  read-write
         STATUS      current
         DESCRIPTION
                "This variable controls saving and loading of configuration
                information for the D56k WAN Driver. The value can be set
                to either save or load by a management station. The other
                values indicate if any configuration operation and what type
                is in progress."
         ::= { usrAdsl 21 }
        usrAdslCfgFileName OBJECT-TYPE
         SYNTAX      DisplayString
         MAX-ACCESS  read-only
         STATUS      current
         DESCRIPTION
                "The name of a ConfigFile to read/write the D56k parameters.
                 If the value of this object is an empty string, then the
                 D56k Driver uses the default name `@file://D56k.cfg'."
         ::= { usrAdsl 22 }
        usrAdslResetStatus OBJECT-TYPE
         SYNTAX   Integer32
         MAX-ACCESS   read-write
         STATUS       current
         DESCRIPTION
            "The Reset Status of the ADSL Starlet chipset"
         ::= { usrAdsl 23 }
END  -- End of ADSL-MIB-DEFINITIONS
-- ************************************************************************
--
--      usr_ntp.mib - An enterprise specific Network Time Protocol MIB
--
-- Created:        Feb-24-1997
--
