-- *************************** Revision ****************************************
-- Date        Version   Author         Chanage Description
--
-- 2010/06/03  1.00.000  ATI            Initial version
-- 2010/08/16  1.00.001  ATI            Change module style to group style
-- 2010/12/07  1.00.002  ATI            Add the snmp server trap mib entry
--                                      Add l2DhcpSnoop mib group
--                                      Modify the fsmsvlan.mib
--                                      Modify the fscfa.mib
--                                      Modify the the bootp type for ifIpAddrAllocProtocol
-- 2011/02/16  1.00.003  ATI            Fix the compile error in MG-SOFT mib compiler 2010
-- 2011/05/17  1.00.004  ATI            Add the sysRadiusExtServerAccPort
--                                      Modify fsradius.mib
-- 2012/02/06  1.00.005	 ATI		Support the snmpb
-- *************************** Revision End ************************************

AT-GS950-16-MIB DEFINITIONS ::= BEGIN

IMPORTS

AutonomousType FROM SNMPv2-TC
Counter FROM RFC1155-SMI
Counter32 FROM SNMPv2-SMI
Counter64 FROM SNMPv2-SMI
DisplayString FROM SNMPv2-TC
enterprises FROM SNMPv2-SMI
InetAddress FROM INET-ADDRESS-MIB
InetAddressPrefixLength FROM INET-ADDRESS-MIB
InetAddressType FROM INET-ADDRESS-MIB
Integer32 FROM SNMPv2-SMI
InterfaceIndex FROM IF-MIB
InterfaceIndexOrZero FROM IF-MIB
IpAddress FROM SNMPv2-SMI
lldpLocPortId FROM LLDP-MIB
lldpLocPortNum FROM LLDP-MIB
lldpRemChassisId FROM LLDP-MIB
lldpRemManAddr FROM LLDP-MIB
lldpRemPortId FROM LLDP-MIB
lldpRemSysName FROM LLDP-MIB
lldpStatsRemTablesAgeouts FROM LLDP-MIB
lldpStatsRemTablesDeletes FROM LLDP-MIB
lldpStatsRemTablesDrops FROM LLDP-MIB
lldpStatsRemTablesInserts FROM LLDP-MIB
lldpXdot1RemPortVlanId FROM LLDP-EXT-DOT1-MIB
lldpXdot1RemProtocolId FROM LLDP-EXT-DOT1-MIB
lldpXdot1RemProtoVlanSupported FROM LLDP-EXT-DOT1-MIB
lldpXdot1RemVlanName FROM LLDP-EXT-DOT1-MIB
lldpXdot3RemLinkAggStatus FROM LLDP-EXT-DOT3-MIB 
lldpXdot3RemMaxFrameSize FROM LLDP-EXT-DOT3-MIB 
lldpXdot3RemPortOperMauType FROM LLDP-EXT-DOT3-MIB 
lldpXdot3RemPowerClass FROM LLDP-EXT-DOT3-MIB 
MacAddress FROM SNMPv2-TC
mib-2 FROM RFC1213-MIB
MODULE-COMPLIANCE FROM SNMPv2-CONF
MODULE-IDENTITY FROM SNMPv2-SMI
NOTIFICATION-TYPE FROM SNMPv2-SMI
OBJECT-GROUP FROM SNMPv2-CONF
OBJECT-TYPE FROM SNMPv2-SMI
PhysAddress FROM RFC1213-MIB
PortList FROM Q-BRIDGE-MIB
RowStatus FROM SNMPv2-TC
SnmpAdminString FROM SNMP-FRAMEWORK-MIB
SnmpEngineID FROM SNMP-FRAMEWORK-MIB
SnmpSecurityLevel FROM SNMP-FRAMEWORK-MIB
SnmpSecurityModel FROM SNMP-FRAMEWORK-MIB
SnmpTagValue FROM SNMP-TARGET-MIB
snmpTargetParamsName FROM SNMP-TARGET-MIB
TAddress FROM SNMPv2-TC
TEXTUAL-CONVENTION FROM SNMPv2-TC
TimeFilter FROM RMON2-MIB
TimeInterval FROM SNMPv2-TC
TimeStamp FROM SNMPv2-TC
TimeTicks FROM SNMPv2-SMI
TruthValue FROM SNMPv2-TC
Unsigned32 FROM SNMPv2-SMI
ZeroBasedCounter32   FROM RMON2-MIB
;

     at-GS95016v3 MODULE-IDENTITY
         LAST-UPDATED "201202060000Z"
         ORGANIZATION "Allied Telesis Inc."
         CONTACT-INFO
                 "Allied Telesis Inc. Customer Service
        
                  Postal: 19800 North Creek Parkway, Suite 100
                          Bothell, WA 98011 USA

                  Email: support@alliedtelesis.com"
        DESCRIPTION
	       "Private MIB for AT-GS950 Series Switches"
        REVISION     "201202060000Z"  -- December 26nd, 2011
        DESCRIPTION
          "No Description"
        ::= { enterprises alliedTelesis (207) products (1) switches (4) 166 }


l2Snmp	OBJECT IDENTIFIER    ::= { at-GS95016v3 1 }
l2Radius	OBJECT IDENTIFIER    ::= { at-GS95016v3 25 }
l2Cfa	OBJECT IDENTIFIER    ::= { at-GS95016v3 27 }
l2Rmon	OBJECT IDENTIFIER    ::= { at-GS95016v3 44 }
l2La	OBJECT IDENTIFIER    ::= { at-GS95016v3 63 }
l2Pnac	OBJECT IDENTIFIER    ::= { at-GS95016v3 64 }
l2System	OBJECT IDENTIFIER    ::= { at-GS95016v3 81 }
l2Dfs	OBJECT IDENTIFIER    ::= { at-GS95016v3 83 }
l2Syslog	OBJECT IDENTIFIER    ::= { at-GS95016v3 89 }
l2Security	OBJECT IDENTIFIER    ::= { at-GS95016v3 95 }
l2Ssl	OBJECT IDENTIFIER    ::= { at-GS95016v3 96 }
l2Ssh	OBJECT IDENTIFIER    ::= { at-GS95016v3 97 }
l2Sntp	OBJECT IDENTIFIER    ::= { at-GS95016v3 99}
l2Dscp	OBJECT IDENTIFIER    ::= { at-GS95016v3 100 }
l2Snoop	OBJECT IDENTIFIER    ::= { at-GS95016v3 105 }
l2Bridge	OBJECT IDENTIFIER    ::= { at-GS95016v3 116 }
l2Mst	OBJECT IDENTIFIER    ::= { at-GS95016v3 118 }
l2Rst	OBJECT IDENTIFIER    ::= { at-GS95016v3 119 }
l2Vlan	OBJECT IDENTIFIER    ::= { at-GS95016v3 120 }
fslldp	OBJECT IDENTIFIER          ::=  { at-GS95016v3 158 } 
l2VoiceVlan	OBJECT IDENTIFIER    ::= { at-GS95016v3 163 }
trafficSeg	OBJECT IDENTIFIER    ::= { at-GS95016v3 165 }
atiAclMib	OBJECT IDENTIFIER    ::= { at-GS95016v3 166 }
l2DhcpSnoop	OBJECT IDENTIFIER    ::= { at-GS95016v3 181 }
dot1dPBridge OBJECT IDENTIFIER ::= { l2Bridge 6 }
dot1qQBridge OBJECT IDENTIFIER ::= { l2Bridge 7 }




   L2snmpLevel ::= TEXTUAL-CONVENTION
    	    STATUS       current
    	    DESCRIPTION  ""
    	    SYNTAX       INTEGER {
                         v1(1),
                         v2c(2),
                         noAuthNoPriv(3),
                         authNoPriv(4),
                         authPriv(5)
                         }

sysSnmpUser                    OBJECT IDENTIFIER ::= { l2Snmp 1 }
sysSnmpGroup                   OBJECT IDENTIFIER ::= { l2Snmp 2 }
sysSnmpGroupAccess             OBJECT IDENTIFIER ::= { l2Snmp 3 }
sysSnmpViewTree                OBJECT IDENTIFIER ::= { l2Snmp 4 }
sysSnmpCommunity               OBJECT IDENTIFIER ::= { l2Snmp 5 }
sysSnmpTrapManager             OBJECT IDENTIFIER ::= { l2Snmp 6 }
sysSnmpEngineID OBJECT-TYPE
   SYNTAX       SnmpEngineID
   MAX-ACCESS   read-write
   STATUS       current
   DESCRIPTION
      "An SNMP engine's administratively-unique identifier.

       In a simple agent, this value is always that agent's
       own snmpEngineID value.

       The value can also take the value of the snmpEngineID
       of a remote SNMP engine with which this user can
       communicate."
   ::=  { l2Snmp 7 }

 snmpGlobalState OBJECT-TYPE 
           SYNTAX      INTEGER {
                          enable(1),
                          disable(2)
                       }
           MAX-ACCESS  read-write 
           STATUS      current 
           DESCRIPTION 
               "This object is for enabling or disabling SNMP Community function."
		   DEFVAL { enable }
           ::= { l2Snmp 8 }


-- SNMP User

sysSnmpUserTable OBJECT-TYPE
   SYNTAX        SEQUENCE OF TabSnmpUserEntry
   MAX-ACCESS    not-accessible
   STATUS        current
   DESCRIPTION
      ""
   ::= { sysSnmpUser 1 }

sysSnmpUserEntry OBJECT-TYPE
   SYNTAX        TabSnmpUserEntry
   MAX-ACCESS    not-accessible
   STATUS        current
   DESCRIPTION
      ""
   INDEX { sysSnmpUserName }
   ::= { sysSnmpUserTable 1 }

TabSnmpUserEntry ::=
   SEQUENCE {
      sysSnmpUserName                SnmpAdminString,
      sysSnmpUserAuthProtocol        AutonomousType,
      sysSnmpUserPrivProtocol        AutonomousType,
      sysSnmpUserStatus              RowStatus
   }

sysSnmpUserName      OBJECT-TYPE
   SYNTAX            SnmpAdminString (SIZE(1..32))
   MAX-ACCESS        not-accessible
   STATUS            current
   DESCRIPTION
      "A human readable string rsysresenting the name of
       the user.

       This is the (User-based Security) Model dependent
       security ID."
   ::= { sysSnmpUserEntry 1 }

sysSnmpUserAuthProtocol OBJECT-TYPE
   SYNTAX               AutonomousType
   MAX-ACCESS           read-create
   STATUS               current
   DESCRIPTION
      "An indication of whether messages sent on behalf of
       this user to/from the SNMP engine identified by
       usmUserEngineID, can be authenticated, and if so,
       the type of authentication protocol which is used.

       An instance of this object is created concurrently
       with the creation of any other object instance for
       the same user (i.e., as part of the processing of
       the set operation which creates the first object
       instance in the same concsystual row).

       If an initial set operation (i.e. at row creation time)
       tries to set a value for an unknown or unsupported
       protocol, then a 'wrongValue' error must be returned.

       The value will be overwritten/set when a set operation
       is performed on the corresponding instance of
       UserCloneFrom.

       Once instantiated, the value of such an instance of
       this object can only be changed via a set operation to
       the value of the NoAuthProtocol.

       If a set operation tries to change the value of an


       existing instance of this object to any value other
       than NoAuthProtocol, then an 'inconsistentValue'
       error must be returned.

       If a set operation tries to set the value to the
       NoAuthProtocol while the UserPrivProtocol value
       in the same row is not equal to NoPrivProtocol,
       then an 'inconsistentValue' error must be returned.
       That means that an SNMP command generator application
       must first ensure that the UserPrivProtocol is set
       to the NoPrivProtocol value before it can set
       the UserAuthProtocol value to NoAuthProtocol."
   ::= { sysSnmpUserEntry 2 }

sysSnmpUserPrivProtocol OBJECT-TYPE
   SYNTAX               AutonomousType
   MAX-ACCESS           read-create
   STATUS               current
   DESCRIPTION
      "An indication of whether messages sent on behalf of
       this user to/from the SNMP engine identified by
       usmUserEngineID, can be protected from disclosure,
       and if so, the type of privacy protocol which is used.

       An instance of this object is created concurrently
       with the creation of any other object instance for
       the same user (i.e., as part of the processing of
       the set operation which creates the first object
       instance in the same concsystual row).

       If an initial set operation (i.e. at row creation time)
       tries to set a value for an unknown or unsupported
       protocol, then a 'wrongValue' error must be returned.

       The value will be overwritten/set when a set operation
       is performed on the corresponding instance of
       usmUserCloneFrom.

       Once instantiated, the value of such an instance of
       this object can only be changed via a set operation to
       the value of the NoPrivProtocol.

       If a set operation tries to change the value of an
       existing instance of this object to any value other
       than NoPrivProtocol, then an 'inconsistentValue'
       error must be returned.

       Note that if any privacy protocol is used, then you
       must also use an authentication protocol. In other
       words, if usmUserPrivProtocol is set to anything else
       than NoPrivProtocol, then the corresponding instance
       of usmUserAuthProtocol cannot have a value of

       usmNoAuthProtocol. If it does, then an
       'inconsistentValue' error must be returned."
   ::= { sysSnmpUserEntry 3 }

sysSnmpUserStatus    OBJECT-TYPE
   SYNTAX            RowStatus
   MAX-ACCESS        read-create
   STATUS            current
   DESCRIPTION
      "The status of this concsystual row.

       Until instances of all corresponding columns are
       appropriately configured, the value of the
       corresponding instance of the usmUserStatus column
       is 'notReady'.

       In particular, a newly created row for a user who
       employs authentication, cannot be made active until the
       corresponding usmUserCloneFrom and usmUserAuthKeyChange
       have been set.

       Further, a newly created row for a user who also
       employs privacy, cannot be made active until the
       usmUserPrivKeyChange has been set.

       The RowStatus TC [RFC2579] requires that this
       DESCRIPTION clause states under which circumstances
       other objects in this row can be modified:

       The value of this object has no effect on whether
       other objects in this concsystual row can be modified,
       excsyst for usmUserOwnAuthKeyChange and
       usmUserOwnPrivKeyChange. For these 2 objects, the
       value of usmUserStatus MUST be active."
   ::= { sysSnmpUserEntry 4 }


-- SNMP Group

sysSnmpGroupTable OBJECT-TYPE
   SYNTAX         SEQUENCE OF TabSnmpGroupEntry
   MAX-ACCESS     not-accessible
   STATUS         current
   DESCRIPTION
      ""
   ::= { sysSnmpGroup 1 }

sysSnmpGroupEntry OBJECT-TYPE
   SYNTAX      TabSnmpGroupEntry
   MAX-ACCESS  not-accessible
   STATUS      current
   DESCRIPTION
      ""
   INDEX { sysSnmpSecurityModel, sysSnmpSecurityName }
   ::= { sysSnmpGroupTable 1 }

TabSnmpGroupEntry ::=
   SEQUENCE {
      sysSnmpSecurityModel               SnmpSecurityModel,
      sysSnmpSecurityName                SnmpAdminString,
      sysSnmpGroupName                   SnmpAdminString,
      sysSnmpGroupStatus                 RowStatus
   }

sysSnmpSecurityModel  OBJECT-TYPE
   SYNTAX             SnmpSecurityModel
   MAX-ACCESS         not-accessible
   STATUS             current
   DESCRIPTION
      "A human readable string rsysresenting the name of
       the user.

       This is the (User-based Security) Model dsysendent
       security ID."
   ::= { sysSnmpGroupEntry 1 }

sysSnmpSecurityName   OBJECT-TYPE
   SYNTAX             SnmpAdminString (SIZE(1..32))
   MAX-ACCESS         not-accessible
   STATUS             current
   DESCRIPTION
      "A human readable string rsysresenting the name of
       the user.

       This is the (User-based Security) Model dsysendent
       security ID."
   ::= { sysSnmpGroupEntry 2 }

sysSnmpGroupName    OBJECT-TYPE
   SYNTAX           SnmpAdminString (SIZE(1..32))
   MAX-ACCESS       read-create
   STATUS           current
   DESCRIPTION
      "The name of the group to which this entry (e.g., the
       combination of securityModel and securityName)
       belongs.

       This groupName is used as index into the
       vacmAccessTable to select an access control policy.
       However, a value in this table does not imply that an
       instance with the value exists in table vacmAccesTable."
   ::= { sysSnmpGroupEntry 3 }

sysSnmpGroupStatus    OBJECT-TYPE
   SYNTAX             RowStatus
   MAX-ACCESS         read-create
   STATUS             current
   DESCRIPTION
      "The status of this concsystual row.

       Until instances of all corresponding columns are
       appropriately configured, the value of the
       corresponding instance of the usmUserStatus column
       is 'notReady'.

       In particular, a newly created row for a user who
       employs authentication, cannot be made active until the
       corresponding usmUserCloneFrom and usmUserAuthKeyChange
       have been set.

       Further, a newly created row for a user who also
       employs privacy, cannot be made active until the
       usmUserPrivKeyChange has been set.

       The RowStatus TC [RFC2579] requires that this
       DESCRIPTION clause states under which circumstances
       other objects in this row can be modified:

       The value of this object has no effect on whether
       other objects in this concsystual row can be modified,
       excsyst for usmUserOwnAuthKeyChange and
       usmUserOwnPrivKeyChange. For these 2 objects, the
       value of usmUserStatus MUST be active."
   ::= { sysSnmpGroupEntry 4 }


-- SNMP Group Access

sysSnmpGroupAccessTable OBJECT-TYPE
   SYNTAX               SEQUENCE OF TabSnmpGroupAccessEntry
   MAX-ACCESS           not-accessible
   STATUS               current
   DESCRIPTION
      ""
   ::= { sysSnmpGroupAccess 1 }

sysSnmpGroupAccessEntry OBJECT-TYPE
   SYNTAX               TabSnmpGroupAccessEntry
   MAX-ACCESS           not-accessible
   STATUS               current
   DESCRIPTION
      ""
   INDEX { sysSnmpaccessGroupIndex ,sysSnmpaccessSecurityModel ,sysSnmpaccessSecurityLevel }
   ::= { sysSnmpGroupAccessTable 1 }

TabSnmpGroupAccessEntry ::=
   SEQUENCE {
      sysSnmpaccessGroupIndex        SnmpAdminString,
      sysSnmpaccessSecurityModel     SnmpSecurityModel,
      sysSnmpaccessSecurityLevel     SnmpSecurityLevel,
      sysSnmpaccessReadViewName      SnmpAdminString,
      sysSnmpaccessWriteViewName     SnmpAdminString,
      sysSnmpaccessNotifyViewName    SnmpAdminString,
      sysSnmpaccessStatus            RowStatus
   }

sysSnmpaccessGroupIndex  OBJECT-TYPE
   SYNTAX                SnmpAdminString (SIZE(1..32))
   MAX-ACCESS            not-accessible
   STATUS                current
   DESCRIPTION 
      "The name of the group to which this entry (e.g., the
       combination of securityModel and securityName)
       belongs.

       This groupName is used as index into the
       vacmAccessTable to select an access control policy.
       However, a value in this table does not imply that an
       instance with the value exists in table vacmAccesTable."
   ::= { sysSnmpGroupAccessEntry 1 }

sysSnmpaccessSecurityModel OBJECT-TYPE
   SYNTAX                  SnmpSecurityModel
   MAX-ACCESS              not-accessible
   STATUS                  current
   DESCRIPTION
      "In order to gain the access rights allowed by this
       concsystual row, this securityModel must be in use."
   ::= { sysSnmpGroupAccessEntry 2 }

sysSnmpaccessSecurityLevel OBJECT-TYPE
   SYNTAX                  SnmpSecurityLevel
   MAX-ACCESS              not-accessible
   STATUS                  current
   DESCRIPTION
      "The minimum level of security required in order to
       gain the access rights allowed by this concsystual
       row.  A securityLevel of noAuthNoPriv is less than
       authNoPriv which in turn is less than authPriv.

       If multiple entries are equally indexed excsyst for
       this vacmAccessSecurityLevel index, then the entry
       which has the highest value for
       vacmAccessSecurityLevel is selected."
   ::= { sysSnmpGroupAccessEntry 3 }

sysSnmpaccessReadViewName OBJECT-TYPE
   SYNTAX                 SnmpAdminString (SIZE(0..32))
   MAX-ACCESS             read-create
   STATUS                 current
   DESCRIPTION
      "The value of an instance of this object identifies
       the MIB view of the SNMP context to which this
       concsystual row authorizes read access.
  
       The identified MIB view is that one for which the
       vacmViewTreeFamilyViewName has the same value as the
       instance of this object; if the value is the empty
       string or if there is no active MIB view having this
       value of vacmViewTreeFamilyViewName, then no access
       is granted."
   ::= { sysSnmpGroupAccessEntry 4 }

sysSnmpaccessWriteViewName OBJECT-TYPE
   SYNTAX                  SnmpAdminString (SIZE(0..32))
   MAX-ACCESS              read-create
   STATUS                  current
   DESCRIPTION
      "The value of an instance of this object identifies
       the MIB view of the SNMP context to which this
       concsystual row authorizes write access.

       The identified MIB view is that one for which the
       vacmViewTreeFamilyViewName has the same value as the
       instance of this object; if the value is the empty
       string or if there is no active MIB view having this
       value of vacmViewTreeFamilyViewName, then no access
       is granted."
   ::= { sysSnmpGroupAccessEntry 5 }

sysSnmpaccessNotifyViewName OBJECT-TYPE
   SYNTAX                   SnmpAdminString (SIZE(0..32))
   MAX-ACCESS               read-create
   STATUS                   current
   DESCRIPTION
      "The value of an instance of this object identifies
       the MIB view of the SNMP context to which this
       concsystual row authorizes access for notifications.

       The identified MIB view is that one for which the
       vacmViewTreeFamilyViewName has the same value as the
       instance of this object; if the value is the empty
       string or if there is no active MIB view having this
       value of vacmViewTreeFamilyViewName, then no access
       is granted."
   ::= { sysSnmpGroupAccessEntry 6 }

sysSnmpaccessStatus     OBJECT-TYPE
   SYNTAX               RowStatus
   MAX-ACCESS           read-create
   STATUS               current
   DESCRIPTION
      "The status of this concsystual row.

       The  RowStatus TC [RFC2579] requires that this
       DESCRIPTION clause states under which circumstances
       other objects in this row can be modified:

       The value of this object has no effect on whether
       other objects in this concsystual row can be modified."
   ::= { sysSnmpGroupAccessEntry 7 }


-- SNMP View Tree

sysSnmpViewTreeTable OBJECT-TYPE
   SYNTAX            SEQUENCE OF TabSnmpViewTreeEntry
   MAX-ACCESS        not-accessible
   STATUS            current
   DESCRIPTION
      ""
   ::= { sysSnmpViewTree 1 }

sysSnmpViewTreeEntry OBJECT-TYPE
   SYNTAX            TabSnmpViewTreeEntry
   MAX-ACCESS        not-accessible
   STATUS            current
   DESCRIPTION
      ""
   INDEX { sysSnmpviewTreeName ,sysSnmpviewTreeSubtree }
   ::= { sysSnmpViewTreeTable 1 }

TabSnmpViewTreeEntry ::=
   SEQUENCE {
      sysSnmpviewTreeName         SnmpAdminString,
      sysSnmpviewTreeSubtree      OBJECT IDENTIFIER,
      sysSnmpviewTreeMask         OCTET STRING,
      sysSnmpviewTreeType         INTEGER,
      sysSnmpviewTreeStatus       RowStatus
   }

sysSnmpviewTreeName OBJECT-TYPE
   SYNTAX           SnmpAdminString (SIZE(1..32))
   MAX-ACCESS       not-accessible
   STATUS           current
   DESCRIPTION
      "The human readable name for a family of view subtrees."
   ::= { sysSnmpViewTreeEntry 1 }

sysSnmpviewTreeSubtree OBJECT-TYPE
   SYNTAX              OBJECT IDENTIFIER
   MAX-ACCESS          not-accessible
   STATUS              current
   DESCRIPTION
      "The MIB subtree which when combined with the
       corresponding instance of vacmViewTreeFamilyMask
       defines a family of view subtrees."
   ::= { sysSnmpViewTreeEntry 2 }

sysSnmpviewTreeMask OBJECT-TYPE
   SYNTAX           OCTET STRING (SIZE (0..16))
   MAX-ACCESS       read-create
   STATUS           current
   DESCRIPTION
      "The bit mask which, in combination with the
       corresponding instance of vacmViewTreeFamilySubtree,
       defines a family of view subtrees.

       Each bit of this bit mask corresponds to a
       sub-identifier of vacmViewTreeFamilySubtree, with the
       most significant bit of the i-th octet of this octet
       string value (extended if necessary, see below)
       corresponding to the (8*i - 7)-th sub-identifier, and
       the least significant bit of the i-th octet of this
       octet string corresponding to the (8*i)-th
       sub-identifier, where i is in the range 1 through 16.

       Each bit of this bit mask specifies whether or not
       the corresponding sub-identifiers must match when
       determining if an OBJECT IDENTIFIER is in this
       family of view subtrees; a '1' indicates that an
       exact match must occur; a '0' indicates 'wild card',
       i.e., any sub-identifier value matches.

       Thus, the OBJECT IDENTIFIER X of an object instance
       is contained in a family of view subtrees if, for
       each sub-identifier of the value of
       vacmViewTreeFamilySubtree, either:

         the i-th bit of vacmViewTreeFamilyMask is 0, or

         the i-th sub-identifier of X is equal to the i-th
         sub-identifier of the value of
         vacmViewTreeFamilySubtree.

       If the value of this bit mask is M bits long and

       there are more than M sub-identifiers in the
       corresponding instance of vacmViewTreeFamilySubtree,
       then the bit mask is extended with 1's to be the
       required length.

       Note that when the value of this object is the
       zero-length string, this extension rule results in
       a mask of all-1's being used (i.e., no 'wild card'),
       and the family of view subtrees is the one view
       subtree uniquely identified by the corresponding
       instance of vacmViewTreeFamilySubtree.

       Note that masks of length greater than zero length
       do not need to be supported.  In this case this
       object is made read-only."
   ::= { sysSnmpViewTreeEntry 3 }

sysSnmpviewTreeType OBJECT-TYPE
   SYNTAX           INTEGER  { included(1), excluded(2) }
   MAX-ACCESS       read-create
   STATUS           current
   DESCRIPTION
      "Indicates whether the corresponding instances of
       vacmViewTreeFamilySubtree and vacmViewTreeFamilyMask
       define a family of view subtrees which is included in
       or excluded from the MIB view."
   ::= { sysSnmpViewTreeEntry 4 }

sysSnmpviewTreeStatus OBJECT-TYPE
   SYNTAX             RowStatus
   MAX-ACCESS         read-create
   STATUS             current
   DESCRIPTION
      "The status of this concsystual row.

       The  RowStatus TC [RFC2579] requires that this
       DESCRIPTION clause states under which circumstances
       other objects in this row can be modified:

       The value of this object has no effect on whether
       other objects in this concsystual row can be modified."
   ::= { sysSnmpViewTreeEntry 5 }


-- SNMP Community

sysSnmpCommunityTable OBJECT-TYPE
   SYNTAX             SEQUENCE OF TabSnmpCommunityEntry
   MAX-ACCESS         not-accessible
   STATUS             current
   DESCRIPTION
      ""
   ::= { sysSnmpCommunity 1 }

sysSnmpCommunityEntry OBJECT-TYPE
   SYNTAX             TabSnmpCommunityEntry
   MAX-ACCESS         not-accessible
   STATUS             current
   DESCRIPTION
      ""
   INDEX { sysSnmpsnmpCommunityIndex }
   ::= { sysSnmpCommunityTable 1 }

TabSnmpCommunityEntry ::=
   SEQUENCE {
      sysSnmpsnmpCommunityIndex              SnmpAdminString,
      sysSnmpsnmpCommunityName                SnmpAdminString,
      sysSnmpsnmpCommunityPolicy              SnmpAdminString,
      sysSnmpsnmpCommunityStatus              RowStatus
   }

sysSnmpsnmpCommunityIndex OBJECT-TYPE
   SYNTAX                 SnmpAdminString (SIZE(1..32))
   MAX-ACCESS             not-accessible
   STATUS                 current
   DESCRIPTION
      "The unique index value of a row in this table."
   ::= { sysSnmpCommunityEntry 1 }

sysSnmpsnmpCommunityName OBJECT-TYPE
   SYNTAX                SnmpAdminString (SIZE(1..32))
   MAX-ACCESS            read-create
   STATUS                current
   DESCRIPTION
      "The unique index value of a row in this table."
   ::= { sysSnmpCommunityEntry 2 }

sysSnmpsnmpCommunityPolicy OBJECT-TYPE
   SYNTAX                  SnmpAdminString (SIZE(1..32))
   MAX-ACCESS              read-create
   STATUS                  current
   DESCRIPTION
      "A human readable string rsysresenting the corresponding
       value of snmpCommunityName in a Security Model
       indsysendent format."
   ::= { sysSnmpCommunityEntry 3 }

sysSnmpsnmpCommunityStatus OBJECT-TYPE
   SYNTAX                  RowStatus
   MAX-ACCESS              read-create
   STATUS                  current
   DESCRIPTION
      "The status of this concsystual row in the
       snmpCommunityTable.

       An entry in this table is not qualified for activation
       until instances of all corresponding columns have been
       initialized, either through default values, or through
       Set operations.  The snmpCommunityName and
       snmpCommunitySecurityName objects must be explicitly set.

       There is no restriction on setting columns in this table
       when the value of snmpCommunityStatus is active(1)."
   ::= { sysSnmpCommunityEntry 4 }


-- SNMP Trap Manager

sysSnmpTrapManagerTable OBJECT-TYPE
   SYNTAX               SEQUENCE OF TabSnmpTrapManagerEntry
   MAX-ACCESS           not-accessible
   STATUS               current
   DESCRIPTION
      ""
   ::= { sysSnmpTrapManager 1 }

sysSnmpTrapManagerEntry OBJECT-TYPE
   SYNTAX               TabSnmpTrapManagerEntry
   MAX-ACCESS           not-accessible
   STATUS               current
   DESCRIPTION
      ""
   INDEX { sysSnmpsnmpTrapManagerName }
   ::= { sysSnmpTrapManagerTable 1 }

TabSnmpTrapManagerEntry ::=
   SEQUENCE {
      sysSnmpsnmpTrapManagerName              SnmpAdminString,
      sysSnmpsnmpTrapManagerAddress           TAddress,
      sysSnmpsnmpTrapManagerSecurityLevel     L2snmpLevel,
      sysSnmpsnmpTrapManagerStatus            RowStatus
   }

sysSnmpsnmpTrapManagerName OBJECT-TYPE
   SYNTAX                  SnmpAdminString (SIZE(1..32))
   MAX-ACCESS              not-accessible
   STATUS                  current
   DESCRIPTION
      "The locally arbitrary, but unique identifier associated
       with this snmpNotifyEntry."
   ::= { sysSnmpTrapManagerEntry 1 }

sysSnmpsnmpTrapManagerAddress OBJECT-TYPE
   SYNTAX                     TAddress
   MAX-ACCESS                 read-create
   STATUS                     current
   DESCRIPTION
      "This object contains a transport address.  The format of
       this address dsysends on the value of the
       snmpTargetAddrTDomain object."
   ::= { sysSnmpTrapManagerEntry 2 }

sysSnmpsnmpTrapManagerSecurityLevel OBJECT-TYPE
   SYNTAX                           L2snmpLevel
   MAX-ACCESS                       read-create
   STATUS                           current
   DESCRIPTION
      "The Level of Security to be used when generating
       SNMP messages using this entry."
   ::= { sysSnmpTrapManagerEntry 3 }

sysSnmpsnmpTrapManagerStatus OBJECT-TYPE
   SYNTAX                    RowStatus
   MAX-ACCESS                read-create
   STATUS                    current
   DESCRIPTION
       "The status of this concsystual row in the
       SnmpTrapManagerTable.

       An entry in this table is not qualified for activation
       until instances of all corresponding columns have been
       initialized, either through default values, or through
       Set operations.  The snmpTrapManagerName, 
	   snmpTrapManagerAddress and snmpTrapManagerSecurityLevel
	   objects must be explicitly set.

       There is no restriction on setting columns in this table
       when the value of snmpTrapManagerStatus is active(1)."
   ::= { sysSnmpTrapManagerEntry 4 }





sysRadiusExtClient           OBJECT IDENTIFIER ::= { l2Radius 1 }

sysRadiusExtServerTable OBJECT-TYPE
   SYNTAX            SEQUENCE OF TabRadiusExtServerEntry
   MAX-ACCESS        not-accessible
   STATUS            current
   DESCRIPTION
      "The (concsystual) table listing the RADIUS servers with
       which the client shares a secret."
   ::=  { sysRadiusExtClient 3 }

sysRadiusExtServerEntry OBJECT-TYPE
   SYNTAX            TabRadiusExtServerEntry
   MAX-ACCESS        not-accessible
   STATUS            current
   DESCRIPTION
      "An entry (concsystual row) rsysresenting a RADIUS server
       with which the client shares a secret."
   INDEX {sysRadiusExtServerIndex}
   ::= { sysRadiusExtServerTable 1 }

TabRadiusExtServerEntry ::=
   SEQUENCE {
      sysRadiusExtServerIndex                  InterfaceIndex,
      sysRadiusExtServerAddress                IpAddress,
      sysRadiusExtServerSharedSecret           DisplayString,
      sysRadiusExtServerResponseTime           INTEGER,
      sysRadiusExtServerMaximumRetransmission  INTEGER,
	  sysRadiusExtServerAuthPortNum				INTEGER,	
      sysRadiusExtServerEntryStatus		    RowStatus,
      sysRadiusExtServerAccPort                         INTEGER 	
   }

sysRadiusExtServerIndex OBJECT-TYPE
   SYNTAX            InterfaceIndex
   MAX-ACCESS        read-only
   STATUS            current
   DESCRIPTION
      "The RADIUS server with whom the client interacts."
   ::= { sysRadiusExtServerEntry 1 }

sysRadiusExtServerAddress OBJECT-TYPE
   SYNTAX              IpAddress
   MAX-ACCESS          read-write
   STATUS              current
   DESCRIPTION
      "The IP address of the RADIUS server
       referred to in this table entry."
   ::= { sysRadiusExtServerEntry 2 }


sysRadiusExtServerSharedSecret OBJECT-TYPE
   SYNTAX                   DisplayString
   MAX-ACCESS               read-write
   STATUS                   current
   DESCRIPTION
      "The secret string which is shared between Server and Client"
   ::= { sysRadiusExtServerEntry 4 }

sysRadiusExtServerResponseTime OBJECT-TYPE
   SYNTAX                   INTEGER (1 ..120)
   MAX-ACCESS               read-write
   STATUS                   current
   DESCRIPTION
      "The maximum time within which the server has to respond for a
       request from the client"
   ::= { sysRadiusExtServerEntry 6 }

sysRadiusExtServerMaximumRetransmission OBJECT-TYPE
   SYNTAX                            INTEGER (1 ..254)
   MAX-ACCESS                        read-write
   STATUS                            current
   DESCRIPTION
      "The allowed maximum no. of trials to be tried by a client to get
       response from the server for a request"
   ::= { sysRadiusExtServerEntry 7 }

sysRadiusExtServerAuthPortNum OBJECT-TYPE
   SYNTAX                            INTEGER (1 ..65535)
   MAX-ACCESS                        read-write
   STATUS                            current
   DESCRIPTION
      "The UDP port the client is using to send authentication
      requests to this server."
   ::= { sysRadiusExtServerEntry 8 }

sysRadiusExtServerEntryStatus	OBJECT-TYPE
   SYNTAX    			    RowStatus
   MAX-ACCESS 			    read-create
   STATUS 			        current
   DESCRIPTION
      "This object indicates the status of this entry. An entry is
      created in this table when this object is SET to 'createAndWait'.
      The entry in this table is used when the status of this object 
      is SET 'active'. The entry in this table is not used when this 
      object is SET 'notInService'. An entry created in this table is
      be deleted when this object is SET 'destroy'."
   ::= { sysRadiusExtServerEntry 9  }

sysRadiusExtServerAccPort OBJECT-TYPE
   SYNTAX                            INTEGER (1 ..65535)
   MAX-ACCESS                        read-write
   STATUS                            current
   DESCRIPTION
	"The UDP port the client is using to send accounting
	requests to this server."
	::= { sysRadiusExtServerEntry 10 }





if               OBJECT IDENTIFIER ::= { l2Cfa 1 }
traps            OBJECT IDENTIFIER ::= { l2Cfa 4 }


-- if

ifMaxInterfaces         OBJECT-TYPE
   SYNTAX               InterfaceIndex
   MAX-ACCESS           read-write
   STATUS               deprecated
   DESCRIPTION
      "Specifies the maximum number of interfaces that can
       be present in the system."
   ::= { if 1 }

ifMaxPhysInterfaces  OBJECT-TYPE
   SYNTAX            InterfaceIndex
   MAX-ACCESS        read-write
   STATUS            deprecated
   DESCRIPTION
      "Specifies the maximum number of physical interfaces
       that can be present in the system."
   ::= { if 2 }

ifAvailableIndex     OBJECT-TYPE
   SYNTAX            InterfaceIndex
   MAX-ACCESS        read-only
   STATUS            current
   DESCRIPTION
      "Shows an ifIndex which is available for creation of
       any new virtual (non-physical) interface in the system.
       This ifIndex value can be used for creation of interfaces
       in the ifMainTable or any media-specif MIB. For creation
       of physical interfaces, any free ifIndex between 1 and
       ifMaxPhysInterfaces can be used."
   ::= { if 3 }

ifMainTable          OBJECT-TYPE
   SYNTAX            SEQUENCE OF TabIfMainEntry
   MAX-ACCESS        not-accessible
   STATUS            current
   DESCRIPTION
      "A list of all the interface entries in the system.
       This table contains objects which are applicable to all
       types of interfaces in the system. This table is a
       proprietary extension to the standard ifTable and
       ifXTable. The index to this table has the semantics of
       the MIB-2 ifIndex."
   ::= { if 4 }

ifMainEntry          OBJECT-TYPE
   SYNTAX            TabIfMainEntry
   MAX-ACCESS        not-accessible
   STATUS            current
   DESCRIPTION
      "An entry containing management information applicable
       to a particular interface."
   INDEX { ifMainIndex }
   ::= { ifMainTable 1 }

TabIfMainEntry ::=
   SEQUENCE {
      ifMainIndex              InterfaceIndex,
      ifMainType               INTEGER,
      ifMainMtu                Integer32,
      ifMainAdminStatus        INTEGER,
      ifMainOperStatus         INTEGER,
      ifMainEncapType          INTEGER,
      ifMainBrgPortType         INTEGER,
      ifMainRowStatus          RowStatus
   }

ifMainIndex          OBJECT-TYPE
   SYNTAX            InterfaceIndex
   MAX-ACCESS        not-accessible
   STATUS            current
   DESCRIPTION
      "A unique value, greater than zero, for each
       interface. This object is identical to the ifIndex
       of the standard MIB-2 ifTable."
   ::= { ifMainEntry 1 }

ifMainType      OBJECT-TYPE
   SYNTAX       INTEGER {
                  rfc877x25(5), -- X.25
                  ethernetCsmacd(6), -- Ethernet/802.3
                  iso88025TokenRing(9), -- Token Ring
                  ppp(23), -- PPP link
                  softwareLoopback(24), -- Loopback Interface
                  frameRelay(32), -- Frame Relay DTE port
                  miox25(38), -- multiprotocol over x.25
                              -- used for X.25 VCs
                  aal5(49), -- AAL5 over ATM
                  async(84), -- ASYNC
                  frameRelayMPI(92), -- multiprotocol
                                     -- over FR
                                     -- used for FR VCs
                                     -- and sub-interfaces
                  pppMultilinkBundle(108), -- PPP Multilink
                                           -- Bundle
                  ipOverAtm(114), -- IPoA virtual
                  hdlc(118), -- HDLC port
                  tunnel(131), -- Encapsulation interface
                  atmSubInterface(134), -- VCs under IPoA
                  l2macvlan(135), -- Layer2 VLAN interface
                  l3ipvlan(136), -- Layer3 VLAN interface
                  mplsTunnel (150), -- MPLS Tunnel Virtual Interface
                  ieee8023ad(161), -- Link Aggregation Mib
                  mpls (166) -- MPLS
                  } -- These are the currently supported
                    -- interfaces. More can be added at a
                    -- later time.
   MAX-ACCESS   read-create
   STATUS       current
   DESCRIPTION
      "The type/protocol of interface. Specification of
       the object is mandatory for all interfaces. This
       value should be specified after the row creation
       in the ifMainTable and before setting any other
       object in this table. Once the type is specified,
       it cannot be changed - the interface should be
       deleted for changing the type of the interface.

       The ethernetCsmacd(6), iso88025TokenRing(9), aal5(49),
       async(84) and hdlc(118) are physical interfaces while
       all other types are virtual or logical interfaces.

       For creation of physical interface types, it is mandatory to
       specify the handle to the device driver using the ifAlias
       object of the standard ifXTable before specifying the type.
       This handle could be something like eth1 or /dev/abcd."
   ::= { ifMainEntry 2 }

ifMainMtu            OBJECT-TYPE
   SYNTAX            Integer32
   MAX-ACCESS        read-create
   STATUS            current
   DESCRIPTION
      "The MTU for the interface as shown to the higher
       interface sub-layer (this value should not include
       the encapsulation or header added by the interface).
       If IP is operating over the interface, then this
       value indicates the IP MTU over this interface.

       For changing the MTU of any interface, the interface
       must be brought down first - changing MTU while the
       interface is administratively up is not permitted.

       If not specified during interface creation, a default
       value is assigned based on the ifMainType given to
       the particular interface.

       While configuring for logical VLAN interfaces, care
       should be taken to, configure this value as the
       lowest of the MTU values of the member ports."
   ::= { ifMainEntry 3 }

ifMainAdminStatus    OBJECT-TYPE
   SYNTAX            INTEGER {
                        up(1),   -- ready to pass packets
                        down(2),
                        testing(3)   -- in some test mode
                        }
   MAX-ACCESS        read-create
   STATUS            current
   DESCRIPTION
      "The desired state of the interface. This object
       can be set only when the ifMainRowStatus of the
       interface is active. This object has the semantics
       of the ifAdminStatus of the standard ifTable.

       The testing(3) state indicates that no operational
       packets can be passed - this state is not currently
       supported.

       When a managed system initializes, all
       interfaces start with ifMainAdminStatus in the
       down(2) state, it's a default state also. As a result
       of either explicit management action or per
       configuration information retained by the managed
       system, ifMainAdminStatus is then changed to
       the up (1) state (or remains in the
       down(2) state)."
   DEFVAL { down }
   ::= { ifMainEntry 4 }

ifMainOperStatus     OBJECT-TYPE
   SYNTAX            INTEGER  {
                        up(1),        -- ready to pass packets
                        down(2),
                        testing(3),   -- in some test mode
                        unknown(4),   -- status can not be
                                      -- determined for
                                      -- some reason.
                        dormant(5),
                        notPresent(6), -- some component is
                                       -- missing
                        lowerLayerDown(7) -- down due to state
                                          --  of lower-layer
                                          -- interface(s).
                        }
   MAX-ACCESS        read-only
   STATUS            current
   DESCRIPTION
      "The current operational state of the interface.
       The testing (3) state indicates that no operational
       packets can be passed - this state is not supported
       currently.

       If ifMainAdminStatus is down (2)
       then ifMainOperStatus would be down (2). If
       ifMainAdminStatus is changed to up (1) then
       ifMainOperStatus should change to up (1) if the
       interface is ready to transmit and receive
       work traffic; it should change to dormant (5)
       the interface is waiting for external actions
       (such as a serial line waiting for an incoming
       connection); it should change to lowerLayerDown(7)
       state if it cannot be made up as the interface sub-layer
       below it is down; it should remain in the down (2) state
       if and only if there is a fault that prevents it
       from going to the up (1) state; it should remain in
       the notPresent (6) state if the interface has
       missing (typically, hardware) components.

       The status unknown(4) is shown when it is not possible
       to determine the exact status of the interface - e.g.
       the interface sub-layer is performing negotiations -
       during this period the interface is not up but at the
       same time, it is not a fault condition and hence it
       cannot be shown as down - in such periods the status
       is shown as unknown.

       This object has the semantics of the ifOperStatus of the
       standard ifTable."
   ::= { ifMainEntry 5 }

ifMainEncapType         OBJECT-TYPE
   SYNTAX               INTEGER {
                           other(1),
                           nlpid(2), -- NLPID based encap
                                     -- in the case of FR
                                     -- and multiplexed
                                     -- NLPID encap for X.25
                           nlpidSnap(3), -- NLPID-SNAP based
                                          -- encap in the case
                                          -- of FR and multiplexed
                                          -- NLPID-SNAP encap for
                                          -- X.25.
                           cudNlpid(4),   -- dedicated NLPID for
                                          -- X.25 only
                           cudNlpidSnap(5),   -- dedicated
                                                -- NLPID-SNAP for
                                                -- X.25 only
                           llcSnap(6),   -- for ATM VCs only
                           vcMultiplexed(7),  -- for ATM VCs only
                           ethernetV2(8) -- for Ethernet interfaces
                           }
   MAX-ACCESS           read-write
   STATUS               current
   DESCRIPTION
      "The encapsulation type to be used over the interface.

       For Ethernet interfaces, the default encapsulation
       type is ethernetV2(8). The other possible encapsulation
       is llcSnap(6). If other(1) is specified then an
       automatic encapsulation type learning method is used
       in ARP for determining the encapsulation for unicast
       destinations while the multicast and broadcast destinations
       use ethernetV2(8).

       For PPP and MLPPP interfaces, the encapsulation type can
       only be other(1) and this is the default value.

       For FR VCs, the value can be nlpid(2) (for carrying protocols
       which have NLPID) or nlpidSnap(3) (for other protocols). The
       default is nlpid(2) and the types of protocols supported are
       inferred from the stack-layering implemented over the
       interface.

       For X.25 VCs, the value can be nlpid(2) or nlpidSnap(3)
       (where the VC can carry multiplexed protocol traffic with
       each data packet containing the NLPID or SNAP header) or
       cudNlpid(4) or cudNlpidSnap(5) (where the CUD specifies
       the NLPID of the protocol or SNAP and the data packets do
       not contain these headers - for dedicated VCs). The default
       is cudNlpid(4).

       For ATM VCs, the default is llcSnap(6) but the
       vcMultiplexed(7) encapsulation is also supported.

       This object is not applicable to other interfaces."
   ::= { ifMainEntry 6 }

ifMainBrgPortType      OBJECT-TYPE
   SYNTAX      INTEGER {
                        providerNetworkPort           (1),
                        customerNetworkPortPortBased (2),
                        customerNetworkPortStagged  (3),
                        customerEdgePort              (4),
                        propCustomerEdgePort          (5),
                        propCustomerNetworkPort       (6),
                        propProviderNetworkPort       (7),
                        customerBridgePort            (8)
    }
   MAX-ACCESS  read-write
   STATUS      current
   DESCRIPTION
      "The Bridge port type of this specified externally accessible port.
       Bridge Port type can be specified only for switch ports and not for
       router ports.

       providerNetworkPort - Port Connected to a single Provider.
       SVLAN Classification is based on only the PVID configured for the
       port for untagged packets.

       customerNetworkPortPortBased - Port in the S-VLAN component that
       can transmit or received frames for single customer.
       All packets received on this port, are mapped to one single service
       instance identified by the PVID of that Port.
       Accsystable Port Type will be always Admit only Untagged or Priority
       Tagged Frames on this port.

       customerNetworkPortStagged - Port in the S-VLAN component that
       can transmit or received frames for single customer.
       VLAN classification on this interface will be based on the S-tag
       received or on the PVID of the port. Ingress Filtering will be
       always enabled on this port.

       customerEdgePort - Port in a Provider Edge Bridge connected to a
       single customer. Multiple services can be provide on this port.
       The Packets received on this interface will be first classified
       to a CVLAN. CVLAN classification can be based on the Vid
       in the C-Tag present in the packet (if it C-tagged packet) or from
       the pvid of the port. Service instance selection (S-VLAN selection)
       for a frame is done based on the entry present in the C-VID
       registration table for the pair (C-VID, recsystion Port).
       CustomerEdgePort configuration is allowed only in Provider Edge
       Bridges.

       propCustomerEdgePort - Port connected to a single customer, where
       multiple services can be provided based on only Proprietary SVLAN
       classification tables. S-VLAN classification will not happen based on
       C-VID registration table on this port. propCustomerEdgePort
       configuration is allowed only in Provider Edge Bridges.

       propCustomerNetworkPort - Port connected to a single customer, where
       multiple service can be provided based on CVLANs by assigning one of
       the Proprietary SVLAN classification tables to this port. The
       services can also be assigned using other proprietary SVLAN
       classification tables where CVLAN is not the index of the table.

       propProviderNetworkPort - Port connected to a Q-in-Q Bridge located
       inside Provider Network. This port is part of S-VLAN component.
       If packets to be tagged and sent out of this port will have 0x8100
       as the ether type. Similarly pakcets with standard Q tag (ether type
       as 0x8100) received will be considered as S-Tagged packets.

       customerBridgePort - Type of the port to be used in customer
       bridges as well in Provider(Q-in-Q) bridges. This type is not valid
       in Provider Core bridges as well as Provider Edge bridge.

       In Customer bridges and in Provider Bridges only customerPort option
       is allowed.

       Bridge Port Type cannot be set for a port-channel port, if some
       physical ports are aggregated in it.
       Also Bridge Port type cannot be set for a port, if part of a
       port-channel.

       Whenever the Bridge port type changes, the previous configuration
       associated with the port will be flushed.

       For example.

       whenever CNP(STagged) and PNP port types are changed to any
       other port type,
         - The unicast entries learnt on this port and
         - The VID translation table entries associated with the port
           will be flushed.

       Whenever CEP port type is changed to any other port type,
         - The unicast entries learnt on this port
         - The C-VID registration table entries associated with the port
         - The PEP configuration table entries
         - The service priority regeneration table entries
         will be flushed.

         Even the vlan membership of the port will be removed when the
         Pbport type is changed."
   DEFVAL { 8 }
   ::= { ifMainEntry 7 }

ifMainRowStatus      OBJECT-TYPE
   SYNTAX            RowStatus
   MAX-ACCESS        read-create
   STATUS            current
   DESCRIPTION
      "A RowStatus variable for addition, deletion and in-activation
       of the interfaces. Specification of the object is mandatory
       for all interfaces.

       When the status is active, the interface is created and
       ready to use in the respective protocol modules.

       When the status is notInService, the interface has not been
       registered with the respective protocol modules and as such
       those modules are not aware of the existence of the interface
       - creation is hence, incomplete. Setting an active interface
       to notInService results in de-registration/deletion of the
       interface from the respective protocol modules and all the
       configurations associated with that interface in those modules
       may be lost.

       Deletion of an interface, may affect the status of other
       interfaces which are layered above or below it in the Interface
       Stack (ifStackTable) and may result in other interfaces being
       made notReady or notInService."
   ::= { ifMainEntry 8 }

ifIpTable            OBJECT-TYPE
   SYNTAX            SEQUENCE OF TabIfIpEntry
   MAX-ACCESS        not-accessible
   STATUS            current
   DESCRIPTION
      "A list of all the interface entries in the system which
       are registered with IP.

       This table contains objects which are applicable for the
       management of IP over the network interfaces
       in the system.

       This table is a extension to the ifMainTable.
       The index to this table has the semantics of
       the ifMainIndex of the ifMainTable.

       Entries are created automatically in this table for
       any interface sub-layer which is layer below IP using
       the ifStackTable. Similarly, entries are deleted from
       this table when the interface's layering below IP is
       removed."
   ::= { if 5 }

ifIpEntry            OBJECT-TYPE
   SYNTAX            TabIfIpEntry
   MAX-ACCESS        not-accessible
   STATUS            current
   DESCRIPTION
      "An entry containing management information applicable
       to a particular interface over which IP is operating."
   INDEX { ifMainIndex }
   ::= { ifIpTable 1 }

TabIfIpEntry ::=
   SEQUENCE {
      ifIpAddrAllocMethod  INTEGER,
      ifIpAddr             IpAddress,
      ifIpSubnetMask       IpAddress,
      ifIpBroadcastAddr    IpAddress,
      ifIpForwardingEnable  TruthValue,
      ifIpAddrAllocProtocol INTEGER
   }

ifIpAddrAllocMethod  OBJECT-TYPE
   SYNTAX            INTEGER {
                        manual(1),  -- To be set by Manager
                        negotiation(2), -- obtained from peer
                        dynamic(3),
           none(4)  -- none of the above
                        } -- Currently only
                          -- these method possible.
   MAX-ACCESS        read-write
   STATUS            current
   DESCRIPTION
      "The mechanism to be used for allocation of IP
       address for this interface.

       The value negotiation can be used only for PPP
       and MLPPP interfaces which support obtaining of
       IP addresses through negotiation.

       The dynamic(3) option takes an IP
       address dynamically from the available
       server (dhcp/bootp/rarp) according to the
       protocol specified in ifIpAddrAllocProtocol.

       If the method specified is manual and the IP
       address is not provided (then the interface
       would be treated as a un-numbered interface."
   DEFVAL { none }
   ::= { ifIpEntry 1 }

ifIpAddr             OBJECT-TYPE
   SYNTAX            IpAddress
   MAX-ACCESS        read-write
   STATUS            current
   DESCRIPTION
      "Specifies the IP address given to this
       interface. The specification of this object is
       mandatory for all network interfaces (Ethernet,
       FR VC, IPoA interface, PPP link - not under MP,
       MP interface and X.25 VC). If the interface is
       not a network interface then the default value
       of 0.0.0.0 is assigned and the interface is
       treated as a un-numbered interface by IP."
   DEFVAL { '00000000'H }
   ::= { ifIpEntry 2 }

ifIpSubnetMask       OBJECT-TYPE
   SYNTAX            IpAddress
   MAX-ACCESS        read-write
   STATUS            current
   DESCRIPTION
      "Specifies the IP Subnet Mask for this
       interface. The value should be specified only
       for network interfaces and any valid VLSM is
       accsysted.

       If not specified, this object takes the default
       subnet mask value based on the class of the IP
       address configured for the interface."
   ::= { ifIpEntry 3 }

ifIpBroadcastAddr    OBJECT-TYPE
   SYNTAX            IpAddress
   MAX-ACCESS        read-write
   STATUS            current
   DESCRIPTION
      "Specifies the IP broadcast address for this
       interface. The value should be specified only
       for network interfaces and any valid broadcast
       address based on a valid VLSM is accsysted.

       If not specified, this object takes the default
       value based on the class of the IP
       address configured for the interface."
   ::= { ifIpEntry 4 }

ifIpForwardingEnable OBJECT-TYPE
   SYNTAX            TruthValue
   MAX-ACCESS        read-write
   STATUS            current
   DESCRIPTION
      "Specifies whether IP forwarding is enable on
       this interface. Disabling IP forwarding on an
       interface will result in packets which are to
       be forwarded on that interface being dropped
       and ICMP error messages being generated for the
       packets."
   DEFVAL { true }
   ::= { ifIpEntry 5 }

ifIpAddrAllocProtocol  OBJECT-TYPE
   SYNTAX              INTEGER {
                          none(0), 
                          rarp(1),
                          dhcp(2),
                          bootp(3)
                        }
   MAX-ACCESS        read-write
   STATUS            current
   DESCRIPTION
     "Specifies the protocol to be used to obtain
       IP address for this interface.  This object is
       valid only when ifIpAddrAllocMethod is set to
       dynamic (3).

       Currently rarp (1) option is not
       supported. The assigned value will be effective
       only when the interface admin status changes"
   DEFVAL { dhcp }
   ::= { ifIpEntry 6 }


ifIvrTable              OBJECT-TYPE
   SYNTAX               SEQUENCE OF TabIfIvrEntry
   MAX-ACCESS           not-accessible
   STATUS               current
   DESCRIPTION
      "A list of all the interfaces in the system with IVR related
       configurations.

       This table is an extension to the ifMainTable. The index to
       this table has the semantics of the ifMainIndex of the
       ifMainTable."
   ::= { if 8 }

ifIvrEntry           OBJECT-TYPE
   SYNTAX            TabIfIvrEntry
   MAX-ACCESS        not-accessible
   STATUS            current
   DESCRIPTION
      "An entry containing IVR-related information applicable
       to a interface."
   INDEX { ifMainIndex }
   ::= { ifIvrTable 1 }

TabIfIvrEntry ::=
   SEQUENCE {
      ifIvrBridgedIface
         TruthValue
      }

ifIvrBridgedIface    OBJECT-TYPE
   SYNTAX            TruthValue
   MAX-ACCESS        read-write
   STATUS            current
   DESCRIPTION
      "Indicates if this interface is a Bridged interface
       or not.
       A value of 'TRUE' indicates that this interface is
       a Bridged interface and is capable of performing
       bridging of packets through this interface.
       A value of 'FALSE' indicates that this
       interface is a Routed interface and is capable of
       performing routing of packets through this interface."
   ::= { ifIvrEntry 1 }

ifSetMgmtVlanList    OBJECT-TYPE
   SYNTAX            OCTET STRING (SIZE (0..512))
   MAX-ACCESS        read-write
   STATUS            current
   DESCRIPTION
      "A string of octets containing one bit per VLAN. The
       first octet corresponds to VLANs with VlanId values
       1 through 8; the second octet to VLANs 9 through
       16 etc.  The most significant bit of each octet
       corresponds to the lowest VlanId value in that octet.
       This is the set of vlans configured by management to associate
       with the management interface."
   ::= { if 9 }

ifResetMgmtVlanList OBJECT-TYPE
   SYNTAX           OCTET STRING (SIZE (0..512))
   MAX-ACCESS       read-write
   STATUS           current
   DESCRIPTION
      "A string of octets containing one bit per VLAN. The
       first octet corresponds to VLANs with VlanId values
       1 through 8; the second octet to VLANs 9 through
       16 etc.  The most significant bit of each octet
       corresponds to the lowest VlanId value in that octet.
       This is the set of vlans configured by management to dis-associate
       from the management interface.
       Get operation is not allowed for this object."
   ::= { if 10 }

ifSecondaryIpAddressTable  OBJECT-TYPE
   SYNTAX                  SEQUENCE OF TabIfSecondaryIpAddressEntry
   MAX-ACCESS              not-accessible
   STATUS                  current
   DESCRIPTION
      "A list of secondary IP addresses configured over the
       interfaces registered with IP.

       This table is a extension to the ifMainTable.
       The index to this table has the semantics of
       the ifMainIndex of the ifMainTable.

       Secondary IpAddress configuration should not override the
       primary ip address configured for any of the interface

       Updation of entries in this table are not allowd when
       RowStatus is active"
   ::= { if 11 }

ifSecondaryIpAddressEntry       OBJECT-TYPE
   SYNTAX                       TabIfSecondaryIpAddressEntry
   MAX-ACCESS                   not-accessible
   STATUS                       current
   DESCRIPTION
      "An entry contains the information associated with the
       secondary(additional) ip address configured to a particular
       interface."
   INDEX { ifMainIndex , ifSecondaryIpAddress}
   ::= { ifSecondaryIpAddressTable 1 }

TabIfSecondaryIpAddressEntry ::=
   SEQUENCE {
      ifSecondaryIpAddress       IpAddress,
      ifSecondaryIpSubnetMask    IpAddress,
      ifSecondaryIpBroadcastAddr IpAddress,
      ifSecondaryIpRowStatus     RowStatus
   }

ifSecondaryIpAddress         OBJECT-TYPE
   SYNTAX                    IpAddress
   MAX-ACCESS                not-accessible
   STATUS                    current
   DESCRIPTION
      "Specifies the Secondary IP address associated with the
       interface"
   ::= {ifSecondaryIpAddressEntry  1 }

ifSecondaryIpSubnetMask     OBJECT-TYPE
   SYNTAX                   IpAddress
   MAX-ACCESS               read-write
   STATUS                   current
   DESCRIPTION
      "Specifies the IP Subnet Mask associted with the
       secondary ip address configuration. The value should be
       specified only for network interfaces and any valid
       VLSM is accsysted.

       If not specified, this object takes the default
       subnet mask value based on the class of the IP
       address configured for the interface."
   ::= { ifSecondaryIpAddressEntry 2 }

ifSecondaryIpBroadcastAddr    OBJECT-TYPE
   SYNTAX                     IpAddress
   MAX-ACCESS                 read-write
   STATUS                     current
   DESCRIPTION
      "Specifies the IP broadcast address associated with
       the configured secondary IP address. The value should be
       specified only for network interfaces and any valid
       broadcast address based on a valid VLSM is accsysted.

       If not specified, this object takes the default
       value based on the class of the IP
       address configured for the interface."
   ::= { ifSecondaryIpAddressEntry 3 }

ifSecondaryIpRowStatus OBJECT-TYPE
   SYNTAX              RowStatus
   MAX-ACCESS          read-create
   STATUS              current
   DESCRIPTION
      "This object is used to manage creation and deletion of rows
       in this table."
   ::= { ifSecondaryIpAddressEntry 4 }




sysRmonEnableStatus OBJECT-TYPE
   SYNTAX  INTEGER { sysRmonenabled(1), sysRmondisabled(2) } 
   MAX-ACCESS read-write
   STATUS current
   DESCRIPTION
      "This object defines the sysRmonenable flag for sysRmon" 
   ::= { l2Rmon 2 }

sysRmonHwStatsSupp OBJECT-TYPE
   SYNTAX  INTEGER { notsupported(0), supported(1)}
   MAX-ACCESS read-write
   STATUS current
   DESCRIPTION
      "This object defines the flag for whether HW supports
       Etherstatistics or not   "
   ::= { l2Rmon 3 }

sysRmonHwHistorySupp OBJECT-TYPE
   SYNTAX  INTEGER { notsupported(0), supported(1)}
   MAX-ACCESS read-write
   STATUS current
   DESCRIPTION
      "This object defines the enabled HWhistorysupp flag for sysRmon"
   ::= { l2Rmon 4 }

sysRmonHwAlarmSupp OBJECT-TYPE
   SYNTAX  INTEGER { notsupported(0), supported(1)}
   MAX-ACCESS read-write
   STATUS current
   DESCRIPTION
      "This object defines the enabled HWAlarmsupp flag for sysRmon"
   ::= { l2Rmon 5 }

sysRmonHwEventSupp OBJECT-TYPE
   SYNTAX  INTEGER { notsupported(0), supported(1)}
   MAX-ACCESS read-write
   STATUS current
   DESCRIPTION
      "This object defines the enabled HWEvent flag for sysRmon"
   ::= { l2Rmon 9 }





PortLaMode ::= TEXTUAL-CONVENTION
   STATUS         current
   DESCRIPTION
      "Defines how a Port Channel does channeling.
       lacp(1)      - place the port into passive
                      negotiation state, in which the
                      port waits for its peer to
                      initiate negotiation.
       manual(2)    - force the port to enable
                      channeling.
       disable(3)   - channeling is disabled."
   SYNTAX INTEGER {
      lacp(1),
      manual(2),
      disable(3)
   }

LacpKey ::= TEXTUAL-CONVENTION
   STATUS    current
   DESCRIPTION
      "The Actor or Partner Key value."
   SYNTAX Integer32 (0..65535)


LacpState ::= TEXTUAL-CONVENTION
   STATUS current
   DESCRIPTION
      "The Actor and Partner State values from the LACPDU."
   SYNTAX BITS {
      lacpActivity(0),
      lacpTimeout(1),
      aggregation(2),
      synchronization(3),
      collecting(4),
      distributing(5),
      defaulted(6),
      expired(7)
   }


sysLaSystem                OBJECT IDENTIFIER ::= { l2La 1 }
sysLaPortChannel           OBJECT IDENTIFIER ::= { l2La 2 }
sysLaPort                  OBJECT IDENTIFIER ::= { l2La 3 }


-- LA System

sysLaSystemControl OBJECT-TYPE
   SYNTAX      INTEGER { start(1), shutdown(2)}
   MAX-ACCESS  read-write
   STATUS      current
   DESCRIPTION
      "Start or shutdown Link Aggregation Module in the system

       When set as 'start',resources required by Link aggregation
       module are allocated & Link aggregation module starts running.

       When shutdown, all resources used by Link aggregation module
       will be released to the system "
   ::= { sysLaSystem 1 }


sysLaStatus OBJECT-TYPE
   SYNTAX      INTEGER { enabled(1), disabled(2) }
   MAX-ACCESS  read-write
   STATUS      current
   DESCRIPTION
      "Sets the Link Aggregation Module administrative status as
       enabled or disabled. The module can be enabled only when this
       object is set to 'enabled'."
   ::= { sysLaSystem 2 }

sysLaTraceOption OBJECT-TYPE
   SYNTAX      Integer32
   MAX-ACCESS  read-write
   STATUS      current
   DESCRIPTION
      "This object is used to enable Trace Statements in
       Link Aggregation Module.

       A FOUR BYTE integer is used for enabling the level of tracing.
       Each BIT in the four byte integer, rsysresents a particular
       level of Trace.

       The mapping between the bit positions & the level of trace is
       as follows:
               0 - Init and Shutdown Traces
               1 - Management Traces
               2 - Data Path Traces
               3 - Control Plane Traces
               4 - Packet Dump Traces
               5 - Traces related to All Resources excsyst Buffers
               6 - All Failure Traces
               7 - Buffer Traces

       The remaining bits are unused. Combination of levels are
       also allowed.

       For example if the bits 0 and 1 are set, then the Trace
       statements related to Init-Shutdown and management
       will be printed.

       The user has to enter the corresponding INTEGER VALUE for the
       bits set. For example if bits 0 and 1 are set then user has to
       set the value 3."
   DEFVAL  { 0 }
   ::= { sysLaSystem 3 }

sysLaMaxPortsPerPortChannel OBJECT-TYPE
   SYNTAX      Integer32
   MAX-ACCESS  read-only
   STATUS      current
   DESCRIPTION
      "This Object specifies the maximun number of
       ports that can attach to a port-channel"
   ::= { sysLaSystem 4 }

sysLaMaxPortChannels  OBJECT-TYPE
  SYNTAX      Integer32
  MAX-ACCESS  read-only
  STATUS      current
  DESCRIPTION
      "This Object specifies the maximum number of
       Port-channels Present in the system"
  ::= { sysLaSystem 5 }

sysLaOperStatus OBJECT-TYPE
   SYNTAX      INTEGER { enabled(1), disabled(2) }
   MAX-ACCESS  read-only
   STATUS      current
   DESCRIPTION
      "This read only objects gives actual status of the Link
       Aggregation Module (Operational status of module). When
       Module is enabled Link Aggregation protocol starts
       functioning. When the module is disabled all the dynamically
       allocated memory will be freed and Link Aggregation protocol
       stops functioning."
   ::= { sysLaSystem 6 }

sysLaActorSystemID    OBJECT-TYPE
   SYNTAX       MacAddress
   MAX-ACCESS   read-write
   STATUS       current
   DESCRIPTION
      "A 6-octet read-write MAC address value used as a unique
       identifier for the System."
   ::= { sysLaSystem 7 }


-- Port Channel

sysLaPortChannelTable  OBJECT-TYPE
   SYNTAX     SEQUENCE OF TabLaPortChannelEntry
   MAX-ACCESS not-accessible
   STATUS     current
   DESCRIPTION
      "A Port-channel is created through ifMain table.
       After the creation of the port-channel, corresponding logical
       interface will be created in the ifMain table.
       This Port-channel table is indexed through Key values and allows to
       configure link selection policy and the Mac address for
       the port-channel. All other objects in this table displays
       the details of the port-channel"
   ::= { sysLaPortChannel 1 }

sysLaPortChannelEntry OBJECT-TYPE
   SYNTAX     TabLaPortChannelEntry
   MAX-ACCESS not-accessible
   STATUS     current
   DESCRIPTION
      "There is one entry in this table for each created
       port-channel port"
   INDEX { sysLaPortChannelIfIndex }
   ::= { sysLaPortChannelTable 1 }

TabLaPortChannelEntry ::=
   SEQUENCE {
      sysLaPortChannelIfIndex                InterfaceIndex,
      sysLaPortChannelGroup                  LacpKey,
      sysLaPortChannelAdminMacAddress        MacAddress,
      sysLaPortChannelMacSelection           INTEGER,
      sysLaPortChannelMode                   PortLaMode,
      sysLaPortChannelPortCount              Integer32,
      sysLaPortChannelActivePortCount        Integer32,
      sysLaPortChannelSelectionPolicy        INTEGER,
      sysLaPortChannelDefaultPortIndex       InterfaceIndexOrZero
   }

sysLaPortChannelIfIndex OBJECT-TYPE
   SYNTAX      InterfaceIndex
   MAX-ACCESS  not-accessible
   STATUS      current
   DESCRIPTION
      "The ifIndex of the port-channel(Aggregator's
       interface index). "
   ::= { sysLaPortChannelEntry 1 }

sysLaPortChannelGroup OBJECT-TYPE
   SYNTAX      LacpKey
   MAX-ACCESS  read-only
   STATUS      current
   DESCRIPTION
      "An index that uniquely identifies an entry in this table. "
   ::= { sysLaPortChannelEntry 2 }

sysLaPortChannelAdminMacAddress OBJECT-TYPE
   SYNTAX      MacAddress
   MAX-ACCESS  read-write
   STATUS      current
   DESCRIPTION
      "This object is used for configuring MacAddress that is
       to be used by the port-channel when sysLaPortChannelMacSelection
       is force.
       WARNING:The value configured should not conflict
       with the MAC address of system ports that are not configured
       to select this port-channel."
   ::= { sysLaPortChannelEntry 3 }

sysLaPortChannelMacSelection OBJECT-TYPE
   SYNTAX      INTEGER { dynamic(1), force(2) }
   MAX-ACCESS  read-write
   STATUS      current
   DESCRIPTION
      "Indicates the MAC address selection method for
       for the port-channel.
       Dynamic - Port-channel MAC address is chosen
                 as MAC address of an active port
                 in the PortChannel.
       Force   - Port-channel MAC address configured through
                 sysLaPortChannelAdminMacAddress is used.
       The value can be changed to Force only after configuring
       a valid MAC address in sysLaPortChannelAdminMacAddress."
   DEFVAL { 1 }
   ::= { sysLaPortChannelEntry 4 }

sysLaPortChannelMode OBJECT-TYPE
   SYNTAX       PortLaMode
   MAX-ACCESS   read-only
   STATUS       current
   DESCRIPTION
      "Current Operating Channel Mode of the port
       Lacp(1)    - forcing the port to negotiate with the
                    partner.
       manual(2)  - force the port to enable channeling (Manual).
       disable(3) - channeling is disabled."
   ::= { sysLaPortChannelEntry 5 }

sysLaPortChannelPortCount OBJECT-TYPE
   SYNTAX      Integer32
   MAX-ACCESS  read-only
   STATUS      current
   DESCRIPTION
      "The number of ports actually configured to the port-channel"
   ::= { sysLaPortChannelEntry 6 }

sysLaPortChannelActivePortCount OBJECT-TYPE
   SYNTAX      Integer32
   MAX-ACCESS  read-only
   STATUS      current
   DESCRIPTION
      "This object will give the number of ports that are attached to the
       port-channel and actively carrying data traffic on the link."
   ::= { sysLaPortChannelEntry 7 }

sysLaPortChannelSelectionPolicy OBJECT-TYPE
   SYNTAX      INTEGER {
                macSrc(1),
                macDst(2),
                macSrcDst(3),
                ipSrc(4),
                ipDst(5),
                ipSrcDst(6),
                vlanId(7)
               }
   MAX-ACCESS  read-write
   STATUS      current
   DESCRIPTION
      "Link selection policy to be used by the port-channel. The
       selection policies based on the IP address can be set if
       and only if hardware is present and supported."
   DEFVAL {macSrcDst}
   ::= { sysLaPortChannelEntry 8 }

sysLaPortChannelDefaultPortIndex OBJECT-TYPE
   SYNTAX      InterfaceIndexOrZero
   MAX-ACCESS  read-write
   STATUS      current
   DESCRIPTION
      "The ifIndex of the default port that gets attached to the
       aggregator. A value of 0 means there is no default port for
       this port-channel.
       If this object is set to 0, it will remove the current default
       port from the aggregator.
       To change the default port of an aggregator, first reset the
       object to 0 and then set the new ifIndex as default port."
   DEFVAL { 0 }
   ::= { sysLaPortChannelEntry 9 }


-- LA Port

sysLaPortTable OBJECT-TYPE
   SYNTAX SEQUENCE OF TabLaPortEntry
   MAX-ACCESS         not-accessible
   STATUS             current
   DESCRIPTION
      "A table that contains objects to set the port lacp mode
       of dot3adAggPortTable."
   ::={ sysLaPort 1 }

sysLaPortEntry OBJECT-TYPE
   SYNTAX      TabLaPortEntry
   MAX-ACCESS  not-accessible
   STATUS      current
   DESCRIPTION
      "Each entry in this table is for each physical port that participates
       in Link Aggregation which can be either aggregatable or individual.
       This table is indexed by the PortIndex."
   INDEX {sysLaPortIndex }
   ::={sysLaPortTable 1 }

TabLaPortEntry ::=
   SEQUENCE {
      sysLaPortIndex                           InterfaceIndex,
      sysLaPortMode                            PortLaMode,
      sysLaPortBundleState                     INTEGER,
      sysLaPortActorResetAdminState            LacpState,
      sysLaPortAggregateWaitTime               TimeTicks,
      sysLaPortPartnerResetAdminState          LacpState,
      sysLaPortActorAdminPort                  Integer32,
      sysLaPortRestoreMtu                      Integer32,
      sysLaPortSelectAggregator                INTEGER
   }

sysLaPortIndex OBJECT-TYPE
   SYNTAX     InterfaceIndex
   MAX-ACCESS not-accessible
   STATUS     current
   DESCRIPTION
      "The ifIndex of the port"
   ::={ sysLaPortEntry 1 }

sysLaPortMode OBJECT-TYPE
   SYNTAX      PortLaMode
   MAX-ACCESS  read-write
   STATUS      current
   DESCRIPTION
    "This object is used to enable LACP, disable LACP or manually
    aggregate a port"
   ::={ sysLaPortEntry 2 }

sysLaPortBundleState OBJECT-TYPE
   SYNTAX      INTEGER {
                upInBndl(0),
                standby(1),
                down(2),
                upIndividual(3)
               }
   MAX-ACCESS  read-only
   STATUS      current
   DESCRIPTION
      "This read-only object is used to display the port state in aggregation
       upInBndl(0)      - The port is operationally up and actively
                          takes part in aggregation.
       standby(1)       - The port is capable of joining in
                          aggregation group, when any of the ports in
                          aggregation group goes down.
       down(2)          - The port is operationally down in lower layers.
                          or the port is operational in lower layers
                          but temporarily not able to participate
                          in aggregation because of different partner
                          information in the same group.
       upIndividual(3)  - The port is operating individually and
                          is not taking part in aggregation."
   ::={ sysLaPortEntry 3 }

sysLaPortActorResetAdminState OBJECT-TYPE
   SYNTAX     LacpState
   MAX-ACCESS read-write
   STATUS     current
   DESCRIPTION
      "A string of 8 bits,corresponding to the administrative values
       of Actor_State as transmitted by the Actor in LACPDUs.
       The first bit corresponds to bit 0 of Actor_State (LACP_Activity),
       the second bit corresponds to bit 1 (LACP_Timeout),the third bit
       corresponds to bit 2 (Aggregation),the fourth bit corresponds to
       bit 3 (Synchronization),the fifth bit corresponds to bit 4
       (Collecting),the sixth bit corresponds to bit 5 (Distributing),
       the seventh bit corresponds to bit 6 (Defaulted),and the eighth
       bit corresponds to bit 7 (Expired).
       This object allows the RESET of the values of Actor LACP_Activity,
       LACP_Timeout and Aggregation.
       Get operation on this object returns the current Port State of
       the Actor"
   ::={ sysLaPortEntry 4 }

sysLaPortAggregateWaitTime OBJECT-TYPE
   SYNTAX     TimeTicks
   MAX-ACCESS read-write
   STATUS     current
   DESCRIPTION
      "Duration of the port to attach to the PortChannel."
   DEFVAL { 2 }
   ::={ sysLaPortEntry 5 }

sysLaPortPartnerResetAdminState OBJECT-TYPE
   SYNTAX     LacpState
   MAX-ACCESS read-write
   STATUS     current
   DESCRIPTION
      "A string of 8 bits,corresponding to the administrative values
       of Partner_State.The first bit corresponds to bit 0 of Partner_State
       (LACP_Activity),the second bit corresponds to bit 1 (LACP_Timeout),
       the third bit corresponds to bit 2 (Aggregation),the fourth bit
       corresponds to bit 3 (Synchronization),the fifth bit corresponds to
       bit 4 (Collecting),the sixth bit corresponds to bit 5 (Distributing),
       the seventh bit corresponds to bit 6 (Defaulted),and the eighth
       bit corresponds to bit 7 (Expired).
       This object allows the RESET of the values of Partner LACP_Activity,
       LACP_Timeout and Aggregation.
       Get operation on this object returns zeros for
       the Partner administrative values"
   ::={ sysLaPortEntry 6 }

sysLaPortActorAdminPort OBJECT-TYPE
   SYNTAX     Integer32 (1..65535)
   MAX-ACCESS read-write
   STATUS     current
   DESCRIPTION
      "The port number used as dot3adAggPortActorPort and is
       communicated in LACPDUs as the Actor_Port."
   ::={ sysLaPortEntry 7 }

sysLaPortRestoreMtu OBJECT-TYPE
   SYNTAX     Integer32
   MAX-ACCESS read-write
   STATUS     current
   DESCRIPTION
      "The Restore mtu stores the original MTU of the port
       before getting aggregated to port channel.
       A SET on the MIB object is not allowed for SNMP users.
       This operation is allowed only during config-save-restore
       operation , during system initialization."
   ::={ sysLaPortEntry 8 }

sysLaPortSelectAggregator OBJECT-TYPE
   SYNTAX      INTEGER {
                static(0),
                dynamic(1)
               }
   MAX-ACCESS  read-only
   STATUS      current
   DESCRIPTION
      "This read-only object is used to display whether the port participates
       in dynamic aggregator selection. The default will be static aggregation
       selection.
       static(0)      - The port is involved only in static aggregation.
                        i.e. the port can be a member of only the aggregation
                        to which it is configured.
       dynamic(1)     - The port participates in dynamic aggregation
                        selection. i.e. the port will be a part of best
                        aggregation selected based on System id and Admin key.
       This object is set to 'dynamic' once the port is configured as a default
       port of a port channel."
   ::={ sysLaPortEntry 9 }





PaeControlledPortStatus ::= TEXTUAL-CONVENTION
   STATUS       current
   DESCRIPTION
      "The status values of the Authenticator PAE controlled
      session."
   SYNTAX       INTEGER {
                 authorized(1),
                 unauthorized(2)
                }

AuthenticMethod ::= TEXTUAL-CONVENTION
   STATUS      current
   DESCRIPTION
      "The Authentication method is using Remote Authentication
       Server or Local Authentication Server."
   SYNTAX      INTEGER {
                remoteServer(1),
                localServer(2)
               }

PermissionType ::= TEXTUAL-CONVENTION
   STATUS      current
   DESCRIPTION
      "The permission values."
   SYNTAX      INTEGER {
                allow(1),
                deny(2)
               }


sysPnacPaeSystem         OBJECT IDENTIFIER ::= { l2Pnac 1 }
sysPnacAuthServer        OBJECT IDENTIFIER ::= { l2Pnac 3 }
sysGuestVlan        	 OBJECT IDENTIFIER ::= { l2Pnac 4 }



-- Pae System

sysPnacSystemControl OBJECT-TYPE
   SYNTAX      INTEGER {
                start (1),
                shutdown (2)
               }
   MAX-ACCESS  read-write
   STATUS      current
   DESCRIPTION
      "Starts or shutdowns PNAC Module in the system.

       When set as 'start',resources required by PNAC
       module are allocated & PNAC module starts running.

       When shutdown, all resources used by PNAC module
       will be released to the system."
   ::= { sysPnacPaeSystem 1 }

sysPnacAuthenticServer OBJECT-TYPE
   SYNTAX      AuthenticMethod
   MAX-ACCESS  read-write
   STATUS      current
   DESCRIPTION
      "This object is used to configure for the choice of
       local or remote Authentication Server to be used by
       the Authenticator for its authentication services."
    ::= { sysPnacPaeSystem 3 }

sysPnacNasId OBJECT-TYPE
   SYNTAX      DisplayString
   MAX-ACCESS  read-write
   STATUS      current
   DESCRIPTION
      "This object is the Network Access Server Identifier
       to be presented before the remote Authentication
       Server."
   ::= { sysPnacPaeSystem 4 }

sysPnacPaePortTable OBJECT-TYPE
   SYNTAX      SEQUENCE OF TabPnacPaePortEntry
   MAX-ACCESS  not-accessible
   STATUS      current
   DESCRIPTION
      "A table of system level information for each port
       supported by the EnterprisePNAC. An entry appears in this
       table for each port of this system. This table is an
       extension of dot1xPaePortTable of IEEE 802.1x MIB."
   ::= { sysPnacPaeSystem 5 }

sysPnacPaePortEntry OBJECT-TYPE
   SYNTAX      TabPnacPaePortEntry
   MAX-ACCESS  not-accessible
   STATUS      current
   DESCRIPTION
      "Configuration as port based or MAC based authentication
       and Supplicant count on a port. Index to this table is
       same as that of the dot1xPaePortTable, which is the
       InterfaceIndex."
   INDEX { sysPnacPaePortNumber }
   ::= { sysPnacPaePortTable 1 }

TabPnacPaePortEntry ::=
   SEQUENCE {
      sysPnacPaePortNumber
         InterfaceIndex,
      sysPnacPaePortStatus
         PaeControlledPortStatus,
      sysPnacPaeMultiAuthEnable
         INTEGER,
	  sysPnacPaeProtocolMode
         Integer32,
	  sysPnacPaePiggybackMode
         INTEGER,
	  sysPnacPaeVlanAssignment
         INTEGER,
	  sysPnacPaeSecureVlan
         INTEGER
		 
   }

sysPnacPaePortNumber OBJECT-TYPE
   SYNTAX      InterfaceIndex
   MAX-ACCESS  not-accessible
   STATUS      current
   DESCRIPTION
      "The port number associated with this port."
   ::= { sysPnacPaePortEntry 1 }


sysPnacPaePortStatus OBJECT-TYPE
   SYNTAX      PaeControlledPortStatus
   MAX-ACCESS  read-only
   STATUS      current
   DESCRIPTION
      "The value of the combined Port status."
   ::= { sysPnacPaePortEntry 6 }

sysPnacPaeMultiAuthEnable OBJECT-TYPE
   SYNTAX      INTEGER {
                  enable(1),
                  disable(2)
                 }
   MAX-ACCESS  read-write
   STATUS      current
   DESCRIPTION
      "This object indicates dot1x multi hsot is enabled or disabled."
   DEFVAL { disable }
   ::= { sysPnacPaePortEntry 7 }
   
   
   sysPnacPaeProtocolMode OBJECT-TYPE
   SYNTAX      Integer32 
   MAX-ACCESS  read-write
   STATUS      current
   DESCRIPTION
      "This object indicates mode is 802.1x or mac based."
   ::= { sysPnacPaePortEntry 8 }
   
   sysPnacPaePiggybackMode OBJECT-TYPE
   SYNTAX      INTEGER {
                  enable(1),
                  disable(2)
                 }
   MAX-ACCESS  read-write
   STATUS      current
   DESCRIPTION
      "This object indicates piggyback mode is enabled or disabled."
   DEFVAL { disable }
   ::= { sysPnacPaePortEntry 9 }
   
   sysPnacPaeVlanAssignment OBJECT-TYPE
   SYNTAX      INTEGER {
                  enable(1),
                  disable(2)
                 }
   MAX-ACCESS  read-write
   STATUS      current
   DESCRIPTION
      "This object indicates vlan assignment is enabled or disabled."
   DEFVAL { disable }
   ::= { sysPnacPaePortEntry 10 }
   
   sysPnacPaeSecureVlan OBJECT-TYPE
   SYNTAX      INTEGER {
                  enable(1),
                  disable(2)
                 }
   MAX-ACCESS  read-write
   STATUS      current
   DESCRIPTION
      "This object indicates Secure vlan is enabled or disabled."
   DEFVAL { disable }
   ::= { sysPnacPaePortEntry 11}
   

sysPnacModuleOperStatus OBJECT-TYPE
   SYNTAX        INTEGER {
                  enabled(1),
                  disabled(2)
                 }
   MAX-ACCESS    read-only
   STATUS        current
   DESCRIPTION
      "This read only objects gives actual status of the PNAC Module
       (Operational status of module). When Module is enabled
       PNAC protocol starts functioning. When the module is disabled
       all the dynamically allocated memory will be freed and PNAC
       protocol stops functioning."
   ::= { sysPnacPaeSystem 6 }


-- Authentication Server

sysPnacASUserConfigTable OBJECT-TYPE
   SYNTAX      SEQUENCE OF TabPnacASUserConfigEntry
   MAX-ACCESS  not-accessible
   STATUS      current
   DESCRIPTION
      "This table contains authentication related User
       configuration information maintained by PNAC
       local Authentication Server."
   ::= { sysPnacAuthServer 1 }

sysPnacASUserConfigEntry OBJECT-TYPE
   SYNTAX      TabPnacASUserConfigEntry
   MAX-ACCESS  not-accessible
   STATUS      current
   DESCRIPTION
      "Each entry contains User name, Password, Authentication
       protocol used, Authenticated session timeout and Access
       ports list of the User seeking authentication."
   INDEX { sysPnacASUserConfigUserName }
   ::= { sysPnacASUserConfigTable 1 }

TabPnacASUserConfigEntry ::=
   SEQUENCE {
      sysPnacASUserConfigUserName
          OCTET STRING,
      sysPnacASUserConfigPassword
          DisplayString,
      sysPnacASUserConfigAuthProtocol
          Unsigned32,
      sysPnacASUserConfigAuthTimeout
          Unsigned32,
      sysPnacASUserConfigPortList
          PortList,
      sysPnacASUserConfigPermission
          PermissionType,
      sysPnacASUserConfigDynamicVlanID
	  Unsigned32,
      sysPnacASUserConfigRowStatus
          RowStatus
   }

sysPnacASUserConfigUserName OBJECT-TYPE
   SYNTAX      OCTET STRING (SIZE(0..115))
   MAX-ACCESS  not-accessible
   STATUS      current
   DESCRIPTION
      "Identity of the User seeking authentication. A string
       of not more than 20 printable characters."
   ::= { sysPnacASUserConfigEntry 1 }

sysPnacASUserConfigPassword OBJECT-TYPE
   SYNTAX      DisplayString
   MAX-ACCESS  read-write
   STATUS      current
   DESCRIPTION
      "The secret Password of the User. A string of not
       more than 20 printable characters.

       When read, this always returns a String
       of length zero."
   ::= { sysPnacASUserConfigEntry 2 }

sysPnacASUserConfigAuthProtocol OBJECT-TYPE
   SYNTAX      Unsigned32
   MAX-ACCESS  read-only
   STATUS      current
   DESCRIPTION
      "The Authentication protocol supported for the User."
   ::= { sysPnacASUserConfigEntry 3 }

sysPnacASUserConfigAuthTimeout OBJECT-TYPE
   SYNTAX      Unsigned32
   MAX-ACCESS  read-write
   STATUS      current
   DESCRIPTION
      "The time in seconds after which the Authentication
       offerred to the User ceases. Maximum value of the
       object can be 7200 seconds. When the object value
       is 0, the ReAuthPeriod of the Authenticator port is
       used by Authenticator."
   ::= { sysPnacASUserConfigEntry 4 }

sysPnacASUserConfigPortList OBJECT-TYPE
   SYNTAX     PortList
   MAX-ACCESS read-write
   STATUS     current
   DESCRIPTION
      "The complete set of ports of Authenticator to
       which the User is allowed or denied access, on the
       basis of setting of 'sysPnacASUserConfigPermission'
       object."
   ::= { sysPnacASUserConfigEntry 5 }

sysPnacASUserConfigPermission OBJECT-TYPE
   SYNTAX      PermissionType
   MAX-ACCESS  read-write
   STATUS      current
   DESCRIPTION
      "For the set of ports indicated by
       'sysPnacASUserConfigPortList' object, the User is
       allowed access when this object is set 'allow' and
       is denied access when this object is set 'deny'."
   ::= { sysPnacASUserConfigEntry 6 }

sysPnacASUserConfigDynamicVlanID OBJECT-TYPE
   SYNTAX      Unsigned32
   MAX-ACCESS  read-write
   STATUS      current
   DESCRIPTION
      "Dynamic Vlan ID is assigned by Switch in local mode"
   ::= { sysPnacASUserConfigEntry 7 }

sysPnacASUserConfigRowStatus OBJECT-TYPE
   SYNTAX      RowStatus
   MAX-ACCESS  read-create
   STATUS      current
   DESCRIPTION
      "This object indicates the status of this entry. An entry is
	   created in this table when this object is SET to 'createAndWait'.
       The entry in this table is used when the status of this object 
       is SET 'active'. The entry in this table is not used when this 
       object is SET 'notInService'. An entry created in this table is
       be deleted when this object is SET 'destroy'."
   ::= { sysPnacASUserConfigEntry 8 }
   
-- The Guest Vlan with each port

sysPnacGuestVlanTable OBJECT-TYPE
   SYNTAX      SEQUENCE OF TabPnacGuestVlanEntry
   MAX-ACCESS  not-accessible
   STATUS      current
   DESCRIPTION
      "This table contains authentication session information
       associated with each Guest vlan  while Authenticator
       operates in port based authentication mode."
   ::= { sysGuestVlan 1 }

sysPnacGuestVlanEntry OBJECT-TYPE
   SYNTAX      TabPnacGuestVlanEntry
   MAX-ACCESS  not-accessible
   STATUS      current
   DESCRIPTION
      "Guest Vlan ID assign with each port."
   INDEX { sysPnacPaePortNo }
   ::= { sysPnacGuestVlanTable 1 }

TabPnacGuestVlanEntry ::=
   SEQUENCE {
	  sysPnacPaePortNo
		  Integer32,
      sysPnacGuestVlanId
          Integer32

   }

sysPnacPaePortNo OBJECT-TYPE
   SYNTAX      Integer32 (0..65535)
   MAX-ACCESS  read-only
   STATUS      current
   DESCRIPTION
      "The port number associated with this port."
   ::= { sysPnacGuestVlanEntry 1 }
   
sysPnacGuestVlanId OBJECT-TYPE
   SYNTAX      Integer32
   MAX-ACCESS  read-write
   STATUS      current
   DESCRIPTION
      "specify the guest vlan tag.0 for non exiting"
   ::= { sysPnacGuestVlanEntry 2}
   




sysSystemInfo            OBJECT IDENTIFIER ::= { l2System 1 }
sysConfigControl         OBJECT IDENTIFIER ::= { l2System 2 }
sysMirror                OBJECT IDENTIFIER ::= { l2System 3 }
sysIpAuthMgr             OBJECT IDENTIFIER ::= { l2System 7 }
sysLBDdetect             OBJECT IDENTIFIER ::= { l2System 22 } 

sysSwitchName OBJECT-TYPE
   SYNTAX      DisplayString (SIZE(1..15))
   MAX-ACCESS  read-write
   STATUS      current
   DESCRIPTION
      "System name used for identification of the device.
       The following characters are allowed to input.
       0 ~ 9 / a ~ z / A ~ Z
       Special character: (  )   A!V  +  _  =  ."
   DEFVAL { "SysName" }
   ::= { sysSystemInfo 1 }

sysHardwareVersion OBJECT-TYPE
   SYNTAX      DisplayString (SIZE(1..15))
   MAX-ACCESS  read-only
   STATUS      current
   DESCRIPTION
      "Version number of the Hardware."
   DEFVAL { "" }
   ::= { sysSystemInfo 2 }

sysFirmwareVersion OBJECT-TYPE
   SYNTAX      DisplayString (SIZE(1..15))
   MAX-ACCESS  read-only
   STATUS      current
   DESCRIPTION
      "Version number of the Firmware."
   DEFVAL { "" }
   ::= { sysSystemInfo 3 }

sysDefaultIpAddrCfgMode OBJECT-TYPE
   SYNTAX      INTEGER {
                manual(1),
                dynamic(2)
               }
   MAX-ACCESS  read-write
   STATUS      current
   DESCRIPTION
      "Specifies the means by which the default interface in the device
       gets the IP address.
       
       If 'manual' mode is selected, the default interface takes the
       'sysDefaultIpAddr' configured in the system.
       
       If 'dynamic' mode is selected, the default interface gets the IP address
       through dynamic IP address configuration protocols such as RARP client,
       BootP client, DHCP Client, etc.
       
       If the system fails to get the IP address dynamically through all the
       above protocols, the default interface uses the 'sysDefaultIpAddr'
       configured in the system."
   DEFVAL { manual }
   ::= { sysSystemInfo 4 }

sysDefaultIpAddr OBJECT-TYPE
   SYNTAX      IpAddress
   MAX-ACCESS  read-write
   STATUS      current
   DESCRIPTION
      "Default IP Address of the system.

       This IP address, if modified, will take effect only when the
       configuration is stored & restored."
   ::= { sysSystemInfo 5 }

sysDefaultIpSubnetMask OBJECT-TYPE
   SYNTAX      IpAddress
   MAX-ACCESS  read-write
   STATUS      current
   DESCRIPTION
      "IP subnet mask for the default IP address.

       This subnet mask, if modified, will take effect only when the
       configuration is stored & restored."
   ::= { sysSystemInfo 6 }


sysRestart OBJECT-TYPE
   SYNTAX      TruthValue
   MAX-ACCESS  read-write
   STATUS      current
   DESCRIPTION
      "This object allows the user to restart the Switch
       (i.e)the entire switch will operationally go down and
       start again.  Setting  a value of 'true' causes the switch
       to be restarted.

       When  the switch operationally goes down, configuration
       save operation is initiated based on the configuration save
       option chosen.

       When the switch operationally come up, the saved configurations
       are restored based on the restore option chosen.

       Once the switch is restarted, the value of this object reverts
       to 'false'."
   DEFVAL { false }
   ::= { sysSystemInfo 9 }

sysConfigSaveOption OBJECT-TYPE
   SYNTAX      INTEGER {
                noSave(1),
                flashSave(2),
                remoteSave(3),
                startupConfig(4)
               }
   MAX-ACCESS  read-write
   STATUS      current
   DESCRIPTION
      "Specifies whether the configurations of the switch has to be
       saved or not.

       The value 'noSave' specifies that the configurations need
       not be saved.

       The value 'flashSave' specifies that the configurations need
       to be saved in flash in the specified file name sysConfigSaveFileName.

       The value 'remoteSave' specifies that the configurations need
       to be saved in specified remote system.

       The value 'startupConfig' specifies that the configurations need
       to be saved in flash in the 'Startup Configuration File'."
   DEFVAL { startupConfig }
   ::= { sysSystemInfo 10 }

sysConfigSaveIpAddr OBJECT-TYPE
   SYNTAX      IpAddress
   MAX-ACCESS  read-write
   STATUS      current
   DESCRIPTION
      "IP Address of the remote system to which the switch
       configurations have to be saved.

       This object is valid only if 'sysConfigSaveOption' is chosen to be
       'remoteSave'."
   ::= { sysSystemInfo 11 }

sysConfigSaveFileName OBJECT-TYPE
   SYNTAX      DisplayString (SIZE(1..128))
   MAX-ACCESS  read-write
   STATUS      current
   DESCRIPTION
      "Name of the file in which the switch configurations are
       to be saved.

       This object is valid only if 'sysConfigSaveOption' is chosen
       to be 'flashSave' or 'remoteSave'."
      DEFVAL { "iss.conf" }
   ::= { sysSystemInfo 12 }

sysInitiateConfigSave  OBJECT-TYPE
   SYNTAX      TruthValue
   MAX-ACCESS  read-write
   STATUS      current
   DESCRIPTION
      "When set as 'true' switch configurations save operation is
       initiated.
       As soon as the configuration save operation is completed, the value
       of this object reverts back to 'false'.

       All the configurations made via the three interfaces
       viz.
           -> commandline interface
           -> Web Interface
           -> SNMP interface
       are saved either in 'Startup Configuration File' in the flash or
       in the specified 'sysConfigSaveFileName' in the flash or
       in the chosen remote system, dsysending upon 'ConfigSaveOption'."
   DEFVAL { false }
   ::= { sysSystemInfo 13 }

sysConfigSaveStatus OBJECT-TYPE
   SYNTAX      INTEGER {
                saveInProgress(1),
                saveSuccessful(2),
                saveFailed(3),
                notInitiated(4)
               }
   MAX-ACCESS  read-only
   STATUS      current
   DESCRIPTION
      "Status of configuration save operation."
   DEFVAL { notInitiated }
   ::= { sysSystemInfo 14 }

sysConfigRestoreOption OBJECT-TYPE
   SYNTAX      INTEGER {
                noRestore(1),
                restore(2)
               }
   MAX-ACCESS  read-write
   STATUS      current
   DESCRIPTION
      "Specifies whether the switch configurations have to be restored
       or not.

       The value 'noRestore' specifies that the switch configurations
       need not be restored when the system is restarted.

       The value 'restore' specifies that the configurations
       need to be restored from the 'Startup Configuration File' in the flash
       when the system is restarted."
   DEFVAL { noRestore }
   ::= { sysSystemInfo 15 }

sysRemoteConfigRestoreIpAddr OBJECT-TYPE
   SYNTAX      IpAddress
   MAX-ACCESS  read-write
   STATUS      current
   DESCRIPTION
      "IP Address of the remote system from where the switch configurations
       have to be downloaded to the 'Startup Configuration File' in the flash."
   ::= { sysSystemInfo 16 }

sysConfigRestoreFileName OBJECT-TYPE
   SYNTAX      DisplayString (SIZE(1..128))
   MAX-ACCESS  read-write
   STATUS      current
   DESCRIPTION
      "The configuration file name in the remote system which has to be
       downloaded to the 'Startup Configuration File' and set this name
       to 'Startup Configuration Restire File Name' in the flash."
   DEFVAL { "iss.conf" }
   ::= { sysSystemInfo 17 }

sysInitiateRemoteConfigRestore OBJECT-TYPE
   SYNTAX      TruthValue
   MAX-ACCESS  read-write
   STATUS      current
   DESCRIPTION
      "When set as 'true', the switch configurations will be downloaded
       from the specified remote system to the 'Startup Configuration File'
       in the flash.

       As soon as the configuration download operation is completed, the value
       of this object reverts back to 'false'."
   DEFVAL { false }
   ::= { sysSystemInfo 18 }

sysConfigRestoreStatus OBJECT-TYPE
   SYNTAX      INTEGER {
                restoreInprogress(1),
                restoreSuccessful(2),
                restoreFailed(3),
                notInitiated(4)
               }
   MAX-ACCESS  read-only
   STATUS      current
   DESCRIPTION
      "The status of the switch configuration restore operation."
   DEFVAL { notInitiated }
   ::= { sysSystemInfo 19 }

sysDlFirmwareFromIp OBJECT-TYPE
   SYNTAX        IpAddress
   MAX-ACCESS    read-write
   STATUS        current
   DESCRIPTION
      "The Ip Address of machine from where the firmware has to be downloaded."
   ::= { sysSystemInfo 20 }

sysDlFirmwareName OBJECT-TYPE
   SYNTAX      DisplayString (SIZE(1..128))
   MAX-ACCESS  read-write
   STATUS      current
   DESCRIPTION
      "The firmware name which is to be downloaded to the switch."
   DEFVAL { "firmware.hex" }
   ::= { sysSystemInfo 21 }

sysInitiateDlFirmware OBJECT-TYPE
   SYNTAX        TruthValue
   MAX-ACCESS    read-write
   STATUS        current
   DESCRIPTION
      "Initiates the firmware Download operation."
   ::= { sysSystemInfo 22 }

sysLoggingOption OBJECT-TYPE
   SYNTAX      INTEGER {
                console(1),
                file(2)
               }
   MAX-ACCESS  read-write
   STATUS      current
   DESCRIPTION
      "The option specifies whether the debug logging messages is to be
       sent to console or to a file(system buffer) in the system."
   ::= { sysSystemInfo 23 }

sysUploadLogFileToIp OBJECT-TYPE
   SYNTAX        IpAddress
   MAX-ACCESS    read-write
   STATUS        current
   DESCRIPTION
      "The Ip address of TFTP server to which the log file is to be uploaded."
   ::= { sysSystemInfo 24 }

sysLogFileName OBJECT-TYPE
   SYNTAX      DisplayString (SIZE(1..128))
   MAX-ACCESS  read-write
   STATUS      current
   DESCRIPTION
      "The file name to be used for uploading the logs to the remote system."
       DEFVAL { "iss.log" }
   ::= { sysSystemInfo 25 }

sysInitiateUlLogFile OBJECT-TYPE
   SYNTAX        TruthValue
   MAX-ACCESS    read-write
   STATUS        current
   DESCRIPTION
      "Initiates uploading of log file to the specified IP address in
       'sysUploadLogFileToIp'.

       The logs will be uploaded and saved in a file using the file name which was 
       specified in 'sysLogFileName'."
   ::= { sysSystemInfo 26 }

sysSysContact OBJECT-TYPE
   SYNTAX      DisplayString (SIZE(1..50))
   MAX-ACCESS  read-write
   STATUS      current
   DESCRIPTION
      "The textual identification of the contact person for this
       managed node, together with information on how to contact
       this person.  If no contact information is known, the value
       is the zero-length string."
   ::= { sysSystemInfo 29 }

sysSysLocation OBJECT-TYPE
   SYNTAX      DisplayString (SIZE(1..50))
   MAX-ACCESS  read-write
   STATUS      current
   DESCRIPTION
      "The physical location of this node (e.g., `telsyshone
       closet, 3rd floor').  If the location is unknown, the value
       is the zero-length string."
   ::= { sysSystemInfo 30 }

sysLoginAuthentication OBJECT-TYPE
   SYNTAX      INTEGER {
                local(1),
                remoteRadius(2),
                remoteTacacs(3)
               }
   MAX-ACCESS  read-write
   STATUS      current
   DESCRIPTION
      "The mechanism by which the user login to access the GUI for
       configuration has to be authenticated. Authentication is done
       either locally or in the remote side through a RADIUS Server."
   ::= { sysSystemInfo 31 }

sysSwitchBaseMacAddress OBJECT-TYPE
   SYNTAX      MacAddress
   MAX-ACCESS  read-write
   STATUS      current
   DESCRIPTION
      "Ethernet address (base address) of the Switch.
       This base Mac Address, if modified, will take effect only when the
       Switch is restarted."
   DEFVAL { '000102030405'h }
   ::= { sysSystemInfo 32 }

sysSwitchDate OBJECT-TYPE
   SYNTAX       DisplayString (SIZE(40))
   MAX-ACCESS   read-only
   STATUS       current
   DESCRIPTION
      " The date is display in the switch in the format,
       Hours:Minutes:Seconds Day Month Year
       e.g 19:10:31 11 08 2005
       
       01-12  Month - beginning from January to December
       The railway time  00 to 24 hours can be displayed.
       The Display of the date is in the format ,
       WeekDay  Month  Day  Hours:Minutes:Seconds Year
       e.g 04 09 21 18:11:30 2005
       
       01-07  WeekDay - beginning from Sunday to Saturday
       01-12  Month - beginning from January to December "
   ::= { sysSystemInfo 34 }

sysHttpPort OBJECT-TYPE
   SYNTAX      Integer32 (0..65535)
   MAX-ACCESS  read-write
   STATUS      current
   DESCRIPTION
      "The port to be used by the hosts/PC to configure ISS using the Web Interface
       The HTTP server must be disabled before this configuration is done"
   DEFVAL { 80 }
   ::= { sysSystemInfo 37 }

sysHttpStatus OBJECT-TYPE
   SYNTAX      INTEGER {
                enable(1),
                disable(2)
               }
   MAX-ACCESS  read-write
   STATUS      current
   DESCRIPTION
      "This object is for enabling or disabling HTTP in the system."
   DEFVAL { enable }
   ::= { sysSystemInfo 38 }

sysDefaultVlanId OBJECT-TYPE
   SYNTAX      Integer32 (1..4094)
   MAX-ACCESS  read-write
   STATUS      current
   DESCRIPTION
      "The Default VLAN Identifier to be used at system startup.
       The VLAN Module creates this vlan as the default vlan.
       The Default VLAN Identifier, if modified, will take effect
       only when the switch is restarted"
   DEFVAL { 1 }
   ::= { sysSystemInfo 41 }

sysWebAutoTimeoutInterval OBJECT-TYPE
   SYNTAX      Integer32 (180..3600)
   MAX-ACCESS  read-write
   STATUS      current
   DESCRIPTION
      "This time interval to be used at counting time seconds to
       logout web interface automatically."
   DEFVAL { 600 }
   ::= { sysSystemInfo 42 }

sysCliAutoTimeoutInterval OBJECT-TYPE
   SYNTAX      Integer32 (1..18000)
   MAX-ACCESS  read-write
   STATUS      current
   DESCRIPTION
      "This time interval to be used at counting time seconds to
       logout command interface automatically."
   DEFVAL { 1800 }
   ::= { sysSystemInfo 43 }

sysCpuPolicerStatus OBJECT-TYPE
   SYNTAX      INTEGER {
                enable(1),
                disable(2)
               }
   MAX-ACCESS  read-write
   STATUS      current
   DESCRIPTION
      "This object is for enabling or disabling cpu policer in the system."
   DEFVAL { enable }
   ::= { sysSystemInfo 44 }

 sysLedEcoModeStatus OBJECT-TYPE
   SYNTAX      INTEGER {
                enable(1),
                disable(2)
               }
   MAX-ACCESS  read-write
   STATUS      current
   DESCRIPTION
      "This object is for enabling or disabling LED ECO mode in the system."
   DEFVAL { enable }
   ::= { sysSystemInfo 45 }

   
sysPowerSavingEnable OBJECT-TYPE   
   SYNTAX      INTEGER {
                enable(1),
                disable(2)
               }   
   MAX-ACCESS  read-write
   STATUS      current
   DESCRIPTION
      "This object is for enabling or disabling powersaving in the system."
   DEFVAL { enable }
   ::= { sysSystemInfo 62 }

sysDhcpAutoConfiguration  OBJECT-TYPE
            SYNTAX      INTEGER {
                    enable(1),
                    disable(2)
            }
            MAX-ACCESS  read-write
            STATUS      current
            DESCRIPTION 
      		"This object is for enabling or disabling DHCP auto configuration in the system."
            DEFVAL { disable }
            ::= { sysSystemInfo 63 }
			   
sysAsyVLANEnable OBJECT-TYPE   
   SYNTAX      INTEGER {
                enable(1),
                disable(2)
               }   
   MAX-ACCESS  read-write
   STATUS      current
   DESCRIPTION
      "This object is for set asyvlan to ivl or svl in the system."
   DEFVAL { enable }
   ::= { sysSystemInfo 64 }			   

issCosEnable OBJECT-TYPE   
   SYNTAX      INTEGER {
                enable(1),
                disable(2)
               }   
   MAX-ACCESS  read-write
   STATUS      current
   DESCRIPTION
      "This object is for enabling or disabling COS in the system."
   DEFVAL { enable }
   ::= { sysSystemInfo 65 }	    
			   
sysTrapEnable OBJECT-TYPE   
   SYNTAX      INTEGER {
                enable(1),
                disable(2)
               }   
   MAX-ACCESS  read-write
   STATUS      current
   DESCRIPTION
      "This object is for enabling or disabling Trap in the system."
   DEFVAL { enable }
   ::= { sysSystemInfo 66 }	    

-- Factory Default Reset
sysFDResetStateEnable OBJECT-TYPE
   SYNTAX      INTEGER {
                enable(1),
                disable(2)
               }
   MAX-ACCESS  read-write
   STATUS      current
   DESCRIPTION
      "Enable/Disable Factory Default Reset function.
                The Factory Default Reset function is used to enable or disable
                the push button and reset function on the device.
                When the user wants to disable reset function that must be configure
                a password to lock it. Once want to recovery the reset function, 
                the password was needed to verify authorize."
   DEFVAL { enable }
   ::= { sysSystemInfo 67 }

sysFDRInputPw OBJECT-TYPE
   SYNTAX      DisplayString (SIZE(1..12))
   MAX-ACCESS  read-write
   STATUS      current
   DESCRIPTION
      "Input a password first and then the sysFDResetStateEnable can work correctly."
   ::= { sysSystemInfo 68 }

   
-- Config Control

sysConfigCtrlTable OBJECT-TYPE
   SYNTAX      SEQUENCE OF TabConfigCtrlEntry
   MAX-ACCESS  not-accessible
   STATUS      current
   DESCRIPTION
      "A table to control device features like egress traffic control,
       stats collection, etc. either for the entire switch or for each
       interface in the switch."
   ::= { sysConfigControl 1 }

sysConfigCtrlEntry OBJECT-TYPE
   SYNTAX      TabConfigCtrlEntry
   MAX-ACCESS  not-accessible
   STATUS      current
   DESCRIPTION
      "An entry appears in this table for each interface in the system.

       In addition to that an entry with index '0' is created in this
       table by default.

       If 'sysConfigCtrlStatus' of the entry '0' is made 'valid', then
       global control is chosen and the values against entry '0' is
       applicable for all the interfaces of the switch.

       If 'sysConfigCtrlStatus' of the entry '0' is made 'invalid',
       then interface-wise control is chosen & the values against each
       interface index is applicable for that interface.

       At a particular point of time, either global control will be
       applicable or interface-wise control is applicable.
       Both will not be considered together.

       Index to the table is the interface index of the port."
   INDEX { sysConfigCtrlIndex }
   ::= { sysConfigCtrlTable 1 }

TabConfigCtrlEntry ::=
   SEQUENCE {
      sysConfigCtrlIndex
         Integer32,
      sysConfigCtrlEgressStatus
         INTEGER,
      sysConfigCtrlStatsCollection
         INTEGER,
      sysConfigCtrlStatus
         INTEGER
   }

sysConfigCtrlIndex OBJECT-TYPE
   SYNTAX      Integer32 (0..65535)
   MAX-ACCESS  not-accessible
   STATUS      current
   DESCRIPTION
      "Interface index of the port for which the configuration
       in this entry applies.

       If any configuration is made in this table for the index '0',
       that configuration will be considered as global configuration
       and is applicable for all the interfaces of the switch."
   ::= { sysConfigCtrlEntry 1 }

sysConfigCtrlEgressStatus OBJECT-TYPE
   SYNTAX      INTEGER {
               enabled (1),
               disabled (2)
               }
   MAX-ACCESS  read-write
   STATUS      current
   DESCRIPTION
      "Controls the transmission of egress traffic over this interface.

       This value for entry '0' controls the egress traffic over all
       interfaces."
   DEFVAL { enabled }
   ::= { sysConfigCtrlEntry 2 }

sysConfigCtrlStatsCollection OBJECT-TYPE
   SYNTAX      INTEGER {
               enabled (1),
               disabled (2)
               }
   MAX-ACCESS  read-write
   STATUS      current
   DESCRIPTION
      "Enables or disables statistics collection for this interface.

       This value for entry '0' controls the stats collection for all
       interfaces."
   DEFVAL { enabled }
   ::= { sysConfigCtrlEntry 3 }

sysConfigCtrlStatus OBJECT-TYPE
   SYNTAX      INTEGER {
               valid (1),
               invalid (2)
               }
   MAX-ACCESS  read-write
   STATUS      current
   DESCRIPTION
      "Speficies the validity of the entry.

       If the 'Config Control Status' for entry '0' is made 'valid',
       then global control is chosen in the system.
       It signifies that the values against entry '0' is applicable
       for all the interfaces of the switch.

       If the 'Config Control Status' for entry '0' is made 'invalid',
       then interface-wise control is chosen.
       Then the values against each interface index is applicable
       for that interface.

       By default, 'sysConfigCtrlStatus' will be 'invalid' for
       entry '0' and 'valid' for all other entries.
       (ie) by default, interface-wise configuration is enabled
       in the system.

       The status of entries other than the zeroth(0th) entry can not be
       made 'invalid'."
   ::= { sysConfigCtrlEntry 4 }


-- Port Control

sysPortCtrlTable OBJECT-TYPE
   SYNTAX      SEQUENCE OF TabPortCtrlEntry
   MAX-ACCESS  not-accessible
   STATUS      current
   DESCRIPTION
       "A table to control the port specific parameters of the device like speed,
        duplex mode, etc."
   ::= { sysConfigControl 2 }

sysPortCtrlEntry OBJECT-TYPE
   SYNTAX      TabPortCtrlEntry
   MAX-ACCESS  not-accessible
   STATUS      current
   DESCRIPTION
       "An entry appears in this table for each interface in the system.

       Index to the table is the interface index of the port."
   INDEX { sysPortCtrlIndex }
   ::= { sysPortCtrlTable 1 }

TabPortCtrlEntry ::=
   SEQUENCE {
      sysPortCtrlIndex
         Integer32,
      sysPortCtrlMode
         INTEGER,
      sysPortCtrlDuplex
         INTEGER,
      sysPortCtrlSpeed
         INTEGER,
      sysPortCtrlFlowControl
         INTEGER,
      sysPortCtrlMDI
         INTEGER,
      issJumboFramePerPortEnable
         INTEGER,
      issJumboFramePerPortMtu
         Integer32,
	  sysPortCtrlEAPPassThrough
		 INTEGER,
	  sysPortCtrlBPDUPassThrough
         INTEGER
  }

sysPortCtrlIndex OBJECT-TYPE
   SYNTAX      Integer32 (1..65535)
   MAX-ACCESS  not-accessible
   STATUS      current
   DESCRIPTION
      "Interface index of the port for which the configuration
       in this entry applies."
   ::= { sysPortCtrlEntry 1 }

sysPortCtrlMode OBJECT-TYPE
   SYNTAX      INTEGER {
                 auto          (1),
                 noNegotiation (2)
              }
   MAX-ACCESS  read-write
   STATUS      current
   DESCRIPTION
      "Speficies the mode in which the speed, duplex modes and flow control
       of the interface is determined.

       If set as 'auto', the hardware senses speed and negotiates with the port
       on the other end of the link for data transfer operation as
       'full-duplex' or 'half-duplex' and about flow contol.

       If set as 'nonegotiation', the configured values for interface
       speed, duplex mode and flow control will be effective."
   DEFVAL { auto }
   ::= { sysPortCtrlEntry 2 }

sysPortCtrlDuplex OBJECT-TYPE
   SYNTAX      INTEGER {
                 full  (1),
                 half  (2)
               }
   MAX-ACCESS  read-write
   STATUS      current
   DESCRIPTION
      "Configures interface data transfer mode as full-duplex or half-duplex.

       This object can be configured only if the 'PortCtrlMode' is 'nonegotiation'.
       If the 'PortCtrlMode' is 'auto', it obtains the value from Hardware
       after negotiating  with its peer"
   ::= { sysPortCtrlEntry 3 }

sysPortCtrlSpeed OBJECT-TYPE
   SYNTAX      INTEGER {
                 tenMBPS     (1),
                 hundredMBPS (2),
                 oneGB       (3),
                 tenGB       (4)
               }
   MAX-ACCESS  read-write
   STATUS      current
   DESCRIPTION
      "Configures interface speed.

      This object can be configured only if the 'PortCtrlMode' is 'nonegotiation'.
      If the 'PortCtrlMode' is 'auto', it obtains the value from Hardware
      after negotiating  with its peer"
   ::= { sysPortCtrlEntry 4 }

sysPortCtrlFlowControl OBJECT-TYPE
   SYNTAX      INTEGER {
                 enable     (1),
                 disable    (2)
               }
   MAX-ACCESS  read-write
   STATUS      current
   DESCRIPTION
      "Enables / disables flow control for the interface.

       This object be configured only if the 'PortCtrlMode' is 'nonegotiation'.
       If the 'PortCtrlMode' is 'auto', it obtains the value from Hardware
       after negotiating  with its peer"
   ::= { sysPortCtrlEntry 5 }


sysPortCtrlMDI OBJECT-TYPE
   SYNTAX      INTEGER {
                 auto     (1),
                 mdi      (2),
                 mdix     (3)
               }
   MAX-ACCESS  read-write
   STATUS      current
   DESCRIPTION
      "Sets the auto/mdi/mdix of the copper interface. Fiber media is not support."
   ::= { sysPortCtrlEntry 10 }

issJumboFramePerPortEnable  OBJECT-TYPE
    SYNTAX      INTEGER {
                  enable(1),
                  disable(2)
                }
    MAX-ACCESS  read-write
    STATUS      current
    DESCRIPTION 
          "Gigabit Web Smart Switches support jumbo frames (frames larger than 
           the Ethernet frame size of 1522 bytes) of up to 10,000 bytes (tagged). 
           Default jumbo frame is disabled."
    DEFVAL { disable }
    ::= { sysPortCtrlEntry 11 }   
   
issJumboFramePerPortMtu OBJECT-TYPE
   SYNTAX      Integer32 (1522..10000)
   MAX-ACCESS  read-write
   STATUS      current
   DESCRIPTION
          "Gigabit Web Smart Switches support jumbo frames (frames larger than 
           the Ethernet frame size of 1522 bytes) of up to 10,000 bytes (tagged). 
           Default jumbo frame MTU is 10000."
    DEFVAL { 10000 }
   ::= { sysPortCtrlEntry 12 }
   
sysPortCtrlEAPPassThrough OBJECT-TYPE
   SYNTAX      INTEGER {
                 enable     (1),
                 disable    (2)
               }
   MAX-ACCESS  read-write
   STATUS      current
   DESCRIPTION
      "Enables / disables dot1x EAP packet pass through for the interface.

       This object be configured only if the dot1x is disabled."
   ::= { sysPortCtrlEntry 13 }
   
sysPortCtrlBPDUPassThrough OBJECT-TYPE
   SYNTAX      INTEGER {
                 enable     (1),
                 disable    (2)
               }
   MAX-ACCESS  read-write
   STATUS      current
   DESCRIPTION
      "Enables / disables STP BPDU passthrough for the interface.

       This object be configured only if the RSTP/MSTP is disabled."
   ::= { sysPortCtrlEntry 14 }
   
-- Port Monitoring

sysMirrorStatus OBJECT-TYPE
   SYNTAX      INTEGER {
                  enabled        (1),
                  disabled       (2)
               }
   MAX-ACCESS  read-write
   STATUS      current
   DESCRIPTION
       "Provides control over the mirroring feature in the switch."
   DEFVAL { disabled }
   ::= { sysMirror 1 }

sysMirrorToPort OBJECT-TYPE
   SYNTAX      Integer32
   MAX-ACCESS  read-write
   STATUS      current
   DESCRIPTION
      "Specifies the port to which the mirrored traffic in the system
       is to be copied."
   ::= { sysMirror 2 }

sysMirrorCtrlTable OBJECT-TYPE
   SYNTAX      SEQUENCE OF TabMirrorCtrlEntry
   MAX-ACCESS  not-accessible
   STATUS      current
   DESCRIPTION
      "A table to control mirroring features either for the entire
       switch or for each interface in the switch.

       Parameters in this table are valid only when the
       'sysMirrorStatus' for the switch is not 'disabled'."
   ::= { sysMirror 3 }

sysMirrorCtrlEntry OBJECT-TYPE
   SYNTAX      TabMirrorCtrlEntry
   MAX-ACCESS  not-accessible
   STATUS      current
   DESCRIPTION
       "An entry appears in this table for each interface
        in the system."
   INDEX { sysMirrorCtrlIndex }
   ::= { sysMirrorCtrlTable 1 }

TabMirrorCtrlEntry ::=
   SEQUENCE {
      sysMirrorCtrlIndex
         Integer32,
      sysMirrorCtrlIngressMirroring
         INTEGER,
      sysMirrorCtrlEgressMirroring
         INTEGER,
      sysMirrorCtrlStatus
         INTEGER
   }

sysMirrorCtrlIndex OBJECT-TYPE
   SYNTAX      Integer32 (1..65535)
   MAX-ACCESS  not-accessible
   STATUS      current
   DESCRIPTION
      "The interface index of the port for which the configuration
      in this entry applies."
   ::= { sysMirrorCtrlEntry 1 }

sysMirrorCtrlIngressMirroring OBJECT-TYPE
   SYNTAX      INTEGER {
               enabled(1),
               disabled(2)
               }
   MAX-ACCESS  read-write
   STATUS      current
   DESCRIPTION
       "Provides control to enable or disable mirroring of ingress
        traffic over this interface to the mirrored-to port."
   DEFVAL { disabled }
   ::= { sysMirrorCtrlEntry 2 }

sysMirrorCtrlEgressMirroring OBJECT-TYPE
   SYNTAX      INTEGER {
               enabled(1),
               disabled(2)
               }
   MAX-ACCESS  read-write
   STATUS      current
   DESCRIPTION
      "Provides control to enable or disable mirroring of egress
       traffic over this interface to the mirrored-to port."
   DEFVAL { disabled }
   ::= { sysMirrorCtrlEntry 3 }

sysMirrorCtrlStatus OBJECT-TYPE
   SYNTAX      INTEGER {
               enabled(1),
               disabled(2)
               }
   MAX-ACCESS  read-only
   STATUS      current
   DESCRIPTION
      "Provides control to enable or disable mirroring of egress
       traffic over this interface to the mirrored-to port."
   DEFVAL { disabled }
   ::= { sysMirrorCtrlEntry 4 }   
   
-- IP Authorized Manager
sysIpAuthMgrStatus OBJECT-TYPE
   SYNTAX      INTEGER {
                  enabled        (1),
                  disabled       (2)
               }
   MAX-ACCESS  read-write
   STATUS      current
   DESCRIPTION
       "Provides control over the Ip authentication management feature in the switch."
   DEFVAL { disabled }
   ::= {sysIpAuthMgr 1 }

sysIpAuthMgrTable OBJECT-TYPE
   SYNTAX      SEQUENCE OF TabIpAuthMgrEntry
   MAX-ACCESS  not-accessible
   STATUS      current
   DESCRIPTION
      "A table to configure IP authorized managers in the system."
   ::= { sysIpAuthMgr 2 }

sysIpAuthMgrEntry OBJECT-TYPE
   SYNTAX      TabIpAuthMgrEntry
   MAX-ACCESS  not-accessible
   STATUS      current
   DESCRIPTION
      "Each entry in this table rsysresents rules for particular
       IP authorized manager."
   INDEX { sysIpAuthMgrIpAddr, sysIpAuthMgrIpMask }
   ::= { sysIpAuthMgrTable 1 }

TabIpAuthMgrEntry ::=
   SEQUENCE {
      sysIpAuthMgrIpAddr
         IpAddress,
      sysIpAuthMgrIpMask
         IpAddress,
      sysIpAuthMgrPortList
         PortList,
      sysIpAuthMgrVlanList
         OCTET STRING,
      sysIpAuthMgrAllowedServices
         Integer32,
      sysIpAuthMgrRowStatus
         RowStatus
   }

sysIpAuthMgrIpAddr OBJECT-TYPE
   SYNTAX      IpAddress
   MAX-ACCESS  not-accessible
   STATUS      current
   DESCRIPTION
      "Specifies either the Network or Host address from which the switch
       can be managed.
       An address 0.0.0.0 indicates 'Any Manager'."
   ::= { sysIpAuthMgrEntry 1 }

sysIpAuthMgrIpMask OBJECT-TYPE
   SYNTAX      IpAddress
   MAX-ACCESS  not-accessible
   STATUS      current
   DESCRIPTION
      "Specifies the IP address mask to be applied on sysIpAuthMgrIpAddr.
       Value 0.0.0.0 indicates mask for 'Any Manager'."
   ::= { sysIpAuthMgrEntry 2 }

sysIpAuthMgrPortList OBJECT-TYPE
   SYNTAX       PortList
   MAX-ACCESS   read-write
   STATUS       current
   DESCRIPTION
      "Specifies the port numbers through which the authorized manager can
       access the switch.

       By default the authorized manager is allowed to access the switch
       through all the ports.

       If a set of ports are configured in the 'PortList', the manager can
       access the switch only through the configured ports."
   ::= { sysIpAuthMgrEntry 3 }

sysIpAuthMgrVlanList OBJECT-TYPE
   SYNTAX       OCTET STRING
   MAX-ACCESS   read-write
   STATUS       current
   DESCRIPTION
      "Specifies the Vlan's in which the IP authorized manager can reside.
       By default the manager is allowed to reside in any vlan.

       If a set of vlans are configured in the 'VlanList', the manager can
       reside only in the configured vlan set.  Access to the switch
       will be denied from any other vlan."
   ::= { sysIpAuthMgrEntry 4 }

sysIpAuthMgrAllowedServices OBJECT-TYPE
   SYNTAX      Integer32
   MAX-ACCESS  read-write
   STATUS      current
   DESCRIPTION
      "Specifies the allowed services through which the authorized manager can
       access the switch.
       This object takes bit mask values. The services rsysresented by each bit
       position is as given below:

       With bit 0 being the Least Significant Bit,

        Bit0  --> snmp
        Bit1  --> telnet
        Bit2  --> http
        Bit3  --> https
        Bit4  --> ssh

       If the particular bit is set to 1,corresponding service is allowed for
       the configured manager.

       By default all services are allowed for the configured manager."
   DEFVAL { '1F'h }
   ::= { sysIpAuthMgrEntry 6 }

sysIpAuthMgrRowStatus OBJECT-TYPE
   SYNTAX      RowStatus
   MAX-ACCESS  read-create
   STATUS      current
   DESCRIPTION
      "This object indicates the status of this entry."
   ::= { sysIpAuthMgrEntry 7 }



-- LBD ---------------------   

sysLBDStateEnable OBJECT-TYPE
   SYNTAX      INTEGER {
                enable(1),
                disable(2)
               }
   MAX-ACCESS  read-write
   STATUS      current
   DESCRIPTION
      "Enable/Disable Loopback detection function.
                The Loopback Detection function is used to detect the loop created
                by a specific port while Spanning Tree Protocol (STP) is not 
                enabled in the network, especially when the down links are hubs 
                or unmanaged switchs.The Switch will automatically shutdown the 
                port and sends a log to the administrator."
   DEFVAL { disable }
   ::= { sysLBDdetect 1 }
   
   sysLBDInterval  OBJECT-TYPE
           SYNTAX      Integer32 (1..32767)
           MAX-ACCESS  read-write
           STATUS      current
           DESCRIPTION
            "Set a Loop detection Interval between 1 and 32767 seconds.
             The default is 2 seconds.
             This time interval to be used at counting time seconds to
            resend the CTP packet automatically."  
           DEFVAL  { 2 }
           ::= { sysLBDdetect 2 }
           
    sysLBDRecoverTime  OBJECT-TYPE
           SYNTAX      Integer32 (0 | 60..1000000)
           MAX-ACCESS  read-write
           STATUS      current
           DESCRIPTION
            "This time interval to be used at counting time seconds to
            recover the disabled port automatically. 
            The Loop Detection Recover Time can be set at 0 seconds, 
            or 60 to 1000000 seconds.
            Entering 0 will disable the Loop Detection Recover Time.
            The default is 60 seconds."  
           DEFVAL  { 60 }
           ::= { sysLBDdetect 3 }     
           
           
 -- LBD Port Control Table
        
        sysLBDCtrlTable OBJECT-TYPE 
           SYNTAX      SEQUENCE OF SysLBDCtrlEntry 
           MAX-ACCESS  not-accessible 
           STATUS      current 
           DESCRIPTION 
              "A table to control Loopback detection features either for 
              the entire switch or for each interface in the switch."
           ::= { sysLBDdetect 4 }
        
        sysLBDCtrlEntry OBJECT-TYPE 
           SYNTAX      SysLBDCtrlEntry 
           MAX-ACCESS  not-accessible 
           STATUS      current 
           DESCRIPTION 
               "An entry appears in this table for each interface 
                in the system."
           INDEX { sysLBDCtrlIndex }
           ::= { sysLBDCtrlTable 1 }
           
        SysLBDCtrlEntry ::= 
           SEQUENCE { 
              sysLBDCtrlIndex
                 Integer32, 
              sysLBDPortStatus 
                 INTEGER, 
              sysLBDPortLoopStatus 
                 INTEGER 
          }
        
        sysLBDCtrlIndex OBJECT-TYPE 
           SYNTAX      Integer32 (0..65535)
           MAX-ACCESS  read-only 
           STATUS      current 
           DESCRIPTION 
              "The interface index of the port for which the configuration
              in this entry applies."
           ::= { sysLBDCtrlEntry 1 }
            
        sysLBDPortStatus OBJECT-TYPE 
           SYNTAX      INTEGER {
                       enabled(1),
                       disabled(2)
                       }
           MAX-ACCESS  read-write 
           STATUS      current 
           DESCRIPTION 
               "Provides control to per port enable or disable the loopback detection 
                function. Default is disabled."
           DEFVAL  { disabled }
           ::= { sysLBDCtrlEntry 2 }
        
        sysLBDPortLoopStatus OBJECT-TYPE 
           SYNTAX      INTEGER {
                       normal(1),
                       disabled(2)
                      }
           MAX-ACCESS  read-only 
           STATUS      current 
           DESCRIPTION 
               "The loop status for this port."
           ::= { sysLBDCtrlEntry 3 }             
   
   





sysRateControl           OBJECT IDENTIFIER ::= { l2System 4 }
sysStormControl          OBJECT IDENTIFIER ::= { l2System 12 }


sysRateCtrlTable OBJECT-TYPE
   SYNTAX      SEQUENCE OF TabRateCtrlEntry
   MAX-ACCESS  not-accessible
   STATUS      current
   DESCRIPTION
      "A table to control the rate limiting parameters
       either for the entire switch or for each interface in the switch."
   ::= { sysRateControl 1 }

sysRateCtrlEntry OBJECT-TYPE
   SYNTAX      TabRateCtrlEntry
   MAX-ACCESS  not-accessible
   STATUS      current
   DESCRIPTION
      "An entry appears in this table for each physical
       interface in the switch."
   INDEX { sysRateCtrlIndex }
   ::= { sysRateCtrlTable 1 }

TabRateCtrlEntry ::=
   SEQUENCE {
      sysRateCtrlIndex
         Integer32,
      sysRateCtrlEgressLimitValue
         Integer32,
      sysRateCtrlIngressLimitValue
         Integer32
   }

sysRateCtrlIndex OBJECT-TYPE
   SYNTAX      Integer32 (1..65535)
   MAX-ACCESS  not-accessible
   STATUS      current
   DESCRIPTION
      "The interface index for which the configuration in this
       entry applies."
   ::= { sysRateCtrlEntry 1 }

sysRateCtrlEgressLimitValue OBJECT-TYPE
   SYNTAX      Integer32 (0..1000000)
   MAX-ACCESS  read-write
   STATUS      current
   DESCRIPTION
      "Configures interface Rate Limit (Packet that can be transferred
       on a port at a particular second).

       This object's value will take effect on the interface speed. Based
       on the operating speed of the port, the rate limit will be applied.
       This value can also be affected by the metering. A value of zero(0)
       disable rate limiting i.e. sets the port to full speed. The value can 
       be set between 64~100000(Kbits per second) in FE port, 64~1000000
       (Kbits per second) in GE port. 
       (Note: The multiple of 1850 Kbits/sec will be set automatically because
       the resolution of Giga-port Tx bandwidth control is 1850 Kbits/sec.)"
   ::= { sysRateCtrlEntry 5 }

sysRateCtrlIngressLimitValue OBJECT-TYPE
   SYNTAX      Integer32 (0..1000000)
   MAX-ACCESS  read-write
   STATUS      current
   DESCRIPTION
      "Allows to configure the limiting value for the maximum number
       of receive packets that can be transmitted per second over this
       interface. Setting this object to the value zero disables rate
       limiting for receive packets on this interface. The value that
       can be set for this object is limited by the underlying hardware. 
       The value can be set between 64~100000(Kbits per second) in FE 
       port,  64~1000000(Kbits per second) in GE port."
   ::= { sysRateCtrlEntry 7}



-- Storm Control

sysStormCtrlTable OBJECT-TYPE
   SYNTAX      SEQUENCE OF TabStormCtrlEntry
   MAX-ACCESS  not-accessible
   STATUS      current
   DESCRIPTION
      "A table to control the rate limiting parameters
       either for the entire switch or for each interface in the switch."
   ::= { sysStormControl 1 }

sysStormCtrlEntry OBJECT-TYPE
   SYNTAX      TabStormCtrlEntry
   MAX-ACCESS  not-accessible
   STATUS      current
   DESCRIPTION
      "An entry appears in this table for each physical
       interface in the switch."
   INDEX { sysStormCtrlIndex }
   ::= { sysStormCtrlTable 1 }

TabStormCtrlEntry ::=
   SEQUENCE {
      sysStormCtrlIndex
         Integer32,
	  sysDlfOnOff
         INTEGER,
 	  sysBroadcastOnOff
         INTEGER,
      sysMulticastOnOff
         INTEGER,
	  sysStormCtrlThreshold
         INTEGER,
      sysStormCtrlRowStatus
         RowStatus		 
   }
   
sysStormCtrlIndex OBJECT-TYPE
   SYNTAX      Integer32 (1..65535)
   MAX-ACCESS  not-accessible
   STATUS      current
   DESCRIPTION
      "The interface index for which the configuration in this
       entry applies."
   ::= { sysStormCtrlEntry 1 }

sysDlfOnOff       OBJECT-TYPE 
    SYNTAX INTEGER  {
                        enabled(1),
                        disabled(2)
                    }
    MAX-ACCESS    read-write 
    STATUS        current
    DESCRIPTION 
           "This object indicates unknown unicast storm control function is enabled or disabled 
            for device.
            When you enable unknown unicast storm control function, it
            will allowed you to limit the number of unknown unicast packets 
            per second going through device." 
	DEFVAL  {1}			
    ::= { sysStormCtrlEntry 2 } 

sysBroadcastOnOff       OBJECT-TYPE 
    SYNTAX INTEGER  {
                        enabled(1),
                        disabled(2)
                    }
    MAX-ACCESS    read-write 
    STATUS        current
    DESCRIPTION 
           "This object indicates broadcast storm control function is enabled or disabled 
            for device.
            When you enable broadcast storm control function, it
            will allowed you to limit the number of broadcast packets 
            per second going through device." 
	DEFVAL  {1}			
    ::= { sysStormCtrlEntry 3 } 
	
sysMulticastOnOff       OBJECT-TYPE 
    SYNTAX INTEGER  {
                        enabled(1),
                        disabled(2)
                    }
    MAX-ACCESS    read-write 
    STATUS        current
    DESCRIPTION 
           "This object indicates multicast storm control function is enabled or disabled 
            for device.
            When you enable multicast storm control function, it
            will allowed you to limit the number of multicast packets 
            per second going through device." 
	DEFVAL  {1}			
    ::= { sysStormCtrlEntry 4 } 

sysStormCtrlThreshold       OBJECT-TYPE 
    SYNTAX INTEGER  {
						disable(0),
                        low(1),
                        medium(2),
						high(3)
                    }
    MAX-ACCESS  read-write 
    STATUS      current 
    DESCRIPTION 
           "Allows to configure the limiting value for the maximum number
            of packets that can be transmitted per second over this interface. 
            Setting this object to the value zero disables rate limiting on 
            this interface. The value that can be set for this object is 
            limited by the underlying hardware. The limit value must be low, 
			medium,	or high. 
            (Notice : if the limit value is 0, it means unlimited.)"
    DEFVAL  {0}
    ::= { sysStormCtrlEntry 5 }

sysStormCtrlRowStatus OBJECT-TYPE
	SYNTAX      RowStatus
	MAX-ACCESS  read-create
	STATUS      current
	DESCRIPTION
		"*This object indicates the status of this entry. An entry is
		created in this table when this object is SET to 'createAndWait'.
		The entry in this table is used when the status of this object 
		is SET 'active'. The entry in this table is not used when this 
		object is SET 'notInService'. An entry created in this table is
		be deleted when this object is SET 'destroy'."
	::= { sysStormCtrlEntry  6 }  
	

-- User Authorized Manager
sysUserAuthMgr           OBJECT IDENTIFIER ::= { l2System 30}
sysUserAuthMgrTable OBJECT-TYPE
   SYNTAX      SEQUENCE OF TabUserAuthMgrEntry
   MAX-ACCESS  not-accessible
   STATUS      current
   DESCRIPTION
      "A table to configure user authorized managers in the system."
   ::= { sysUserAuthMgr 1 }

  
sysUserAuthMgrEntry OBJECT-TYPE
   SYNTAX      TabUserAuthMgrEntry
   MAX-ACCESS  not-accessible
   STATUS      current
   DESCRIPTION
      "User tabale entry."
   INDEX {sysUserAuthMgrId}
   ::= { sysUserAuthMgrTable 1 }

TabUserAuthMgrEntry ::=
   SEQUENCE {
      sysUserAuthMgrId
         Integer32,
      sysUserAuthMgrName
         OCTET STRING,
      sysUserAuthMgrRowStatus
         RowStatus
   }

sysUserAuthMgrId OBJECT-TYPE
   SYNTAX      Integer32 (0..65535)
   MAX-ACCESS  read-only
   STATUS      current
   DESCRIPTION
      "User ID used for administration of this device."
   ::= {sysUserAuthMgrEntry 1 }
 
sysUserAuthMgrName OBJECT-TYPE
   SYNTAX      OCTET STRING (SIZE (0..20))
   MAX-ACCESS  read-only
   STATUS      current
   DESCRIPTION
      "User Name used for administration of this device."
   ::= { sysUserAuthMgrEntry 2 }

sysUserAuthMgrRowStatus OBJECT-TYPE
   SYNTAX      RowStatus
   MAX-ACCESS  read-create
   STATUS      current
   DESCRIPTION
	   "This object indicates the status of this entry. An entry is
	   created in this table when this object is SET to 'createAndWait'.
	   The entry in this table is used when the status of this object 
	   is SET 'active'. The entry in this table is not used when this 
	   object is SET 'notInService'. An entry created in this table is
	   be deleted when this object is SET 'destroy'."
   ::= {sysUserAuthMgrEntry  3}  




IfDirection ::= TEXTUAL-CONVENTION
   STATUS  current
   DESCRIPTION
      "IfDirection specifies a direction of data travel on an
       interface. 'inbound' traffic is operated on during recsystion from
       the interface, while 'outbound' traffic is operated on prior to
       transmission on the interface."
   SYNTAX INTEGER {
           outbound(1),     -- egress interface
           inbound(2)       -- ingress interface
          }


DscpOrAny ::= TEXTUAL-CONVENTION
   DISPLAY-HINT "d"
   STATUS   current
   DESCRIPTION
      "The IP header Differentiated Services Code-Point that may be
      used for discriminating among traffic streams. The value -1 is
      used to indicate a wild card i.e. any value."
   REFERENCE
      "RFC 2474, RFC 2780"
   SYNTAX   Unsigned32 (0..63)


sysDfsMIBObjects                OBJECT IDENTIFIER ::= { l2Dfs 1 }
sysDfsMFClassifier              OBJECT IDENTIFIER ::= { sysDfsMIBObjects 2 }
sysDfsClassifier                OBJECT IDENTIFIER ::= { sysDfsMIBObjects 3 }
sysDfsInProfileAction           OBJECT IDENTIFIER ::= { sysDfsMIBObjects 4 }
sysDfsOutProfileAction          OBJECT IDENTIFIER ::= { sysDfsMIBObjects 5 }
sysDfsMeter                     OBJECT IDENTIFIER ::= { sysDfsMIBObjects 6 }
sysDfsEnterpriseCoSqAlgorithm   OBJECT IDENTIFIER ::= { sysDfsMIBObjects 8 }


-- DSCP System


-- DSCP MFC Classifier

sysDfsMultiFieldClfrTable OBJECT-TYPE
   SYNTAX       SEQUENCE OF TabDscpMultiFieldClfrEntry
   MAX-ACCESS   not-accessible
   STATUS       current
   DESCRIPTION
      "This table contains the Multifield Classifier details. (In WEB, it means Class Map)"
   ::= { sysDfsMFClassifier 1 }

sysDfsMultiFieldClfrEntry OBJECT-TYPE
   SYNTAX       TabDscpMultiFieldClfrEntry
   MAX-ACCESS   not-accessible
   STATUS   current
   DESCRIPTION
      "An IP Multi-field Classifier entry describes a single MF Classifier."
   INDEX { sysDfsMultiFieldClfrId }
   ::= { sysDfsMultiFieldClfrTable 1 }

TabDscpMultiFieldClfrEntry ::=
   SEQUENCE {
      sysDfsMultiFieldClfrId           Integer32,
      sysDfsMultiFieldClfrFilterId     Unsigned32,
      sysDfsMultiFieldClfrFilterType   INTEGER,
      sysDfsMultiFieldClfrStatus       RowStatus
   }

sysDfsMultiFieldClfrId OBJECT-TYPE
   SYNTAX         Integer32 (1..2147483647)
   MAX-ACCESS     not-accessible
   STATUS         current
   DESCRIPTION
      "An index that enumerates the MultiField Classifier filter."
   ::= { sysDfsMultiFieldClfrEntry 1 }

sysDfsMultiFieldClfrFilterId OBJECT-TYPE
   SYNTAX         Unsigned32
   MAX-ACCESS     read-write
   STATUS         current
   DESCRIPTION
      "This Object specifies the ID of the filter the details of which
       should be matched against the incoming packet"
   ::= { sysDfsMultiFieldClfrEntry 2 }

sysDfsMultiFieldClfrFilterType OBJECT-TYPE
   SYNTAX         INTEGER { macfilter(1), ipfilter(2)}
   MAX-ACCESS     read-write
   STATUS         current
   DESCRIPTION
      "This Object specifies the type of the filter"
   ::= { sysDfsMultiFieldClfrEntry 3 }

sysDfsMultiFieldClfrStatus OBJECT-TYPE
   SYNTAX      RowStatus
   MAX-ACCESS  read-create
   STATUS      current
   DESCRIPTION
      "The status of this concsystual row. All writable objects in this
       row may be modified only when the row status is not active."
   ::= { sysDfsMultiFieldClfrEntry 4 }


-- DSCP Classifier

sysDfsClfrTable OBJECT-TYPE
   SYNTAX       SEQUENCE OF TabDscpClfrEntry
   MAX-ACCESS   not-accessible
   STATUS       current
   DESCRIPTION
      "This table contains the Multifield filter details. (In WEB, it means Policy Map)"
   ::= { sysDfsClassifier 1 }

sysDfsClfrEntry OBJECT-TYPE
   SYNTAX       TabDscpClfrEntry
   MAX-ACCESS   not-accessible
   STATUS       current
   DESCRIPTION
      "An entry in the classifier table describes a single classifier.
       All classifier elements belonging to the same classifier use the
       classifier's sysDfsClfrId as part of their index."
   INDEX { sysDfsClfrId }
   ::= { sysDfsClfrTable 1 }

TabDscpClfrEntry ::=
   SEQUENCE  {
      sysDfsClfrId              Integer32,
      sysDfsClfrMFClfrId        Integer32,
      sysDfsClfrInProActionId   Integer32,
      sysDfsClfrOutProActionId  Integer32,
      sysDfsClfrStatus          RowStatus
   }

sysDfsClfrId OBJECT-TYPE
   SYNTAX       Integer32(1..2147483647)
   MAX-ACCESS   not-accessible
   STATUS       current
   DESCRIPTION
      "An index that enumerates the classifier entries."
   ::= { sysDfsClfrEntry 1 }

sysDfsClfrMFClfrId OBJECT-TYPE
   SYNTAX       Integer32
   MAX-ACCESS   read-write
   STATUS       current
   DESCRIPTION
      "The Object refers to a MultiField Classifier Id which is the index
       for  the MF  Classifier  table. A Valid value of this object is
       not mandatory for the creation of an entry in this table. 
       Need to map a Class ID (sysDfsMultiFieldClfrId)"
   DEFVAL { 0 }
   ::= { sysDfsClfrEntry 2 }

sysDfsClfrInProActionId   OBJECT-TYPE
   SYNTAX       Integer32
   MAX-ACCESS   read-write
   STATUS       current
   DESCRIPTION
      "The Object refers to a In Profile Action Id which is the index
       for the InProfile Action Table. A Valid value of this object is
       not mandatory for the creation of an entry in this table.
       Must the same with sysDfsClfrId. "
   DEFVAL { 0 }
   ::= { sysDfsClfrEntry 3 }

sysDfsClfrOutProActionId  OBJECT-TYPE
   SYNTAX       Integer32
   MAX-ACCESS   read-write
   STATUS       current
   DESCRIPTION
      "The Object refers to a Out Profile Action Id which is the index
       for the OutProfile Action Table. A Valid value of this object is
       not mandatory for the creation of an entry in this table.
       Must the same with sysDfsClfrId. "
   DEFVAL { 0 }
   ::= { sysDfsClfrEntry 4 }

sysDfsClfrStatus OBJECT-TYPE
   SYNTAX       RowStatus
   MAX-ACCESS   read-create
   STATUS       current
   DESCRIPTION
      "The status of this concsystual row. The objects
       sysDfsClfrInProActionId and  sysDfsClfrOutProActionId
       can be modified at any time. But the other Objects can not be
       modified when the RowStatus is 'active'for the particular entry.
       when the Row Status is set to 'destroy'for any of the entries
       only the entry is removed from the table. As the Object in this
       table are indexed to various other tables they stand unmodified
       by setting the RowStatus to 'destroy'."
   ::= { sysDfsClfrEntry 5 }


-- DSCP InProfile Action

sysDfsInProfileActionTable OBJECT-TYPE
   SYNTAX       SEQUENCE OF TabDscpInProfileActionEntry
   MAX-ACCESS   not-accessible
   STATUS       current
   DESCRIPTION
      "The Action Table enumerates actions that can be performed to a
       stream of traffic which is inprofile.For example, traffic exiting
       from a meter may be counted, marked, and potentially dropped before
       entering a queue."
   ::= { sysDfsInProfileAction 1 }

sysDfsInProfileActionEntry OBJECT-TYPE
   SYNTAX       TabDscpInProfileActionEntry
   MAX-ACCESS   not-accessible
   STATUS       current
   DESCRIPTION
      "Each entry in the action table allows description of one of
       action to be applied to traffic dsysending upon the treatment
       selected by sysDfsInProfileActionFlag."
   INDEX { sysDfsInProfileActionId }
   ::= { sysDfsInProfileActionTable 1 }

TabDscpInProfileActionEntry ::=
   SEQUENCE  {
      sysDfsInProfileActionId                Integer32,
      sysDfsInProfileActionFlag              Unsigned32,
      sysDfsInProfileActionNewPrio           Unsigned32,
      sysDfsInProfileActionDscp              DscpOrAny,
      sysDfsInProfileActionStatus            RowStatus
   }

sysDfsInProfileActionId OBJECT-TYPE
   SYNTAX       Integer32(1..2147483647)
   MAX-ACCESS   not-accessible
   STATUS       current
   DESCRIPTION
      "An index that enumerates the In Profile Action entries.
      Must be match the Policy ID. "
   ::= { sysDfsInProfileActionEntry 1 }

sysDfsInProfileActionFlag OBJECT-TYPE
   SYNTAX       Unsigned32
   MAX-ACCESS   read-write
   STATUS       current
   DESCRIPTION
      "This Object defines the action to be performed on the packet,
       when the packets are found to be In profile.
       Default Priority = 1 (0x0001), TOS = 4 (0x0004), DSCP = 1024 (0x0400)"
   ::= { sysDfsInProfileActionEntry 2 }

sysDfsInProfileActionNewPrio OBJECT-TYPE
   SYNTAX       Unsigned32
   MAX-ACCESS   read-write
   STATUS       current
   DESCRIPTION
      "This Object kesyss the new priority value in case the action
       selected by sysDfsInProfileActionFlag is to assign a new
       priority/COS value."
   ::= { sysDfsInProfileActionEntry 3 }

sysDfsInProfileActionDscp OBJECT-TYPE
   SYNTAX       DscpOrAny
   MAX-ACCESS   read-write
   STATUS       current
   DESCRIPTION
      "This Object kesyss the new DSCP value in case the action
       selected by sysDfsInProfileActionFlag is to assign a new
       DSCP value."
   ::= { sysDfsInProfileActionEntry 6 }

sysDfsInProfileActionStatus OBJECT-TYPE
   SYNTAX       RowStatus
   MAX-ACCESS   read-create
   STATUS       current
   DESCRIPTION
      "The status of this concsystual row. All writable objects in this
       row may be modified only when the row status is not active."
   ::= { sysDfsInProfileActionEntry 7 }


-- DSCP OutProfile Action

sysDfsOutProfileActionTable OBJECT-TYPE
   SYNTAX       SEQUENCE OF TabDscpOutProfileActionEntry
   MAX-ACCESS   not-accessible
   STATUS       current
   DESCRIPTION
      "The Action Table enumerates actions that can be performed to a
       stream of traffic which is out of profile.For example, traffic exiting
       from a meter may be counted, marked, and potentially dropped before
       entering a queue."
   ::= { sysDfsOutProfileAction 1 }

sysDfsOutProfileActionEntry OBJECT-TYPE
   SYNTAX       TabDscpOutProfileActionEntry
   MAX-ACCESS   not-accessible
   STATUS       current
   DESCRIPTION
      "Each entry in the action table allows description of one of
       action to be applied to traffic dsysending upon the treatment
       selected by sysDfsOutProfileActionFlag."
   INDEX { sysDfsOutProfileActionId }
   ::= { sysDfsOutProfileActionTable 1 }

TabDscpOutProfileActionEntry ::=
   SEQUENCE  {
      sysDfsOutProfileActionId               Integer32,
      sysDfsOutProfileActionFlag             Unsigned32,
      sysDfsOutProfileActionMID              Integer32,
      sysDfsOutProfileActionStatus           RowStatus
   }

sysDfsOutProfileActionId OBJECT-TYPE
   SYNTAX       Integer32(1..2147483647)
   MAX-ACCESS   not-accessible
   STATUS       current
   DESCRIPTION
      "An index that enumerates the Out Profile Action entries.
      Must the same with sysDfsClfrId. "
   ::= { sysDfsOutProfileActionEntry 1 }

sysDfsOutProfileActionFlag OBJECT-TYPE
   SYNTAX       Unsigned32
   MAX-ACCESS   read-write
   STATUS       current
   DESCRIPTION
      "This Object defines the action to be performed on the packet
       when the packets are found to be out of profile.
       Drop = 2 (0x0002) DSCP = 4 (0x0004)"
   ::= { sysDfsOutProfileActionEntry 2 }

sysDfsOutProfileActionMID OBJECT-TYPE
   SYNTAX       Integer32
   MAX-ACCESS   read-write
   STATUS       current
   DESCRIPTION
      "This Object kesyss the Meter Id to be added to the DataPath
       to which this particular OutProfileAction is applicable.
       Must the same with sysDfsClfrId. "
   ::= { sysDfsOutProfileActionEntry 4 }

sysDfsOutProfileActionStatus OBJECT-TYPE
   SYNTAX       RowStatus
   MAX-ACCESS   read-create
   STATUS       current
   DESCRIPTION
      "The status of this concsystual row. All writable objects in this
       row may be modified only when the row status is not active. The
       row comprises of an Meter Id which is an index to the Meter Table."
   ::= { sysDfsOutProfileActionEntry 5 }


-- DSCP Meter

sysDfsMeterTable OBJECT-TYPE
   SYNTAX       SEQUENCE OF TabDscpMeterEntry
   MAX-ACCESS   not-accessible
   STATUS       current
   DESCRIPTION
      "The Meter Table has the number of token with it and refreshCount value
       for associated with the meter."
   ::= { sysDfsMeter 1 }

sysDfsMeterEntry OBJECT-TYPE
   SYNTAX       TabDscpMeterEntry
   MAX-ACCESS   not-accessible
   STATUS       current
   DESCRIPTION
      "An entry in the Meter Table describing a single instance of
      a Metering Unit."
   INDEX { sysDfsMeterId }
   ::= { sysDfsMeterTable 1 }

TabDscpMeterEntry ::=
   SEQUENCE  {
      sysDfsMeterId                       Integer32,
      sysDfsMeterRefreshCount             Unsigned32,
      sysDfsMeterStatus                   RowStatus
   }

sysDfsMeterId OBJECT-TYPE
   SYNTAX       Integer32(1..2147483647)
   MAX-ACCESS   not-accessible
   STATUS       current
   DESCRIPTION
      "An index that enumerates the Meter entries.
      Must the same with sysDfsClfrId. "
   ::= { sysDfsMeterEntry 1 }

sysDfsMeterRefreshCount OBJECT-TYPE
   SYNTAX       Unsigned32
   MAX-ACCESS   read-write
   STATUS       current
   DESCRIPTION
      "This values specifies the number of tokens to be added to the
       meter bucket after each 8 usec. (Threshold kbps)"
   ::= { sysDfsMeterEntry 3 }

sysDfsMeterStatus OBJECT-TYPE
   SYNTAX       RowStatus
   MAX-ACCESS   read-create
   STATUS       current
   DESCRIPTION
      "The status of this concsystual row. All writable objects in this
       row may be modified only when this rowstatus in not active."
   ::= { sysDfsMeterEntry 4 }


-- DSCP Scheduler


-- DSCP Scheduling Algorithm Table

sysDfsCoSqAlgorithmTable OBJECT-TYPE
   SYNTAX      SEQUENCE OF TabDscpCoSqAlgorithmEntry
   MAX-ACCESS  not-accessible
   STATUS      current
   DESCRIPTION
      "A table containing the scheduling algorithm applied to
       a particular port."
   ::= { sysDfsEnterpriseCoSqAlgorithm 1 }

sysDfsCoSqAlgorithmEntry OBJECT-TYPE
   SYNTAX      TabDscpCoSqAlgorithmEntry
   MAX-ACCESS  not-accessible
   STATUS      current
   DESCRIPTION
      "An entry in this table gives mapping of a Port to
       user defined scheduled algorithm."
   INDEX   { sysDfsPortId }
   ::= { sysDfsCoSqAlgorithmTable 1 }

TabDscpCoSqAlgorithmEntry ::=
   SEQUENCE {
      sysDfsPortId            Integer32,
      sysDfsCoSqAlgorithm     INTEGER
   }

sysDfsPortId OBJECT-TYPE
   SYNTAX      Integer32 (1..24)
   MAX-ACCESS  not-accessible
   STATUS      current
   DESCRIPTION
      "Port identifier to which scheduling algorightm is set."
   ::= { sysDfsCoSqAlgorithmEntry 1 }

sysDfsCoSqAlgorithm OBJECT-TYPE
   SYNTAX      INTEGER {
                strictPriority(1),
                weightedRoundRobin(3)
               }
   MAX-ACCESS  read-write
   STATUS      current
   DESCRIPTION
      "Sets the packet scheduling algorithm for the port
       The default is strictPriority(1)."
   ::= { sysDfsCoSqAlgorithmEntry 2 }





InetAddressIPv4 ::= TEXTUAL-CONVENTION
  DISPLAY-HINT "1d.1d.1d.1d"
  STATUS       current
  DESCRIPTION
      "Represents an IPv4 network address:

         octets   contents         encoding
          1-4     IP address       network-byte order

       The corresponding InetAddressType value is ipv4(1)."
  SYNTAX       OCTET STRING (SIZE (4))

InetAddressIPv6 ::= TEXTUAL-CONVENTION
  DISPLAY-HINT "2x:2x:2x:2x:2x:2x:2x:2x%4d"
  STATUS       current
  DESCRIPTION
      "Represents an IPv6 network address:

         octets   contents         encoding
          1-16    IPv6 address     network-byte order
         17-20    scope identifier network-byte order

       The corresponding InetAddressType value is ipv6(2).

       The scope identifier (bytes 17-20) MUST NOT be present
       for global IPv6 addresses. For non-global IPv6 addresses
       (e.g. link-local or site-local addresses), the scope
       identifier MUST always be present. It contains a link
       identifier for link-local and a site identifier for
       site-local IPv6 addresses.

       The scope identifier MUST disambiguate identical address
       values. For link-local addresses, the scope identifier will
       typically be the interface index (ifIndex as defined in the
       IF-MIB, RFC 2233) of the interface on which the address is
       configured.

       The scope identifier may contain the special value 0
       which refers to the default scope. The default scope
       may be used in cases where the valid scope identifier
       is not known (e.g., a management application needs to
       write a site-local InetAddressIPv6 address without
       knowing the site identifier value). The default scope
       SHOULD NOT be used as an easy way out in cases where
       the scope identifier for a non-global IPv6 is known."
  SYNTAX       OCTET STRING (SIZE (16|20))

InetAddressDNS ::= TEXTUAL-CONVENTION
  DISPLAY-HINT "255a"
  STATUS       current
  DESCRIPTION
      "Represents a DNS domain name. The name SHOULD be
       fully qualified whenever possible.

       The corresponding InetAddressType is dns(16).

       The DESCRIPTION clause of InetAddress objects that
       may have InetAddressDNS values must fully describe
       how (and when) such names are to be resolved to IP
       addresses."
  SYNTAX       OCTET STRING (SIZE (1..255))





sysSyslogGeneralGroup          OBJECT IDENTIFIER ::= { l2Syslog 1 }
sysSyslogLogs                  OBJECT IDENTIFIER ::= { l2Syslog 2 }

-- SYSLOG General

sysSyslogLogging OBJECT-TYPE
   SYNTAX      INTEGER {
                enable(1),
                disable(2)
               }
   MAX-ACCESS  read-write
   STATUS      current
   DESCRIPTION
      "This object is for enabling or disabling syslog alert
       features in the system."
   DEFVAL { enable }
   ::= { sysSyslogGeneralGroup 1 }

sysSyslogTimeStamp OBJECT-TYPE
   SYNTAX      INTEGER {
                enable(1),
                disable(2)
               }
   MAX-ACCESS  read-write
   STATUS      current
   DESCRIPTION
      "This object is for enabling or disabling timestamp option.

       When enabled, the messages (log alert messages) will
       hold the time stamp information.

       When disabled, the time stamp information will not be carried with
       the messages sent to the log servers."
   DEFVAL { enable }
   ::= { sysSyslogGeneralGroup 2 }

sysSyslogSysBuffers OBJECT-TYPE
   SYNTAX      Integer32 (1..200)
   MAX-ACCESS  read-write
   STATUS      current
   DESCRIPTION
      "Number of log buffers to be allocated in the system"
   DEFVAL { 50 }
   ::= { sysSyslogGeneralGroup 4 }

sysSyslogClearLog OBJECT-TYPE
   SYNTAX      TruthValue
   MAX-ACCESS  read-write
   STATUS      current
   DESCRIPTION
      "Clears the buffered logs.

       This object is set to 'false' by default.

       When set to 'True', the buffered logs will be cleared and the value
       of this object will become 'false' again."
   DEFVAL { false }
   ::= { sysSyslogGeneralGroup 5 }

sysSyslogConfigTable    OBJECT-TYPE
   SYNTAX               SEQUENCE OF TabSyslogConfigEntry
   MAX-ACCESS           not-accessible
   STATUS               current
   DESCRIPTION
      "A table for configuring module specific log levels."
   ::= { sysSyslogGeneralGroup 6 }

sysSyslogConfigEntry OBJECT-TYPE
   SYNTAX            TabSyslogConfigEntry
   MAX-ACCESS        not-accessible
   STATUS            current
   DESCRIPTION
      "An entry containing logging level options for a particular module."
   INDEX { sysSyslogConfigModule }
   ::= { sysSyslogConfigTable 1 }

TabSyslogConfigEntry ::=
   SEQUENCE {
      sysSyslogConfigModule    Integer32,
      sysSyslogConfigLogLevel  INTEGER
   }

sysSyslogConfigModule     OBJECT-TYPE
   SYNTAX                 Integer32 (0..65535)
   MAX-ACCESS             not-accessible
   STATUS                 current
   DESCRIPTION
      "Specifies the module for which the log level option has to be
       configured."
   ::= { sysSyslogConfigEntry 1 }

sysSyslogConfigLogLevel   OBJECT-TYPE
   SYNTAX                 INTEGER{
                           emergency(0), -- For logging messages that
                                         -- are equivalent to panic
                                         -- condition.
                           alert(1),     -- For logging messages that
                                         -- require immediate attention.
                           critical(2),  -- For logging critical errors.
                           error(3),     -- For logging error messages.
                           warning(4),   -- For logging warning messages.
                           notice(5),    -- For logging messages that
                                         -- require attention
                                         -- and not errors.
                           info(6),      -- For logging informational
                                         -- messages.
                           debug(7)      -- For logging debug messages.
                          }
   MAX-ACCESS             read-write
   STATUS                 current
   DESCRIPTION
      "Specifies the log level option to be set for a specific module."
   ::= { sysSyslogConfigEntry 2 }

sysSyslogFacility OBJECT-TYPE
   SYNTAX      INTEGER {
                local0(128),     -- Reserved local use
                local1(136),     -- Reserved local use
                local2(144),     -- Reserved local use
                local3(152),     -- Reserved local use
                local4(160),     -- Reserved local use
                local5(168),     -- Reserved local use
                local6(176),     -- Reserved local use
                local7(184)      -- Reserved local use
               }
   MAX-ACCESS  read-write
   STATUS      current
   DESCRIPTION
      "The Syslog standard facilities.
       The facility to be used when sending Syslog messages to this server."
   DEFVAL { local0 }
   ::= { sysSyslogGeneralGroup 7 }



-- SYSLOG Logs

sysSyslogLogSrvAddr OBJECT-TYPE
   SYNTAX       IpAddress
   MAX-ACCESS  read-write
   STATUS      current
   DESCRIPTION
      "Specifies the syslog server IP to be used for remote logging. When
       configured, a new socket will be opened for this address.
       When the address is changed, the socket opened for the previous address
       will be closed and a new socket will be opened for this address."
   ::= { sysSyslogLogs 1 }





sysPortSecurity                  OBJECT IDENTIFIER ::= { l2Security 1 }


sysPortSecurityTable     OBJECT-TYPE
   SYNTAX      SEQUENCE OF TabPortSecEntry
   MAX-ACCESS  not-accessible
   STATUS      current
   DESCRIPTION
      "A list of  port default priority Entries."
   ::= { sysPortSecurity 1 }

sysPortSecurityEntry OBJECT-TYPE
   SYNTAX      TabPortSecEntry
   MAX-ACCESS  not-accessible
   STATUS      current
   DESCRIPTION
      "A list of  port default priority priorities."
   INDEX { sysPortSecurityIndex }
   ::= { sysPortSecurityTable 1 }

TabPortSecEntry ::=
   SEQUENCE {
      sysPortSecurityIndex
         Integer32,
      sysPortSecurityState
         INTEGER,
      sysPortSecurityMLA
         Integer32
   }

sysPortSecurityIndex OBJECT-TYPE
   SYNTAX      Integer32 (0..65535)
   MAX-ACCESS  not-accessible
   STATUS      current
   DESCRIPTION
      "The interface index for which the configuration in this
       entry applies."
   ::= { sysPortSecurityEntry 1 }

sysPortSecurityState OBJECT-TYPE
   SYNTAX INTEGER {
      enabled (1), disabled (2)
   }
   MAX-ACCESS  read-write
   STATUS      current
   DESCRIPTION
      "The security state on specific port."
   ::= { sysPortSecurityEntry 2 }

sysPortSecurityMLA OBJECT-TYPE
   SYNTAX      Integer32
   MAX-ACCESS  read-write
   STATUS      current
   DESCRIPTION
      "The max. learning number of MAC entries on specific port"
   ::= {sysPortSecurityEntry 3 }





sysSslGeneralGroup             OBJECT IDENTIFIER ::= { l2Ssl 1 }
sysSslCiphers                  OBJECT IDENTIFIER ::= { l2Ssl 2 }


-- SSL General

sysSslSecureHttpStatus OBJECT-TYPE
   SYNTAX      INTEGER {
                enable(1),
                disable(2)
               }
   MAX-ACCESS  read-write
   STATUS      current
   DESCRIPTION
      "This object is for enabling or disabling secure HTTP in the system."
   DEFVAL { disable }
   ::= { sysSslGeneralGroup 2 }

sysSslPort      OBJECT-TYPE
   SYNTAX       Integer32 (1..65535)
   MAX-ACCESS   read-write
   STATUS       current
   DESCRIPTION
      "This object is to configure the SSL port."
   DEFVAL { 443 }
   ::= { sysSslGeneralGroup 3 }

sysSslTrace     OBJECT-TYPE
   SYNTAX       Integer32
   MAX-ACCESS   read-write
   STATUS       current
   DESCRIPTION
      "Set the trace level for SSL.
       BIT 0 - Initialisation and Shutdown Trace.
       BIT 1 - Management trace.
       BIT 2 - Data path trace.
       BIT 3 - Control Plane trace.
       BIT 4 - Packet Dump.
       BIT 5 - OS Resource trace.
       BIT 6 - All Failure trace (All failures including Packet Validation)
       BIT 7 - Buffer Trace.
       
       Note:BIT 0 - Least significant bit
            BIT 7 - Most significant bit
       
       For example,setting the trace level to the value -0001 0101,
       will enable Init-Shutdown, data path and packet dump trace levels.
       
       Setting all the bits will enable all the trace levels and
       resetting them will disable all the trace levels."
   ::= { sysSslGeneralGroup 4 }


-- SSL Ciphers

sysSslCipherList OBJECT-TYPE
   SYNTAX        Integer32
   MAX-ACCESS    read-write
   STATUS        current
   DESCRIPTION
      "This object is to configure the cipher-suites list.

       This field is a bit mask, setting a bit indicates that the
       corresponding cipher-list will be involved in the server
       authentication.

       BIT 0 - RSA-NULL-MD5
       BIT 1 - RSA-NULL-SHA1
       BIT 2 - RSA-DES-SHA1
       BIT 3 - RSA-3DES-SHA1
       BIT 4 - DH-RSA-DES-SHA1
       BIT 5 - DH-RSA-3DES-SHA1
       BIT 6 - RSA-EXP1024-DES-SHA1

       Note:BIT 0 - Least significant bit
            BIT 6 - Most significant bit

       For example,setting the cipher list to the value - 001 0101,
       will include RSA-NULL-MD5, RSA-DES-SHA1 and DH-RSA-DES-SHA1 as
       cipher-list for authentication."
   DEFVAL { 0 }
   ::= { sysSslCiphers 1}

sysSslDefaultCipherList OBJECT-TYPE
   SYNTAX               TruthValue
   MAX-ACCESS           read-write
   STATUS               current
   DESCRIPTION
      "This object is to set the default cipher-suites list in 'sysSslCipherList'.
   
       Setting DefaultCipherList to TRUE would set the following cipher-list for
       authentication:
       - RSA_3DES_SHA1
       - RSA_DES_SHA1
       - RSA_EXP1024_DES_SHA1
       
       The value of this object reverts back to FALSE once the default cipher list is set."
   DEFVAL { false }
   ::= { sysSslCiphers 2}





sysSshGeneralGroup             OBJECT IDENTIFIER ::= { l2Ssh 1 }

-- SSH General

sysSshVersionCompatibility      OBJECT-TYPE
   SYNTAX      TruthValue
   MAX-ACCESS  read-write
   STATUS      current
   DESCRIPTION
      "This object is to configure the SSH version compatibility mode.
       When set to TRUE, both SSH version-1 and SSH Version-2 will be supported.
       When set to FALSE, SSH version-2 only will be supported.

       By default SSH version-2 is supported."
   DEFVAL { false }
   ::= { sysSshGeneralGroup 1 }

sysSshCipherList OBJECT-TYPE
   SYNTAX     Integer32(1..3)
   MAX-ACCESS read-write
   STATUS     current
   DESCRIPTION
      "This object is to configure the cipher-suites list.

       This object takes values as bit mask.  Setting a bit indicates that the
       corresponding cipher-list will be used for Encryption.

       The value of each bit position is as given below with bit 0 being the
       least significant bit:
       BIT 1 - DES-CBC
       BIT 0 - 3DES-CBC"
   DEFVAL { 1 }
   ::= { sysSshGeneralGroup 2}

sysSshMacList OBJECT-TYPE
   SYNTAX     Integer32(1..3)
   MAX-ACCESS read-write
   STATUS     current
   DESCRIPTION
      "This object is to configure the MAC-list.

       This object takes values as bit mask. Setting a bit indicates that the
       corresponding MAC-list will be used for authentication.

       The value of each bit position is as given below with bit 0  being the
       least significant bit:
       BIT 1 - HMAC-MD5
       BIT 0 - HMAC-SHA1"
   DEFVAL { 1 }
   ::= { sysSshGeneralGroup 3}

sysSshTrace     OBJECT-TYPE
   SYNTAX       Integer32
   MAX-ACCESS   read-write
   STATUS       current
   DESCRIPTION
      "Set the trace level for SSH.
       BIT 0 - Initialisation and Shutdown Trace.
       BIT 1 - Management trace.
       BIT 2 - Data path trace.
       BIT 3 - Control Plane trace.
       BIT 4 - Packet Dump.
       BIT 5 - OS Resource trace.
       BIT 6 - All Failure trace (All failures including Packet Validation)
       BIT 7 - Buffer Trace.

       Note:BIT 0 - Least significant bit
            BIT 7 - Most significant bit

       For example,setting the trace level to the value -0001 0101,
       will enable Init-Shutdown, data path and packet dump trace levels.

       Setting all the bits will enable all the trace levels and
       resetting them will disable all the trace levels."
   ::= { sysSshGeneralGroup 4 }

sysSshStatus  OBJECT-TYPE
   SYNTAX     TruthValue 
   MAX-ACCESS read-write
   STATUS     current
   DESCRIPTION
      "This object is for enabling or disabling ssh in the system."
   DEFVAL { true }
   ::= { sysSshGeneralGroup 5}





sysSntpGeneralGroup         OBJECT IDENTIFIER ::= { l2Sntp 1 }
sysSntpTzGroup              OBJECT IDENTIFIER ::= { l2Sntp 2 }      
 

-- SNTP General

sysSntpStatus OBJECT-TYPE
   SYNTAX     INTEGER {
                enable(1),
                disable(2)
              }
   MAX-ACCESS read-write 
   STATUS     current 
   DESCRIPTION 
      "This object is for enabling or disabling SNTP Client
       feature in the system."
   DEFVAL { enable } 
   ::= { sysSntpGeneralGroup 1 }
   
sysSntpPollInterval OBJECT-TYPE
   SYNTAX      Integer32 
   MAX-ACCESS  read-write 
   STATUS      current 
   DESCRIPTION 
      "The SNTP server polling interval in seconds."
   ::= { sysSntpGeneralGroup 2 }   
   
sysSntpTimeSeconds OBJECT-TYPE
   SYNTAX      Integer32 
   MAX-ACCESS  read-write 
   STATUS      current 
   DESCRIPTION 
      "This object is for setting the system time in seconds from 
       Epoch (00:00:00 UTC, January 1, 1970)."
   ::= { sysSntpGeneralGroup 3 }   

sysSntpPrimarySrvAddr OBJECT-TYPE
   SYNTAX      IpAddress
   MAX-ACCESS  read-write
   STATUS      current
   DESCRIPTION 
      "Specifies the primary SNTP server IP to be used for network time syncronization.
       When configured, a new socket will be opened for this address. 
       When the address is changed, the socket opened for the previous address 
       will be closed and a new socket will be opened for this address."
   ::= { sysSntpGeneralGroup 4 }

sysSntpSecondSrvAddr OBJECT-TYPE
   SYNTAX      IpAddress
   MAX-ACCESS  read-write
   STATUS      current
   DESCRIPTION 
      "Specifies the secondary SNTP server IP to be used for network time syncronization.
       If the primary SNTP server fail, the system will try secondary SNTP server.
       When configured, a new socket will be opened for this address. 
       When the address is changed, the socket opened for the previous address 
       will be closed and a new socket will be opened for this address."
   ::= { sysSntpGeneralGroup 5 }
   
sysSntpTimeZoneMappingIndex OBJECT-TYPE
   SYNTAX      Integer32
   MAX-ACCESS  read-write
   STATUS      current
   DESCRIPTION 
      "This object is used for distinguishing areas in the same time zone."
   ::= { sysSntpGeneralGroup 6 }   
   
-- SNTP Time Zone

sysSntpTzDSTStatus OBJECT-TYPE
   SYNTAX      INTEGER {
                enable(1),
                disable(2)
               }
   MAX-ACCESS  read-write 
   STATUS      current 
   DESCRIPTION 
      "This object is for enabling or disabling Time Zone Daylight Saving Time
       feature in the system."
   DEFVAL { enable } 
   ::= { sysSntpTzGroup 1 }

sysSntpTzMinutesWest OBJECT-TYPE
   SYNTAX      Integer32
   MAX-ACCESS  read-write
   STATUS      current
   DESCRIPTION 
      "Specifies the Time Zone Offset from GMT in +/- Minutes."
   ::= { sysSntpTzGroup 2 }

sysSntpTzDSTStartMon OBJECT-TYPE
   SYNTAX      Integer32 
   MAX-ACCESS  read-write 
   STATUS      current 
   DESCRIPTION 
      "The start month of Daylight Saving Time." 
   ::= { sysSntpTzGroup 3 }   
   
sysSntpTzDSTStartDay OBJECT-TYPE
   SYNTAX      Integer32 
   MAX-ACCESS  read-write 
   STATUS      current 
   DESCRIPTION 
      "The start day of Daylight Saving Time." 
   ::= { sysSntpTzGroup 4 }
   
sysSntpTzDSTStartHour OBJECT-TYPE
   SYNTAX      Integer32 
   MAX-ACCESS  read-write 
   STATUS      current 
   DESCRIPTION 
      "The start hour of Daylight Saving Time." 
   ::= { sysSntpTzGroup 5 }

sysSntpTzDSTStartMinute OBJECT-TYPE
   SYNTAX      Integer32 
   MAX-ACCESS  read-write 
   STATUS      current 
   DESCRIPTION 
      "The start minutes of Daylight Saving Time." 
   ::= { sysSntpTzGroup 6 }    
   
sysSntpTzDSTEndMon OBJECT-TYPE
   SYNTAX      Integer32 
   MAX-ACCESS  read-write 
   STATUS      current 
   DESCRIPTION 
      "The end month of Daylight Saving Time." 
   ::= { sysSntpTzGroup 7 }   
   
sysSntpTzDSTEndDay OBJECT-TYPE
   SYNTAX      Integer32 
   MAX-ACCESS  read-write 
   STATUS      current 
   DESCRIPTION 
      "The end day of Daylight Saving Time." 
   ::= { sysSntpTzGroup 8 }
   
sysSntpTzDSTEndHour OBJECT-TYPE
   SYNTAX      Integer32 
   MAX-ACCESS  read-write 
   STATUS      current 
   DESCRIPTION 
      "The end hour of Daylight Saving Time." 
   ::= { sysSntpTzGroup 9 }

sysSntpTzDSTEndMinute OBJECT-TYPE
   SYNTAX      Integer32 
   MAX-ACCESS  read-write 
   STATUS      current 
   DESCRIPTION 
      "The end minutes of Daylight Saving Time." 
   ::= { sysSntpTzGroup 10 }            
                                
sysSntpTzDSTForwardOffset OBJECT-TYPE
   SYNTAX      INTEGER  {
                halfHour(30),
                oneHour(60)
              }
   MAX-ACCESS  read-write 
   STATUS      current 
   DESCRIPTION 
      "The adjusted time of Daylight Saving Time." 
   ::= { sysSntpTzGroup 11 }    
                                   




sysDscpMIBObjects     OBJECT IDENTIFIER ::= { l2Dscp 1 }
sysDscpTypeGroup      OBJECT IDENTIFIER ::= { sysDscpMIBObjects 2 }


sysDscpEnable OBJECT-TYPE
   SYNTAX     INTEGER {
               enable(1),
               disable(2)
              }
   MAX-ACCESS read-write
   STATUS     current
   DESCRIPTION
      "Enable / Disable DiffServ function"
   ::= { sysDscpMIBObjects 1 }

sysDscpType01 OBJECT-TYPE
   SYNTAX     INTEGER {
               class0(0),
               class1(1),
               class2(2),
               class3(3)
              }
   MAX-ACCESS read-write
   STATUS     current
   DESCRIPTION
      "DiffServ Type 01 : IP ToS value = 0"
   ::= { sysDscpTypeGroup 1 }

sysDscpType02 OBJECT-TYPE
   SYNTAX     INTEGER {
               class0(0),
               class1(1),
               class2(2),
               class3(3)
              }
   MAX-ACCESS read-write
   STATUS     current
   DESCRIPTION
      "DiffServ Type 02 : IP ToS value = 4"
   ::= { sysDscpTypeGroup 2 }

sysDscpType03 OBJECT-TYPE
   SYNTAX     INTEGER {
               class0(0),
               class1(1),
               class2(2),
               class3(3)
              }
   MAX-ACCESS read-write
   STATUS     current
   DESCRIPTION
      "DiffServ Type 03 : IP ToS value = 8"
   ::= { sysDscpTypeGroup 3 }

sysDscpType04 OBJECT-TYPE
   SYNTAX     INTEGER {
               class0(0),
               class1(1),
               class2(2),
               class3(3)
              }
   MAX-ACCESS read-write
   STATUS     current
   DESCRIPTION
      "DiffServ Type 04 : IP ToS value = 12"
   ::= { sysDscpTypeGroup 4 }

sysDscpType05 OBJECT-TYPE
   SYNTAX     INTEGER {
               class0(0),
               class1(1),
               class2(2),
               class3(3)
              }
   MAX-ACCESS read-write
   STATUS     current
   DESCRIPTION
      "DiffServ Type 05 : IP ToS value = 16"
   ::= { sysDscpTypeGroup 5 }

sysDscpType06 OBJECT-TYPE
   SYNTAX     INTEGER {
               class0(0),
               class1(1),
               class2(2),
               class3(3)
              }
   MAX-ACCESS read-write
   STATUS     current
   DESCRIPTION
      "DiffServ Type 06 : IP ToS value = 20"
   ::= { sysDscpTypeGroup 6 }

sysDscpType07 OBJECT-TYPE
   SYNTAX     INTEGER {
               class0(0),
               class1(1),
               class2(2),
               class3(3)
              }
   MAX-ACCESS read-write
   STATUS     current
   DESCRIPTION
      "DiffServ Type 07 : IP ToS value = 24"
   ::= { sysDscpTypeGroup 7 }

sysDscpType08 OBJECT-TYPE
   SYNTAX     INTEGER {
               class0(0),
               class1(1),
               class2(2),
               class3(3)
              }
   MAX-ACCESS read-write
   STATUS     current
   DESCRIPTION
      "DiffServ Type 08 : IP ToS value = 28"
   ::= { sysDscpTypeGroup 8 }

sysDscpType09 OBJECT-TYPE
   SYNTAX     INTEGER {
               class0(0),
               class1(1),
               class2(2),
               class3(3)
              }
   MAX-ACCESS read-write
   STATUS     current
   DESCRIPTION
      "DiffServ Type 09 : IP ToS value = 32"
   ::= { sysDscpTypeGroup 9 }

sysDscpType10 OBJECT-TYPE
   SYNTAX     INTEGER {
               class0(0),
               class1(1),
               class2(2),
               class3(3)
              }
   MAX-ACCESS read-write
   STATUS     current
   DESCRIPTION
      "DiffServ Type 10 : IP ToS value = 36"
   ::= { sysDscpTypeGroup 10 }

sysDscpType11 OBJECT-TYPE
   SYNTAX     INTEGER {
               class0(0),
               class1(1),
               class2(2),
               class3(3)
              }
   MAX-ACCESS read-write
   STATUS     current
   DESCRIPTION
      "DiffServ Type 11 : IP ToS value = 40"
   ::= { sysDscpTypeGroup 11 }

sysDscpType12 OBJECT-TYPE
   SYNTAX     INTEGER {
               class0(0),
               class1(1),
               class2(2),
               class3(3)
              }
   MAX-ACCESS read-write
   STATUS     current
   DESCRIPTION
      "DiffServ Type 12 : IP ToS value = 44"
   ::= { sysDscpTypeGroup 12 }

sysDscpType13 OBJECT-TYPE
   SYNTAX     INTEGER {
               class0(0),
               class1(1),
               class2(2),
               class3(3)
              }
   MAX-ACCESS read-write
   STATUS     current
   DESCRIPTION
      "DiffServ Type 13 : IP ToS value = 48"
   ::= { sysDscpTypeGroup 13 }

sysDscpType14 OBJECT-TYPE
   SYNTAX     INTEGER {
               class0(0),
               class1(1),
               class2(2),
               class3(3)
              }
   MAX-ACCESS read-write
   STATUS     current
   DESCRIPTION
      "DiffServ Type 14 : IP ToS value = 52"
   ::= { sysDscpTypeGroup 14 }

sysDscpType15 OBJECT-TYPE
   SYNTAX     INTEGER {
               class0(0),
               class1(1),
               class2(2),
               class3(3)
              }
   MAX-ACCESS read-write
   STATUS     current
   DESCRIPTION
      "DiffServ Type 15 : IP ToS value = 56"
   ::= { sysDscpTypeGroup 15 }

sysDscpType16 OBJECT-TYPE
   SYNTAX     INTEGER {
               class0(0),
               class1(1),
               class2(2),
               class3(3)
              }
   MAX-ACCESS read-write
   STATUS     current
   DESCRIPTION
      "DiffServ Type 16 : IP ToS value = 60"
   ::= { sysDscpTypeGroup 16 }

sysDscpType17 OBJECT-TYPE
   SYNTAX     INTEGER {
               class0(0),
               class1(1),
               class2(2),
               class3(3)
              }
   MAX-ACCESS read-write
   STATUS     current
   DESCRIPTION
      "DiffServ Type 17 : IP ToS value = 64"
   ::= { sysDscpTypeGroup 17 }

sysDscpType18 OBJECT-TYPE
   SYNTAX     INTEGER {
               class0(0),
               class1(1),
               class2(2),
               class3(3)
              }
   MAX-ACCESS read-write
   STATUS     current
   DESCRIPTION
      "DiffServ Type 18 : IP ToS value = 68"
   ::= { sysDscpTypeGroup 18 }

sysDscpType19 OBJECT-TYPE
   SYNTAX     INTEGER {
               class0(0),
               class1(1),
               class2(2),
               class3(3)
              }
   MAX-ACCESS read-write
   STATUS     current
   DESCRIPTION
      "DiffServ Type 19 : IP ToS value = 72"
   ::= { sysDscpTypeGroup 19 }

sysDscpType20 OBJECT-TYPE
   SYNTAX     INTEGER {
               class0(0),
               class1(1),
               class2(2),
               class3(3)
              }
   MAX-ACCESS read-write
   STATUS     current
   DESCRIPTION
      "DiffServ Type 20 : IP ToS value = 76"
   ::= { sysDscpTypeGroup 20 }

sysDscpType21 OBJECT-TYPE
   SYNTAX     INTEGER {
               class0(0),
               class1(1),
               class2(2),
               class3(3)
              }
   MAX-ACCESS read-write
   STATUS     current
   DESCRIPTION
      "DiffServ Type 21 : IP ToS value = 80"
   ::= { sysDscpTypeGroup 21 }

sysDscpType22 OBJECT-TYPE
   SYNTAX     INTEGER {
               class0(0),
               class1(1),
               class2(2),
               class3(3)
              }
   MAX-ACCESS read-write
   STATUS     current
   DESCRIPTION
      "DiffServ Type 22 : IP ToS value = 84"
   ::= { sysDscpTypeGroup 22 }

sysDscpType23 OBJECT-TYPE
   SYNTAX     INTEGER {
               class0(0),
               class1(1),
               class2(2),
               class3(3)
              }
   MAX-ACCESS read-write
   STATUS     current
   DESCRIPTION
      "DiffServ Type 23 : IP ToS value = 88"
   ::= { sysDscpTypeGroup 23 }

sysDscpType24 OBJECT-TYPE
   SYNTAX     INTEGER {
               class0(0),
               class1(1),
               class2(2),
               class3(3)
              }
   MAX-ACCESS read-write
   STATUS     current
   DESCRIPTION
      "DiffServ Type 24 : IP ToS value = 92"
   ::= { sysDscpTypeGroup 24 }

sysDscpType25 OBJECT-TYPE
   SYNTAX     INTEGER {
               class0(0),
               class1(1),
               class2(2),
               class3(3)
              }
   MAX-ACCESS read-write
   STATUS     current
   DESCRIPTION
      "DiffServ Type 25 : IP ToS value = 96"
   ::= { sysDscpTypeGroup 25 }

sysDscpType26 OBJECT-TYPE
   SYNTAX     INTEGER {
               class0(0),
               class1(1),
               class2(2),
               class3(3)
              }
   MAX-ACCESS read-write
   STATUS     current
   DESCRIPTION
      "DiffServ Type 26 : IP ToS value = 100"
   ::= { sysDscpTypeGroup 26 }

sysDscpType27 OBJECT-TYPE
   SYNTAX     INTEGER {
               class0(0),
               class1(1),
               class2(2),
               class3(3)
              }
   MAX-ACCESS read-write
   STATUS     current
   DESCRIPTION
      "DiffServ Type 27 : IP ToS value = 104"
   ::= { sysDscpTypeGroup 27 }

sysDscpType28 OBJECT-TYPE
   SYNTAX     INTEGER {
               class0(0),
               class1(1),
               class2(2),
               class3(3)
              }
   MAX-ACCESS read-write
   STATUS     current
   DESCRIPTION
      "DiffServ Type 28 : IP ToS value = 108"
   ::= { sysDscpTypeGroup 28 }

sysDscpType29 OBJECT-TYPE
   SYNTAX     INTEGER {
               class0(0),
               class1(1),
               class2(2),
               class3(3)
              }
   MAX-ACCESS read-write
   STATUS     current
   DESCRIPTION
      "DiffServ Type 29 : IP ToS value = 112"
   ::= { sysDscpTypeGroup 29 }

sysDscpType30 OBJECT-TYPE
   SYNTAX     INTEGER {
               class0(0),
               class1(1),
               class2(2),
               class3(3)
              }
   MAX-ACCESS read-write
   STATUS     current
   DESCRIPTION
      "DiffServ Type 30 : IP ToS value = 116"
   ::= { sysDscpTypeGroup 30 }

sysDscpType31 OBJECT-TYPE
   SYNTAX     INTEGER {
               class0(0),
               class1(1),
               class2(2),
               class3(3)
              }
   MAX-ACCESS read-write
   STATUS     current
   DESCRIPTION
      "DiffServ Type 31 : IP ToS value = 120"
   ::= { sysDscpTypeGroup 31 }

sysDscpType32 OBJECT-TYPE
   SYNTAX     INTEGER {
               class0(0),
               class1(1),
               class2(2),
               class3(3)
              }
   MAX-ACCESS read-write
   STATUS     current
   DESCRIPTION
      "DiffServ Type 32 : IP ToS value = 124"
   ::= { sysDscpTypeGroup 32 }

sysDscpType33 OBJECT-TYPE
   SYNTAX     INTEGER {
               class0(0),
               class1(1),
               class2(2),
               class3(3)
              }
   MAX-ACCESS read-write
   STATUS     current
   DESCRIPTION
      "DiffServ Type 33 : IP ToS value = 128"
   ::= { sysDscpTypeGroup 33 }

sysDscpType34 OBJECT-TYPE
   SYNTAX     INTEGER {
               class0(0),
               class1(1),
               class2(2),
               class3(3)
              }
   MAX-ACCESS read-write
   STATUS     current
   DESCRIPTION
      "DiffServ Type 34 : IP ToS value = 132"
   ::= { sysDscpTypeGroup 34 }

sysDscpType35 OBJECT-TYPE
   SYNTAX     INTEGER {
               class0(0),
               class1(1),
               class2(2),
               class3(3)
              }
   MAX-ACCESS read-write
   STATUS     current
   DESCRIPTION
      "DiffServ Type 35 : IP ToS value = 136"
   ::= { sysDscpTypeGroup 35 }

sysDscpType36 OBJECT-TYPE
   SYNTAX     INTEGER {
               class0(0),
               class1(1),
               class2(2),
               class3(3)
              }
   MAX-ACCESS read-write
   STATUS     current
   DESCRIPTION
      "DiffServ Type 36 : IP ToS value = 140"
   ::= { sysDscpTypeGroup 36 }

sysDscpType37 OBJECT-TYPE
   SYNTAX     INTEGER {
               class0(0),
               class1(1),
               class2(2),
               class3(3)
              }
   MAX-ACCESS read-write
   STATUS     current
   DESCRIPTION
      "DiffServ Type 37 : IP ToS value = 144"
   ::= { sysDscpTypeGroup 37 }

sysDscpType38 OBJECT-TYPE
   SYNTAX     INTEGER {
               class0(0),
               class1(1),
               class2(2),
               class3(3)
              }
   MAX-ACCESS read-write
   STATUS     current
   DESCRIPTION
      "DiffServ Type 38 : IP ToS value = 148"
   ::= { sysDscpTypeGroup 38 }

sysDscpType39 OBJECT-TYPE
   SYNTAX     INTEGER {
               class0(0),
               class1(1),
               class2(2),
               class3(3)
              }
   MAX-ACCESS read-write
   STATUS     current
   DESCRIPTION
      "DiffServ Type 39 : IP ToS value = 152"
   ::= { sysDscpTypeGroup 39 }

sysDscpType40 OBJECT-TYPE
   SYNTAX     INTEGER {
               class0(0),
               class1(1),
               class2(2),
               class3(3)
              }
   MAX-ACCESS read-write
   STATUS     current
   DESCRIPTION
      "DiffServ Type 40 : IP ToS value = 156"
   ::= { sysDscpTypeGroup 40 }

sysDscpType41 OBJECT-TYPE
   SYNTAX     INTEGER {
               class0(0),
               class1(1),
               class2(2),
               class3(3)
              }
   MAX-ACCESS read-write
   STATUS     current
   DESCRIPTION
      "DiffServ Type 41 : IP ToS value = 160"
   ::= { sysDscpTypeGroup 41 }

sysDscpType42 OBJECT-TYPE
   SYNTAX     INTEGER {
               class0(0),
               class1(1),
               class2(2),
               class3(3)
              }
   MAX-ACCESS read-write
   STATUS     current
   DESCRIPTION
      "DiffServ Type 42 : IP ToS value = 164"
   ::= { sysDscpTypeGroup 42 }

sysDscpType43 OBJECT-TYPE
   SYNTAX     INTEGER {
               class0(0),
               class1(1),
               class2(2),
               class3(3)
              }
   MAX-ACCESS read-write
   STATUS     current
   DESCRIPTION
      "DiffServ Type 43 : IP ToS value = 168"
   ::= { sysDscpTypeGroup 43 }

sysDscpType44 OBJECT-TYPE
   SYNTAX     INTEGER {
               class0(0),
               class1(1),
               class2(2),
               class3(3)
              }
   MAX-ACCESS read-write
   STATUS     current
   DESCRIPTION
      "DiffServ Type 44 : IP ToS value = 172"
   ::= { sysDscpTypeGroup 44 }

sysDscpType45 OBJECT-TYPE
   SYNTAX     INTEGER {
               class0(0),
               class1(1),
               class2(2),
               class3(3)
              }
   MAX-ACCESS read-write
   STATUS     current
   DESCRIPTION
      "DiffServ Type 45 : IP ToS value = 176"
   ::= { sysDscpTypeGroup 45 }

sysDscpType46 OBJECT-TYPE
   SYNTAX     INTEGER {
               class0(0),
               class1(1),
               class2(2),
               class3(3)
              }
   MAX-ACCESS read-write
   STATUS     current
   DESCRIPTION
      "DiffServ Type 46 : IP ToS value = 180"
   ::= { sysDscpTypeGroup 46 }

sysDscpType47 OBJECT-TYPE
   SYNTAX     INTEGER {
               class0(0),
               class1(1),
               class2(2),
               class3(3)
              }
   MAX-ACCESS read-write
   STATUS     current
   DESCRIPTION
      "DiffServ Type 47 : IP ToS value = 184"
   ::= { sysDscpTypeGroup 47 }

sysDscpType48 OBJECT-TYPE
   SYNTAX     INTEGER {
               class0(0),
               class1(1),
               class2(2),
               class3(3)
              }
   MAX-ACCESS read-write
   STATUS     current
   DESCRIPTION
      "DiffServ Type 48 : IP ToS value = 188"
   ::= { sysDscpTypeGroup 48 }

sysDscpType49 OBJECT-TYPE
   SYNTAX     INTEGER {
               class0(0),
               class1(1),
               class2(2),
               class3(3)
              }
   MAX-ACCESS read-write
   STATUS     current
   DESCRIPTION
      "DiffServ Type 49 : IP ToS value = 192"
   ::= { sysDscpTypeGroup 49 }

sysDscpType50 OBJECT-TYPE
   SYNTAX     INTEGER {
               class0(0),
               class1(1),
               class2(2),
               class3(3)
              }
   MAX-ACCESS read-write
   STATUS     current
   DESCRIPTION
      "DiffServ Type 50 : IP ToS value = 196"
   ::= { sysDscpTypeGroup 50 }

sysDscpType51 OBJECT-TYPE
   SYNTAX     INTEGER {
               class0(0),
               class1(1),
               class2(2),
               class3(3)
              }
   MAX-ACCESS read-write
   STATUS     current
   DESCRIPTION
      "DiffServ Type 51 : IP ToS value = 200"
   ::= { sysDscpTypeGroup 51 }

sysDscpType52 OBJECT-TYPE
   SYNTAX     INTEGER {
               class0(0),
               class1(1),
               class2(2),
               class3(3)
              }
   MAX-ACCESS read-write
   STATUS     current
   DESCRIPTION
      "DiffServ Type 52 : IP ToS value = 204"
   ::= { sysDscpTypeGroup 52 }

sysDscpType53 OBJECT-TYPE
   SYNTAX     INTEGER {
               class0(0),
               class1(1),
               class2(2),
               class3(3)
              }
   MAX-ACCESS read-write
   STATUS     current
   DESCRIPTION
      "DiffServ Type 53 : IP ToS value = 208"
   ::= { sysDscpTypeGroup 53 }

sysDscpType54 OBJECT-TYPE
   SYNTAX     INTEGER {
               class0(0),
               class1(1),
               class2(2),
               class3(3)
              }
   MAX-ACCESS read-write
   STATUS     current
   DESCRIPTION
      "DiffServ Type 54 : IP ToS value = 212"
   ::= { sysDscpTypeGroup 54 }

sysDscpType55 OBJECT-TYPE
   SYNTAX     INTEGER {
               class0(0),
               class1(1),
               class2(2),
               class3(3)
              }
   MAX-ACCESS read-write
   STATUS     current
   DESCRIPTION
      "DiffServ Type 55 : IP ToS value = 216"
   ::= { sysDscpTypeGroup 55 }

sysDscpType56 OBJECT-TYPE
   SYNTAX     INTEGER {
               class0(0),
               class1(1),
               class2(2),
               class3(3)
              }
   MAX-ACCESS read-write
   STATUS     current
   DESCRIPTION
      "DiffServ Type 56 : IP ToS value = 220"
   ::= { sysDscpTypeGroup 56 }

sysDscpType57 OBJECT-TYPE
   SYNTAX     INTEGER {
               class0(0),
               class1(1),
               class2(2),
               class3(3)
              }
   MAX-ACCESS read-write
   STATUS     current
   DESCRIPTION
      "DiffServ Type 57 : IP ToS value = 224"
   ::= { sysDscpTypeGroup 57 }

sysDscpType58 OBJECT-TYPE
   SYNTAX     INTEGER {
               class0(0),
               class1(1),
               class2(2),
               class3(3)
              }
   MAX-ACCESS read-write
   STATUS     current
   DESCRIPTION
      "DiffServ Type 58 : IP ToS value = 228"
   ::= { sysDscpTypeGroup 58 }

sysDscpType59 OBJECT-TYPE
   SYNTAX     INTEGER {
               class0(0),
               class1(1),
               class2(2),
               class3(3)
              }
   MAX-ACCESS read-write
   STATUS     current
   DESCRIPTION
      "DiffServ Type 59 : IP ToS value = 232"
   ::= { sysDscpTypeGroup 59 }

sysDscpType60 OBJECT-TYPE
   SYNTAX     INTEGER {
               class0(0),
               class1(1),
               class2(2),
               class3(3)
              }
   MAX-ACCESS read-write
   STATUS     current
   DESCRIPTION
      "DiffServ Type 60 : IP ToS value = 236"
   ::= { sysDscpTypeGroup 60 }

sysDscpType61 OBJECT-TYPE
   SYNTAX     INTEGER {
               class0(0),
               class1(1),
               class2(2),
               class3(3)
              }
   MAX-ACCESS read-write
   STATUS     current
   DESCRIPTION
      "DiffServ Type 61 : IP ToS value = 240"
   ::= { sysDscpTypeGroup 61 }

sysDscpType62 OBJECT-TYPE
   SYNTAX     INTEGER {
               class0(0),
               class1(1),
               class2(2),
               class3(3)
              }
   MAX-ACCESS read-write
   STATUS     current
   DESCRIPTION
      "DiffServ Type 62 : IP ToS value = 244"
   ::= { sysDscpTypeGroup 62 }

sysDscpType63 OBJECT-TYPE
   SYNTAX     INTEGER {
               class0(0),
               class1(1),
               class2(2),
               class3(3)
              }
   MAX-ACCESS read-write
   STATUS     current
   DESCRIPTION
      "DiffServ Type 63 : IP ToS value = 248"
   ::= { sysDscpTypeGroup 63 }

sysDscpType64 OBJECT-TYPE
   SYNTAX     INTEGER {
               class0(0),
               class1(1),
               class2(2),
               class3(3)
              }
   MAX-ACCESS read-write
   STATUS     current
   DESCRIPTION
      "DiffServ Type 64 : IP ToS value = 252"
   ::= { sysDscpTypeGroup 64 }





sysSnoopInst              OBJECT IDENTIFIER ::= { l2Snoop 2 }
sysSnoopVlan              OBJECT IDENTIFIER ::= { l2Snoop 3 }
sysSnoopStats             OBJECT IDENTIFIER ::= { l2Snoop 4 }


-- Snoop System


-- Snoop Instance

sysSnoopInstanceGlobalTable OBJECT-TYPE
   SYNTAX      SEQUENCE OF TabSnoopInstanceGlobalEntry
   MAX-ACCESS  not-accessible
   STATUS      current
   DESCRIPTION
      "This table contains multicast forwarding mode configuration
       for each instance running in the snooping switch"
   ::= { sysSnoopInst 1 }

sysSnoopInstanceGlobalEntry OBJECT-TYPE
   SYNTAX      TabSnoopInstanceGlobalEntry
   MAX-ACCESS  not-accessible
   STATUS      current
   DESCRIPTION
      "This table contains instance number and the multicast
       forwarding mode configuration for the particular instance"
       INDEX { sysSnoopInstanceGlobalInstId }
   ::= { sysSnoopInstanceGlobalTable 1 }

TabSnoopInstanceGlobalEntry ::=
   SEQUENCE {
      sysSnoopInstanceGlobalInstId               Integer32,
      sysSnoopInstanceGlobalSystemControl        INTEGER
   }

sysSnoopInstanceGlobalInstId OBJECT-TYPE
   SYNTAX      Integer32 (0..255)
   MAX-ACCESS  not-accessible
   STATUS      current
   DESCRIPTION
      "Instance ID pertaining to the global configuration entry."
   ::= { sysSnoopInstanceGlobalEntry 1 }

sysSnoopInstanceGlobalSystemControl OBJECT-TYPE
   SYNTAX      INTEGER  { start(1), shutdown(2) }
   MAX-ACCESS  read-write
   STATUS      current
   DESCRIPTION
      "Snooping module is shutdown or started through
       this object.
       When set to 'start', resources required by the Enterprise
       SNOOP module is allocated and the module starts running.
       When set to 'shutdown', all the resources are released back
       to the system and the module stops running."
   DEFVAL { 1 }
   ::= { sysSnoopInstanceGlobalEntry 3 }

sysSnoopInstanceConfigTable OBJECT-TYPE
   SYNTAX      SEQUENCE OF TabSnoopInstanceConfigEntry
   MAX-ACCESS  not-accessible
   STATUS      current
   DESCRIPTION
      "This table contains global configuration of snooping for each
       instance running in switch"
   ::= { sysSnoopInst 2 }

sysSnoopInstanceConfigEntry OBJECT-TYPE
   SYNTAX      TabSnoopInstanceConfigEntry
   MAX-ACCESS  not-accessible
   STATUS      current
   DESCRIPTION
      "This table contains instance number, address type and the list of global
       configuration for the particular instance and address type"
   INDEX {
      sysSnoopInstanceConfigInstId,
      sysSnoopInetAddressType }
   ::= { sysSnoopInstanceConfigTable 1 }

TabSnoopInstanceConfigEntry ::=
   SEQUENCE {
      sysSnoopInstanceConfigInstId        Integer32,
      sysSnoopInetAddressType             InetAddressType,
      sysSnoopStatus                      INTEGER,
      sysSnoopRouterPortPurgeInterval     Integer32,
      sysSnoopPortPurgeInterval           Integer32,
      sysSnoopReportForwardInterval       Integer32,
      sysSnoopRetryCount                  Integer32,
      sysSnoopGrpQueryInterval            Integer32,
      sysSnoopReportFwdOnAllPorts         INTEGER,
      sysSnoopOperStatus                  INTEGER,
      sysSnoopSendQueryOnTopoChange       INTEGER,
      sysSnoopQuerierQueryInterval        Integer32
   }

sysSnoopInstanceConfigInstId OBJECT-TYPE
   SYNTAX      Integer32 (0..255)
   MAX-ACCESS  not-accessible
   STATUS      current
   DESCRIPTION
      "Instance ID pertaining to the global configuration entry.
       Currently only one instance is supported so it is always 1"
   ::= { sysSnoopInstanceConfigEntry 1 }

sysSnoopInetAddressType OBJECT-TYPE
   SYNTAX      InetAddressType
   MAX-ACCESS  not-accessible
   STATUS      current
   DESCRIPTION
      "Inet Address Type corresponding to  the global configuration entry.
       This indicates whether the row is for IGMP/MLD Snooping"
   ::= { sysSnoopInstanceConfigEntry 2 }

sysSnoopStatus OBJECT-TYPE
   SYNTAX      INTEGER  { enabled(1), disabled(2) }
   MAX-ACCESS  read-write
   STATUS      current
   DESCRIPTION
      "Enables or disables IGMP/MLD snooping in the system.
       When set to 'enabled', the Enterprise IGS/MLDS module starts
       protocol operations.
       When set to 'disabled', the IGS/MLDS module stops performing
       protocol operations."
   DEFVAL { 2 }
   ::= { sysSnoopInstanceConfigEntry 3 }

sysSnoopRouterPortPurgeInterval OBJECT-TYPE
   SYNTAX      Integer32 (60..600)
   MAX-ACCESS  read-write
   STATUS      current
   DESCRIPTION
      "This is the interval (in seconds) after which a learnt
       router port entry will be purged. For each router port learnt,
       this timer runs for 'RouterPortPurgeInterval' seconds.When the
       timer expires, the learnt router port entry is purged. However
       if control messages are received from the router before the
       timer expiry, then the timer is restarted."
   DEFVAL { 125 }
   ::= { sysSnoopInstanceConfigEntry 5 }

sysSnoopPortPurgeInterval OBJECT-TYPE
   SYNTAX      Integer32 (130..1225)
   MAX-ACCESS  read-write
   STATUS      current
   DESCRIPTION
      "This is the interval (in seconds) after which a learnt
       port entry will be purged. For each port on which rsysort
       has been received this timer runs for 'PortPurgeInterval'
       seconds. This timer will be restarted whenever a rsysort
       message is received from a host on the specific port. If
       the timer expires, then , the learnt port entry  will
       be purged from the multicast group."
   DEFVAL {260}
   ::= { sysSnoopInstanceConfigEntry 6 }

sysSnoopReportForwardInterval OBJECT-TYPE
   SYNTAX      Integer32 (1..25)
   MAX-ACCESS  read-write
   STATUS      current
   DESCRIPTION
      "This timer is used when proxy-reporting is disabled,the
       switch then has to suppress multiple IGMPv2/ MLDv1 report
       messages for the same group from being forwarded to the router.
       This is the interval (in seconds) within which report
       messages for the same multicast group will not be forwarded.
       The 'ReportForwardTimer' is per multicast group. This timer is
       started as soon as a report message for that group is forwarded
       out. Within this 'ReportForwardInterval' if another report for
       the same group arrives, that report will not be forwarded."
   DEFVAL { 5 }
   ::= { sysSnoopInstanceConfigEntry 7 }

sysSnoopRetryCount OBJECT-TYPE
   SYNTAX      Integer32 (1..5)
   MAX-ACCESS  read-write
   STATUS      current
   DESCRIPTION
      "When the switch receives leave message on a port, it
       sends group specific query to check if there are any other
       interested receivers for the group. This attribute defines
       the maximum number of queries sent by the switch before deleting
       the port from the group membership information in the forwarding
       database. If the maximum retry count exceeds 'sysSnoopRetryCount',
       then the port will be deleted from the multicast group membership
       information in the forwarding database and received leave message
       will be forwarded onto the router ports if there are no
       interested receivers for the group."
   DEFVAL { 2 }
   ::= { sysSnoopInstanceConfigEntry 8 }

sysSnoopGrpQueryInterval OBJECT-TYPE
   SYNTAX      Integer32 (1..5)
   MAX-ACCESS  read-write
   STATUS      current
   DESCRIPTION
      "The value of this attribute defines the time period with which
       the switch will send group specific queries on a port to check
       if there are any intersted receivers. The switch will send
       'sysSnoopRetryCount' queries before removing the port from the
       group membership information in the forwarding database."
   DEFVAL { 1 }
   ::= { sysSnoopInstanceConfigEntry 9 }

sysSnoopReportFwdOnAllPorts OBJECT-TYPE
   SYNTAX      INTEGER  { allports(1), rtrports(2) }
   MAX-ACCESS  read-write
   STATUS      current
   DESCRIPTION
      "Snooping module will forward reports only on router
       ports by default, to enable forwarding on all other ports
       this object to provide a administrative control to forward the
       reports on all the member ports of the VLAN"
   DEFVAL { 2 }
   ::= { sysSnoopInstanceConfigEntry 10 }

sysSnoopOperStatus OBJECT-TYPE
   SYNTAX      INTEGER  { enabled(1), disabled(2) }
   MAX-ACCESS  read-only
   STATUS      current
   DESCRIPTION
      "The operational status of the IGS/MLDS protocol.
       The value enabled(1) indicates the IGS/MLDS module is currently
       enabled in the system.
       The value disable(1) indicates the IGS/MLDS module is currently
       disabled in the system."
   ::= { sysSnoopInstanceConfigEntry 12 }

sysSnoopSendQueryOnTopoChange OBJECT-TYPE
   SYNTAX      INTEGER  { enabled(1), disabled(2) }
   MAX-ACCESS  read-write
   STATUS      current
   DESCRIPTION
      "The Snooping Switch can be configured to send IGMP/MLD General
      queries on all non router ports when spanning tree topology change
      occurs in a network. If the spanning tree mode is RSTP, IGMP/MLD
      general queries will be sent on all the non router ports present
      in the switch.If the spanning tree mode is MSTP, IGMP/MLD general
      queries will be sent on all the non router ports of the VLAN mapped
      for the MSTP instance.When this object is set to 'enabled' ,the
      switch will generate general query messages"
   DEFVAL { 2 }
   ::= { sysSnoopInstanceConfigEntry 13 }

sysSnoopQuerierQueryInterval OBJECT-TYPE
   SYNTAX      Integer32 (60..600)
   MAX-ACCESS  read-write
   STATUS      current
   DESCRIPTION
      "This is the interval (in seconds) for which the switch
       sends general queries when it is configured as a querier.
       A switch should be configured as a querier for a VLAN
       only when there are no queriers in the network."
   DEFVAL { 125 }
   ::= { sysSnoopInstanceConfigEntry 16 }


-- Snoop VLAN

sysSnoopVlanMcastMacFwdTable OBJECT-TYPE
   SYNTAX      SEQUENCE OF TabSnoopVlanMcastMacFwdEntry
   MAX-ACCESS  not-accessible
   STATUS      current
   DESCRIPTION
      "This table contains MAC based multicast forwarding
       information. This information is applicable only if
       the 'sysSnoopMcastForwardingMode' is set to 'macbased' "
   ::= { sysSnoopVlan 1 }

sysSnoopVlanMcastMacFwdEntry OBJECT-TYPE
   SYNTAX      TabSnoopVlanMcastMacFwdEntry
   MAX-ACCESS  not-accessible
   STATUS      current
   DESCRIPTION
      "This table contains VLAN ID, multicast group MAC address and the
       list of ports onto which the multicast data packets for group
       should be forwarded."
   INDEX { sysSnoopVlanMcastMacFwdInstId,
           sysSnoopVlanMcastMacFwdVlanId,
           sysSnoopVlanMcastMacFwdInetAddressType,
           sysSnoopVlanMcastMacFwdGroupAddress }
   ::= { sysSnoopVlanMcastMacFwdTable 1 }

TabSnoopVlanMcastMacFwdEntry ::=
   SEQUENCE {
      sysSnoopVlanMcastMacFwdInstId           Integer32,
      sysSnoopVlanMcastMacFwdVlanId           Integer32,
      sysSnoopVlanMcastMacFwdInetAddressType  InetAddressType,
      sysSnoopVlanMcastMacFwdGroupAddress     MacAddress,
      sysSnoopVlanMcastMacFwdPortList         PortList
   }

sysSnoopVlanMcastMacFwdInstId OBJECT-TYPE
   SYNTAX      Integer32 (0..255)
   MAX-ACCESS  not-accessible
   STATUS      current
   DESCRIPTION
      "Instance ID pertaining to the Multicast forwarding entry.
       Currently only one instance is supported so it is always 1"
   ::= { sysSnoopVlanMcastMacFwdEntry 1 }

sysSnoopVlanMcastMacFwdVlanId OBJECT-TYPE
   SYNTAX      Integer32 (1..4094)
   MAX-ACCESS  not-accessible
   STATUS      current
   DESCRIPTION
      "VLAN ID pertaining to the Multicast forwarding entry"
   ::= { sysSnoopVlanMcastMacFwdEntry 2 }

sysSnoopVlanMcastMacFwdInetAddressType OBJECT-TYPE
   SYNTAX      InetAddressType
   MAX-ACCESS  not-accessible
   STATUS      current
   DESCRIPTION
      "InetAddressType pertaining to the Multicast forwarding entry"
   ::= { sysSnoopVlanMcastMacFwdEntry 3 }

sysSnoopVlanMcastMacFwdGroupAddress OBJECT-TYPE
   SYNTAX      MacAddress
   MAX-ACCESS  not-accessible
   STATUS      current
   DESCRIPTION
      "Multicast group MAC address."
   ::= { sysSnoopVlanMcastMacFwdEntry 4 }

sysSnoopVlanMcastMacFwdPortList OBJECT-TYPE
   SYNTAX      PortList
   MAX-ACCESS  read-only
   STATUS      current
   DESCRIPTION
      "List of ports onto which the multicast data
       packets destined for this group will be forwarded."
   ::= { sysSnoopVlanMcastMacFwdEntry 5 }

sysSnoopVlanRouterTable OBJECT-TYPE
   SYNTAX      SEQUENCE OF TabSnoopVlanRouterEntry
   MAX-ACCESS  not-accessible
   STATUS      current
   DESCRIPTION
      "This table contains the list of ports through which
       a router, in a particular VLAN is reachable."
   ::= { sysSnoopVlan 3 }

sysSnoopVlanRouterEntry OBJECT-TYPE
   SYNTAX      TabSnoopVlanRouterEntry
   MAX-ACCESS  not-accessible
   STATUS      current
   DESCRIPTION
      "Contains the VLAN ID and list of ports on which
       routers are present in the VLAN."
   INDEX { sysSnoopVlanRouterInstId,
           sysSnoopVlanRouterVlanId,
           sysSnoopVlanRouterInetAddressType }
   ::= { sysSnoopVlanRouterTable 1 }

TabSnoopVlanRouterEntry ::=
   SEQUENCE {
      sysSnoopVlanRouterInstId             Integer32,
      sysSnoopVlanRouterVlanId             Integer32,
      sysSnoopVlanRouterInetAddressType    InetAddressType,
      sysSnoopVlanRouterPortList           PortList
   }

sysSnoopVlanRouterInstId OBJECT-TYPE
   SYNTAX      Integer32 (0..255)
   MAX-ACCESS  not-accessible
   STATUS      current
   DESCRIPTION
      "Instance ID pertaining to the router port entry.
       Currently only one instance is supported so it is always 1"
   ::= { sysSnoopVlanRouterEntry 1 }

sysSnoopVlanRouterVlanId OBJECT-TYPE
   SYNTAX      Integer32 (1..4094)
   MAX-ACCESS  not-accessible
   STATUS      current
   DESCRIPTION
      "VLAN ID of the ports through which router is reachable."
   ::= { sysSnoopVlanRouterEntry 2 }

sysSnoopVlanRouterInetAddressType OBJECT-TYPE
   SYNTAX      InetAddressType
   MAX-ACCESS  not-accessible
   STATUS      current
   DESCRIPTION
      "It indicates whether the row belongs to IGMP / MLD snooping."
   ::= { sysSnoopVlanRouterEntry 3 }

sysSnoopVlanRouterPortList OBJECT-TYPE
   SYNTAX      PortList
   MAX-ACCESS  read-only
   STATUS      current
   DESCRIPTION
      "List of ports on which routers are present.
       These router ports are learnt through control messages
       received from routers, and can also be configured
       statically."
   ::= { sysSnoopVlanRouterEntry 4 }

sysSnoopVlanFilterTable OBJECT-TYPE
   SYNTAX      SEQUENCE OF TabSnoopVlanFilterEntry
   MAX-ACCESS  not-accessible
   STATUS      current
   DESCRIPTION
      "This table contains configuration of snooping
       on specific Vlans. This Table is valid only when VLAN is
       enabled in the system."
   ::= { sysSnoopVlan 4 }

sysSnoopVlanFilterEntry OBJECT-TYPE
   SYNTAX      TabSnoopVlanFilterEntry
   MAX-ACCESS  not-accessible
   STATUS      current
   DESCRIPTION
      "Contains snooping status , version and fast leave
       configuration for a specific VLAN."
   INDEX { sysSnoopVlanFilterInstId,
           sysSnoopVlanFilterVlanId,
           sysSnoopVlanFilterInetAddressType }
   ::= { sysSnoopVlanFilterTable 1 }

TabSnoopVlanFilterEntry ::=
   SEQUENCE {
      sysSnoopVlanFilterInstId           Integer32,
      sysSnoopVlanFilterVlanId           Integer32,
      sysSnoopVlanFilterInetAddressType  InetAddressType,
      sysSnoopVlanSnoopStatus            INTEGER,
      sysSnoopVlanOperatingVersion       INTEGER,
      sysSnoopVlanFastLeave              INTEGER,
      sysSnoopVlanQuerier                INTEGER,
      sysSnoopVlanCfgQuerier             INTEGER,
      sysSnoopVlanQueryInterval          Integer32,
      sysSnoopVlanRtrPortList            PortList,
      sysSnoopVlanRowStatus              RowStatus
   }

sysSnoopVlanFilterInstId OBJECT-TYPE
   SYNTAX      Integer32 (0..255)
   MAX-ACCESS  not-accessible
   STATUS      current
   DESCRIPTION
      "Instance ID pertaining to VLAN filter table entry.
       Currently only one instance is supported so it is always 1"
   ::= { sysSnoopVlanFilterEntry 1 }

sysSnoopVlanFilterVlanId OBJECT-TYPE
   SYNTAX      Integer32 (1..4094)
   MAX-ACCESS  not-accessible
   STATUS      current
   DESCRIPTION
      "VLAN ID for which snooping configuration is to be done."
   ::= { sysSnoopVlanFilterEntry 2 }

sysSnoopVlanFilterInetAddressType OBJECT-TYPE
   SYNTAX      InetAddressType
   MAX-ACCESS  not-accessible
   STATUS      current
   DESCRIPTION
      "Indicates whether the row belongs to IGS/MLD snooping"
   ::= { sysSnoopVlanFilterEntry 3 }

sysSnoopVlanSnoopStatus OBJECT-TYPE
   SYNTAX      INTEGER { enabled(1), disabled(2) }
   MAX-ACCESS  read-write
   STATUS      current
   DESCRIPTION
      "Enables or disables IGS/MLDS on that specific VLAN"
   DEFVAL  { 1 }
   ::= { sysSnoopVlanFilterEntry 4 }

sysSnoopVlanOperatingVersion OBJECT-TYPE
   SYNTAX      INTEGER { v1(1), v2(2) }
   MAX-ACCESS  read-only
   STATUS      current
   DESCRIPTION
      "Indicates the operating version of the IGS/MLDS switch for
       a specific VLAN. The default operating mode on a specific VLAN
       is IGMP version 2 i.e, V2(2) or MLD version 1 i.e, V1(1)"
   DEFVAL  { 2 }
   ::= { sysSnoopVlanFilterEntry 5 }

sysSnoopVlanFastLeave OBJECT-TYPE
   SYNTAX      INTEGER { enabled(1), disabled(2) }
   MAX-ACCESS  read-write
   STATUS      current
   DESCRIPTION
      "Enables or disables fast leave for the VLAN. When it is
       'disabled',on reception of a leave message the switch checks
       if they are any interested receivers for the group by sending
       a group specific query before removing the port from the
       forwarding table. If set to 'enabled', the switch does not
       send a group specific query and immediately removes the port
       from the forwarding table."
   DEFVAL  { 2 }
   ::= { sysSnoopVlanFilterEntry 7 }

sysSnoopVlanQuerier OBJECT-TYPE
   SYNTAX      INTEGER  { enabled(1), disabled(2) }
   MAX-ACCESS  read-only
   STATUS      current
   DESCRIPTION
      "Indicates whether the switch is configured as a querier in the VLAN"
   DEFVAL  { 2 }
   ::= { sysSnoopVlanFilterEntry 8 }

sysSnoopVlanCfgQuerier OBJECT-TYPE
   SYNTAX      INTEGER  { enabled(1), disabled(2) }
   MAX-ACCESS  read-write
   STATUS      current
   DESCRIPTION
      "The snooping switch can be configured to send IGMP/MLD queries
       when IGMP/MLD routers are not present in the VLAN. When set to
       'enabled' the switch will generate general query messages."
   DEFVAL { 2 }
   ::= { sysSnoopVlanFilterEntry 9 }

sysSnoopVlanQueryInterval OBJECT-TYPE
   SYNTAX      Integer32 (60..600)
   MAX-ACCESS  read-only
   STATUS      current
   DESCRIPTION
      "This is the interval (in seconds) for which the switch
       sends general queries when it is configured as a querier for
       the VLAN. A switch should be configured as a querier for a VLAN
       only when there are no queriers in the network."
   DEFVAL { 125 }
   ::= { sysSnoopVlanFilterEntry 10 }

sysSnoopVlanRtrPortList OBJECT-TYPE
   SYNTAX      PortList
   MAX-ACCESS  read-write
   STATUS      current
   DESCRIPTION
      "List of ports which are configured statically as router ports"
   ::= { sysSnoopVlanFilterEntry 11 }

sysSnoopVlanRowStatus OBJECT-TYPE
   SYNTAX      RowStatus
   MAX-ACCESS  read-create
   STATUS      current
   DESCRIPTION
      "The status of a row in the VLAN filter table. By
       'sysSnoopVlanRowStatus' new entries can be created in the VLAN
       filter table and the existing entries can be removed from the
       VLAN filter table"
   ::= { sysSnoopVlanFilterEntry 12 }


-- Snoop Statistics

sysSnoopStatsTable OBJECT-TYPE
   SYNTAX      SEQUENCE OF TabSnoopStatsEntry
   MAX-ACCESS  not-accessible
   STATUS      current
   DESCRIPTION
      "This table contains snooping statistics
       maintained by the switch. The statistics are
       maintained on a per VLAN basis."
   ::= { sysSnoopStats 1 }

sysSnoopStatsEntry OBJECT-TYPE
   SYNTAX      TabSnoopStatsEntry
   MAX-ACCESS  not-accessible
   STATUS      current
   DESCRIPTION
      "Contains snooping statistics for a particular VLAN."
   INDEX { sysSnoopStatsInstId,
           sysSnoopStatsVlanId,
           sysSnoopStatsInetAddressType }
   ::= { sysSnoopStatsTable 1 }

TabSnoopStatsEntry ::=
   SEQUENCE {
      sysSnoopStatsInstId                Integer32,
      sysSnoopStatsVlanId                Integer32,
      sysSnoopStatsInetAddressType       InetAddressType,
      sysSnoopStatsRxGenQueries          Counter32,
      sysSnoopStatsRxGrpQueries          Counter32,
      sysSnoopStatsRxAsmReports         Counter32,
      sysSnoopStatsRxAsmLeaves           Counter32,
      sysSnoopStatsTxGenQueries          Counter32,
      sysSnoopStatsTxGrpQueries          Counter32,
      sysSnoopStatsTxAsmReports         Counter32,
      sysSnoopStatsTxAsmLeaves           Counter32,
      sysSnoopStatsDroppedPkts           Counter32
   }

sysSnoopStatsInstId OBJECT-TYPE
   SYNTAX      Integer32 (0..255)
   MAX-ACCESS  not-accessible
   STATUS      current
   DESCRIPTION
      "Instance ID pertaining for the statistics entry.
       Currently only one instance is supported so it is always 1"
   ::= { sysSnoopStatsEntry 1 }

sysSnoopStatsVlanId OBJECT-TYPE
   SYNTAX      Integer32 (1..4094)
   MAX-ACCESS  not-accessible
   STATUS      current
   DESCRIPTION
      "VLAN ID for which snooping statistics are displayed"
   ::= { sysSnoopStatsEntry 2 }

sysSnoopStatsInetAddressType OBJECT-TYPE
   SYNTAX      InetAddressType
   MAX-ACCESS  not-accessible
   STATUS      current
   DESCRIPTION
      "Indicates whether the statistics are for IGS/MLDS"
   ::= { sysSnoopStatsEntry 3 }

sysSnoopStatsRxGenQueries OBJECT-TYPE
   SYNTAX      Counter32
   MAX-ACCESS  read-only
   STATUS      current
   DESCRIPTION
      "Provides the statistics of General Queries received by the
       snooping switch."
   ::= { sysSnoopStatsEntry 4 }

sysSnoopStatsRxGrpQueries OBJECT-TYPE
   SYNTAX      Counter32
   MAX-ACCESS  read-only
   STATUS      current
   DESCRIPTION
      "Provides the statistics of Group Specific Queries received
       by the snooping switch."
   ::= { sysSnoopStatsEntry 5 }

sysSnoopStatsRxAsmReports OBJECT-TYPE
   SYNTAX      Counter32
   MAX-ACCESS  read-only
   STATUS      current
   DESCRIPTION
      "Provides the statistics of IGMPv1/IGMPv2 Membership reports
       received by the snooping switch. In case of MLDS, it provides
       the statistics of MLDv1 membership reports."
   ::= { sysSnoopStatsEntry 7 }

sysSnoopStatsRxAsmLeaves OBJECT-TYPE
   SYNTAX      Counter32
   MAX-ACCESS  read-only
   STATUS      current
   DESCRIPTION
      "Provides the statistics of IGMPv2/MLDv1 Leave messages
       received by the snooping switch."
   ::= { sysSnoopStatsEntry 15 }

sysSnoopStatsTxGenQueries OBJECT-TYPE
   SYNTAX      Counter32
   MAX-ACCESS  read-only
   STATUS      current
   DESCRIPTION
      "Provides the statistics of General Queries transmitted by the
       snooping switch when it is act as a querier."
   ::= { sysSnoopStatsEntry 16 }

sysSnoopStatsTxGrpQueries OBJECT-TYPE
   SYNTAX      Counter32
   MAX-ACCESS  read-only
   STATUS      current
   DESCRIPTION
      "Provides the statistics of Group Specific Queries transmitted
       by the snooping switch."
   ::= { sysSnoopStatsEntry 17 }

sysSnoopStatsTxAsmReports OBJECT-TYPE
   SYNTAX      Counter32
   MAX-ACCESS  read-only
   STATUS      current
   DESCRIPTION
      "Provides the statistics of IGMPv1/IGMPv2 Membership reports
       transmitted by the snooping switch."
   ::= { sysSnoopStatsEntry 18 }

sysSnoopStatsTxAsmLeaves OBJECT-TYPE
   SYNTAX      Counter32
   MAX-ACCESS  read-only
   STATUS      current
   DESCRIPTION
      "Provides the statistics of IGMPv2/MLDv1 Leave messages
       transmitted by the snooping switch."
   ::= { sysSnoopStatsEntry 20 }

sysSnoopStatsDroppedPkts OBJECT-TYPE
   SYNTAX      Counter32
   MAX-ACCESS  read-only
   STATUS      current
   DESCRIPTION
      "Provides the number of erroneous IGMP/MLD packets dropped
       by the snooping switch due to failure in checksum
       calculation."
   ::= { sysSnoopStatsEntry 21 }





BridgeId ::= TEXTUAL-CONVENTION
   STATUS current
   DESCRIPTION
      "The Bridge-Identifier as used in the
       Spanning Tree
       Protocol to uniquely identify a bridge.  Its first two
       octets (in network byte order) contain a priority
       value and its last 6 octets contain the MAC address
       used to refer to a bridge in a unique fashion
       (typically, the numerically smallest MAC address
       of all ports on the bridge).
       Several objects in this MIB module represent values of
       timers used by the Spanning Tree Protocol.  In this
       MIB, these timers have values in units of hundreths of
       a second (i.e. 1/100 secs).
       These timers, when stored in a Spanning Tree Protocol's
       BPDU, are in units of 1/256 seconds.  Note, however,
       that 802.1D-1990 specifies a settable granularity of
       no more than 1 second for these timers.  To avoid
       ambiguity, a data type is defined here as a textual
       convention and all representation of these timers
       in this MIB module are defined using this data type.  An
       algorithm is also defined for converting between the
       different units, to ensure a timer's value is not
       distorted by multiple conversions."
   SYNTAX OCTET STRING (SIZE (8))

Timeout ::= TEXTUAL-CONVENTION
   DISPLAY-HINT "d4"
   STATUS current
   DESCRIPTION
      "A STP timer in units of 1/100 seconds

       To convert a Timeout value into a value in units of
       1/256 seconds, the following algorithm should be used:
            b  = floor( (n * 256) / 100)
       where:
            floor   =  quotient [ignore remainder]
            n is the value in 1/100 second units
            b is the value in 1/256 second units
      
       To convert the value from 1/256 second units back to
       1/100 seconds, the following algorithm should be used:
            n = ceiling( (b * 100) / 256)
       where:
            ceiling =  quotient [if remainder is 0], or
                       quotient + 1 [if remainder is non-zero]
            n is the value in 1/100 second units
            b is the value in 1/256 second units

       Note: it is important that the arithmetic operations are
       done in the order specified (i.e., multiply first, divide
       second)."
   SYNTAX INTEGER


dot1dNotifications               OBJECT IDENTIFIER ::= { l2Bridge 0 }
dot1dBase                        OBJECT IDENTIFIER ::= { l2Bridge 1 }
l2Dot1dStp                         OBJECT IDENTIFIER ::= { l2Bridge 2 }
dot1dSr                          OBJECT IDENTIFIER ::= { l2Bridge 3 }
dot1dTp                          OBJECT IDENTIFIER ::= { l2Bridge 4 }
dot1dStatic                      OBJECT IDENTIFIER ::= { l2Bridge 5 }


-- Dot1d Base

dot1dBaseTable OBJECT-TYPE
   SYNTAX        SEQUENCE OF TabDot1dBaseEntry
   MAX-ACCESS    not-accessible
   STATUS        current
   DESCRIPTION
      "List of per Virtual Bridge Module Parameters."
   ::= { dot1dBase 1 }

dot1dBaseEntry OBJECT-TYPE
   SYNTAX       TabDot1dBaseEntry
   MAX-ACCESS   not-accessible
   STATUS       current
   DESCRIPTION
      "Virtual Bridge Rst Module Parameters."
   INDEX { dot1dBaseContextId}
   ::= { dot1dBaseTable 1 }

TabDot1dBaseEntry ::=
   SEQUENCE {
      dot1dBaseContextId
         Integer32,
      dot1dBaseBridgeAddress
         MacAddress,
      dot1dBaseNumPorts
         Integer32,
      dot1dBaseType
         INTEGER
   }

dot1dBaseContextId OBJECT-TYPE
   SYNTAX       Integer32 (0..65535)
   MAX-ACCESS   not-accessible
   STATUS       current
   DESCRIPTION
      "Virtual Bridge number"
   ::= { dot1dBaseEntry 1}

dot1dBaseBridgeAddress OBJECT-TYPE
   SYNTAX       MacAddress
   MAX-ACCESS   read-only
   STATUS       current
   DESCRIPTION
      "The MAC address used by this bridge when it must
       be referred to in a unique fashion.   It is
       recommended that this be the numerically smallest
       MAC address of all ports that belong to this
       bridge.  However it is only required to be unique.
       When concatenated with dot1dStpPriority a unique
       BridgeIdentifier is formed which is used in the
       Spanning Tree Protocol."
   REFERENCE
      "IEEE 802.1D-1990: Sections 6.4.1.1.3 and 3.12.5"
   ::= { dot1dBaseEntry 2 }

dot1dBaseNumPorts OBJECT-TYPE
   SYNTAX       Integer32
   MAX-ACCESS   read-only
   STATUS       current
   DESCRIPTION
      "The number of ports controlled by this bridging entity."
   REFERENCE
      "IEEE 802.1D-1990: Section 6.4.1.1.3"
   ::= { dot1dBaseEntry 3 }

dot1dBaseType OBJECT-TYPE
   SYNTAX      INTEGER {
                unknown(1),
                transparentonly(2),
                sourcerouteonly(3),
                srt(4)
               }
   MAX-ACCESS  read-only
   STATUS      current
   DESCRIPTION
      "Indicates what type of bridging this bridge can
       perform.  If a bridge is actually performing a
       certain type of bridging this will be indicated by
       entries in the port table for the given type."
   ::= { dot1dBaseEntry 4 }

dot1dBasePortTable OBJECT-TYPE
   SYNTAX      SEQUENCE OF TabDot1dBasePortEntry
   MAX-ACCESS  not-accessible
   STATUS      current
   DESCRIPTION
      "A table that contains generic information about
       every port that is associated with this bridge.
       Transparent, source-route, and srt ports are
       included."
   ::= { dot1dBase 2 }

dot1dBasePortEntry OBJECT-TYPE
   SYNTAX    TabDot1dBasePortEntry
   MAX-ACCESS  not-accessible
   STATUS  current
   DESCRIPTION
      "A list of information for each port of the
       bridge."
   REFERENCE
      "IEEE 802.1D-1990: Section 6.4.2, 6.6.1"
   INDEX { dot1dBasePort }
   ::= { dot1dBasePortTable 1 }

TabDot1dBasePortEntry ::=
   SEQUENCE {
      dot1dBasePort
          Integer32,
      dot1dBasePortIfIndex
          Integer32,
      dot1dBasePortCircuit
          OBJECT IDENTIFIER,
      dot1dBasePortDelayExceededDiscards
          Counter32,
      dot1dBasePortMtuExceededDiscards
          Counter32
   }

dot1dBasePort OBJECT-TYPE
   SYNTAX      Integer32 (1..65535)
   MAX-ACCESS  not-accessible
   STATUS      current
   DESCRIPTION
      "The port number of the port for which this entry
       contains bridge management information."
   ::= { dot1dBasePortEntry 1 }

dot1dBasePortIfIndex OBJECT-TYPE
   SYNTAX      Integer32
   MAX-ACCESS  read-only
   STATUS      current
   DESCRIPTION
      "The value of the instance of the ifIndex object,
       defined in MIB-II, for the interface corresponding
       to this port."
   ::= { dot1dBasePortEntry 2 }

dot1dBasePortCircuit OBJECT-TYPE
   SYNTAX      OBJECT IDENTIFIER
   MAX-ACCESS  read-only
   STATUS      current
   DESCRIPTION
      "For a port which (potentially) has the same value
       of dot1dBasePortIfIndex as another port on the
       same bridge, this object contains the name of an
       object instance unique to this port.  For example,
       in the case where multiple ports correspond one-
       to-one with multiple X.25 virtual circuits, this
       value might identify an (e.g., the first) object
       instance associated with the X.25 virtual circuit
       corresponding to this port.
       
       For a port which has a unique value of
       dot1dBasePortIfIndex, this object can have the
       value { 0 0 }."
   ::= { dot1dBasePortEntry 3 }

dot1dBasePortDelayExceededDiscards OBJECT-TYPE
   SYNTAX      Counter32
   MAX-ACCESS  read-only
   STATUS      current
   DESCRIPTION
      "The number of frames discarded by this port due
       to excessive transit delay through the bridge.  It
       is incremented by both transparent and source
       route bridges."
   REFERENCE
      "IEEE 802.1D-1990: Section 6.6.1.1.3"
   ::= { dot1dBasePortEntry 4 }

dot1dBasePortMtuExceededDiscards OBJECT-TYPE
   SYNTAX      Counter32
   MAX-ACCESS  read-only
   STATUS      current
   DESCRIPTION
      "The number of frames discarded by this port due
       to an excessive size.  It is incremented by both
       transparent and source route bridges."
   REFERENCE
      "IEEE 802.1D-1990: Section 6.6.1.1.3"
   ::= { dot1dBasePortEntry 5 }


-- Dot1d STP

dot1dStpTable OBJECT-TYPE
   SYNTAX       SEQUENCE OF TabDot1dStpEntry
   MAX-ACCESS   not-accessible
   STATUS       current
   DESCRIPTION
      "Table of StpScalars per virtual bridge"
   ::= { l2Dot1dStp 1 }

dot1dStpEntry OBJECT-TYPE
   SYNTAX       TabDot1dStpEntry
   MAX-ACCESS   not-accessible
   STATUS       current
   DESCRIPTION
      "Per bridge StpScalars"
   INDEX { dot1dStpContextId }
   ::= { dot1dStpTable 1 }

TabDot1dStpEntry ::=
   SEQUENCE {
      dot1dStpContextId
         Integer32,
      dot1dStpProtocolSpecification
         INTEGER,
      dot1dStpPriority
         Integer32,
      dot1dStpTimeSinceTopologyChange
         TimeTicks,
      dot1dStpTopChanges
         Counter32,
      dot1dStpDesignatedRoot
         BridgeId,
      dot1dStpRootCost
         Integer32,
      dot1dStpRootPort
         Integer32,
      dot1dStpMaxAge
         Timeout,
      dot1dStpHelloTime
         Timeout,
      dot1dStpHoldTime
         Integer32,
      dot1dStpForwardDelay
         Timeout,
      dot1dStpBridgeMaxAge
         Timeout,
      dot1dStpBridgeHelloTime
         Timeout,
      dot1dStpBridgeForwardDelay
         Timeout
   }

dot1dStpContextId OBJECT-TYPE
   SYNTAX       Integer32 (0..65535)
   MAX-ACCESS   not-accessible
   STATUS       current
   DESCRIPTION
      "Virtual Bridge number"
   ::= { dot1dStpEntry 1}


dot1dStpProtocolSpecification OBJECT-TYPE
   SYNTAX      INTEGER {
                unknown(1),
                decLb100(2),
                ieee8021d(3)
               }
   MAX-ACCESS  read-only
   STATUS  current
   DESCRIPTION
      "An indication of what version of the Spanning
       Tree Protocol is being run.  The value
       'decLb100(2)' indicates the DEC LANbridge 100
       Spanning Tree protocol.  IEEE 802.1d
       implementations will return 'ieee8021d(3)'.  If
       enterprise versions of the IEEE Spanning Tree Protocol
       are released that are incompatible with the
       current version a new value will be defined."
   ::= { dot1dStpEntry 2 }

dot1dStpPriority OBJECT-TYPE
   SYNTAX      Integer32 (0..65535)
   MAX-ACCESS  read-write
   STATUS      current
   DESCRIPTION
      "The value of the write-able portion of the Bridge
       ID, i.e., the first two octets of the (8 octet
       long) Bridge ID.  The other (last) 6 octets of the
       Bridge ID are given by the value of
       dot1dBaseBridgeAddress."
   REFERENCE
      "IEEE 802.1D-1990: Section 4.5.3.7"
   ::= { dot1dStpEntry 3 }

dot1dStpTimeSinceTopologyChange OBJECT-TYPE
   SYNTAX      TimeTicks
   MAX-ACCESS  read-only
   STATUS      current
   DESCRIPTION
      "The time (in hundredths of a second) since the
       last time a topology change was detected by the
       bridge entity."
   REFERENCE
      "IEEE 802.1D-1990: Section 6.8.1.1.3"
   ::= { dot1dStpEntry 4 }

dot1dStpTopChanges OBJECT-TYPE
   SYNTAX      Counter32
   MAX-ACCESS  read-only
   STATUS      current
   DESCRIPTION
      "The total number of topology changes detected by
       this bridge since the management entity was last
       reset or initialized."
   REFERENCE
      "IEEE 802.1D-1990: Section 6.8.1.1.3"
   ::= { dot1dStpEntry 5 }

dot1dStpDesignatedRoot OBJECT-TYPE
   SYNTAX      BridgeId
   MAX-ACCESS  read-only
   STATUS      current
   DESCRIPTION
      "The bridge identifier of the root of the spanning
       tree as determined by the Spanning Tree Protocol
       as executed by this node.  This value is used as
       the Root Identifier parameter in all Configuration
       Bridge PDUs originated by this node."
   REFERENCE
      "IEEE 802.1D-1990: Section 4.5.3.1"
   ::= { dot1dStpEntry 6 }

dot1dStpRootCost OBJECT-TYPE
   SYNTAX      Integer32
   MAX-ACCESS  read-only
   STATUS      current
   DESCRIPTION
      "The cost of the path to the root as seen from
       this bridge."
   REFERENCE
      "IEEE 802.1D-1990: Section 4.5.3.2"
   ::= { dot1dStpEntry 7 }

dot1dStpRootPort OBJECT-TYPE
   SYNTAX      Integer32
   MAX-ACCESS  read-only
   STATUS      current
   DESCRIPTION
      "The port number of the port which offers the
       lowest cost path from this bridge to the root
       bridge."
   REFERENCE
      "IEEE 802.1D-1990: Section 4.5.3.3"
   ::= { dot1dStpEntry 8 }

dot1dStpMaxAge OBJECT-TYPE
   SYNTAX      Timeout
   MAX-ACCESS  read-only
   STATUS      current
   DESCRIPTION
      "The maximum age of Spanning Tree Protocol
       information learned from the network on any port
       before it is discarded, in units of hundredths of
       a second.  This is the actual value that this
       bridge is currently using."
   REFERENCE
      "IEEE 802.1D-1990: Section 4.5.3.4"
   ::= { dot1dStpEntry 9 }

dot1dStpHelloTime OBJECT-TYPE
   SYNTAX      Timeout
   MAX-ACCESS  read-only
   STATUS      current
   DESCRIPTION
      "The amount of time between the transmission of
       Configuration bridge PDUs by this node on any port
       when it is the root of the spanning tree or trying
       to become so, in units of hundredths of a second.
       This is the actual value that this bridge is
       currently using."
   REFERENCE
      "IEEE 802.1D-1990: Section 4.5.3.5"
   ::= { dot1dStpEntry 10 }

dot1dStpHoldTime OBJECT-TYPE
   SYNTAX      Integer32
   MAX-ACCESS  read-only
   STATUS      current
   DESCRIPTION
      "This time value determines the interval length
       during which no more than two Configuration bridge
       PDUs shall be transmitted by this node, in units
       of hundredths of a second."
   REFERENCE
      "IEEE 802.1D-1990: Section 4.5.3.14"
   ::= { dot1dStpEntry 11 }

dot1dStpForwardDelay OBJECT-TYPE
   SYNTAX      Timeout
   MAX-ACCESS  read-only
   STATUS      current
   DESCRIPTION
      "This time value, measured in units of hundredths
       of a second, controls how fast a port changes its
       spanning state when moving towards the Forwarding
       state.  The value determines how long the port
       stays in each of the Listening and Learning
       states, which precede the Forwarding state.  This
       value is also used, when a topology change has
       been detected and is underway, to age all dynamic
       entries in the Forwarding Database.  [Note that
       this value is the one that this bridge is
       currently using, in contrast to
       dot1dStpBridgeForwardDelay which is the value that
       this bridge and all others would start using
       if/when this bridge were to become the root.]"
   REFERENCE
      "IEEE 802.1D-1990: Section 4.5.3.6"
   ::= { dot1dStpEntry 12 }

dot1dStpBridgeMaxAge OBJECT-TYPE
   SYNTAX      Timeout (600..4000)
   MAX-ACCESS  read-write
   STATUS      current
   DESCRIPTION
      "The value that all bridges use for MaxAge when
       this bridge is acting as the root.  Note that
       802.1D-1990 specifies that the range for this
       parameter is related to the value of
       dot1dStpBridgeHelloTime. The granularity of this
       timer is specified by 802.1D-1990 to be 1 second.
       An agent may return a badValue error if a set is
       attempted to a value which is not a whole number
       of seconds."
   REFERENCE
      "IEEE 802.1D-1990: Section 4.5.3.8"
   ::= { dot1dStpEntry 13 }

dot1dStpBridgeHelloTime OBJECT-TYPE
   SYNTAX      Timeout (100..200)
   MAX-ACCESS  read-write
   STATUS      current
   DESCRIPTION
      "The value that all bridges use for HelloTime when
       this bridge is acting as the root.  The
       granularity of this timer is specified by 802.1D-
       1990 to be 1 second.  An agent may return a
       badValue error if a set is attempted to a value
       which is not a whole number of seconds."
   REFERENCE
      "IEEE 802.1D-1990: Section 4.5.3.9"
   ::= { dot1dStpEntry 14 }

dot1dStpBridgeForwardDelay OBJECT-TYPE
   SYNTAX      Timeout (400..3000)
   MAX-ACCESS  read-write
   STATUS      current
   DESCRIPTION
      "The value that all bridges use for ForwardDelay
       when this bridge is acting as the root.  Note that
       802.1D-1990 specifies that the range for this
       parameter is related to the value of
       dot1dStpBridgeMaxAge.  The granularity of this
       timer is specified by 802.1D-1990 to be 1 second.
       An agent may return a badValue error if a set is
       attempted to a value which is not a whole number
       of seconds."
   REFERENCE
      "IEEE 802.1D-1990: Section 4.5.3.10"
   ::= { dot1dStpEntry 15 }

dot1dStpPortTable OBJECT-TYPE
   SYNTAX      SEQUENCE OF TabDot1dStpPortEntry
   MAX-ACCESS  not-accessible
   STATUS      current
   DESCRIPTION
      "A table that contains port-specific information
       for the Spanning Tree Protocol."
   ::= { l2Dot1dStp 2 }

dot1dStpPortEntry OBJECT-TYPE
   SYNTAX      TabDot1dStpPortEntry
   MAX-ACCESS  not-accessible
   STATUS      current
   DESCRIPTION
      "A list of information maintained by every port
       about the Spanning Tree Protocol state for that
       port."
   INDEX { dot1dStpPort }
   ::= { dot1dStpPortTable 1 }

TabDot1dStpPortEntry ::=
   SEQUENCE {
      dot1dStpPort
         Integer32,
      dot1dStpPortPriority
         Integer32,
      dot1dStpPortState
         INTEGER,
      dot1dStpPortEnable
         INTEGER,
      dot1dStpPortPathCost
         Integer32,
      dot1dStpPortDesignatedRoot
         BridgeId,
      dot1dStpPortDesignatedCost
         INTEGER,
      dot1dStpPortDesignatedBridge
         BridgeId,
      dot1dStpPortDesignatedPort
         OCTET STRING,
      dot1dStpPortForwardTransitions
         Counter32
   }

dot1dStpPort OBJECT-TYPE
   SYNTAX      Integer32 (1..65535)
   MAX-ACCESS  not-accessible
   STATUS      current
   DESCRIPTION
      "The port number of the port for which this entry
       contains Spanning Tree Protocol management
       information."
   REFERENCE
      "IEEE 802.1D-1990: Section 6.8.2.1.2"
   ::= { dot1dStpPortEntry 1 }

dot1dStpPortPriority OBJECT-TYPE
   SYNTAX      Integer32 (0..255)
   MAX-ACCESS  read-write
   STATUS      current
   DESCRIPTION
      "The value of the priority field which is
       contained in the first (in network byte order)
       octet of the (2 octet long) Port ID.  The other
       octet of the Port ID is given by the value of
       dot1dStpPort."
   REFERENCE
      "IEEE 802.1D-1990: Section 4.5.5.1"
   ::= { dot1dStpPortEntry 2 }

dot1dStpPortState OBJECT-TYPE
   SYNTAX      INTEGER {
                disabled(1),
                blocking(2),
                listening(3),
                learning(4),
                forwarding(5),
                broken(6)
               }
   MAX-ACCESS  read-only
   STATUS      current
   DESCRIPTION
      "The port's current state as defined by
       application of the Spanning Tree Protocol.  This
       state controls what action a port takes on
       reception of a frame.  If the bridge has detected
       a port that is malfunctioning it will place that
       port into the broken(6) state.  For ports which
       are disabled (see dot1dStpPortEnable), this object
       will have a value of disabled(1)."
   REFERENCE
      "IEEE 802.1D-1990: Section 4.5.5.2"
   ::= { dot1dStpPortEntry 3 }

dot1dStpPortEnable OBJECT-TYPE
   SYNTAX      INTEGER {
                enabled(1),
                disabled(2)
               }
   MAX-ACCESS  read-write
   STATUS      current
   DESCRIPTION
      "The enabled/disabled status of the port."
   REFERENCE
      "IEEE 802.1D-1990: Section 4.5.5.2"
   ::= { dot1dStpPortEntry 4 }

dot1dStpPortPathCost OBJECT-TYPE
   SYNTAX      Integer32 (1..65535)
   MAX-ACCESS  read-write
   STATUS      current
   DESCRIPTION
      "The contribution of this port to the path cost of
       paths towards the spanning tree root which include
       this port.  802.1D-1990 recommends that the
       default value of this parameter be in inverse
       proportion to the speed of the attached LAN."
   REFERENCE
      "IEEE 802.1D-1990: Section 4.5.5.3"
   ::= { dot1dStpPortEntry 5 }

dot1dStpPortDesignatedRoot OBJECT-TYPE
   SYNTAX      BridgeId
   MAX-ACCESS  read-only
   STATUS      current
   DESCRIPTION
      "The unique Bridge Identifier of the Bridge
       recorded as the Root in the Configuration BPDUs
       transmitted by the Designated Bridge for the
       segment to which the port is attached."
   REFERENCE
      "IEEE 802.1D-1990: Section 4.5.5.4"
   ::= { dot1dStpPortEntry 6 }

dot1dStpPortDesignatedCost OBJECT-TYPE
   SYNTAX      INTEGER
   MAX-ACCESS  read-only
   STATUS      current
   DESCRIPTION
      "The path cost of the Designated Port of the
       segment connected to this port.  This value is
       compared to the Root Path Cost field in received
       bridge PDUs."
   REFERENCE
      "IEEE 802.1D-1990: Section 4.5.5.5"
   ::= { dot1dStpPortEntry 7 }

dot1dStpPortDesignatedBridge OBJECT-TYPE
   SYNTAX      BridgeId
   MAX-ACCESS  read-only
   STATUS      current
   DESCRIPTION
      "The Bridge Identifier of the bridge which this
       port considers to be the Designated Bridge for
       this port's segment."
   REFERENCE
      "IEEE 802.1D-1990: Section 4.5.5.6"
   ::= { dot1dStpPortEntry 8 }

dot1dStpPortDesignatedPort OBJECT-TYPE
   SYNTAX      OCTET STRING (SIZE (2))
   MAX-ACCESS  read-only
   STATUS      current
   DESCRIPTION
      "The Port Identifier of the port on the Designated
       Bridge for this port's segment."
   REFERENCE
      "IEEE 802.1D-1990: Section 4.5.5.7"
   ::= { dot1dStpPortEntry 9 }

dot1dStpPortForwardTransitions OBJECT-TYPE
   SYNTAX      Counter32
   MAX-ACCESS  read-only
   STATUS      current
   DESCRIPTION
      "The number of times this port has transitioned
       from the Learning state to the Forwarding state."
   ::= { dot1dStpPortEntry 10 }


-- Dot1d TP

dot1dTpTable OBJECT-TYPE
   SYNTAX       SEQUENCE OF TabDot1dTpEntry
   MAX-ACCESS   not-accessible
   STATUS       current
   DESCRIPTION
      "Table of Tp per virtual bridge"
   ::= { dot1dTp 1 }

dot1dTpEntry OBJECT-TYPE
   SYNTAX       TabDot1dTpEntry
   MAX-ACCESS   not-accessible
   STATUS       current
   DESCRIPTION
      "Per bridge TpScalars"
   INDEX { dot1dBaseContextId}
   ::= { dot1dTpTable 1 }

TabDot1dTpEntry ::=
   SEQUENCE {
      dot1dTpLearnedEntryDiscards
         Counter32,
      dot1dTpAgingTime
         INTEGER
   }

dot1dTpLearnedEntryDiscards OBJECT-TYPE
   SYNTAX      Counter32
   MAX-ACCESS  read-only
   STATUS      current
   DESCRIPTION
      "The total number of Forwarding Database entries,
       which have been or would have been learned, but
       have been discarded due to a lack of space to
       store them in the Forwarding Database.  If this
              counter is increasing, it indicates that the
       Forwarding Database is regularly becoming full (a
       condition which has unpleasant performance effects
              on the subnetwork).  If this counter has a
       significant value but is not presently increasing,
       it indicates that the problem has been occurring
       but is not persistent."
   REFERENCE
      "IEEE 802.1D-1990: Section 6.7.1.1.3"
   ::= {dot1dTpEntry 1 }

dot1dTpAgingTime OBJECT-TYPE
   SYNTAX       INTEGER (10..600)
   MAX-ACCESS   read-write
   STATUS       current
   DESCRIPTION
      "The timeout period in seconds for aging out
       dynamically learned forwarding information.
       802.1D-1990 recommends a default of 300 seconds."
   REFERENCE
      "IEEE 802.1D-1990: Section 6.7.1.1.3"
   ::= { dot1dTpEntry 2 }


--  Dot1d FDB

dot1dTpFdbTable OBJECT-TYPE
   SYNTAX      SEQUENCE OF TabDot1dTpFdbEntry
   MAX-ACCESS  not-accessible
   STATUS      current
   DESCRIPTION
      "A table that contains information about unicast
       entries for which the bridge has forwarding and/or
       filtering information.  This information is used
       by the transparent bridging function in
       determining how to propagate a received frame. This
       table maintains context ID as one more index to
       support Multiple Instances."
   ::= { dot1dTp 2 }

dot1dTpFdbEntry OBJECT-TYPE
   SYNTAX  TabDot1dTpFdbEntry
   MAX-ACCESS  not-accessible
   STATUS  current
   DESCRIPTION
      "Information about a specific unicast MAC address
       for which the bridge has some forwarding and/or
       filtering information."
   INDEX { dot1dBaseContextId, dot1dTpFdbAddress }
   ::= { dot1dTpFdbTable 1 }

TabDot1dTpFdbEntry ::=
   SEQUENCE {
      dot1dTpFdbAddress
         MacAddress,
      dot1dTpFdbPort
         Integer32,
      dot1dTpFdbStatus
         INTEGER
   }

dot1dTpFdbAddress OBJECT-TYPE
   SYNTAX      MacAddress
   MAX-ACCESS  not-accessible
   STATUS      current
   DESCRIPTION
      "A unicast MAC address for which the bridge has
       forwarding and/or filtering information."
   REFERENCE
      "IEEE 802.1D-1990: Section 3.9.1, 3.9.2"
   ::= { dot1dTpFdbEntry 1 }

dot1dTpFdbPort OBJECT-TYPE
   SYNTAX      Integer32
   MAX-ACCESS  read-only
   STATUS      current
   DESCRIPTION
      "Either the value '0', or the port number of the
       port on which a frame having a source address
       equal to the value of the corresponding instance
       of dot1dTpFdbAddress has been seen.  A value of
       '0' indicates that the port number has not been
       learned but that the bridge does have some
       forwarding/filtering information about this
       address (e.g. in the dot1dStaticTable).
       Implementors are encouraged to assign the port
       value to this object whenever it is learned even
       for addresses for which the corresponding value of
       dot1dTpFdbStatus is not learned(3)."
   ::= { dot1dTpFdbEntry 2 }

dot1dTpFdbStatus OBJECT-TYPE
   SYNTAX      INTEGER {
                other(1),
                invalid(2),
                learned(3),
                self(4),
                mgmt(5)
               }
   MAX-ACCESS  read-only
   STATUS      current
   DESCRIPTION
      "The status of this entry.  The meanings of the
       values are:
      
       other(1)   : none of the following.  This would
                    include the case where some other
                    MIB object (not the corresponding
                    instance of dot1dTpFdbPort, nor an
                    entry in the dot1dStaticTable) is
                    being used to determine if and how
                    frames addressed to the value of
                    the corresponding instance of
                    dot1dTpFdbAddress are being
                    forwarded.
      
       invalid(2) : this entry is not longer valid
                    (e.g., it was learned but has since
                    aged-out), but has not yet been
                    flushed from the table.
      
       learned(3) : the value of the corresponding
                    instance of dot1dTpFdbPort was
             learned, and is being used.
      
       self(4)    : the value of the corresponding
             instance of dot1dTpFdbAddress
             represents one of the bridge's
             addresses.  The corresponding
                    instance of dot1dTpFdbPort
             indicates which of the bridge's
             ports has this address.
      
       mgmt(5)    : the value of the corresponding
                    instance of dot1dTpFdbAddress is
                    also the value of an existing
                    instance of dot1dStaticAddress."
   ::= { dot1dTpFdbEntry 3 }

dot1dTpPortTable OBJECT-TYPE
   SYNTAX      SEQUENCE OF TabDot1dTpPortEntry
   MAX-ACCESS  not-accessible
   STATUS      current
   DESCRIPTION
      "A table that contains information about every
       port that is associated with this transparent
       bridge."
   ::= { dot1dTp 3 }

dot1dTpPortEntry OBJECT-TYPE
   SYNTAX      TabDot1dTpPortEntry
   MAX-ACCESS  not-accessible
   STATUS      current
   DESCRIPTION
      "A list of information for each port of a
       transparent bridge."
   INDEX { dot1dTpPort }
   ::= { dot1dTpPortTable 1 }

TabDot1dTpPortEntry ::=
   SEQUENCE {
      dot1dTpPort
         Integer32,
      dot1dTpPortMaxInfo
         Integer32,
      dot1dTpPortInFrames
         Counter32,
      dot1dTpPortOutFrames
         Counter32,
      dot1dTpPortInDiscards
         Counter32
   }

dot1dTpPort OBJECT-TYPE
   SYNTAX      Integer32 (1..65535)
   MAX-ACCESS  not-accessible
   STATUS      current
   DESCRIPTION
      "The port number of the port for which this entry
       contains Transparent bridging management
       information."
   ::= { dot1dTpPortEntry 1 }

dot1dTpPortMaxInfo OBJECT-TYPE
   SYNTAX      Integer32
   MAX-ACCESS  read-only
   STATUS      current
   DESCRIPTION
      "The maximum size of the INFO (non-MAC) field that
       this port will receive or transmit."
   ::= { dot1dTpPortEntry 2 }

dot1dTpPortInFrames OBJECT-TYPE
   SYNTAX      Counter32
   MAX-ACCESS  read-only
   STATUS      current
   DESCRIPTION
      "The number of frames that have been received by
       this port from its segment. Note that a frame
       received on the interface corresponding to this
       port is only counted by this object if and only if
       it is for a protocol being processed by the local
       bridging function, including bridge management
       frames."
   REFERENCE
      "IEEE 802.1D-1990: Section 6.6.1.1.3"
   ::= { dot1dTpPortEntry 3 }

dot1dTpPortOutFrames OBJECT-TYPE
   SYNTAX      Counter32
   MAX-ACCESS  read-only
   STATUS      current
   DESCRIPTION
      "The number of frames that have been transmitted
       by this port to its segment.  Note that a frame
       transmitted on the interface corresponding to this
       port is only counted by this object if and only if
       it is for a protocol being processed by the local
       bridging function, including bridge management
       frames."
   REFERENCE
      "IEEE 802.1D-1990: Section 6.6.1.1.3"
   ::= { dot1dTpPortEntry 4 }

dot1dTpPortInDiscards OBJECT-TYPE
   SYNTAX       Counter32
   MAX-ACCESS   read-only
   STATUS       current
   DESCRIPTION
      "Count of valid frames received which were
       discarded (i.e., filtered) by the Forwarding
       Process."
   REFERENCE
      "IEEE 802.1D-1990: Section 6.6.1.1.3"
   ::= { dot1dTpPortEntry 5 }


-- Dot1d Static

dot1dStaticTable OBJECT-TYPE
   SYNTAX      SEQUENCE OF TabDot1dStaticEntry
   MAX-ACCESS  not-accessible
   STATUS      current
   DESCRIPTION
      "A table containing filtering information
       configured into the bridge by (local or network)
       management specifying the set of ports to which
       frames received from specific ports and containing
       specific destination addresses are allowed to be
       forwarded.  The value of zero in this table as the
       port number from which frames with a specific
       destination address are received, is used to
       specify all ports for which there is no specific
       entry in this table for that particular
       destination address.  Entries are valid for
       unicast and for group/broadcast addresses.This
       table maintains context ID as one more index to
       support Multiple Instances."
   REFERENCE
      "IEEE 802.1D-1990: Section 6.7.2"
   ::= { dot1dStatic 1 }

dot1dStaticEntry OBJECT-TYPE
   SYNTAX      TabDot1dStaticEntry
   MAX-ACCESS  not-accessible
   STATUS      current
   DESCRIPTION
      "Filtering information configured into the bridge
       by (local or network) management specifying the
       set of ports to which frames received from a
       specific port and containing a specific
       destination address are allowed to be forwarded."
   REFERENCE
      "IEEE 802.1D-1990: Section 6.7.2"
   INDEX { dot1dBaseContextId,
           dot1dStaticAddress, dot1dStaticReceivePort }
   ::= { dot1dStaticTable 1 }

TabDot1dStaticEntry ::=
   SEQUENCE {
      dot1dStaticAddress
         MacAddress,
      dot1dStaticReceivePort
         INTEGER,
      dot1dStaticRowStatus
         RowStatus,
      dot1dStaticStatus
         INTEGER
   }

dot1dStaticAddress OBJECT-TYPE
   SYNTAX      MacAddress
   MAX-ACCESS  not-accessible
   STATUS      current
   DESCRIPTION
      "The destination MAC address in a frame to which
       this entry's filtering information applies.  This
       object can take the value of a unicast address, a
       group address or the broadcast address."
   REFERENCE
      "IEEE 802.1D-1990: Section 3.9.1, 3.9.2"
   ::= { dot1dStaticEntry 1 }

dot1dStaticReceivePort OBJECT-TYPE
   SYNTAX      INTEGER (0..65535)
   MAX-ACCESS  not-accessible
   STATUS      current
   DESCRIPTION
      "Either the value '0', or the port number of the
       port from which a frame must be received in order
       for this entry's filtering information to apply.
       A value of zero indicates that this entry applies
       on all ports of the bridge for which there is no
       other applicable entry."
   ::= { dot1dStaticEntry 2 }

dot1dStaticRowStatus OBJECT-TYPE
   SYNTAX      RowStatus
   MAX-ACCESS  read-create
   STATUS      current
   DESCRIPTION
      "This object indicates the status of the AllowedToGoTo
       PortList to which a frame with a specific unicast
       address will be flooded in the event that it has not
       been learned. To fill the AllowedToGoTo portlist,
       we have to set the rowstatus as 'NOT_IN_SERVICE' and
       set the appropriate port in the
       dot1dStaticAllowedToGoTable and set the rowstatus as
       'ACTIVE' to make the portlist available."
   ::= { dot1dStaticEntry 3 }

dot1dStaticStatus OBJECT-TYPE
   SYNTAX      INTEGER {
                other(1),
                invalid(2),
                permanent(3),
                deleteOnReset(4),
                deleteOnTimeout(5)
               }
   MAX-ACCESS  read-write
   STATUS      current
   DESCRIPTION
      "This object indicates the status of this entry.
       The default value is permanent(3).
     
       other(1) - this entry is currently in use but
            the conditions under which it will
            remain so are different from each of the
            following values.
       invalid(2) - writing this value to the object
            removes the corresponding entry.
       permanent(3) - this entry is currently in use
            and will remain so after the next reset
            of the bridge.
       deleteOnReset(4) - this entry is currently in
            use and will remain so until the next
            reset of the bridge.
       deleteOnTimeout(5) - this entry is currently
            in use and will remain so until it is
            aged out."
   ::= { dot1dStaticEntry 4 }

dot1dStaticAllowedToGoTable OBJECT-TYPE
   SYNTAX      SEQUENCE OF TabDot1dStaticAllowedToGoEntry
   MAX-ACCESS  not-accessible
   STATUS      current
   DESCRIPTION
      "A table containing the information of AllowedToGoTo
       ports for each static unicast entry. This table
       maintains context ID as one more index to support
       Multiple Instances."
   ::= { dot1dStatic 2 }

dot1dStaticAllowedToGoEntry OBJECT-TYPE
   SYNTAX      TabDot1dStaticAllowedToGoEntry
   MAX-ACCESS  not-accessible
   STATUS      current
   DESCRIPTION
      "Information about a port, Whether it is an AllowedToGoTo
       member or not."
   INDEX   { dot1dBaseContextId, dot1dStaticAddress,
             dot1dStaticReceivePort, dot1dTpPort }
   ::= { dot1dStaticAllowedToGoTable 1 }

TabDot1dStaticAllowedToGoEntry ::=
   SEQUENCE {
      dot1dStaticAllowedIsMember
         TruthValue
   }

dot1dStaticAllowedIsMember OBJECT-TYPE
   SYNTAX      TruthValue
   MAX-ACCESS  read-write
   STATUS      current
   DESCRIPTION
      "Indicates whether the port is an allowedToGoTo member."
   ::= { dot1dStaticAllowedToGoEntry 1 }


-- Dot1d Notification

newRoot NOTIFICATION-TYPE
   STATUS             current
   DESCRIPTION
      "The newRoot trap indicates that the sending agent
       has become the new root of the Spanning Tree; the
       trap is sent by a bridge soon after its election
       as the new root, e.g., upon expiration of the
       Topology Change Timer immediately subsequent to
       its election.  Implementation of this trap is
       optional."
   ::= { dot1dNotifications 1 }

topologyChange NOTIFICATION-TYPE
   STATUS             current
   DESCRIPTION
      "A topologyChange trap is sent by a bridge when
       any of its configured ports transitions from the
       Learning state to the Forwarding state, or from
       the Forwarding state to the Blocking state.  The
       trap is not sent if a newRoot trap is sent for the
       same transition.  Implementation of this trap is
       optional."
   ::= { dot1dNotifications 2 }






dot1dStpExtTable OBJECT-TYPE
   SYNTAX       SEQUENCE OF TabDot1dStpExtEntry
   MAX-ACCESS   not-accessible
   STATUS       current
   DESCRIPTION
      "Table of ExtStpScalars per Virtual Context."
   ::= { l2Dot1dStp 3 }

dot1dStpExtEntry OBJECT-TYPE
   SYNTAX       TabDot1dStpExtEntry
   MAX-ACCESS   not-accessible
   STATUS       current
   DESCRIPTION
      "Per Virtual Context Stp Scalars"
   AUGMENTS { dot1dStpEntry }
   ::= { dot1dStpExtTable 1 }

TabDot1dStpExtEntry ::=
   SEQUENCE {
      dot1dStpVersion
         INTEGER,
      dot1dStpTxHoldCount
         Integer32,
      dot1dStpPathCostDefault
         INTEGER
   }

dot1dStpVersion OBJECT-TYPE
   SYNTAX      INTEGER {
                stpCompatible(0),
                rstp(2)
               }
   MAX-ACCESS  read-write
   STATUS      current
   DESCRIPTION
      "The version of Spanning Tree Protocol the bridge is
       currently running.  The value 'stpCompatible(0)'
       indicates the Spanning Tree Protocol specified in
       IEEE 802.1D and 'rstp(2)' indicates the Rapid Spanning
       Tree Protocol specified in IEEE 802.1w.  New value may
       be defined as future versions of the protocol become
       available."
   REFERENCE
      "IEEE 802.1w clause 14.8.1, 17.12, 17.16.1"
   DEFVAL { rstp }
   ::= { dot1dStpExtEntry 1 }

dot1dStpTxHoldCount OBJECT-TYPE
   SYNTAX      Integer32 (1..10)
   MAX-ACCESS  read-write
   STATUS      current
   DESCRIPTION
      "The value used by the Port Transmit state machine to limit
       the maximum transmission rate."
   REFERENCE
      "IEEE 802.1w clause 17.16.6"
   DEFVAL { 3 }
   ::= { dot1dStpExtEntry 2 }

dot1dStpPathCostDefault OBJECT-TYPE
   SYNTAX      INTEGER {
                stp8021d1998(1),
                stp8021t2001(2)
               }
   MAX-ACCESS  read-write
   STATUS      current
   DESCRIPTION
      "The version of the Spanning Tree default Path Costs that
       are to be used by this Bridge.  A value of 8021d1998(1)
       uses the 16-bit default Path Costs from IEEE Std. 802.1D-1998.
       A value of stp8021t2001(2) uses the 32-bit default Path
       Costs from IEEE Std. 802.1t."
   REFERENCE
      "IEEE 802.1D & 802.1t Table 8-5"
   ::= { dot1dStpExtEntry 3 }

dot1dStpExtPortTable OBJECT-TYPE
   SYNTAX      SEQUENCE OF TabDot1dStpExtPortEntry
   MAX-ACCESS  not-accessible
   STATUS      current
   DESCRIPTION
      "A table that contains port-specific Rapid Spanning Tree
       information."
   ::= { l2Dot1dStp 4 }

dot1dStpExtPortEntry OBJECT-TYPE
   SYNTAX      TabDot1dStpExtPortEntry
   MAX-ACCESS  not-accessible
   STATUS      current
   DESCRIPTION
      "A list of Rapid Spanning Tree information maintained by
       each port."
   AUGMENTS    { dot1dStpPortEntry }
   ::= { dot1dStpExtPortTable 1 }

TabDot1dStpExtPortEntry ::=
   SEQUENCE {
      dot1dStpPortProtocolMigration
          TruthValue,
      dot1dStpPortAdminEdgePort
          TruthValue,
      dot1dStpPortOperEdgePort
          TruthValue,
      dot1dStpPortAdminPointToPoint
          INTEGER,
      dot1dStpPortOperPointToPoint
          TruthValue
   }

dot1dStpPortProtocolMigration OBJECT-TYPE
   SYNTAX      TruthValue
   MAX-ACCESS  read-write
   STATUS      current
   DESCRIPTION
      "When operating in RSTP (version 2) mode, writing TRUE(1)
       to this object forces this port to transmit RSTP BPDUs.
       Any other operation on this object has no effect and
       it always returns FALSE(2) when read."
   REFERENCE
      "IEEE 802.1w clause 14.8.2.4, 17.18.10, 17.26"
   ::= { dot1dStpExtPortEntry 1 }

dot1dStpPortAdminEdgePort OBJECT-TYPE
   SYNTAX      TruthValue
   MAX-ACCESS  read-write
   STATUS      current
   DESCRIPTION
      "The administrative value of the Edge Port parameter.  A
       value of TRUE(1) indicates that this port should be
       assumed as an edge-port and a value of FALSE(2) indicates
       that this port should be assumed as a non-edge-port."
   REFERENCE
      "IEEE 802.1t clause 14.8.2, 18.3.3"
   ::= { dot1dStpExtPortEntry 2 }

dot1dStpPortOperEdgePort OBJECT-TYPE
   SYNTAX      TruthValue
   MAX-ACCESS  read-only
   STATUS      current
   DESCRIPTION
      "The operational value of the Edge Port parameter.  The
       object is initialized to the value of
       dot1dStpPortAdminEdgePort and is set FALSE on reception of
       a BPDU."
   REFERENCE
      "IEEE 802.1t clause 14.8.2, 18.3.4"
   ::= { dot1dStpExtPortEntry 3 }

dot1dStpPortAdminPointToPoint OBJECT-TYPE
   SYNTAX      INTEGER {
                forceTrue(0),
                forceFalse(1),
                auto(2)
               }
   MAX-ACCESS  read-write
   STATUS      current
   DESCRIPTION
      "The administrative point-to-point status of the LAN segment
       attached to this port.  A value of forceTrue(0) indicates that
       this port should always be treated as if it is connected to
       a point-to-point link.  A value of forceFalse(1) indicates
       that this port should be treated as having a shared media
       connection.  A value of auto(2) indicates that this port is
       considered to have a point-to-point link if it is an Aggregator
       and all of its members are aggregatable, or if the MAC entity
       is configured for full duplex operation, either through
       auto-negotiation or by management means."
   REFERENCE
      "IEEE 802.1w clause 6.4.3, 6.5, 14.8.2"
   ::= { dot1dStpExtPortEntry 4 }

dot1dStpPortOperPointToPoint OBJECT-TYPE
   SYNTAX      TruthValue
   MAX-ACCESS  read-only
   STATUS      current
   DESCRIPTION
      "The operational point-to-point status of the LAN segment
       attached to this port.  It indicates whether a port is
       considered to have a point-to-point connection or not.
       The value is determined by management or by auto-detection,
       as described in the dot1dStpPortAdminPointToPoint object."
   REFERENCE
      "IEEE 802.1w clause 6.4.3, 6.5, 14.8.2"
   ::= { dot1dStpExtPortEntry 5 }





EnabledStatus ::= TEXTUAL-CONVENTION
   STATUS current
   DESCRIPTION
      "A simple status value for the object."
   SYNTAX INTEGER { enabled(1), disabled(2) }


dot1dMIBObjects      OBJECT IDENTIFIER ::= { dot1dPBridge 1 }

dot1dExtBase         OBJECT IDENTIFIER ::= { dot1dMIBObjects 1 }
dot1dPriority        OBJECT IDENTIFIER ::= { dot1dMIBObjects 2 }
dot1dGarp            OBJECT IDENTIFIER ::= { dot1dMIBObjects 3 }

dot1dConformance     OBJECT IDENTIFIER ::= { dot1dPBridge 2 }

dot1dGroups          OBJECT IDENTIFIER ::= { dot1dConformance 1 }
dot1dCompliances     OBJECT IDENTIFIER ::= { dot1dConformance 2 }


-- P Bridge Ext Base

dot1dExtBaseTable OBJECT-TYPE
   SYNTAX        SEQUENCE OF TabDot1dExtBaseEntry
   MAX-ACCESS    not-accessible
   STATUS        current
   DESCRIPTION
      "List of dot1dExtBase group objects that can be configured per
       virtual context in the system."
   ::= { dot1dExtBase 1 }

dot1dExtBaseEntry OBJECT-TYPE
   SYNTAX       TabDot1dExtBaseEntry
   MAX-ACCESS   not-accessible
   STATUS       current
   DESCRIPTION
      "dot1dExtBase group objects per virtual context."
   INDEX { dot1dBridgeContextId }
   ::= { dot1dExtBaseTable 1 }

TabDot1dExtBaseEntry ::=
   SEQUENCE {
      dot1dBridgeContextId
         Integer32,
      dot1dDeviceCapabilities
         BITS,
      dot1dTrafficClassesEnabled
         TruthValue,
      dot1dGmrpStatus
         EnabledStatus
   }

dot1dBridgeContextId OBJECT-TYPE
   SYNTAX        Integer32 (0..65535)
   MAX-ACCESS    not-accessible
   STATUS        current
   DESCRIPTION
      "Identifies the virtual context."
   ::= {dot1dExtBaseEntry 1 }

dot1dDeviceCapabilities OBJECT-TYPE
   SYNTAX      BITS {
                dot1dExtendedFilteringServices(0),
                                      -- can perform filtering of
                                      -- individual multicast addresses
                                      -- controlled by GMRP.
                dot1dTrafficClasses(1),
                                      -- can map user priority to
                                      -- multiple traffic classes.
                dot1qStaticEntryIndividualPort(2),
                                      -- epDot1qStaticUnicastReceivePort &
                                      -- epDot1qStaticMulticastReceivePort
                                      -- can represent non-zero entries.
                dot1qIVLCapable(3),   -- Independent VLAN Learning.
                dot1qSVLCapable(4),   -- Shared VLAN Learning.
                dot1qHybridCapable(5),
                                      -- both IVL & SVL simultaneously.
                dot1qConfigurablePvidTagging(6),
                                      -- whether the implementation
                                      -- supports the ability to
                                      -- override the default PVID
                                      -- setting and its egress status
                                      -- (VLAN-Tagged or Untagged) on
                                      -- each port.
                dot1dLocalVlanCapable(7)
                                      -- can support multiple local
                                      -- bridges, outside of the scope
                                       -- of 802.1Q defined VLANs.
               }
   MAX-ACCESS  read-only
   STATUS      current
   DESCRIPTION
      "Indicates the optional parts of IEEE 802.1D and 802.1Q
       that are implemented by this device and are manageable
       through this MIB.  Capabilities that are allowed on a
       per-port basis are indicated in dot1dPortCapabilities."
   REFERENCE
      "ISO/IEC 15802-3 Section 5.2,
       IEEE 802.1Q/D11 Section 5.2, 12.10.1.1.3/b/2"
   ::= { dot1dExtBaseEntry 2 }

dot1dTrafficClassesEnabled OBJECT-TYPE
   SYNTAX      TruthValue
   MAX-ACCESS  read-write
   STATUS      current
   DESCRIPTION
      "The value true(1) indicates that Traffic Classes are
       enabled on this bridge.  When false(2), the bridge
       operates with a single priority level for all traffic."
   DEFVAL { true }
   ::= { dot1dExtBaseEntry 3 }

dot1dGmrpStatus OBJECT-TYPE
    SYNTAX      EnabledStatus
    MAX-ACCESS  read-write
    STATUS      current
    DESCRIPTION
        "The administrative status requested by management for
        GMRP.  The value enabled(1) indicates that GMRP should
        be enabled on this device, in all VLANs, on all ports
        for which it has not been specifically disabled.  When
        disabled(2), GMRP is disabled, in all VLANs and on all
        ports, and all GMRP packets will be forwarded
        transparently.  This object affects both Applicant and
        Registrar state machines.  A transition from disabled(2)
        to enabled(1) will cause a reset of all GMRP state
        machines on all ports.

        The value of this object MUST be retained across
        reinitializations of the management system."
    DEFVAL      { enabled }
    ::= { dot1dExtBaseEntry 4 }

dot1dPortCapabilitiesTable OBJECT-TYPE
   SYNTAX      SEQUENCE OF TabDot1dPortCapabilitiesEntry
   MAX-ACCESS  not-accessible
   STATUS      current
   DESCRIPTION
      "A table that contains capabilities information about
       every port that is associated with this bridge."
   ::= { dot1dExtBase 2 }

dot1dPortCapabilitiesEntry OBJECT-TYPE
   SYNTAX      TabDot1dPortCapabilitiesEntry
   MAX-ACCESS  not-accessible
   STATUS      current
   DESCRIPTION
      "A set of capabilities information about this port
       indexed by dot1dBasePort."
   AUGMENTS { dot1dBasePortEntry }
   ::= { dot1dPortCapabilitiesTable 1 }

TabDot1dPortCapabilitiesEntry ::=
   SEQUENCE {
      dot1dPortCapabilities
         BITS
   }

dot1dPortCapabilities OBJECT-TYPE
   SYNTAX      BITS {
                dot1qDot1qTagging(0), -- supports 802.1Q VLAN tagging of
                                      -- frames and GVRP.
                dot1qConfigurableAcceptableFrameTypes(1),
                                      -- allows modified values of
                                      -- epDot1qPortAcceptableFrameTypes.
                dot1qIngressFiltering(2)
                                      -- supports the discarding of any
                                      -- frame received on a Port whose
                                      -- VLAN classification does not
                                      -- include that Port in its Member
                                      -- set.
               }
   MAX-ACCESS  read-only
   STATUS      current
   DESCRIPTION
      "Indicates the parts of IEEE 802.1D and 802.1Q that are
       optional on a per-port basis that are implemented by
       this device and are manageable through this MIB."
   REFERENCE
      "ISO/IEC 15802-3 Section 5.2,
       IEEE 802.1Q/D11 Section 5.2"
   ::= { dot1dPortCapabilitiesEntry 1 }


-- P Bridge Port Priority

dot1dPortPriorityTable OBJECT-TYPE
   SYNTAX      SEQUENCE OF TabDot1dPortPriorityEntry
   MAX-ACCESS  not-accessible
   STATUS      current
   DESCRIPTION
      "A table that contains information about every port that
       is associated with this transparent bridge."
   ::= { dot1dPriority 1 }

dot1dPortPriorityEntry OBJECT-TYPE
   SYNTAX      TabDot1dPortPriorityEntry
   MAX-ACCESS  not-accessible
   STATUS      current
   DESCRIPTION
      "A list of Default User Priorities for each port of a
       transparent bridge.  This is indexed by dot1dBasePort."
   AUGMENTS { dot1dBasePortEntry }
   ::= { dot1dPortPriorityTable 1 }

TabDot1dPortPriorityEntry ::=
   SEQUENCE {
      dot1dPortDefaultUserPriority
         Integer32,
      dot1dPortNumTrafficClasses
         Integer32
   }

dot1dPortDefaultUserPriority OBJECT-TYPE
   SYNTAX      Integer32 (0..7)
   MAX-ACCESS  read-write
   STATUS      current
   DESCRIPTION
      "The default ingress User Priority for this port.  This
       only has effect on media, such as Ethernet, that do not
       support native User Priority."
   ::= { dot1dPortPriorityEntry 1 }

dot1dPortNumTrafficClasses OBJECT-TYPE
    SYNTAX      Integer32 (1..8)
    MAX-ACCESS  read-write
    STATUS      current
    DESCRIPTION
        "The number of egress traffic classes supported on this
        port.  This object may optionally be read-only.

        The value of this object MUST be retained across
        reinitializations of the management system."
    ::= { dot1dPortPriorityEntry 2 }

-- -------------------------------------------------------------
-- User Priority Regeneration Table
-- -------------------------------------------------------------



dot1dUserPriorityRegenTable OBJECT-TYPE
    SYNTAX      SEQUENCE OF Dot1dUserPriorityRegenEntry
    MAX-ACCESS  not-accessible
    STATUS      current
    DESCRIPTION
        "A list of Regenerated User Priorities for each received
        User Priority on each port of a bridge.  The Regenerated
        User Priority value may be used to index the Traffic
        Class Table for each input port.  This only has effect
        on media that support native User Priority.  The default
        values for Regenerated User Priorities are the same as
        the User Priorities."
    REFERENCE
        "ISO/IEC 15802-3 Section 6.4"
    ::= { dot1dPriority 2 }

dot1dUserPriorityRegenEntry OBJECT-TYPE
    SYNTAX      Dot1dUserPriorityRegenEntry
    MAX-ACCESS  not-accessible
    STATUS      current
    DESCRIPTION
        "A mapping of incoming User Priority to a Regenerated
        User Priority."
    INDEX   { dot1dBasePort, dot1dUserPriority }
    ::= { dot1dUserPriorityRegenTable 1 }

Dot1dUserPriorityRegenEntry ::=
    SEQUENCE {
        dot1dUserPriority
            Integer32,
        dot1dRegenUserPriority
            Integer32
    }

dot1dUserPriority OBJECT-TYPE
    SYNTAX      Integer32 (0..7)
    MAX-ACCESS  not-accessible
    STATUS      current
    DESCRIPTION
        "The User Priority for a frame received on this port."
    ::= { dot1dUserPriorityRegenEntry 1 }

dot1dRegenUserPriority OBJECT-TYPE
    SYNTAX      Integer32 (0..7)
    MAX-ACCESS  read-write
    STATUS      current
    DESCRIPTION
        "The Regenerated User Priority that the incoming User



        Priority is mapped to for this port.

        The value of this object MUST be retained across
        reinitializations of the management system."
    ::= { dot1dUserPriorityRegenEntry 2 }

-- -------------------------------------------------------------
-- Traffic Class Table
-- -------------------------------------------------------------

dot1dTrafficClassTable OBJECT-TYPE
   SYNTAX      SEQUENCE OF TabDot1dTrafficClassEntry
   MAX-ACCESS  not-accessible
   STATUS      current
   DESCRIPTION
      "A table mapping evaluated User Priority to Traffic
       Class, for forwarding by the bridge.  Traffic class is a
       number in the range (0..(dot1dPortNumTrafficClasses-1))."
   REFERENCE
      "ISO/IEC 15802-3 Table 7-2"
   ::= { dot1dPriority 3 }

dot1dTrafficClassEntry OBJECT-TYPE
   SYNTAX      TabDot1dTrafficClassEntry
   MAX-ACCESS  not-accessible
   STATUS      current
   DESCRIPTION
      "User Priority to Traffic Class mapping."
   INDEX { dot1dBasePort, dot1dTrafficClassPriority }
   ::= { dot1dTrafficClassTable 1 }

TabDot1dTrafficClassEntry ::=
   SEQUENCE {
      dot1dTrafficClassPriority
         Integer32,
      dot1dTrafficClass
         Integer32
   }

dot1dTrafficClassPriority OBJECT-TYPE
   SYNTAX      Integer32 (0..7)
   MAX-ACCESS  not-accessible
   STATUS      current
   DESCRIPTION
      "The Priority value determined for the received frame.
       This value is equivalent to the priority indicated in
       the tagged frame received, or one of the evaluated
       priorities, determined according to the media-type.

       For untagged frames received from Ethernet media, this
       value is equal to the dot1dPortDefaultUserPriority value
       for the ingress port.

       For untagged frames received from non-Ethernet media,
       this value is equal to the dot1dRegenUserPriority value
       for the ingress port and media-specific user priority."
   ::= { dot1dTrafficClassEntry 1 }

dot1dTrafficClass OBJECT-TYPE
   SYNTAX      Integer32 (0..7)
   MAX-ACCESS  read-write
   STATUS      current
   DESCRIPTION
      "The Traffic Class the received frame is mapped to."
   ::= { dot1dTrafficClassEntry 2 }

-- -------------------------------------------------------------
-- Outbound Access Priority Table
-- -------------------------------------------------------------

dot1dPortOutboundAccessPriorityTable OBJECT-TYPE
    SYNTAX      SEQUENCE OF Dot1dPortOutboundAccessPriorityEntry
    MAX-ACCESS  not-accessible
    STATUS      current
    DESCRIPTION
        "A table mapping Regenerated User Priority to Outbound
        Access Priority.  This is a fixed mapping for all port
        types, with two options for 802.5 Token Ring."
    REFERENCE
        "ISO/IEC 15802-3 Table 7-3"
    ::= { dot1dPriority 4 }

dot1dPortOutboundAccessPriorityEntry OBJECT-TYPE
    SYNTAX      Dot1dPortOutboundAccessPriorityEntry
    MAX-ACCESS  not-accessible
    STATUS      current
    DESCRIPTION
        "Regenerated User Priority to Outbound Access Priority
        mapping."
    INDEX   { dot1dBasePort, dot1dRegenUserPriority }
    ::= { dot1dPortOutboundAccessPriorityTable 1 }

Dot1dPortOutboundAccessPriorityEntry ::=
    SEQUENCE {



        dot1dPortOutboundAccessPriority
            Integer32
    }

dot1dPortOutboundAccessPriority OBJECT-TYPE
    SYNTAX      Integer32 (0..7)
    MAX-ACCESS  read-only
    STATUS      current
    DESCRIPTION
        "The Outbound Access Priority the received frame is
        mapped to."
    ::= { dot1dPortOutboundAccessPriorityEntry 1 }


-- P Bridge GARP

dot1dPortGarpTable OBJECT-TYPE
   SYNTAX      SEQUENCE OF TabDot1dPortGarpEntry
   MAX-ACCESS  not-accessible
   STATUS      current
   DESCRIPTION
      "A table of GARP control information about every bridge
       port.  This is indexed by dot1dBasePort."
   ::= { dot1dGarp 1 }

dot1dPortGarpEntry OBJECT-TYPE
   SYNTAX      TabDot1dPortGarpEntry
   MAX-ACCESS  not-accessible
   STATUS      current
   DESCRIPTION
      "GARP control information for a bridge port."
   AUGMENTS { dot1dBasePortEntry }
   ::= { dot1dPortGarpTable 1 }

TabDot1dPortGarpEntry ::=
   SEQUENCE {
      dot1dPortGarpJoinTime
         TimeInterval,
      dot1dPortGarpLeaveTime
         TimeInterval,
      dot1dPortGarpLeaveAllTime
         TimeInterval
}

dot1dPortGarpJoinTime OBJECT-TYPE
   SYNTAX      TimeInterval
   MAX-ACCESS  read-write
   STATUS      current
   DESCRIPTION
      "The GARP Join time, in centiseconds."
   DEFVAL { 20 }
   ::= { dot1dPortGarpEntry 1 }

dot1dPortGarpLeaveTime OBJECT-TYPE
   SYNTAX      TimeInterval
   MAX-ACCESS  read-write
   STATUS      current
   DESCRIPTION
      "The GARP Leave time, in centiseconds."
   DEFVAL { 60 }
   ::= { dot1dPortGarpEntry 2 }

dot1dPortGarpLeaveAllTime OBJECT-TYPE
   SYNTAX      TimeInterval
   MAX-ACCESS  read-write
   STATUS      current
   DESCRIPTION
      "The GARP LeaveAll time, in centiseconds."
   DEFVAL { 1000 }
   ::= { dot1dPortGarpEntry 3 }


-- P Bridge TP

dot1dTpHCPortTable OBJECT-TYPE
   SYNTAX      SEQUENCE OF TabDot1dTpHCPortEntry
   MAX-ACCESS  not-accessible
   STATUS      current
   DESCRIPTION
      "A table that contains information about every high
       capacity port that is associated with this transparent
       bridge."
   ::= { dot1dTp 5 }

dot1dTpHCPortEntry OBJECT-TYPE
   SYNTAX      TabDot1dTpHCPortEntry
   MAX-ACCESS  not-accessible
   STATUS      current
   DESCRIPTION
      "Statistics information for each high capacity port of a
       transparent bridge."
   INDEX   { dot1dTpPort }
   ::= { dot1dTpHCPortTable 1 }

TabDot1dTpHCPortEntry ::=
   SEQUENCE {
      dot1dTpHCPortInFrames
         Counter64,
      dot1dTpHCPortOutFrames
         Counter64,
      dot1dTpHCPortInDiscards
         Counter64
   }

dot1dTpHCPortInFrames OBJECT-TYPE
   SYNTAX      Counter64
   MAX-ACCESS  read-only
   STATUS      current
   DESCRIPTION
      "The number of frames that have been received by this
       port from its segment.  Note that a frame received on
       the interface corresponding to this port is only counted
       by this object if and only if it is for a protocol being
       processed by the local bridging function, including
       bridge management frames."
   REFERENCE
      "ISO/IEC 15802-3 Section 14.6.1.1.3"
   ::= { dot1dTpHCPortEntry 1 }

dot1dTpHCPortOutFrames OBJECT-TYPE
   SYNTAX      Counter64
   MAX-ACCESS  read-only
   STATUS      current
   DESCRIPTION
      "The number of frames that have been transmitted by this
       port to its segment.  Note that a frame transmitted on
       the interface corresponding to this port is only counted
       by this object if and only if it is for a protocol being
       processed by the local bridging function, including
       bridge management frames."
   REFERENCE
      "ISO/IEC 15802-3 Section 14.6.1.1.3"
   ::= { dot1dTpHCPortEntry 2 }

dot1dTpHCPortInDiscards OBJECT-TYPE
   SYNTAX      Counter64
   MAX-ACCESS  read-only
   STATUS      current
   DESCRIPTION
      "Count of valid frames that have been received by this
       port from its segment which were discarded (i.e.,
       filtered) by the Forwarding Process."
   REFERENCE
      "ISO/IEC 15802-3 Section 14.6.1.1.3"
   ::= { dot1dTpHCPortEntry 3 }

dot1dTpPortOverflowTable OBJECT-TYPE
   SYNTAX      SEQUENCE OF TabDot1dTpPortOverflowEntry
   MAX-ACCESS  not-accessible
   STATUS      current
   DESCRIPTION
      "A table that contains the most-significant bits of
       statistics counters for ports that are associated with this
       transparent bridge that are on high capacity interfaces, as
       defined in the conformance clauses for this table. This table
       is provided as a way to read 64-bit counters for agents which
       support only SNMPv1.

       Note that the reporting of most-significant and
       least-significant counter bits separately runs the risk of
       missing an overflow of the lower bits in the interval between
       sampling. The manager must be aware of this possibility, even
       within the same varbindlist, when interpreting the results of
       a request or asynchronous notification."
   ::= { dot1dTp 6 }

dot1dTpPortOverflowEntry OBJECT-TYPE
   SYNTAX      TabDot1dTpPortOverflowEntry
   MAX-ACCESS  not-accessible
   STATUS      current
   DESCRIPTION
      "The most significant bits of statistics counters for a high
       capacity interface of a transparent bridge. Each object is
       associated with a corresponding object in dot1dTpPortTable
       which indicates the least significant bits of the counter."
   INDEX { dot1dTpPort }
   ::= { dot1dTpPortOverflowTable 1 }

TabDot1dTpPortOverflowEntry ::=
   SEQUENCE {
      dot1dTpPortInOverflowFrames
         Counter32,
      dot1dTpPortOutOverflowFrames
         Counter32,
      dot1dTpPortInOverflowDiscards
         Counter32
   }

dot1dTpPortInOverflowFrames OBJECT-TYPE
   SYNTAX      Counter32
   MAX-ACCESS  read-only
   STATUS      current
   DESCRIPTION
      "The number of times the associated dot1dTpPortInFrames
       counter has overflowed."
   REFERENCE
      "ISO/IEC 15802-3 Section 14.6.1.1.3"
   ::= { dot1dTpPortOverflowEntry 1 }

dot1dTpPortOutOverflowFrames OBJECT-TYPE
   SYNTAX      Counter32
   MAX-ACCESS  read-only
   STATUS      current
   DESCRIPTION
      "The number of times the associated dot1dTpPortOutFrames
       counter has overflowed."
   REFERENCE
      "ISO/IEC 15802-3 Section 14.6.1.1.3"
   ::= { dot1dTpPortOverflowEntry 2 }

dot1dTpPortInOverflowDiscards OBJECT-TYPE
   SYNTAX      Counter32
   MAX-ACCESS  read-only
   STATUS      current
   DESCRIPTION
      "The number of times the associated
       dot1dTpPortInDiscards counter has overflowed."
   REFERENCE
      "ISO/IEC 15802-3 Section 14.6.1.1.3"
   ::= { dot1dTpPortOverflowEntry 3 }


-- P Bridge Group

dot1dExtCapGroup OBJECT-GROUP
   OBJECTS {
       dot1dDeviceCapabilities,
       dot1dPortCapabilities
   }
  STATUS      current
  DESCRIPTION
      "A collection of objects indicating the optional
       capabilities of the device."
  ::= { dot1dGroups 1 }

dot1dDeviceGmrpGroup OBJECT-GROUP
   OBJECTS {
       dot1dGmrpStatus
   }
   STATUS      current
   DESCRIPTION
      "A collection of objects providing device-level control
       for the Multicast Filtering extended bridge services."
   ::= { dot1dGroups 2 }

dot1dDevicePriorityGroup OBJECT-GROUP
   OBJECTS {
       dot1dTrafficClassesEnabled
   }
   STATUS      current
   DESCRIPTION
      "A collection of objects providing device-level control
       for the Priority services."
   ::= { dot1dGroups 3 }

dot1dDefaultPriorityGroup OBJECT-GROUP
   OBJECTS {
       dot1dPortDefaultUserPriority
   }
   STATUS      current
   DESCRIPTION
      "A collection of objects defining the User Priority
       applicable to each port for media which do not support
       native User Priority."
   ::= { dot1dGroups 4 }

dot1dRegenPriorityGroup OBJECT-GROUP
   OBJECTS {
       dot1dRegenUserPriority
   }
   STATUS      current
   DESCRIPTION
      "A collection of objects defining the User Priorities
       applicable to each port for media which support native
       User Priority."
   ::= { dot1dGroups 5 }

dot1dPriorityGroup OBJECT-GROUP
   OBJECTS {
       dot1dPortNumTrafficClasses,
       dot1dTrafficClass
   }
   STATUS      current
   DESCRIPTION
      "A collection of objects defining the traffic classes
       within a bridge for each evaluated User Priority."
   ::= { dot1dGroups 6 }

dot1dAccessPriorityGroup OBJECT-GROUP
   OBJECTS {
       dot1dPortOutboundAccessPriority
   }
   STATUS      current
   DESCRIPTION
      "A collection of objects defining the media dependent
       outbound access level for each priority."
   ::= { dot1dGroups 7 }

dot1dPortGarpGroup OBJECT-GROUP
   OBJECTS {
       dot1dPortGarpJoinTime,
       dot1dPortGarpLeaveTime,
       dot1dPortGarpLeaveAllTime
   }
   STATUS      current
   DESCRIPTION
      "A collection of objects providing port level control
       and status information for GARP operation."
   ::= { dot1dGroups 8 }

dot1dHCPortGroup OBJECT-GROUP
   OBJECTS {
       dot1dTpHCPortInFrames,
       dot1dTpHCPortOutFrames,
       dot1dTpHCPortInDiscards
   }
   STATUS      current
   DESCRIPTION
      "A collection of objects providing 64-bit statistics
        counters for high capacity bridge ports."
   ::= { dot1dGroups 10 }

dot1dPortOverflowGroup OBJECT-GROUP
   OBJECTS {
       dot1dTpPortInOverflowFrames,
       dot1dTpPortOutOverflowFrames,
       dot1dTpPortInOverflowDiscards
   }
   STATUS      current
   DESCRIPTION
      "A collection of objects providing overflow statistics
       counters for high capacity bridge ports."
   ::= { dot1dGroups 11 }


-- P Bridge Compliance

dot1dCompliance MODULE-COMPLIANCE
   STATUS  current
   DESCRIPTION
      "The compliance statement for device support of Priority
       and Multicast Filtering extended bridging services."

   MODULE
      MANDATORY-GROUPS { dot1dExtCapGroup }

      GROUP       dot1dDeviceGmrpGroup
      DESCRIPTION
          "This group is mandatory for devices supporting the GMRP
          application, defined by IEEE 802.1D Extended Filtering
          Services."

      GROUP       dot1dDevicePriorityGroup
      DESCRIPTION
          "This group is mandatory only for devices supporting
          the priority forwarding operations defined by IEEE
          802.1D."
      GROUP       dot1dDefaultPriorityGroup
      DESCRIPTION
          "This group is mandatory only for devices supporting
          the priority forwarding operations defined by the
          extended bridge services with media types, such as
          Ethernet, that do not support native User Priority."

      GROUP       dot1dRegenPriorityGroup
      DESCRIPTION
          "This group is mandatory only for devices supporting
          the priority forwarding operations defined by IEEE 802.1D
          and which have interface media types that support
          native User Priority e.g. IEEE 802.5."

      GROUP       dot1dPriorityGroup
      DESCRIPTION
          "This group is mandatory only for devices supporting
          the priority forwarding operations defined by IEEE 802.1D."

      GROUP       dot1dAccessPriorityGroup
      DESCRIPTION
          "This group is optional and is relevant only for devices
          supporting the priority forwarding operations defined by
          IEEE 802.1D and which have interface media types that support
          native Access Priority e.g. IEEE 802.5."

      GROUP       dot1dPortGarpGroup
      DESCRIPTION
          "This group is mandatory for devices supporting any
          of the GARP applications: e.g. GMRP, defined by the
          extended filtering services of 802.1D; or GVRP,
          defined by 802.1Q (refer to the Q-BRIDGE-MIB for
          conformance statements for GVRP)."

      GROUP       dot1dHCPortGroup
      DESCRIPTION
          "Support for this group in a device is mandatory for those
          bridge ports which map to network interfaces that have the
          value of the corresponding instance of ifSpeed
          greater than 650,000,000 bits/second."

      GROUP       dot1dPortOverflowGroup
      DESCRIPTION
          "Support for this group in a device is mandatory for those
          bridge ports which map to network interfaces that have the
          value of the corresponding instance of ifSpeed
          greater than 650,000,000 bits/second."

      OBJECT      dot1dPortNumTrafficClasses
      MIN-ACCESS  read-only
      DESCRIPTION
          "Write access is not required."

      OBJECT      dot1dTrafficClass
      MIN-ACCESS  read-only
      DESCRIPTION
          "Write access is not required."

      OBJECT      dot1dRegenUserPriority
      MIN-ACCESS  read-only
      DESCRIPTION
          "Write access is not required."

     ::= { dot1dCompliances 1 }





VlanIndex ::= TEXTUAL-CONVENTION
   STATUS      current
   DESCRIPTION
      "A value used to index per-VLAN tables: values of 0 and
       4095 are not permitted; if the value is between 1 and
       4094 inclusive, it represents an IEEE 802.1Q VLAN-ID with
       global scope within a given bridged domain (see VlanId
       textual convention).  If the value is greater than 4095
       then it represents a VLAN with scope local to the
       particular agent, i.e. one without a global VLAN-ID
       assigned to it. Such VLANs are outside the scope of
       IEEE 802.1Q but it is convenient to be able to manage them
       in the same way using this MIB."
   SYNTAX      Unsigned32

VlanId ::= TEXTUAL-CONVENTION
   STATUS      current
   DESCRIPTION
      "A 12-bit VLAN ID used in the VLAN Tag header."
   SYNTAX      Integer32 (1..4094)


dot1qMIBObjects          OBJECT IDENTIFIER ::= { dot1qQBridge 1 }

dot1qBase                OBJECT IDENTIFIER ::= { dot1qMIBObjects 1 }
dot1qTp                  OBJECT IDENTIFIER ::= { dot1qMIBObjects 2 }
dot1qStatic              OBJECT IDENTIFIER ::= { dot1qMIBObjects 3 }
dot1qVlan                OBJECT IDENTIFIER ::= { dot1qMIBObjects 4 }


-- Q Bridge Base

dot1qBaseTable OBJECT-TYPE
   SYNTAX        SEQUENCE OF TabDot1qBaseEntry
   MAX-ACCESS    not-accessible
   STATUS        current
   DESCRIPTION
      "List of dot1qBase objects that can be configured per
       virtual context in the system."
   ::= { dot1qBase 1 }

dot1qBaseEntry OBJECT-TYPE
   SYNTAX        TabDot1qBaseEntry
   MAX-ACCESS    not-accessible
   STATUS        current
   DESCRIPTION
      "Virtual context dot1qBase objects."
   INDEX { dot1qVlanContextId }
   ::= { dot1qBaseTable 1 }

TabDot1qBaseEntry ::=
   SEQUENCE {
      dot1qVlanContextId
         Integer32,
      dot1qVlanVersionNumber
         INTEGER,
      dot1qMaxVlanId
         VlanId,
      dot1qMaxSupportedVlans
         Unsigned32,
      dot1qNumVlans
         Unsigned32,
      dot1qGvrpStatus
         INTEGER
   }

dot1qVlanContextId OBJECT-TYPE
   SYNTAX       Integer32 (0..65535)
   MAX-ACCESS   not-accessible
   STATUS       current
   DESCRIPTION
      "Identifies a virtual context."
   ::= { dot1qBaseEntry 1 }

dot1qVlanVersionNumber OBJECT-TYPE
   SYNTAX      INTEGER {
                version1(1)
               }
   MAX-ACCESS  read-only
   STATUS      current
   DESCRIPTION
      "The version number of IEEE 802.1Q that this device
       supports."
   REFERENCE
      "IEEE 802.1Q/D11 Section 12.10.1.1"
   ::= { dot1qBaseEntry 2 }

dot1qMaxVlanId OBJECT-TYPE
   SYNTAX      VlanId
   MAX-ACCESS  read-only
   STATUS      current
   DESCRIPTION
      "The maximum IEEE 802.1Q VLAN ID that this device
       supports."
   REFERENCE
      "IEEE 802.1Q/D11 Section 9.3.2.3"
   ::= { dot1qBaseEntry 3 }

dot1qMaxSupportedVlans OBJECT-TYPE
   SYNTAX      Unsigned32
   MAX-ACCESS  read-only
   STATUS      current
   DESCRIPTION
      "The maximum number of IEEE 802.1Q VLANs that this
       device supports."
   REFERENCE
      "IEEE 802.1Q/D11 Section 12.10.1.1"
   ::= { dot1qBaseEntry 4 }

dot1qNumVlans OBJECT-TYPE
   SYNTAX      Unsigned32
   MAX-ACCESS  read-only
   STATUS      current
   DESCRIPTION
      "The current number of IEEE 802.1Q VLANs that are
       configured in this device."
   REFERENCE
      "IEEE 802.1Q/D11 Section 12.7.1.1"
   ::= { dot1qBaseEntry 5 }

dot1qGvrpStatus OBJECT-TYPE
   SYNTAX      INTEGER  { enabled(1), disabled(2) }
   MAX-ACCESS  read-write
   STATUS      current
   DESCRIPTION
      "The administrative status requested by management for
       GVRP.  The value enabled(1) indicates that GVRP should
       be enabled on this device, on all ports for which it has
       not been specifically disabled.  When disabled(2), GVRP
       is disabled on all ports and all GVRP packets will be
       forwarded transparently.  This object affects all GVRP
       Applicant and Registrar state machines.  A transition
       from disabled(2) to enabled(1) will cause a reset of all
       GVRP state machines on all ports."
   DEFVAL { 2 }
   ::= { dot1qBaseEntry 6 }


-- Q Bridge TP

dot1qFdbTable OBJECT-TYPE
   SYNTAX      SEQUENCE OF TabDot1qFdbEntry
   MAX-ACCESS  not-accessible
   STATUS      current
   DESCRIPTION
      "A table that contains configuration and control
       information for each Filtering Database currently
       operating on this device.  Entries in this table appear
       automatically when VLANs are assigned FDB IDs in the
       dot1qVlanCurrentTable. This table maintains context ID
       as one more index to support Multiple Instances."
   ::= { dot1qTp 1 }

dot1qFdbEntry OBJECT-TYPE
   SYNTAX      TabDot1qFdbEntry
   MAX-ACCESS  not-accessible
   STATUS      current
   DESCRIPTION
      "Information about a specific Filtering Database."
   INDEX { dot1qVlanContextId, dot1qFdbId }
   ::= { dot1qFdbTable 1 }

TabDot1qFdbEntry ::=
   SEQUENCE {
      dot1qFdbId
         Unsigned32,
      dot1qFdbDynamicCount
         Counter32
   }

dot1qFdbId OBJECT-TYPE
   SYNTAX       Unsigned32
   MAX-ACCESS   not-accessible
   STATUS       current
   DESCRIPTION
      "The identity of this Filtering Database."
   ::= { dot1qFdbEntry 1 }

dot1qFdbDynamicCount OBJECT-TYPE
   SYNTAX       Counter32
   MAX-ACCESS   read-only
   STATUS       current
   DESCRIPTION
      "The current number of dynamic entries in this
       Filtering Database."
   REFERENCE
      "IEEE 802.1Q/D11 Section 12.7.1.1.3"
   ::= { dot1qFdbEntry 2 }

dot1qTpFdbTable OBJECT-TYPE
   SYNTAX      SEQUENCE OF TabDot1qTpFdbEntry
   MAX-ACCESS  not-accessible
   STATUS      current
   DESCRIPTION
      "A table that contains information about unicast entries
       for which the device has forwarding and/or filtering
       information.  This information is used by the
       transparent bridging function in determining how to
       propagate a received frame. This table maintains context ID
       as one more index to support Multiple Instances."
   REFERENCE
      "IEEE 802.1Q/D11 Section 12.7.7"
   ::= { dot1qTp 2 }

dot1qTpFdbEntry OBJECT-TYPE
   SYNTAX      TabDot1qTpFdbEntry
   MAX-ACCESS  not-accessible
   STATUS      current
   DESCRIPTION
      "Information about a specific unicast MAC address for
       which the device has some forwarding and/or filtering
       information."
   INDEX { dot1qVlanContextId, dot1qFdbId, dot1qTpFdbAddress }
   ::= { dot1qTpFdbTable 1 }

TabDot1qTpFdbEntry ::=
   SEQUENCE {
      dot1qTpFdbAddress
         MacAddress,
      dot1qTpFdbPort
         Integer32,
      dot1qTpFdbStatus
         INTEGER,
      dot1qTpFdbPw
         Unsigned32
   }

dot1qTpFdbAddress OBJECT-TYPE
   SYNTAX      MacAddress
   MAX-ACCESS  read-only
   STATUS      current
   DESCRIPTION
      "A unicast MAC address for which the device has
       forwarding and/or filtering information."
   ::= { dot1qTpFdbEntry 1 }

dot1qTpFdbPort OBJECT-TYPE
   SYNTAX      Integer32 (0..65535)
   MAX-ACCESS  read-only
   STATUS      current
   DESCRIPTION
      "Either the value '0', or the port number of the port on
       which a frame having a source address equal to the value
       of the corresponding instance of dot1qTpFdbAddress has
       been seen.  A value of '0' indicates that the port
       number has not been learned but that the device does
       have some forwarding/filtering information about this
       address (e.g. in the dot1qStaticUnicastTable).
       Implementors are encouraged to assign the port value to
       this object whenever it is learned even for addresses
       for which the corresponding value of dot1qTpFdbStatus is
       not learned(3)."
   ::= { dot1qTpFdbEntry 2 }

dot1qTpFdbStatus OBJECT-TYPE
   SYNTAX      INTEGER {
                other(1),
                invalid(2),
                learned(3),
                self(4),
                mgmt(5)
               }
   MAX-ACCESS  read-only
   STATUS      current
   DESCRIPTION
      "The status of this entry.  The meanings of the values
       are:
           other(1) - none of the following.  This may include
               the case where some other MIB object (not the
               corresponding instance of dot1qTpFdbPort, nor an
               entry in the dot1qStaticUnicastTable) is being
               used to determine if and how frames addressed to
               the value of the corresponding instance of
               dot1qTpFdbAddress are being forwarded.
           invalid(2) - this entry is no longer valid (e.g., it
               was learned but has since aged out), but has not
               yet been flushed from the table.
           learned(3) - the value of the corresponding instance
               of dot1qTpFdbPort was learned and is being used.
           self(4) - the value of the corresponding instance of
               dot1qTpFdbAddress represents one of the device's
               addresses.  The corresponding instance of
               dot1qTpFdbPort indicates which of the device's
               ports has this address.
           mgmt(5) - the value of the corresponding instance of
               dot1qTpFdbAddress is also the value of an
               existing instance of dot1qStaticAddress."
   ::= { dot1qTpFdbEntry 3 }

dot1qTpFdbPw OBJECT-TYPE
   SYNTAX      Unsigned32
   MAX-ACCESS  read-only
   STATUS      current
   DESCRIPTION
      "Either the value '0', or the pseudowire number on
       which a frame having a source address equal to the value
       of the corresponding instance of dot1qTpFdbAddress has
       been seen. A value of '0' indicates that the entry was
       learned via the layer2 port. Non-zero value indicates
       that this value must be used for forwading irrespective
       of dot1qTpFdbPort"
   ::= { dot1qTpFdbEntry 4 }

-- Q Bridge Static

dot1qStaticUnicastTable OBJECT-TYPE
   SYNTAX      SEQUENCE OF TabDot1qStaticUnicastEntry
   MAX-ACCESS  not-accessible
   STATUS      current
   DESCRIPTION
      "A table containing filtering information for Unicast
       MAC addresses for each Filtering Database, configured
       into the device by (local or network) management
       specifying the set of ports to which frames received
       from specific ports and containing specific unicast
       destination addresses are allowed to be forwarded.  A
       value of zero in this table as the port number from
       which frames with a specific destination address are
       received, is used to specify all ports for which there
       is no specific entry in this table for that particular
       destination address.  Entries are valid for unicast
       addresses only. This table maintains context ID as
       one more index to support Multiple Instances."
   REFERENCE
      "IEEE 802.1Q/D11 Section 12.7.7,
       ISO/IEC 15802-3 Section 7.9.1"
   ::= { dot1qStatic 1 }

dot1qStaticUnicastEntry OBJECT-TYPE
   SYNTAX      TabDot1qStaticUnicastEntry
   MAX-ACCESS  not-accessible
   STATUS      current
   DESCRIPTION
      "Filtering information configured into the device by
       (local or network) management specifying the set of
       ports to which frames received from a specific port and
       containing a specific unicast destination address are
       allowed to be forwarded."
   INDEX {
      dot1qVlanContextId,
      dot1qFdbId,
      dot1qStaticUnicastAddress,
      dot1qStaticUnicastReceivePort
   }
   ::= { dot1qStaticUnicastTable 1 }

TabDot1qStaticUnicastEntry ::=
   SEQUENCE {
      dot1qStaticUnicastAddress
         MacAddress,
      dot1qStaticUnicastReceivePort
         Integer32,
      dot1qStaticUnicastRowStatus
         RowStatus,
      dot1qStaticUnicastStatus
         INTEGER
   }

dot1qStaticUnicastAddress OBJECT-TYPE
   SYNTAX      MacAddress
   MAX-ACCESS  read-only
   STATUS      current
   DESCRIPTION
      "The destination MAC address in a frame to which this
       entry's filtering information applies.  This object must
       take the value of a unicast address."
   ::= { dot1qStaticUnicastEntry 1 }

dot1qStaticUnicastReceivePort OBJECT-TYPE
   SYNTAX      Integer32 (0..65535)
   MAX-ACCESS  read-only
   STATUS      current
   DESCRIPTION
      "Either the value '0', or the port number of the port
       from which a frame must be received in order for this
       entry's filtering information to apply.  A value of zero
       indicates that this entry applies on all ports of the
       device for which there is no other applicable entry."
   ::= { dot1qStaticUnicastEntry 2 }

dot1qStaticUnicastRowStatus OBJECT-TYPE
   SYNTAX      RowStatus
   MAX-ACCESS  read-create
   STATUS      current
   DESCRIPTION
      "This object indicates the status of the AllowedToGoTo
       PortList to which a frame with a specific unicast
       address will be flooded in the event that it has not
       been learned. To fill the AllowedToGoTo portlist,
       we have to set the rowstatus as 'NOT_IN_SERVICE' and
       set the appropriate port in the
       dot1qStaticAllowedToGoTable and set the rowstatus as
       'ACTIVE' to make the portlist available."
   ::= { dot1qStaticUnicastEntry 3 }

dot1qStaticUnicastStatus OBJECT-TYPE
   SYNTAX      INTEGER {
                other(1),
                invalid(2),
                permanent(3),
                deleteOnReset(4),
                deleteOnTimeout(5)
               }
   MAX-ACCESS  read-write
   STATUS      current
   DESCRIPTION
      "This object indicates the status of this entry.
       other(1) - this entry is currently in use but
           the conditions under which it will remain
           so differ from the following values.
       invalid(2) - writing this value to the object
           removes the corresponding entry.
       permanent(3) - this entry is currently in use
           and will remain so after the next reset of
           the bridge.
       deleteOnReset(4) - this entry is currently in
           use and will remain so until the next
           reset of the bridge.
       deleteOnTimeout(5) - this entry is currently in
           use and will remain so until it is aged out."
   DEFVAL { permanent }
   ::= { dot1qStaticUnicastEntry 4 }

dot1qStaticAllowedToGoTable OBJECT-TYPE
   SYNTAX      SEQUENCE OF TabDot1qStaticAllowedToGoEntry
   MAX-ACCESS  not-accessible
   STATUS      current
   DESCRIPTION
      "A table containing the information of AllowedToGoTo
       ports for each static unicast entry. This table
       maintains context ID as one more index to support
       Multiple Instances."
   REFERENCE
      "IEEE 802.1Q/D11 Table 8-5, ISO/IEC 15802-3 Table 7-5"
   ::= { dot1qStatic 2 }

dot1qStaticAllowedToGoEntry OBJECT-TYPE
   SYNTAX      TabDot1qStaticAllowedToGoEntry
   MAX-ACCESS  not-accessible
   STATUS      current
   DESCRIPTION
      "Information about a port, Whether it is an AllowedToGoTo
       member or not."
   INDEX {
      dot1qVlanContextId,
      dot1qFdbId,
      dot1qStaticUnicastAddress,
      dot1qStaticUnicastReceivePort,
      dot1qTpPort
   }
   ::= { dot1qStaticAllowedToGoTable 1 }

TabDot1qStaticAllowedToGoEntry ::=
   SEQUENCE {
      dot1qStaticAllowedIsMember
         TruthValue,
      dot1qTpPort
         Integer32  
   }

dot1qStaticAllowedIsMember OBJECT-TYPE
   SYNTAX      TruthValue
   MAX-ACCESS  read-write
   STATUS      current
   DESCRIPTION
      "Indicates whether the port is an allowedToGoTo member."
   REFERENCE
      "IEEE 802.1Q/D11 Table 8-5, ISO/IEC 15802-3 Table 7-5"
   ::= { dot1qStaticAllowedToGoEntry 1 }

dot1qTpPort OBJECT-TYPE
    SYNTAX      Integer32 (1..65535) 
    MAX-ACCESS  not-accessible 
    STATUS      current 
    DESCRIPTION 
       "The port number of the port for which this entry applies." 
   REFERENCE
      "IEEE 802.1Q/D11 Table 8-5, ISO/IEC 15802-3 Table 7-5"
   ::= { dot1qStaticAllowedToGoEntry 2 }

dot1qStaticMulticastTable OBJECT-TYPE
   SYNTAX      SEQUENCE OF TabDot1qStaticMulticastEntry
   MAX-ACCESS  not-accessible
   STATUS      current
   DESCRIPTION
      "A table containing filtering information for Multicast
       and Broadcast MAC addresses for each VLAN, configured
       into the device by (local or network) management
       specifying the set of ports to which frames received
       from specific ports and containing specific Multicast
       and Broadcast destination addresses are allowed to be
       forwarded.  A value of zero in this table as the port
       number from which frames with a specific destination
       address are received, is used to specify all ports for
       which there is no specific entry in this table for that
       particular destination address.  Entries are valid for
       Multicast and Broadcast addresses only. This table
       maintains context ID as one more index to support
       Multiple Instances."
   REFERENCE
      "IEEE 802.1Q/D11 Section 12.7.7,
       ISO/IEC 15802-3 Section 7.9.1"
   ::= { dot1qStatic 3 }

dot1qStaticMulticastEntry OBJECT-TYPE
   SYNTAX      TabDot1qStaticMulticastEntry
   MAX-ACCESS  not-accessible
   STATUS      current
   DESCRIPTION
      "Filtering information configured into the device by
       (local or network) management specifying the set of
       ports to which frames received from this specific port
       for this VLAN and containing this Multicast or Broadcast
       destination address are allowed to be forwarded."
   INDEX   {
      dot1qVlanContextId,
      dot1qVlanIndex,
      dot1qStaticMulticastAddress,
      dot1qStaticMulticastReceivePort
   }
   ::= { dot1qStaticMulticastTable 1 }

TabDot1qStaticMulticastEntry ::=
   SEQUENCE {
      dot1qStaticMulticastAddress
         MacAddress,
      dot1qStaticMulticastReceivePort
         Integer32,
      dot1qStaticMulticastRowStatus
         RowStatus,
      dot1qStaticMulticastStatus
         INTEGER
   }

dot1qStaticMulticastAddress OBJECT-TYPE
   SYNTAX      MacAddress
   MAX-ACCESS  read-only
   STATUS      current
   DESCRIPTION
      "The destination MAC address in a frame to which this
       entry's filtering information applies.  This object must
       take the value of a Multicast or Broadcast address."
   ::= { dot1qStaticMulticastEntry 1 }

dot1qStaticMulticastReceivePort OBJECT-TYPE
   SYNTAX      Integer32 (0..65535)
   MAX-ACCESS  read-only
   STATUS      current
   DESCRIPTION
      "Either the value '0', or the port number of the port
       from which a frame must be received in order for this
       entry's filtering information to apply.  A value of zero
       indicates that this entry applies on all ports of the
       device for which there is no other applicable entry."
   ::= { dot1qStaticMulticastEntry 2 }

dot1qStaticMulticastRowStatus OBJECT-TYPE
   SYNTAX      RowStatus
   MAX-ACCESS  read-create
   STATUS      current
   DESCRIPTION
      "This object indicates the status of the PortLists
       (Eggress, Forbidden) used in the static multicast
       table. To fill the eggress and forbidden portlist,
       we have to set the rowstatus as 'NOT_IN_SERVICE'
       and set the appropriate port in the
       dot1qForwardUnregPortConfigTable and set the
       rowstatus as 'ACTIVE' to make the portlist available."
   ::= { dot1qStaticMulticastEntry 3 }

dot1qStaticMulticastStatus OBJECT-TYPE
   SYNTAX      INTEGER {
                other(1),
                invalid(2),
                permanent(3),
                deleteOnReset(4),
                deleteOnTimeout(5)
               }
   MAX-ACCESS  read-write
   STATUS      current
   DESCRIPTION
      "This object indicates the status of this entry.
       other(1) - this entry is currently in use but
           the conditions under which it will remain
           so differ from the following values.
       invalid(2) - writing this value to the object
           removes the corresponding entry.
       permanent(3) - this entry is currently in use
           and will remain so after the next reset of
           the bridge.
       deleteOnReset(4) - this entry is currently in
           use and will remain so until the next
           reset of the bridge.
       deleteOnTimeout(5) - this entry is currently in
           use and will remain so until it is aged out."
   DEFVAL { permanent }
   ::= { dot1qStaticMulticastEntry 4 }

dot1qStaticMcastPortTable OBJECT-TYPE
   SYNTAX      SEQUENCE OF TabDot1qStaticMcastPortEntry
   MAX-ACCESS  not-accessible
   STATUS      current
   DESCRIPTION
      "A table containing egress and forbidden ports for
       static multicast entry. This table maintains context
       ID as one more index to support Multiple Instance."
   ::= { dot1qStatic 4 }

dot1qStaticMcastPortEntry OBJECT-TYPE
   SYNTAX      TabDot1qStaticMcastPortEntry
   MAX-ACCESS  not-accessible
   STATUS      current
   DESCRIPTION
      "Information about a port, Whether it is a member or
       a forbidden member."
   INDEX {
      dot1qVlanContextId,
      dot1qVlanIndex,
      dot1qStaticMulticastAddress,
      dot1qStaticMulticastReceivePort,
      dot1qTpPort
   }
   ::= { dot1qStaticMcastPortTable 1 }

TabDot1qStaticMcastPortEntry ::=
   SEQUENCE {
      dot1qStaticMcastPort
         INTEGER,
      dot1qVlanIndex
         VlanIndex
   }

dot1qStaticMcastPort OBJECT-TYPE
   SYNTAX      INTEGER  {
                addMember(1),
                addForbidden(2),
                delMember(3),
                delForbidden(4)
               }
   MAX-ACCESS  read-write
   STATUS      current
   DESCRIPTION
      "Indicates whether the port is a member or a forbidden
       member in the static multicast entry.
       'addMember'    - to add the port in the egress
                        member-list.
       'addForbidden' - to add the port in the forbidden
                        member-list.
       'delMember'    - to remove the port from the egress
                        member-list.
       'delForbidden' - to remove the port from the forbidden
                        member-list."
   ::= { dot1qStaticMcastPortEntry 1 }

dot1qVlanIndex OBJECT-TYPE
    SYNTAX      VlanIndex
    MAX-ACCESS  not-accessible
    STATUS      current
    DESCRIPTION
        "The VLAN-ID or other identifier referring to this VLAN."
    ::= { dot1qStaticMcastPortEntry 2 }

-- Q Bridge VLAN

dot1qVlanNumDeletesTable OBJECT-TYPE
  SYNTAX      SEQUENCE OF TabDot1qVlanNumDeletesEntry
  MAX-ACCESS  not-accessible
  STATUS      current
  DESCRIPTION
      "Table containing number of VLAN deletions in the VLAN
       current database. This table maintains context ID as index
       to support Multiple Instances."
  ::= { dot1qVlan 1 }

dot1qVlanNumDeletesEntry OBJECT-TYPE
  SYNTAX        TabDot1qVlanNumDeletesEntry
  MAX-ACCESS    not-accessible
  STATUS        current
  DESCRIPTION
      "Entry for a virtual context."
  INDEX { dot1qVlanContextId }
  ::= { dot1qVlanNumDeletesTable 1 }

TabDot1qVlanNumDeletesEntry ::=
   SEQUENCE {
      dot1qVlanNumDeletes
         Counter32
   }

dot1qVlanNumDeletes OBJECT-TYPE
   SYNTAX     Counter32
   MAX-ACCESS read-only
   STATUS     current
   DESCRIPTION
      "The number of times a VLAN entry has been deleted from
       the dot1qVlanCurrentTable (for any reason).  If an entry
       is deleted, then inserted, and then deleted, this
       counter will be incremented by 2."
   ::= { dot1qVlanNumDeletesEntry 1 }


dot1qVlanCurrentTable OBJECT-TYPE
   SYNTAX      SEQUENCE OF TabDot1qVlanCurrentEntry
   MAX-ACCESS  not-accessible
   STATUS      current
   DESCRIPTION
      "A table containing current configuration information
       for each VLAN currently configured into the device by
       (local or network) management, or dynamically created
       as a result of GVRP requests received. This table
       maintains context ID as one more index to support
       Multiple Instances."
   ::= { dot1qVlan 2 }

dot1qVlanCurrentEntry OBJECT-TYPE
   SYNTAX      TabDot1qVlanCurrentEntry
   MAX-ACCESS  not-accessible
   STATUS      current
   DESCRIPTION
      "Information for a VLAN configured into the device by
       (local or network) management, or dynamically created
       as a result of GVRP requests received."
   INDEX   { dot1qVlanContextId, dot1qVlanTimeMark, dot1qVlanIndex }
   ::= { dot1qVlanCurrentTable 1 }

TabDot1qVlanCurrentEntry ::=
   SEQUENCE {
      dot1qVlanTimeMark
         TimeFilter,
      dot1qVlanFdbId
         Unsigned32,
      dot1qVlanStatus
         INTEGER,
      dot1qVlanCreationTime
         TimeTicks
   }

dot1qVlanTimeMark OBJECT-TYPE
   SYNTAX      TimeFilter
   MAX-ACCESS  not-accessible
   STATUS      current
   DESCRIPTION
      "A TimeFilter for this entry.  See the TimeFilter
       textual convention to see how this works."
   ::= { dot1qVlanCurrentEntry 1 }

dot1qVlanFdbId OBJECT-TYPE
   SYNTAX      Unsigned32
   MAX-ACCESS  read-only
   STATUS      current
   DESCRIPTION
      "The Filtering Database used by this VLAN.  This is one
       of the dot1qFdbId values in the dot1qFdbTable.  This
       value is allocated automatically by the device whenever
       the VLAN is created: either dynamically by GVRP, or by
       management, in dot1qVlanStaticTable.  Allocation of this
       value follows the learning constraints defined for this
       VLAN in dot1qLearningConstraintsTable."
   ::= { dot1qVlanCurrentEntry 2 }

dot1qVlanStatus OBJECT-TYPE
   SYNTAX      INTEGER {
                other(1),
                permanent(2),
                dynamicGvrp(3)
               }
   MAX-ACCESS  read-only
   STATUS      current
   DESCRIPTION
      "This object indicates the status of this entry.
       other(1) - this entry is currently in use but the
           conditions under which it will remain so differ
           from the following values.
       permanent(2) - this entry, corresponding to an entry
           in dot1qVlanStaticTable, is currently in use and
           will remain so after the next reset of the
           device.  The port lists for this entry include
           ports from the equivalent dot1qVlanStaticTable
           entry and ports learnt dynamically.
       dynamicGvrp(3) - this entry is currently in use
           and will remain so until removed by GVRP.  There
           is no static entry for this VLAN and it will be
           removed when the last port leaves the VLAN."
   ::= { dot1qVlanCurrentEntry 3 }

dot1qVlanCreationTime OBJECT-TYPE
   SYNTAX      TimeTicks
   MAX-ACCESS  read-only
   STATUS      current
   DESCRIPTION
      "The value of sysUpTime when this VLAN was created."
   ::= { dot1qVlanCurrentEntry 4 }


dot1qVlanEgressPortTable OBJECT-TYPE
   SYNTAX      SEQUENCE OF TabDot1qVlanEgressPortEntry
   MAX-ACCESS  not-accessible
   STATUS      current
   DESCRIPTION
      "A table containing the information of egress ports
       for each VLAN. This table maintains context ID as
       one more index to support Multiple Instance."
   ::= { dot1qVlan 3 }

dot1qVlanEgressPortEntry OBJECT-TYPE
   SYNTAX      TabDot1qVlanEgressPortEntry
   MAX-ACCESS  not-accessible
   STATUS      current
   DESCRIPTION
      "Information about a port, Whether it is a tagged
       or an untagged member."
   INDEX   { dot1qVlanContextId, dot1qVlanTimeMark, dot1qVlanIndex,
               dot1qTpPort}
   ::= { dot1qVlanEgressPortTable 1 }

TabDot1qVlanEgressPortEntry ::=
   SEQUENCE {
      dot1qVlanCurrentEgressPort INTEGER
   }

dot1qVlanCurrentEgressPort OBJECT-TYPE
   SYNTAX      INTEGER {
                tagged(1),
                untagged(2)
               }
   MAX-ACCESS  read-only
   STATUS      current
   DESCRIPTION
      "Indicates whether the port is a tagged or a untagged
       member in the VLAN.
       'tagged'   - to add the port in the tagged portlist.
       'untagged' - to add the port in the untagged portlist."
   ::= { dot1qVlanEgressPortEntry 1 }

dot1qVlanStaticTable OBJECT-TYPE
   SYNTAX      SEQUENCE OF TabDot1qVlanStaticEntry
   MAX-ACCESS  not-accessible
   STATUS      current
   DESCRIPTION
      "A table containing static configuration information for
       each VLAN configured into the device by (local or
       network) management.  All entries are permanent and will
       be restored after the device is reset. This table
       maintains context ID as one more index to support
       Multiple Instance."
   ::= { dot1qVlan 4 }

dot1qVlanStaticEntry OBJECT-TYPE
   SYNTAX      TabDot1qVlanStaticEntry
   MAX-ACCESS  not-accessible
   STATUS      current
   DESCRIPTION
      "Static information for a VLAN configured into the
       device by (local or network) management."
   INDEX   { dot1qVlanContextId, dot1qVlanIndex }
   ::= { dot1qVlanStaticTable 1 }

TabDot1qVlanStaticEntry ::=
   SEQUENCE {
      dot1qVlanStaticName
         SnmpAdminString,
      dot1qVlanStaticRowStatus
         RowStatus
   }

dot1qVlanStaticName OBJECT-TYPE
   SYNTAX      SnmpAdminString (SIZE (0..32))
   MAX-ACCESS  read-create
   STATUS      current
   DESCRIPTION
      "An administratively assigned string, which may be used
       to identify the VLAN."
   REFERENCE
      "IEEE 802.1Q/D11 Section 12.10.2.1"
   ::= { dot1qVlanStaticEntry 1 }

dot1qVlanStaticRowStatus OBJECT-TYPE
   SYNTAX      RowStatus
   MAX-ACCESS  read-create
   STATUS      current
   DESCRIPTION
      "This object indicates the status of this entry."
   ::= { dot1qVlanStaticEntry 2 }

dot1qVlanStaticPortConfigTable OBJECT-TYPE
   SYNTAX      SEQUENCE OF TabDot1qVlanStaticPortConfigEntry
   MAX-ACCESS  not-accessible
   STATUS      current
   DESCRIPTION
      "A table containing the information of tagged, untagged
       and forbidden ports for each VLAN. This table
       maintains context ID as one more index to support
       Multiple Instance."
   ::= { dot1qVlan 5 }

dot1qVlanStaticPortConfigEntry OBJECT-TYPE
   SYNTAX      TabDot1qVlanStaticPortConfigEntry
   MAX-ACCESS  not-accessible
   STATUS      current
   DESCRIPTION
      "Forwarding information about a port, Whether it is a
       member or a forbidden member."
   INDEX { dot1qVlanContextId, dot1qVlanIndex, dot1qTpPort }
   ::= { dot1qVlanStaticPortConfigTable 1 }

TabDot1qVlanStaticPortConfigEntry ::=
   SEQUENCE {
      dot1qVlanStaticPort
         INTEGER
   }

dot1qVlanStaticPort OBJECT-TYPE
   SYNTAX      INTEGER {
                addTagged(1),
                addUntagged(2),
                addForbidden(3),
                delTagged(4),
                delUntagged(5),
                delForbidden(6)
               }
   MAX-ACCESS  read-write
   STATUS      current
   DESCRIPTION
      "Indicates whether the port is a member or a forbidden
       member in the forwarding information for this VLAN.
       'addTagged'    - to add the port in the tagged portlist.
       'addUntagged'  - to add the port in the untagged portlist.
       'addForbidden' - to add the port in the forbidden portlist.
       'delTagged'    - to delete the port from the tagged portlist.
       'delUntagged'  - to delete the port from the untagged portlist.
       'delForbidden' - to delete the port from the forbidden portlist."
   REFERENCE
      "IEEE 802.1Q/D11 Section 12.10.2.1"
   ::= { dot1qVlanStaticPortConfigEntry 1 }

dot1qPortVlanTable OBJECT-TYPE
   SYNTAX      SEQUENCE OF TabDot1qPortVlanEntry
   MAX-ACCESS  not-accessible
   STATUS      current
   DESCRIPTION
      "A table containing per port control and status
       information for VLAN configuration in the device."
   ::= { dot1qVlan 7 }

dot1qPortVlanEntry OBJECT-TYPE
   SYNTAX      TabDot1qPortVlanEntry
   MAX-ACCESS  not-accessible
   STATUS      current
   DESCRIPTION
      "Information controlling VLAN configuration for a port
       on the device.  This is indexed by dot1dBasePort."
   INDEX { dot1dBasePort }
   ::= { dot1qPortVlanTable 1 }

TabDot1qPortVlanEntry ::=
   SEQUENCE {
      dot1qPvid
         VlanIndex,
      dot1qPortAcceptableFrameTypes
         INTEGER,
      dot1qPortIngressFiltering
         TruthValue,
      dot1qPortGvrpStatus
         EnabledStatus,
      dot1qPortGvrpFailedRegistrations
         Counter32,
      dot1qPortGvrpLastPduOrigin
         MacAddress,
      dot1qPortRestrictedVlanRegistration
         TruthValue
   }

dot1qPvid OBJECT-TYPE
   SYNTAX      VlanIndex
   MAX-ACCESS  read-write
   STATUS      current
   DESCRIPTION
      "The PVID, the VLAN ID assigned to untagged frames or
       Priority-Tagged frames received on this port."
   REFERENCE
      "IEEE 802.1Q/D11 Section 12.10.1.1"
   DEFVAL { 1 }
   ::= { dot1qPortVlanEntry 1 }

dot1qPortAcceptableFrameTypes OBJECT-TYPE
   SYNTAX      INTEGER {
                admitAll(1),
                admitOnlyVlanTagged(2),
                admitOnlyUntaggedAndPriorityTagged(3)
               }
   MAX-ACCESS  read-write
   STATUS      current
   DESCRIPTION
      "When this is admitOnlyVlanTagged(2) the device will
       discard untagged frames or Priority-Tagged frames
       received on this port.  When admitAll(1), untagged
       frames or Priority-Tagged frames received on this port
       will be accepted and assigned to the PVID for this port.

       When this is admitOnlyUntaggedAndPriorityTagged the device
       will recieve only untagged and priority tagged frames on
       this port.

       This control does not affect VLAN independent BPDU
       frames, such as GVRP and STP.  It does affect VLAN
       dependent BPDU frames, such as GMRP."
   REFERENCE
      "IEEE 802.1Q/D11 Section 12.10.1.3"
   DEFVAL { admitAll }
   ::= { dot1qPortVlanEntry 2 }

dot1qPortIngressFiltering OBJECT-TYPE
   SYNTAX      TruthValue
   MAX-ACCESS  read-write
   STATUS      current
   DESCRIPTION
      "When this is true(1) the device will discard incoming
       frames for VLANs which do not include this Port in its
       Member set.  When false(2), the port will accept all
       incoming frames.

       This control does not affect VLAN independent BPDU
       frames, such as GVRP and STP.  It does affect VLAN
       dependent BPDU frames, such as GMRP."
   REFERENCE
      "IEEE 802.1Q/D11 Section 12.10.1.4"
   DEFVAL      { false }
   ::= { dot1qPortVlanEntry 3 }

dot1qPortGvrpStatus OBJECT-TYPE
   SYNTAX      EnabledStatus
   MAX-ACCESS  read-write
   STATUS      current
   DESCRIPTION
      "The state of GVRP operation on this port.  The value
       enabled(1) indicates that GVRP is enabled on this port,
       as long as dot1qGvrpStatus is also enabled for this
       device.  When disabled(2) but dot1qGvrpStatus is still
       enabled for the device, GVRP is disabled on this port:
       any GVRP packets received will be silently discarded and
       no GVRP registrations will be propagated from other
       ports.  This object affects all GVRP Applicant and
       Registrar state machines on this port.  A transition
       from disabled(2) to enabled(1) will cause a reset of all
       GVRP state machines on this port."
   DEFVAL { enabled }
   ::= { dot1qPortVlanEntry 4 }

dot1qPortGvrpFailedRegistrations OBJECT-TYPE
   SYNTAX      Counter32
   MAX-ACCESS  read-only
   STATUS      current
   DESCRIPTION
      "The total number of failed GVRP registrations, for any
       reason, on this port."
   ::= { dot1qPortVlanEntry 5 }

dot1qPortGvrpLastPduOrigin OBJECT-TYPE
   SYNTAX      MacAddress
   MAX-ACCESS  read-only
   STATUS      current
   DESCRIPTION
      "The Source MAC Address of the last GVRP message
       received on this port."
   ::= { dot1qPortVlanEntry 6 }

dot1qPortRestrictedVlanRegistration OBJECT-TYPE
   SYNTAX      TruthValue
   MAX-ACCESS  read-write
   STATUS      current
   DESCRIPTION
      "The state of Restricted VLAN Registration on this port.
       If the value of this control is true(1), then creation
       of a new dynamic VLAN entry is permitted only if there
       is a Static VLAN Registration Entry for the VLAN concerned,
       in which the Registrar Administrative Control value for
       this port is Normal Registration."
   REFERENCE
      "IEEE 802.1u clause 11.2.3.2.3, 12.10.1.7."
   DEFVAL { false }
   ::= { dot1qPortVlanEntry 7 }




dot1sMst                         OBJECT IDENTIFIER  ::= { l2Mst 1 }
dot1sMstTrapsControl             OBJECT IDENTIFIER ::= { l2Mst 2 }
dot1sMstTraps                    OBJECT IDENTIFIER ::= { l2Mst 3 }


-- Dot1s MST

dot1sMstTable OBJECT-TYPE
   SYNTAX SEQUENCE OF TabDot1sMstEntry
   MAX-ACCESS    not-accessible
   STATUS        current
   DESCRIPTION
      "List of per Virtual Context Mst Module Parameters."
   ::= { dot1sMst 3 }

dot1sMstEntry OBJECT-TYPE
   SYNTAX       TabDot1sMstEntry
   MAX-ACCESS   not-accessible
   STATUS       current
   DESCRIPTION
      "Virtual Context Mst Module Parameters."
   INDEX { dot1sMstContextId }
   ::= { dot1sMstTable 1 }

TabDot1sMstEntry ::=
   SEQUENCE {
      dot1sMstContextId
         Integer32,
      dot1sSystemControl
         INTEGER,
      dot1sModuleStatus
         EnabledStatus,
      dot1sMaxMstInstanceNumber
         Integer32,
      dot1sNoOfMstiSupported
         Integer32,
      dot1sMaxHopCount
         Integer32,
      dot1sBrgAddress
         MacAddress,
      dot1sCistRoot
         BridgeId,
      dot1sCistRegionalRoot
         BridgeId,
      dot1sCistRootCost
         Integer32,
      dot1sCistRegionalRootCost
         Integer32,
      dot1sCistRootPort
         Integer32,
      dot1sCistBridgePriority
         Integer32,
      dot1sCistBridgeMaxAge
         Timeout,
      dot1sCistBridgeForwardDelay
         Timeout,
      dot1sCistHoldTime
         Integer32,
      dot1sCistMaxAge
         Timeout,
      dot1sCistForwardDelay
         Timeout,
      dot1sMstpUpCount
         Counter32,
      dot1sMstpDownCount
         Counter32,
      dot1sPathCostDefaultType
         INTEGER,
      dot1sTrace
         Integer32,
      dot1sDebug
         Integer32,
      dot1sForceProtocolVersion
         INTEGER,
      dot1sTxHoldCount
         Integer32,
      dot1sMstiConfigIdSel
         Integer32,
      dot1sMstiRegionName
         OCTET STRING,
      dot1sMstiRegionVersion
         Integer32,
      dot1sMstiConfigDigest
         OCTET STRING,
      dot1sBufferOverFlowCount
         Counter32,
      dot1sMemAllocFailureCount
         Counter32,
      dot1sRegionConfigChangeCount
         Counter32,
      dot1sCistBridgeRoleSelectionSemState
         INTEGER,
      dot1sCistTimeSinceTopologyChange
         TimeTicks,
      dot1sCistTopChanges
         Counter32,
      dot1sCistNewRootBridgeCount
         Counter32,
      dot1sCistHelloTime
         Timeout,
      dot1sCistBridgeHelloTime
         Timeout,
      dot1sCistDynamicPathcostCalculation
         TruthValue,
      dot1sContextName
         DisplayString
   }

dot1sMstContextId OBJECT-TYPE
   SYNTAX        Integer32 (0..65535)
   MAX-ACCESS    not-accessible
   STATUS        current
   DESCRIPTION
      "Identifies the Virtual Context."
   ::= { dot1sMstEntry 1 }

dot1sSystemControl OBJECT-TYPE
   SYNTAX      INTEGER { start(1), shutdown(2) }
   MAX-ACCESS  read-write
   STATUS      current
   DESCRIPTION
      "The administrative shutdown status requested by management for the MST
       feature. The value start (1) indicates that MST should be active in
       the device on all ports. The value shutdown (2) indicates that MST
       should be shutdown in the device on all ports. All memory should
       be released on all ports."
   ::= { dot1sMstEntry 2 }

dot1sModuleStatus OBJECT-TYPE
   SYNTAX      EnabledStatus
   MAX-ACCESS  read-write
   STATUS      current
   DESCRIPTION
      "The administrative status requested by management for the MST
       feature. The value enabled(1) indicates that Mst should be enabled
       in the device on all ports. The value disabled(2) indicates that
       Mst should be disabled in the device on all ports. The object can
       be set to enabled(1) if and only if, dot1sSystemControl set to start."
   ::= { dot1sMstEntry 3 }

dot1sMaxMstInstanceNumber OBJECT-TYPE
   SYNTAX      Integer32 (1..64)
   MAX-ACCESS  read-write
   STATUS      current
   DESCRIPTION
      "The Maximun number of spanning trees to be allowed.
       A User may limit the Number of Spanning Tree instance
       to be allowed in the Bridge."
   ::= { dot1sMstEntry 4 }

dot1sNoOfMstiSupported OBJECT-TYPE
   SYNTAX      Integer32
   MAX-ACCESS  read-only
   STATUS      current
   DESCRIPTION
      "Indicates Maximum number of spanning tree Instances supported."
   ::= { dot1sMstEntry 5 }

dot1sMaxHopCount OBJECT-TYPE
   SYNTAX      Integer32 (600..4000)
   MAX-ACCESS  read-write
   STATUS      current
   DESCRIPTION
      "Indicates the Maximum Hop Count value.
       The granularity of this timer is specified
       to be 1 second.  An agent may return a badValue
       error if a set is attempted to a value which is
       not a whole number of seconds."
   DEFVAL { 2000 }
   ::= { dot1sMstEntry 6 }

dot1sBrgAddress OBJECT-TYPE
   SYNTAX      MacAddress
   MAX-ACCESS  read-only
   STATUS      current
   DESCRIPTION
      "The MAC address used by this bridge when it must
       be referred to in a unique fashion.   It is
       recommended that this be the numerically smallest
       MAC address of all ports that belong to this
       bridge.  However it is only required to be unique.
       When concatenated with dot1sCistBridgePriority or
       dot1sMstiBridgePriority a unique BridgeIdentifier
       is formed which is used in the Spanning Tree Protocol."
   ::= { dot1sMstEntry 7 }

dot1sCistRoot OBJECT-TYPE
   SYNTAX      BridgeId
   MAX-ACCESS  read-only
   STATUS      current
   DESCRIPTION
      "The bridge identifier of the Root of the common spanning
       tree as determined by the Spanning Tree Protocol
       as executed by this node.  This value is used as
       the CIST Root Identifier parameter in all Configuration
       Bridge PDUs originated by this node."
   ::= { dot1sMstEntry 8 }

dot1sCistRegionalRoot OBJECT-TYPE
   SYNTAX      BridgeId
   MAX-ACCESS  read-only
   STATUS      current
   DESCRIPTION
      "The bridge identifier of the Root of the Multiple
       spanning tree region as determined by the Spanning Tree
       Protocol as executed by this node.  This value is used as
       the CIST Regional Root Identifier parameter in all Configuration
       Bridge PDUs originated by this node."
   ::= { dot1sMstEntry 9 }

dot1sCistRootCost OBJECT-TYPE
   SYNTAX      Integer32
   MAX-ACCESS  read-only
   STATUS      current
   DESCRIPTION
      "The Cost of the path to the CIST Root as seen
       from this bridge."
   ::= { dot1sMstEntry 10 }

dot1sCistRegionalRootCost OBJECT-TYPE
   SYNTAX      Integer32
   MAX-ACCESS  read-only
   STATUS      current
   DESCRIPTION
      "The Cost of the path to the CIST Regional Root
       as seen from this bridge."
   ::= { dot1sMstEntry 11 }

dot1sCistRootPort OBJECT-TYPE
   SYNTAX      Integer32
   MAX-ACCESS  read-only
   STATUS      current
   DESCRIPTION
      "The Port Number of the Port which offers the lowest
       path cost from this bridge to the CIST Root Bridge."
   ::= { dot1sMstEntry 12 }

dot1sCistBridgePriority OBJECT-TYPE
   SYNTAX      Integer32 (0..61440)
   MAX-ACCESS  read-write
   STATUS      current
   DESCRIPTION
      "The Value of the writable portion of the Bridge
       Identifier comprising of the first two octets.
       The values that are set for Bridge Priority must be
       in steps of 4096."
   DEFVAL {32768}
   ::= { dot1sMstEntry 13 }

dot1sCistBridgeMaxAge OBJECT-TYPE
   SYNTAX      Timeout (600..4000)
   MAX-ACCESS  read-write
   STATUS      current
   DESCRIPTION
      "The value that all bridges use for MaxAge when
       this bridge is acting as the root. The granularity
       of this timer is specified to be 1 second.
       An agent may return a badValue error if a set is
       attempted to a value which is not a whole number
       of seconds."
   DEFVAL {2000}
   ::= { dot1sMstEntry 14 }

dot1sCistBridgeForwardDelay OBJECT-TYPE
   SYNTAX      Timeout (400..3000)
   MAX-ACCESS  read-write
   STATUS      current
   DESCRIPTION
      "The value that all bridges use for ForwardDelay
       when this bridge is acting as the root.  Note that
       802.1D specifies that the range for this
       parameter is related to the value of
       BridgeMaxAge.  The granularity of this
       timer is specified to be 1 second.
       An agent may return a badValue error if a set is
       attempted to a value which is not a whole number
       of seconds."
   DEFVAL {1500}
   ::= { dot1sMstEntry 15 }

dot1sCistHoldTime OBJECT-TYPE
   SYNTAX      Integer32
   MAX-ACCESS  read-only
   STATUS      current
   DESCRIPTION
      "This time value determines the interval length
       during which no more than two Configuration bridge
       PDUs shall be transmitted by this node, in units
       of hundredths of a second."
   ::= { dot1sMstEntry 16 }

dot1sCistMaxAge OBJECT-TYPE
   SYNTAX      Timeout
   MAX-ACCESS  read-only
   STATUS      current
   DESCRIPTION
      "The maximum age of Spanning Tree Protocol
       information learned from the network on any port
       before it is discarded, in units of hundredths of
       a second.  This is the actual value that this
       bridge is currently using."
   ::= { dot1sMstEntry 17 }

dot1sCistForwardDelay OBJECT-TYPE
   SYNTAX      Timeout
   MAX-ACCESS  read-only
   STATUS      current
   DESCRIPTION
      "This time value, measured in units of hundredths
       of a second, controls how fast a port changes its
       spanning state when moving towards the Forwarding
       state.  The value determines how long the port
       stays in a particular state before moving to the
       next state."
   ::= { dot1sMstEntry 18 }

dot1sMstpUpCount OBJECT-TYPE
   SYNTAX      Counter32
   MAX-ACCESS  read-only
   STATUS      current
   DESCRIPTION
      "The number of times MSTP Module has been enabled."
   ::= { dot1sMstEntry 19 }

dot1sMstpDownCount OBJECT-TYPE
   SYNTAX      Counter32
   MAX-ACCESS  read-only
   STATUS      current
   DESCRIPTION
      "The number of times MSTP Module has been disabled."
   ::= { dot1sMstEntry 20 }

dot1sPathCostDefaultType OBJECT-TYPE
   SYNTAX      INTEGER {
                stp8021d1998(1),
                stp8021t2001(2)
               }
   MAX-ACCESS  read-write
   STATUS      current
   DESCRIPTION
      "The version of the Spanning Tree default Path Costs that
       are to be used by this Bridge.  A value of 8021d1998(1)
       uses the 16-bit default Path Costs from IEEE Std. 802.1D-1998.
       A value of stp8021t2001(2) uses the 32-bit default Path
       Costs from IEEE Std. 802.1t."
   ::= { dot1sMstEntry 21 }

dot1sTrace OBJECT-TYPE
   SYNTAX      Integer32 (0..255)
   MAX-ACCESS  read-write
   STATUS      current
   DESCRIPTION
      "This object is used to enable Trace Statements in the MSTP
       Module.
      
       A FOUR BYTE integer is used for enabling the level of tracing.
       Each BIT in the four byte integer, represents a particular
       level of Trace.
      
       The mapping between the bit positions & the level of trace is
       as follows:
       0 - Init and Shutdown Traces
       1 - Management Traces
       2 - Data Path Traces
       3 - Control Plane Traces
       4 - Packet Dump Traces
       5 - Traces related to All Resources except Buffers
       6 - All Failure Traces
       7 - Buffer Traces
      
       The remaining bits are unused. Combination of trace levels are
       also allowed.
      
       For example if the bits 0 and 1 are set, then the Trace
       statements related to Init-Shutdown and management
       will be printed.
      
       The user has to enter the corresponding INTEGER VALUE for the
       bits set. For example if bits 0 and 1 are to be set then user has
       to give the value for this object as 3.
      
       Setting the Trace Option to any value will cause the Debug Option
       to be set to 0 (i.e.) the Trace Option and Debug Option are mutually
       exclusive."
   DEFVAL  { 0 }
   ::= { dot1sMstEntry 22 }

dot1sDebug OBJECT-TYPE
   SYNTAX      Integer32 (0..131071)
   MAX-ACCESS  read-write
   STATUS      current
   DESCRIPTION
      "This object is used to enable Debug Statements in the MSTP
       Module.
     
       A FOUR BYTE integer is used for enabling the level of debugging.
       Each BIT in the four byte integer, represents a particular
       level of Debug.
     
       The mapping between the bit positions & the level of debug is
       as follows:
       0 - Init and Shutdown Debug statements
       1 - Management Debug statements
       2 - Memory related Debug statements
       3 - BPDU related Debug statements
       4 - Event Handling Debug statements
       5 - Timer Module Debug statements
       6 - Port Information SEM Debug statements
       7 - Port Receive SEM Debug statements (valid in the case of MSTP alone)
       8 - Role Selection SEM Debug statements
       9 - Role Transition SEM Debug statements
       10 - State Transition SEM Debug statements
       11 - Protocol Migration SEM Debug statements
       12 - Topology Change SEM Debug statements
       13 - Port Transmit SEM Debug statements
       14 - Bridge Detection SEM Debug statements
       15 - All Failure Debug statements
       16 - Redundancy code flow Debug statements
     
       The remaining bits are unused. Combination of debug levels are
       also allowed.
     
       For example if the bits 0 and 1 are set, then the Debug
       statements related to Init-Shutdown and management
       will be printed.
     
       The user has to enter the corresponding INTEGER VALUE for the
       bits set. For example if bits 0 and 1 are to be set then user has
       to give the value for this object as 3.
     
       Setting the Debug Option to any value will cause the Trace Option
       to be set to 0 (i.e.) the Trace Option and Debug Option are mutually
       exclusive."
   DEFVAL  { 0 }
   ::= { dot1sMstEntry 23 }

dot1sForceProtocolVersion OBJECT-TYPE
   SYNTAX      INTEGER {
                stpCompatible(0),
                rstp(2),
                mstp(3)
               }
   MAX-ACCESS  read-write
   STATUS      current
   DESCRIPTION
      "The version of Spanning Tree Protocol the bridge is
       currently running.  The value 'stpCompatible(0)'
       indicates the Spanning Tree Protocol specified in
       IEEE 802.1D and 'rstp(2)' indicates the Rapid Spanning
       Tree Protocol specified in IEEE 802.1w and 'mstp(3)'
       indicates the Multiple Spanning Tree Protocol Specified
       in IEEE 802.1s."
   DEFVAL { mstp }
   ::= { dot1sMstEntry 24 }

dot1sTxHoldCount OBJECT-TYPE
   SYNTAX      Integer32 (1..10)
   MAX-ACCESS  read-write
   STATUS      current
   DESCRIPTION
      "The value used by the Port Transmit state machine to limit
       the maximum transmission rate."
   DEFVAL { 3 }
   ::= { dot1sMstEntry 25 }

dot1sMstiConfigIdSel OBJECT-TYPE
   SYNTAX      Integer32 (0..255)
   MAX-ACCESS  read-write
   STATUS      current
   DESCRIPTION
      "The Configuration Identifier Format Selector used
       by the Bridge. This has a fixed value of 0 to indicate
       RegionName, RegionVersion are specified as in Standard."
   ::= { dot1sMstEntry 26 }

dot1sMstiRegionName OBJECT-TYPE
   SYNTAX      OCTET STRING (SIZE (0..32))
   MAX-ACCESS  read-write
   STATUS      current
   DESCRIPTION
      "The Name for the Region's configuration. By Default
       Region Name will be equal to the Bridge Mac Address."
   ::= { dot1sMstEntry 27 }

dot1sMstiRegionVersion OBJECT-TYPE
   SYNTAX      Integer32 (0..65535)
   MAX-ACCESS  read-write
   STATUS      current
   DESCRIPTION
      "Version of the MST Region."
   ::= { dot1sMstEntry 28 }

dot1sMstiConfigDigest OBJECT-TYPE
   SYNTAX      OCTET STRING (SIZE (0..32))
   MAX-ACCESS  read-only
   STATUS      current
   DESCRIPTION
      "The Configuration Digest value for this Region."
   ::= { dot1sMstEntry 29 }

dot1sBufferOverFlowCount OBJECT-TYPE
   SYNTAX      Counter32
   MAX-ACCESS  read-only
   STATUS      current
   DESCRIPTION
      "The number of times Buffer overflows/failures have occured.
       A Trap is generated on the occurence of this event."
   ::= { dot1sMstEntry 30 }

dot1sMemAllocFailureCount OBJECT-TYPE
   SYNTAX      Counter32
   MAX-ACCESS  read-only
   STATUS      current
   DESCRIPTION
      "The number of times memory allocation failures have occured.
       A Trap is generated on the occurence of this event."
   ::= { dot1sMstEntry 31 }

dot1sRegionConfigChangeCount OBJECT-TYPE
   SYNTAX      Counter32
   MAX-ACCESS  read-only
   STATUS      current
   DESCRIPTION
      "The number of times a Region Configuration Identifier Change
       was detected.
       A Trap is generated on the occurence of this event."
   ::= { dot1sMstEntry 32 }

dot1sCistBridgeRoleSelectionSemState OBJECT-TYPE
   SYNTAX      INTEGER {
                initbridge (0),
                roleselection (1)
               }
   MAX-ACCESS  read-only
   STATUS      current
   DESCRIPTION
      "Current state of the Port Role Selection State Machine
       of this bridge in Common Spanning Tree context"
   ::= { dot1sMstEntry 33 }

dot1sCistTimeSinceTopologyChange OBJECT-TYPE
   SYNTAX      TimeTicks
   MAX-ACCESS  read-only
   STATUS      current
   DESCRIPTION
      "The time (in hundredths of a second) since the
       TcWhile Timer for any port in this Bridge was
       non-zero for Common Spanning Tree context."
   ::= { dot1sMstEntry 34 }

dot1sCistTopChanges OBJECT-TYPE
   SYNTAX      Counter32
   MAX-ACCESS  read-only
   STATUS      current
   DESCRIPTION
      "The number of times that there have been atleast
       one non-zero TcWhile Timer on this Bridge for Common
       Spanning Tree context."
   ::= { dot1sMstEntry 35 }

dot1sCistNewRootBridgeCount OBJECT-TYPE
   SYNTAX      Counter32
   MAX-ACCESS  read-only
   STATUS      current
   DESCRIPTION
      "The number of times this Bridge has detected a Root
       Bridge change for Common Spanning Tree context.
       A Trap is generated on the occurence of this event."
   ::= { dot1sMstEntry 36 }

dot1sCistHelloTime OBJECT-TYPE
   SYNTAX      Timeout
   MAX-ACCESS  read-only
   STATUS      current
   DESCRIPTION
      "This time value, measured in units of hundredths
       of a second, specifies the amount of time between
       the transmission of configuration BPDUs by this node
       on any port when it is the root of the spanning tree
       or trying to become so."
   ::= { dot1sMstEntry 37 }

dot1sCistBridgeHelloTime OBJECT-TYPE
   SYNTAX      Timeout (100..200)
   MAX-ACCESS  read-write
   STATUS      current
   DESCRIPTION
      "The amount of time between the transmission of
       Configuration bridge PDUs by this node in units
       of hundredths of a second."
   ::= { dot1sMstEntry 38 }

dot1sCistDynamicPathcostCalculation OBJECT-TYPE
   SYNTAX      TruthValue
   MAX-ACCESS  read-write
   STATUS      current
   DESCRIPTION
      "This object is used to determine whether dynamic pathcost
       calculation is allowed or not.The value is determined by
       management. If set to true, pathcost is calculated dynamically
       from port speed, otherwise the link speed at the time of port
       creation is used for calculating the path cost. In both cases
       if the user has configured a pathcost for the port that will be
       used. By default dynamic pathcost calculation is set to false."
   DEFVAL { false }
   ::= { dot1sMstEntry 39 }

dot1sContextName OBJECT-TYPE
   SYNTAX   DisplayString (SIZE (1..32))
   MAX-ACCESS   read-only
   STATUS   current
   DESCRIPTION
      "This object is used to identity the context-name."
   ::= { dot1sMstEntry 40 }

dot1sMstiBridgeTable OBJECT-TYPE
   SYNTAX      SEQUENCE OF TabDot1sMstiBridgeEntry
   MAX-ACCESS  not-accessible
   STATUS      current
   DESCRIPTION
      "Table containing Bridge Information specific to Spanning
       Tree Instance. This table maintains context ID as one
       more index to support Multiple Instances."
   ::= { dot1sMst 4 }

dot1sMstiBridgeEntry OBJECT-TYPE
   SYNTAX      TabDot1sMstiBridgeEntry
   MAX-ACCESS  not-accessible
   STATUS      current
   DESCRIPTION
      "Entry indicating the Bridge Information."
   INDEX { dot1sMstContextId, dot1sMstiInstanceIndex }
   ::= { dot1sMstiBridgeTable 1 }

TabDot1sMstiBridgeEntry ::=
   SEQUENCE {
      dot1sMstiInstanceIndex
          Integer32,
      dot1sMstiBridgeRegionalRoot
          BridgeId,
      dot1sMstiBridgePriority
          Integer32,
      dot1sMstiRootCost
          Integer32,
      dot1sMstiRootPort
          Integer32,
      dot1sMstiTimeSinceTopologyChange
          TimeTicks,
      dot1sMstiTopChanges
          Counter32,
      dot1sMstiNewRootBridgeCount
          Counter32,
      dot1sMstiBridgeRoleSelectionSemState
          INTEGER,
      dot1sInstanceUpCount
          Counter32,
      dot1sInstanceDownCount
          Counter32,
      dot1sOldDesignatedRoot
          BridgeId
   }

dot1sMstiInstanceIndex OBJECT-TYPE
   SYNTAX      Integer32 (1..64)
   MAX-ACCESS  not-accessible
   STATUS      current
   DESCRIPTION
      "Spanning Tree Instance to which the information belongs."
   ::= { dot1sMstiBridgeEntry 1 }

dot1sMstiBridgeRegionalRoot OBJECT-TYPE
   SYNTAX      BridgeId
   MAX-ACCESS  read-only
   STATUS      current
   DESCRIPTION
      "MSTI Regional Root Identifier value for the Instance. This value
       is used as the MSTI Regional Root Identifier parameter in all
       Configuration Bridge PDUs originated by this node"
   ::= { dot1sMstiBridgeEntry 2 }

dot1sMstiBridgePriority OBJECT-TYPE
   SYNTAX      Integer32 (0..61440)
   MAX-ACCESS  read-write
   STATUS      current
   DESCRIPTION
      "The writable portion of the MSTI Bridge Identifier.
       comprising of the first two octets.
       The values that are set for Bridge Priority must be
       in steps of 4096."
   DEFVAL {32768}
   ::= { dot1sMstiBridgeEntry 3 }

dot1sMstiRootCost OBJECT-TYPE
   SYNTAX      Integer32
   MAX-ACCESS  read-only
   STATUS      current
   DESCRIPTION
      "The Cost of the path to the MSTI Regional Root as seen
       by this bridge."
   ::= { dot1sMstiBridgeEntry 4 }

dot1sMstiRootPort OBJECT-TYPE
   SYNTAX      Integer32
   MAX-ACCESS  read-only
   STATUS      current
   DESCRIPTION
      "The Port Number of the Port which offers the lowest
       path cost from this bridge to the MSTI Region Root Bridge."
   ::= { dot1sMstiBridgeEntry 5 }

dot1sMstiTimeSinceTopologyChange OBJECT-TYPE
   SYNTAX      TimeTicks
   MAX-ACCESS  read-only
   STATUS      current
   DESCRIPTION
      "The time (in hundredths of a second) since the
       TcWhile Timer for any port in this Bridge was
       non-zero for this spanning tree instance."
   ::= { dot1sMstiBridgeEntry 6 }

dot1sMstiTopChanges OBJECT-TYPE
   SYNTAX      Counter32
   MAX-ACCESS  read-only
   STATUS      current
   DESCRIPTION
      "The number of times that there have been atleast
       one non-zero TcWhile Timer on this Bridge for this
       spanning tree instance."
   ::= { dot1sMstiBridgeEntry 7 }

dot1sMstiNewRootBridgeCount OBJECT-TYPE
   SYNTAX      Counter32
   MAX-ACCESS  read-only
   STATUS      current
   DESCRIPTION
      "The number of times this Bridge has detected a Root
       Bridge change for this spanning tree instance.
       A Trap is generated on the occurence of this event."
   ::= { dot1sMstiBridgeEntry 8 }

dot1sMstiBridgeRoleSelectionSemState OBJECT-TYPE
   SYNTAX      INTEGER {
                initbridge (0),
                roleselection (1)
               }
   MAX-ACCESS  read-only
   STATUS      current
   DESCRIPTION
      "Current state of the Port Role Selection State Machine
       for this spanning tree instance for this bridge."
   ::= { dot1sMstiBridgeEntry 9 }

dot1sInstanceUpCount OBJECT-TYPE
   SYNTAX      Counter32
   MAX-ACCESS  read-only
   STATUS      current
   DESCRIPTION
      "The number of times a new spanning tree instance has
       been created.
       A Trap is generated on the occurence of this event."
   ::= { dot1sMstiBridgeEntry 10 }

dot1sInstanceDownCount OBJECT-TYPE
   SYNTAX      Counter32
   MAX-ACCESS  read-only
   STATUS      current
   DESCRIPTION
      "The number of times a spanning tree instance has
       been deleted.
       A Trap is generated on the occurence of this event."
   ::= { dot1sMstiBridgeEntry 11 }

dot1sOldDesignatedRoot OBJECT-TYPE
   SYNTAX  BridgeId
   MAX-ACCESS  read-only
   STATUS  current
   DESCRIPTION
      "The bridge identifier of the old root of the spanning
       tree instance as determined by the Spanning Tree Protocol
       as executed by this node. "
   ::= { dot1sMstiBridgeEntry 12 }

dot1sVlanInstanceMappingTable OBJECT-TYPE
   SYNTAX      SEQUENCE OF TabDot1sVlanInstanceMappingEntry
   MAX-ACCESS  not-accessible
   STATUS      current
   DESCRIPTION
      "This table contains one entry for each instance of MSTP.
       This table maintains context ID as one more index to
       support Multiple Instances."
   ::= { dot1sMst 5 }

dot1sVlanInstanceMappingEntry OBJECT-TYPE
   SYNTAX      TabDot1sVlanInstanceMappingEntry
   MAX-ACCESS  not-accessible
   STATUS      current
   DESCRIPTION
      "A conceptual row containing the status of the MSTP instance."
   INDEX { dot1sMstContextId, dot1sInstanceIndex }
   ::= { dot1sVlanInstanceMappingTable 1 }

TabDot1sVlanInstanceMappingEntry ::=
SEQUENCE {
   dot1sInstanceIndex
      Integer32,
   dot1sMapVlanIndex
      VlanId,
   dot1sUnMapVlanIndex
      VlanId,
   dot1sSetVlanList
      OCTET STRING,
   dot1sResetVlanList
      OCTET STRING,
   dot1sInstanceVlanMapped
      OCTET STRING,
   dot1sInstanceVlanMapped2k
      OCTET STRING,
   dot1sInstanceVlanMapped3k
      OCTET STRING,
   dot1sInstanceVlanMapped4k
      OCTET STRING
}

dot1sInstanceIndex OBJECT-TYPE
   SYNTAX      Integer32 (1..64)
   MAX-ACCESS  not-accessible
   STATUS      current
   DESCRIPTION
      "An arbitrary integer within the range from 1 to the value of
       Max Instance Number that uniquely identifies an instance."
   ::= { dot1sVlanInstanceMappingEntry 1 }

dot1sMapVlanIndex OBJECT-TYPE
   SYNTAX        VlanId
   MAX-ACCESS    read-write
   STATUS        current
   DESCRIPTION
      "The VlanId will get mapped to the spanning tree instance
       specified. All the Instance Specific information for the
       Member ports of the Vlan will be created.This object is
       used only for SET operation.GET Operation returns null values.
       If the VlanId to Instance Mapping has to be known then any
       one of the VlanMapped object should be used."
   ::= { dot1sVlanInstanceMappingEntry 2 }

dot1sUnMapVlanIndex OBJECT-TYPE
   SYNTAX        VlanId
   MAX-ACCESS    read-write
   STATUS        current
   DESCRIPTION
      "The VlanId will get unmapped from spanning tree instance
       to which it it mapped. All the Instance Specific information
       for the Member ports of the Vlan will get released.This object
       is used only for SET operation.GET Operation returns null values."
   ::= { dot1sVlanInstanceMappingEntry 3 }

dot1sSetVlanList OBJECT-TYPE
   SYNTAX     OCTET STRING (SIZE (0..512))
   MAX-ACCESS read-write
   STATUS     current
   DESCRIPTION
      "A string of octets containing one bit per VLAN. The
       first octet corresponds to VLANs with VlanIndex values
       1 through 8; the second octet to VLANs 9 through
       16 etc.  The most significant bit of each octet
       corresponds to the lowest VlanIndex value in that octet.
       The set of vlans configured by management to map for this
       Instance.  If the VlanId to Instance Mapping has to be known
       then any one of the VlanMapped object should be used.If a
       vlan is already mapped to this Instance, it may not be mapped
       again. This object is used only for SET operation.
       GET Operation returns null values."
   ::= { dot1sVlanInstanceMappingEntry 4 }

dot1sResetVlanList OBJECT-TYPE
   SYNTAX     OCTET STRING (SIZE (0..512))
   MAX-ACCESS read-write
   STATUS     current
   DESCRIPTION
      "A string of octets containing one bit per VLAN. The
       first octet corresponds to VLANs with VlanIndex values
       1 through 8; the second octet to VLANs 9 through
       16 etc.  The most significant bit of each octet
       corresponds to the lowest VlanIndex value in that octet.
       The set of vlans configured by management to unmap from this
       Instance. A vlan may not be unmapped from this instance if
       it is not already mapped to this Instance. This object is
       used only for SET operation.GET Operation returns null values."
   ::= { dot1sVlanInstanceMappingEntry 5 }

dot1sInstanceVlanMapped OBJECT-TYPE
   SYNTAX     OCTET STRING (SIZE (0..128))
   MAX-ACCESS read-only
   STATUS     current
   DESCRIPTION
      "A string of octets containing one bit per VLAN. The
       first octet corresponds to VLANs with VlanIndex values
       1 through 8; the second octet to VLANs 9 through
       16 etc.  The most significant bit of each octet
       corresponds to the lowest VlanIndex value in that octet.
     
       For each VLAN that is mapped to this MSTP instance,
       the bit corresponding to that VLAN is set to '1'."
   ::= { dot1sVlanInstanceMappingEntry 6 }

dot1sInstanceVlanMapped2k OBJECT-TYPE
   SYNTAX     OCTET STRING (SIZE (0..128))
   MAX-ACCESS read-only
   STATUS     current
   DESCRIPTION
      "A string of octets containing one bit per VLAN for
       VLANS with VlanIndex values 1024 through 2047. The
       first octet corresponds to VLANs with VlanIndex values
       1024 through 1031; the second octet to VLANs 1032
       through 1039 etc.  The most significant bit of each
       octet corresponds to the lowest VlanIndex value in that
       octet.

       For each VLAN that is mapped to this MSTP instance,
       the bit corresponding to that VLAN is set to '1'.

       This object is only instantiated on devices with
       support for VlanIndex values up to 4095."
   ::= { dot1sVlanInstanceMappingEntry 7 }

dot1sInstanceVlanMapped3k OBJECT-TYPE
   SYNTAX     OCTET STRING (SIZE (0..128))
   MAX-ACCESS read-only
   STATUS     current
   DESCRIPTION
      "A string of octets containing one bit per VLAN for
       VLANS with VlanIndex values 2048 through 3071. The
       first octet corresponds to VLANs with VlanIndex values
       of 2048 through 2055; the second octet to VLANs 2056
       through 2063 etc.  The most significant bit of each
       octet corresponds to the lowest VlanIndex value in that
       octet.
     
       For each VLAN that is mapped to this MSTP instance,
       the bit corresponding to that VLAN is set to '1'.
     
       This object is only instantiated on devices with
       support for VlanIndex values up to 4095."
   ::= { dot1sVlanInstanceMappingEntry 8 }

dot1sInstanceVlanMapped4k OBJECT-TYPE
   SYNTAX     OCTET STRING (SIZE (0..128))
   MAX-ACCESS read-only
   STATUS     current
   DESCRIPTION
      "A string of octets containing one bit per VLAN for
       VLANS with VlanIndex values 3072 through 4095. The
       first octet corresponds to VLANs with VlanIndex values
       3072 through 3079; the second octet to VLANs 3080
       through 3087 etc.  The most significant bit of each
       octet corresponds to the lowest VlanIndex value in that
       octet.

       For each VLAN that is mapped to this MSTP instance,
       the bit corresponding to that VLAN is set to '1'.

       This object is only instantiated on devices with
       support for VlanIndex values up to 4095."
   ::= { dot1sVlanInstanceMappingEntry 9 }

dot1sCistPortTable OBJECT-TYPE
   SYNTAX      SEQUENCE OF TabDot1sCistPortEntry
   MAX-ACCESS  not-accessible
   STATUS      current
   DESCRIPTION
      "This table contains Common Spanning Tree Port
       Information."
    ::= { dot1sMst 6 }

dot1sCistPortEntry OBJECT-TYPE
   SYNTAX      TabDot1sCistPortEntry
   MAX-ACCESS  not-accessible
   STATUS      current
   DESCRIPTION
      "A list of information maintained by every port for
       Common Spanning tree."
   INDEX { dot1sCistPort }
   ::= { dot1sCistPortTable 1 }

TabDot1sCistPortEntry ::=
   SEQUENCE {
      dot1sCistPort
         Integer32,
      dot1sCistPortPathCost
         Integer32,
      dot1sCistPortPriority
         Integer32,
      dot1sCistPortDesignatedRoot
         BridgeId,
      dot1sCistPortDesignatedBridge
         BridgeId,
      dot1sCistPortDesignatedPort
         OCTET STRING,
      dot1sCistPortAdminP2P
         INTEGER,
      dot1sCistPortOperP2P
         TruthValue,
      dot1sCistPortAdminEdgeStatus
         TruthValue,
      dot1sCistPortOperEdgeStatus
         TruthValue,
      dot1sCistPortProtocolMigration
         TruthValue,
      dot1sCistPortState
         INTEGER,
      dot1sCistForcePortState
         INTEGER,
      dot1sCistPortForwardTransitions
         Counter32,
      dot1sCistPortRxMstBpduCount
         Counter32,
      dot1sCistPortRxRstBpduCount
         Counter32,
      dot1sCistPortRxConfigBpduCount
         Counter32,
      dot1sCistPortRxTcnBpduCount
         Counter32,
      dot1sCistPortTxMstBpduCount
         Counter32,
      dot1sCistPortTxRstBpduCount
         Counter32,
      dot1sCistPortTxConfigBpduCount
         Counter32,
      dot1sCistPortTxTcnBpduCount
         Counter32,
      dot1sCistPortInvalidMstBpduRxCount
         Counter32,
      dot1sCistPortInvalidRstBpduRxCount
         Counter32,
      dot1sCistPortInvalidConfigBpduRxCount
         Counter32,
      dot1sCistPortInvalidTcnBpduRxCount
         Counter32,
      dot1sCistPortTransmitSemState
         INTEGER,
      dot1sCistPortReceiveSemState
         INTEGER,
      dot1sCistPortProtMigrationSemState
         INTEGER,
      dot1sCistProtocolMigrationCount
         Counter32,
      dot1sCistPortDesignatedCost
         Integer32,
      dot1sCistPortRegionalRoot
         BridgeId,
      dot1sCistPortRegionalPathCost
         Integer32,
      dot1sCistSelectedPortRole
         INTEGER,
      dot1sCistCurrentPortRole
         INTEGER,
      dot1sCistPortInfoSemState
         INTEGER,
      dot1sCistPortRoleTransitionSemState
         INTEGER,
      dot1sCistPortStateTransitionSemState
         INTEGER,
      dot1sCistPortTopologyChangeSemState
         INTEGER,
      dot1sCistPortHelloTime
         Timeout,
      dot1sCistPortOperVersion
         INTEGER,
      dot1sCistPortEffectivePortState
         TruthValue,
      dot1sCistPortAutoEdgeStatus
         TruthValue,
      dot1sCistPortRestrictedRole
         TruthValue,
      dot1sCistPortRestrictedTCN
         TruthValue
   }

dot1sCistPort OBJECT-TYPE
      SYNTAX      Integer32 (1..65535)
      MAX-ACCESS  not-accessible
      STATUS      current
      DESCRIPTION
          "The Port number of the port for which this entry contains
           spanning tree information."
      ::= { dot1sCistPortEntry 1 }

dot1sCistPortPathCost OBJECT-TYPE
      SYNTAX      Integer32 (1..200000000)
      MAX-ACCESS  read-write
      STATUS      current
      DESCRIPTION
            "The contribution of this port to the path cost of
             paths towards the CIST Root which include this port."
      ::= { dot1sCistPortEntry 2 }

dot1sCistPortPriority OBJECT-TYPE
      SYNTAX      Integer32 (0..240)
      MAX-ACCESS  read-write
      STATUS      current
      DESCRIPTION
          "The four most significant bits of the Port Identifier
          of the Spanning Tree instance can be modified by setting
          the CistPortPriority value. The values that are set for Port
          Priority must be in steps of 16."
     DEFVAL {128}
      ::= { dot1sCistPortEntry 3 }

dot1sCistPortDesignatedRoot OBJECT-TYPE
      SYNTAX      BridgeId
      MAX-ACCESS  read-only
      STATUS      current
      DESCRIPTION
          "The unique Bridge Identifier of the bridge recorded as the
           CIST Root in the configuration BPDUs transmitted."
      ::= { dot1sCistPortEntry 4 }

dot1sCistPortDesignatedBridge OBJECT-TYPE
      SYNTAX      BridgeId
      MAX-ACCESS  read-only
      STATUS      current
      DESCRIPTION
          "The unique Bridge Identifier of the bridge which this port
           considers to be the Designated Bridge for the port's segment."
      ::= { dot1sCistPortEntry 5 }

dot1sCistPortDesignatedPort OBJECT-TYPE
      SYNTAX  OCTET STRING (SIZE (2))
      MAX-ACCESS  read-only
      STATUS      current
      DESCRIPTION
          "The Port identifier of the port on the Designated Bridge
           for this port's segment."
      ::= { dot1sCistPortEntry 6 }

dot1sCistPortAdminP2P OBJECT-TYPE
      SYNTAX      INTEGER {
                    forceTrue(0),
                    forceFalse(1),
                    auto(2)
                  }
      MAX-ACCESS  read-write
      STATUS      current
      DESCRIPTION
          "The administrative point-to-point status of the LAN segment
          attached to this port.  A value of forceTrue(0) indicates that
          this port should always be treated as if it is connected to
          a point-to-point link.  A value of forceFalse(1) indicates
          that this port should be treated as having a shared media
          connection.  A value of auto(2) indicates that this port is
          considered to have a point-to-point link if it is an Aggregator
          and all of its members are aggregatable, or if the MAC entity
          is configured for full duplex operation, either through
          auto-negotiation or by management means."
      ::= { dot1sCistPortEntry 7 }

dot1sCistPortOperP2P OBJECT-TYPE
      SYNTAX      TruthValue
      MAX-ACCESS  read-only
      STATUS      current
      DESCRIPTION
          "The operational point-to-point status of the LAN segment
          attached to this port.  It indicates whether a port is
          considered to have a point-to-point connection or not.
          The value is determined by management or by auto-detection,
          as described in the dot1sCistPortAdminP2P object."
      ::= { dot1sCistPortEntry 8 }

dot1sCistPortAdminEdgeStatus OBJECT-TYPE
      SYNTAX      TruthValue
      MAX-ACCESS  read-write
      STATUS      current
      DESCRIPTION
          "The administrative value of the Edge Port parameter.  A
          value of TRUE(1) indicates that this port should be
          assumed as an edge-port and a value of FALSE(2) indicates
          that this port should be assumed as a non-edge-port."
      ::= { dot1sCistPortEntry 9 }

dot1sCistPortOperEdgeStatus OBJECT-TYPE
      SYNTAX      TruthValue
      MAX-ACCESS  read-only
      STATUS      current
      DESCRIPTION
          "The operational value of the Edge Port parameter.  The
          object is initialized to the value of
          dot1sCistPortAdminEdgeStatus and is set FALSE on reception
          of a BPDU."
      ::= { dot1sCistPortEntry 10 }

dot1sCistPortProtocolMigration OBJECT-TYPE
      SYNTAX      TruthValue
      MAX-ACCESS  read-write
      STATUS      current
      DESCRIPTION
          "Indicates the Protocol migration state of this Port.
           When operating in RSTP/MSTP (version >= 2) mode, writing
          TRUE(1) to this object forces this port to transmit MSTP
          BPDUs without instance information.
          Any other operation on this object has no effect and
          it always returns FALSE(2) when read."
      ::= { dot1sCistPortEntry 11 }

dot1sCistPortState OBJECT-TYPE
      SYNTAX      INTEGER {
                  disabled (1),
                  discarding (2),
                  learning (4),
                  forwarding (5)
                  }
      MAX-ACCESS  read-only
      STATUS      current
      DESCRIPTION
          "Current state of the Port as defined by the Common
           spanning tree protocol."
      ::= { dot1sCistPortEntry 12 }

dot1sCistForcePortState OBJECT-TYPE
      SYNTAX      INTEGER {
                   disabled(0),
                   enabled(1)
                  }
      MAX-ACCESS  read-write
      STATUS      current
      DESCRIPTION
          "Current state of the Port which can be changed to either
           Disabled or Enabled for ALL spanning tree
           instances. Setting this object will override the port's
           status in any of the MSTI contexts"
      ::= { dot1sCistPortEntry 13 }

dot1sCistPortForwardTransitions OBJECT-TYPE
      SYNTAX      Counter32
      MAX-ACCESS  read-only
      STATUS      current
      DESCRIPTION
          "Number of times this port has transitioned to the
           Forwarding State."
      ::= { dot1sCistPortEntry 14 }

dot1sCistPortRxMstBpduCount OBJECT-TYPE
      SYNTAX      Counter32
      MAX-ACCESS  read-only
      STATUS      current
      DESCRIPTION
          "Number of MST BPDUs received on this port."
      ::= { dot1sCistPortEntry 15 }

dot1sCistPortRxRstBpduCount OBJECT-TYPE
      SYNTAX      Counter32
      MAX-ACCESS  read-only
      STATUS      current
      DESCRIPTION
          "Number of RST BPDUs received on this port."
      ::= { dot1sCistPortEntry 16 }

dot1sCistPortRxConfigBpduCount OBJECT-TYPE
      SYNTAX      Counter32
      MAX-ACCESS  read-only
      STATUS      current
      DESCRIPTION
          "Number of Configuration BPDUs received on this port."
      ::= { dot1sCistPortEntry 17 }

dot1sCistPortRxTcnBpduCount OBJECT-TYPE
      SYNTAX      Counter32
      MAX-ACCESS  read-only
      STATUS      current
      DESCRIPTION
          "Number of TCN BPDUs received on this port."
      ::= { dot1sCistPortEntry 18 }

dot1sCistPortTxMstBpduCount OBJECT-TYPE
      SYNTAX      Counter32
      MAX-ACCESS  read-only
      STATUS      current
      DESCRIPTION
          "Number of MST BPDUs Transmitted from this port."
      ::= { dot1sCistPortEntry 19 }

dot1sCistPortTxRstBpduCount OBJECT-TYPE
      SYNTAX      Counter32
      MAX-ACCESS  read-only
      STATUS      current
      DESCRIPTION
          "Number of RST BPDUs Transmitted from this port."
      ::= { dot1sCistPortEntry 20 }

dot1sCistPortTxConfigBpduCount OBJECT-TYPE
      SYNTAX      Counter32
      MAX-ACCESS  read-only
      STATUS      current
      DESCRIPTION
          "Number of Configuration BPDUs Transmitted from this port."
      ::= { dot1sCistPortEntry 21 }

dot1sCistPortTxTcnBpduCount OBJECT-TYPE
      SYNTAX      Counter32
      MAX-ACCESS  read-only
      STATUS      current
      DESCRIPTION
          "Number of TCN BPDUs Transmitted from this port."
      ::= { dot1sCistPortEntry 22 }

dot1sCistPortInvalidMstBpduRxCount OBJECT-TYPE
      SYNTAX      Counter32
      MAX-ACCESS  read-only
      STATUS      current
      DESCRIPTION
          "Number of Invalid MST BPDUs Received on this port."
      ::= { dot1sCistPortEntry 23 }

dot1sCistPortInvalidRstBpduRxCount OBJECT-TYPE
      SYNTAX      Counter32
      MAX-ACCESS  read-only
      STATUS      current
      DESCRIPTION
          "Number of Invalid RST BPDUs Received on this port."
      ::= { dot1sCistPortEntry 24 }

dot1sCistPortInvalidConfigBpduRxCount OBJECT-TYPE
      SYNTAX      Counter32
      MAX-ACCESS  read-only
      STATUS      current
      DESCRIPTION
          "Number of Invalid Configuration BPDUs Received on this port."
      ::= { dot1sCistPortEntry 25 }

dot1sCistPortInvalidTcnBpduRxCount OBJECT-TYPE
      SYNTAX      Counter32
      MAX-ACCESS  read-only
      STATUS      current
      DESCRIPTION
          "Number of Invalid TCN BPDUs Received on this port."
      ::= { dot1sCistPortEntry 26 }

dot1sCistPortTransmitSemState OBJECT-TYPE
      SYNTAX      INTEGER {
                  transmitinit (0),
                  transmitperiodic (1),
                  transmitconfig (2),
                  transmittcn (3),
                  transmitrstp (4),
                  idle (5)
               }
      MAX-ACCESS  read-only
      STATUS      current
      DESCRIPTION
          "Indicates current State of the Port Transmit state machine."
      ::= { dot1sCistPortEntry 27 }

dot1sCistPortReceiveSemState OBJECT-TYPE
      SYNTAX      INTEGER {
                  discard (0),
                  receive (1)
               }
      MAX-ACCESS  read-only
      STATUS      current
      DESCRIPTION
          "Indicates current State of the Port Receive state machine."
      ::= { dot1sCistPortEntry 28 }

dot1sCistPortProtMigrationSemState OBJECT-TYPE
      SYNTAX      INTEGER {
                  init (0),
                  sendrstp (1),
                  sendingrstp (2),
                  sendstp (3),
                  sendingstp (4)
               }
      MAX-ACCESS  read-only
      STATUS      current
      DESCRIPTION
          "Indicates current State of the Port Protocol Migration
           State machine."
      ::= { dot1sCistPortEntry 29 }

dot1sCistProtocolMigrationCount OBJECT-TYPE
   SYNTAX      Counter32
   MAX-ACCESS  read-only
   STATUS      current
   DESCRIPTION
        "The number of times this Port has migrated from one STP protocol
        version to another. The relevant protocols are STP-COMPATIBLE and
        RSTP/MSTP.
        A Trap is generated on the occurence of this event."
      ::= { dot1sCistPortEntry 30 }

dot1sCistPortDesignatedCost OBJECT-TYPE
      SYNTAX      Integer32
      MAX-ACCESS  read-only
      STATUS      current
      DESCRIPTION
           "The path cost of the Designated Port of the
            segment connected to this port."
      ::= { dot1sCistPortEntry 31 }

dot1sCistPortRegionalRoot OBJECT-TYPE
      SYNTAX      BridgeId
      MAX-ACCESS  read-only
      STATUS      current
      DESCRIPTION
          "The unique Bridge Identifier of the bridge recorded as the
           CIST Regional Root Identifier in the configuration BPDUs
           transmitted."
      ::= { dot1sCistPortEntry 32 }

dot1sCistPortRegionalPathCost OBJECT-TYPE
      SYNTAX      Integer32
      MAX-ACCESS  read-only
      STATUS      current
      DESCRIPTION
          "The contribution of this port to the path cost of paths
           towards the CIST Regional Root which include this port."
      ::= { dot1sCistPortEntry 33 }

dot1sCistSelectedPortRole OBJECT-TYPE
      SYNTAX      INTEGER {
                   disabled(0),
                   alternate(1),
                   backup(2),
                   root(3),
                   designated(4)
                  }
      MAX-ACCESS  read-only
      STATUS      current
      DESCRIPTION
          "Selected Port Role of the port for this spanning
          tree instance."
      ::= { dot1sCistPortEntry 34 }

dot1sCistCurrentPortRole OBJECT-TYPE
      SYNTAX      INTEGER {
                   disabled(0),
                   alternate(1),
                   backup(2),
                   root(3),
                   designated(4)
                  }
      MAX-ACCESS  read-only
      STATUS      current
      DESCRIPTION
          "Current Port Role of the port for this spanning
          tree instance."
      ::= { dot1sCistPortEntry 35 }

dot1sCistPortInfoSemState OBJECT-TYPE
    SYNTAX      INTEGER {
               disabled (0),
               aged (1),
               update (2),
               superiordesg (3),
               repeatdesg (4),
               inferiordesg (5),
               notdesg (6),
               current (7),
               receive (8),
               other (9)
            }
      MAX-ACCESS  read-only
      STATUS      current
      DESCRIPTION
          "Current state of the Port Information State Machine
           for this port in this spanning tree context."
      ::= { dot1sCistPortEntry 36 }

dot1sCistPortRoleTransitionSemState OBJECT-TYPE
      SYNTAX      INTEGER {
                  init (0),
                  disableport (1),
                  disabledport (2),
                  rootport (3),
                  designatedport (4),
                  alternateport (5),
                  masterport (6)
               }
      MAX-ACCESS  read-only
      STATUS      current
      DESCRIPTION
          "Current state of the Port Role Transition State Machine
           for this port in this spanning tree context."
      ::= { dot1sCistPortEntry 37 }

dot1sCistPortStateTransitionSemState OBJECT-TYPE
      SYNTAX      INTEGER {
                  discarding (0),
                  learning (1),
                  forwarding (2)
               }
      MAX-ACCESS  read-only
      STATUS      current
      DESCRIPTION
          "Current state of the Port State Transition State Machine
           for this port in this spanning tree context."
      ::= { dot1sCistPortEntry 38 }

dot1sCistPortTopologyChangeSemState OBJECT-TYPE
      SYNTAX      INTEGER {
                  inactive (0),
                  learning (1),
                  detected (2),
                  active (3),
                  notifiedtcn (4),
                  notifiedtc (5),
                  propagating (6),
                  acknowledged (7)
               }
      MAX-ACCESS  read-only
      STATUS      current
      DESCRIPTION
          "Current state of the Topology Change State Machine
           for this port in this spanning tree context."
      ::= { dot1sCistPortEntry 39 }

dot1sCistPortHelloTime OBJECT-TYPE
   SYNTAX      Timeout (100..200)
   MAX-ACCESS  read-write
   STATUS      current
   DESCRIPTION
      "The amount of time between the transmission of
       Configuration bridge PDUs by this node on this port
       in units of hundredths of a second."
      ::= { dot1sCistPortEntry 40 }

dot1sCistPortOperVersion OBJECT-TYPE
   SYNTAX      INTEGER {
               stpCompatible(0),
               rstp(2),
               mstp(3)
            }
   MAX-ACCESS  read-only
   STATUS      current
   DESCRIPTION
      "This indicates whether the Port is operationally in the Mstp
       mode, Rstp mode or the Stp-compatible mode i.e., whether the
       Port is transmitting MST BPDUs, RST BPDUs or Config/TCN BPDUs."
      ::= { dot1sCistPortEntry 41 }

dot1sCistPortEffectivePortState OBJECT-TYPE
      SYNTAX      TruthValue
      MAX-ACCESS  read-only
      STATUS      current
      DESCRIPTION
          "The effective operational state of the port for CIST. This will
          TRUE only when the port is operationally up in the Interface level
          and Protocol level for CIST. This is will be set to False for all
          other times."

      ::= { dot1sCistPortEntry 42 }

dot1sCistPortAutoEdgeStatus OBJECT-TYPE
      SYNTAX      TruthValue
      MAX-ACCESS  read-write
      STATUS      current
      DESCRIPTION
          "This parameter when TRUE(1) indicates that detection
          of a port as Edge Port happens automatically
          and FALSE(2) indicates that this feature is disabled."
      ::= { dot1sCistPortEntry 43 }

dot1sCistPortRestrictedRole OBJECT-TYPE
    SYNTAX      TruthValue
    MAX-ACCESS  read-write
    STATUS      current
    DESCRIPTION
        "A Boolean value set by management. If TRUE causes the Port not
        to be selected as Root Port for the CIST or any MSTI, even it has
        the best spanning tree priority vector. Such a Port will be selected
        as an Alternate Port after the Root Port has been selected. This
        parameter should be FALSE by default. If set it can cause lack of
        spanning tree connectivity. It is set by a network administrator to
        prevent bridges external to a core region of the network influencing
        the spanning tree active topology, possibly because those bridges are
        not under the full control of the administrator.

        This administrator configuration is also known as 'Root Guard'."

        ::= {dot1sCistPortEntry 44}

dot1sCistPortRestrictedTCN OBJECT-TYPE
    SYNTAX      TruthValue
    MAX-ACCESS  read-write
    STATUS      current
    DESCRIPTION
        "A Boolean value set by management. If TRUE causes the Port not
        to propagate received topology change notifications and topology
        changes to other Ports. This parameter should be FALSE by default.
        If set it can cause temporary loss of connectivity after changes in
        a spanning trees active topology as a result of persistent
        incorrectly learnt station location information. It is set by a
        network administrator to prevent bridges external to a core region of
        the network causing address flushing in that region, possibly because
        those bridges are not under the full control of the administrator or
        MAC_Operational for the attached LANs transitions frequently."

        ::= {dot1sCistPortEntry 45}

-- -----------------------------------------------------------------
-- Future Mst Multiple Spanning Tree Instance Port Table
-- -----------------------------------------------------------------
dot1sMstiPortTable OBJECT-TYPE
   SYNTAX      SEQUENCE OF TabDot1sMstiPortEntry
   MAX-ACCESS  not-accessible
   STATUS      current
   DESCRIPTION
      "This table contains Spanning Tree Instance Specific Port
       Information."
   ::= { dot1sMst 7 }

dot1sMstiPortEntry OBJECT-TYPE
   SYNTAX      TabDot1sMstiPortEntry
   MAX-ACCESS  not-accessible
   STATUS      current
   DESCRIPTION
      "A list of information maintained by every port for each
       and every spanning tree instance."
   INDEX { dot1sMstiPort, dot1sInstanceIndex }
   ::= { dot1sMstiPortTable 1 }

TabDot1sMstiPortEntry ::=
   SEQUENCE {
      dot1sMstiPort
         Integer32,
      dot1sMstiPortPathCost
         Integer32,
      dot1sMstiPortPriority
         Integer32,
      dot1sMstiPortDesignatedRoot
         BridgeId,
      dot1sMstiPortDesignatedBridge
         BridgeId,
      dot1sMstiPortDesignatedPort
         OCTET STRING,
      dot1sMstiPortState
         INTEGER,
      dot1sMstiForcePortState
         INTEGER,
      dot1sMstiPortForwardTransitions
         Counter32,
      dot1sMstiPortReceivedBPDUs
         Counter32,
      dot1sMstiPortTransmittedBPDUs
         Counter32,
      dot1sMstiPortInvalidBPDUsRcvd
         Counter32,
      dot1sMstiPortDesignatedCost
         Integer32,
      dot1sMstiSelectedPortRole
         INTEGER,
      dot1sMstiCurrentPortRole
         INTEGER,
      dot1sMstiPortInfoSemState
         INTEGER,
      dot1sMstiPortRoleTransitionSemState
         INTEGER,
      dot1sMstiPortStateTransitionSemState
         INTEGER,
      dot1sMstiPortTopologyChangeSemState
         INTEGER,
      dot1sMstiPortEffectivePortState
         TruthValue
   }

dot1sMstiPort OBJECT-TYPE
   SYNTAX      Integer32 (1..65535)
   MAX-ACCESS  not-accessible
   STATUS      current
   DESCRIPTION
      "The Port number of the port for which this entry contains
       spanning tree information."
   ::= { dot1sMstiPortEntry 1 }

dot1sMstiPortPathCost OBJECT-TYPE
   SYNTAX      Integer32 (1..200000000)
   MAX-ACCESS  read-write
   STATUS      current
   DESCRIPTION
      "The contribution of this port to the path cost of
       paths towards the MSTI Root which include this port."
   ::= { dot1sMstiPortEntry 2 }

dot1sMstiPortPriority OBJECT-TYPE
   SYNTAX      Integer32 (0..240)
   MAX-ACCESS  read-write
   STATUS      current
   DESCRIPTION
      "The four most significant bits of the Port Identifier
       for a given Spanning Tree instance can be modified
       independently for each Spanning Tree instance
       supported by the Bridge. The values that are set for Port
       Priority must be in steps of 16."
   DEFVAL {128}
   ::= { dot1sMstiPortEntry 3 }

dot1sMstiPortDesignatedRoot OBJECT-TYPE
   SYNTAX      BridgeId
   MAX-ACCESS  read-only
   STATUS      current
   DESCRIPTION
      "The unique Bridge Identifier of the bridge recorded as the
       MSTI Regional Root in the configuration BPDUs transmitted."
   ::= { dot1sMstiPortEntry 4 }

dot1sMstiPortDesignatedBridge OBJECT-TYPE
   SYNTAX      BridgeId
   MAX-ACCESS  read-only
   STATUS      current
   DESCRIPTION
      "The unique Bridge Identifier of the bridge which this port
       considers to be the Designated Bridge for the port's segment."
   ::= { dot1sMstiPortEntry 5 }

dot1sMstiPortDesignatedPort OBJECT-TYPE
   SYNTAX  OCTET STRING (SIZE (2))
   MAX-ACCESS  read-only
   STATUS      current
   DESCRIPTION
      "The Port identifier of the port on the Designated Bridge
       for this port's segment."
   ::= { dot1sMstiPortEntry 6 }

dot1sMstiPortState OBJECT-TYPE
   SYNTAX      INTEGER {
                disabled (1),
                discarding (2),
                learning (4),
                forwarding (5)
               }
   MAX-ACCESS  read-only
   STATUS      current
   DESCRIPTION
      "Current state of the Port as defined by the Multiple
       spanning tree protocol. Port which is Forwarding state
       in one instance can be in Discarding (Blocking) state
       in another instance."
   ::= { dot1sMstiPortEntry 7 }

dot1sMstiForcePortState OBJECT-TYPE
   SYNTAX      INTEGER {
                disabled(0),
                enabled(1)
               }
   MAX-ACCESS  read-write
   STATUS      current
   DESCRIPTION
      "Current state of the Port which can be changed to either
       Disabled or Enabled for the specific spanning tree
       instance. This object can be set to enabled only if the
       'dot1sCistForcePortState' is set to 'enabled' for this port"
   ::= { dot1sMstiPortEntry 8 }

dot1sMstiPortForwardTransitions OBJECT-TYPE
   SYNTAX      Counter32
   MAX-ACCESS  read-only
   STATUS      current
   DESCRIPTION
      "Number of times this port has transitioned to the
       Forwarding State for specific instance."
   ::= { dot1sMstiPortEntry 9 }

dot1sMstiPortReceivedBPDUs OBJECT-TYPE
   SYNTAX      Counter32
   MAX-ACCESS  read-only
   STATUS      current
   DESCRIPTION
      "Number of BPDUs received by this port for this
       spanning tree instance."
   ::= { dot1sMstiPortEntry 10 }

dot1sMstiPortTransmittedBPDUs OBJECT-TYPE
   SYNTAX      Counter32
   MAX-ACCESS  read-only
   STATUS      current
   DESCRIPTION
      "Number of BPDUs transmitted on this port for
       this spanning tree instance."
   ::= { dot1sMstiPortEntry 11 }

dot1sMstiPortInvalidBPDUsRcvd OBJECT-TYPE
   SYNTAX      Counter32
   MAX-ACCESS  read-only
   STATUS      current
   DESCRIPTION
      "Number of Invalid BPDUs received on this Port
        for this spanning tree instance."
   ::= { dot1sMstiPortEntry 12 }

dot1sMstiPortDesignatedCost OBJECT-TYPE
   SYNTAX      Integer32
   MAX-ACCESS  read-only
   STATUS      current
   DESCRIPTION
      "The path cost of the Designated Port of the
       segment connected to this port."
   ::= { dot1sMstiPortEntry 13 }

dot1sMstiSelectedPortRole OBJECT-TYPE
   SYNTAX      INTEGER {
                disabled(0),
                alternate(1),
                backup(2),
                root(3),
                designated(4),
                master(5)
               }
   MAX-ACCESS  read-only
   STATUS      current
   DESCRIPTION
      "Selected Port Role of the port for this spanning
       tree instance."
   ::= { dot1sMstiPortEntry 14 }

dot1sMstiCurrentPortRole OBJECT-TYPE
   SYNTAX      INTEGER {
                disabled(0),
                alternate(1),
                backup(2),
                root(3),
                designated(4),
                master(5)
               }
   MAX-ACCESS  read-only
   STATUS      current
   DESCRIPTION
      "Current Port Role of the port for this spanning
       tree instance."
   ::= { dot1sMstiPortEntry 15 }

dot1sMstiPortInfoSemState OBJECT-TYPE
   SYNTAX      INTEGER {
                disabled (0),
                aged (1),
                update (2),
                superiordesg (3),
                repeatdesg (4),
                inferiordesg (5),
                notdesg (6),
                current (7),
                receive (8),
                other (9)
               }
   MAX-ACCESS  read-only
   STATUS      current
   DESCRIPTION
      "Current state of the Port Information State Machine
       for this port in this spanning tree context."
   ::= { dot1sMstiPortEntry 16 }

dot1sMstiPortRoleTransitionSemState OBJECT-TYPE
   SYNTAX      INTEGER {
                init (0),
                disableport (1),
                disabledport (2),
                rootport (3),
                designatedport (4),
                alternateport (5),
                masterport (6)
               }
   MAX-ACCESS  read-only
   STATUS      current
   DESCRIPTION
      "Current state of the Port Role Transition State Machine
       for this port in this spanning tree context."
   ::= { dot1sMstiPortEntry 17 }

dot1sMstiPortStateTransitionSemState OBJECT-TYPE
   SYNTAX      INTEGER {
                discarding (0),
                learning (1),
                forwarding (2)
               }
   MAX-ACCESS  read-only
   STATUS      current
   DESCRIPTION
      "Current state of the Port State Transition State Machine
       for this port in this spanning tree context."
   ::= { dot1sMstiPortEntry 18 }

dot1sMstiPortTopologyChangeSemState OBJECT-TYPE
   SYNTAX      INTEGER {
                inactive (0),
                learning (1),
                detected (2),
                active (3),
                notifiedtcn (4),
                notifiedtc (5),
                propagating (6),
                acknowledged (7)
               }
   MAX-ACCESS  read-only
   STATUS      current
   DESCRIPTION
      "Current state of the Topology Change State Machine
       for this port in this spanning tree context."
   ::= { dot1sMstiPortEntry 19 }

dot1sMstiPortEffectivePortState OBJECT-TYPE
   SYNTAX      TruthValue
   MAX-ACCESS  read-only
   STATUS      current
   DESCRIPTION
      "The effective operational stae of the port for specific instance.
       This is will be TRUE only when the port is operationally up in the
       interface level and Protocol level for the specific instance.
       This is will be set to false at all other times."
   ::= { dot1sMstiPortEntry 20 }


-- Dot1s Trap Control

dot1sMstSetGlobalTrapOption OBJECT-TYPE
   SYNTAX       Integer32 (0..1)
   MAX-ACCESS   read-write
   STATUS       current
   DESCRIPTION
      "This object is used to enable and disable MSTP traps for memory
       failure or buffer failure irrespective of the context in which
       the failure occurs.
       0 - Traps are not enabled.
       1 - Memory and buffer failure traps enabled"
   ::= { dot1sMstTrapsControl 1 }

dot1sGlobalErrTrapType OBJECT-TYPE
   SYNTAX      INTEGER {
                none (0),
                memfail (1),
                bufffail (2)
               }
   MAX-ACCESS  read-only
   STATUS      current
   DESCRIPTION
      "Used within the Trap Notification PDU.
       It returns the following values
       none - none of the below values
       memfail - memory allocation failure
       bufffail - buffer allocation failure"
   ::= { dot1sMstTrapsControl 2 }

dot1sMstTrapsControlTable OBJECT-TYPE
   SYNTAX        SEQUENCE OF TabDot1sMstTrapsControlEntry
   MAX-ACCESS    not-accessible
   STATUS        current
   DESCRIPTION
      "List of per virtual bridge Trap Control Info."
   ::= { dot1sMstTrapsControl 3 }

dot1sMstTrapsControlEntry OBJECT-TYPE
   SYNTAX        TabDot1sMstTrapsControlEntry
   MAX-ACCESS    not-accessible
   STATUS        current
   DESCRIPTION
      "Virtual bridge TrapsControl information."
   INDEX { dot1sMstContextId }
   ::= { dot1sMstTrapsControlTable 1 }

TabDot1sMstTrapsControlEntry ::=
   SEQUENCE {
      dot1sSetTraps
         Integer32,
      dot1sGenTrapType
         INTEGER
   }

dot1sSetTraps OBJECT-TYPE
   SYNTAX       Integer32 (0..3)
   MAX-ACCESS   read-write
   STATUS       current
   DESCRIPTION
      "This object is used to enable and  disable context-specific
       MSTP traps. Currently the following are defined
       0 - Traps are not enabled.
       1 - General Traps like protocol up or down
       2 - Exception Traps like port protocol migration or
           invalid packet rcvd in port
       3 - All the above Traps "
   ::= { dot1sMstTrapsControlEntry 1 }

dot1sGenTrapType OBJECT-TYPE
   SYNTAX      INTEGER {
                none (0),
                up (1),
                down (2)
               }
   MAX-ACCESS  read-only
   STATUS  current
   DESCRIPTION
      "Used within the Trap Notification PDU.
       It denotes general events like
       none - none of the below values
       up - protocol UP,
       down - protocol DOWN"
   ::= { dot1sMstTrapsControlEntry 2 }

dot1sPortTrapNotificationTable OBJECT-TYPE
   SYNTAX SEQUENCE OF TabDot1sPortTrapNotificationEntry
   MAX-ACCESS not-accessible
   STATUS     current
   DESCRIPTION
      "This table is used to store the notification information
       occured in each of the port for protocol migration and
       invalid packet received. This table is maintained per virtual
       context in the system."
   ::= { dot1sMstTrapsControl 4 }

dot1sPortTrapNotificationEntry OBJECT-TYPE
   SYNTAX      TabDot1sPortTrapNotificationEntry
   MAX-ACCESS  not-accessible
   STATUS      current
   DESCRIPTION
      "This entry is used to store the notification information"
   INDEX { dot1sPortTrapIndex}
   ::= { dot1sPortTrapNotificationTable 1 }

TabDot1sPortTrapNotificationEntry ::=
   SEQUENCE {
      dot1sPortTrapIndex
         Integer32,
      dot1sPortMigrationType
         INTEGER,
      dot1sPktErrType
         INTEGER,
      dot1sPktErrVal
         Integer32
   }

dot1sPortTrapIndex OBJECT-TYPE
   SYNTAX      Integer32 (1..4096)
   MAX-ACCESS  not-accessible
   STATUS      current
   DESCRIPTION
      "A unique value, greater than zero, indicating the Port number."
   ::= { dot1sPortTrapNotificationEntry 1 }

dot1sPortMigrationType OBJECT-TYPE
   SYNTAX      INTEGER {
                sendstp (0),
                sendrstp (1)
               }
   MAX-ACCESS  read-only
   STATUS      current
   DESCRIPTION
      "Port Protocol migration type occured in the port"
  ::= { dot1sPortTrapNotificationEntry 2 }

dot1sPktErrType OBJECT-TYPE
   SYNTAX      INTEGER {
                protocolIdErr(0),
                invalidBpdu(1),
                configLengthErr(2),
                tcnLengthErr(3),
                rstpLengthErr(4),
                maxAgeErr(5),
                fwdDelayErr(6),
                helloTimeErr(7),
                mstpLengthErr(8)
               }
   MAX-ACCESS  read-only
   STATUS      current
   DESCRIPTION
      "Type of invalid packet received in each of the port "
   ::= { dot1sPortTrapNotificationEntry 3 }

dot1sPktErrVal OBJECT-TYPE
   SYNTAX      Integer32
   MAX-ACCESS  read-only
   STATUS      current
   DESCRIPTION
      "Packet error value corresponding to the above type "
   ::= { dot1sPortTrapNotificationEntry 4 }

dot1sPortRoleTrapNotificationTable OBJECT-TYPE
   SYNTAX SEQUENCE OF TabDot1sPortRoleTrapNotificationEntry
   MAX-ACCESS not-accessible
   STATUS     current
   DESCRIPTION
      "This table is used to store the notification information
       occured in each of the port for its role change. This table
       is maintained per virtual context in the system."
   ::= { dot1sMstTrapsControl 5 }

dot1sPortRoleTrapNotificationEntry OBJECT-TYPE
   SYNTAX      TabDot1sPortRoleTrapNotificationEntry
   MAX-ACCESS  not-accessible
   STATUS      current
   DESCRIPTION
      "This entry is used to store the notification information"
   INDEX { dot1sPortTrapIndex, dot1sMstiInstanceIndex }
   ::= { dot1sPortRoleTrapNotificationTable 1 }

TabDot1sPortRoleTrapNotificationEntry ::=
   SEQUENCE {
      dot1sPortRoleType
         INTEGER,
      dot1sOldRoleType
         INTEGER
   }

dot1sPortRoleType OBJECT-TYPE
   SYNTAX      INTEGER {
                disabledPort(0),
                alternatePort(1),
                backupPort(2),
                rootPort(3),
                designatedPort(4),
                masterport(5)
               }
   MAX-ACCESS  read-only
   STATUS      current
   DESCRIPTION
      "Particular Role Selected for the Port"
   ::= { dot1sPortRoleTrapNotificationEntry 1 }

dot1sOldRoleType OBJECT-TYPE
   SYNTAX      INTEGER {
                disabledPort(0),
                alternatePort(1),
                backupPort(2),
                rootPort(3),
                designatedPort(4),
                masterport(5)
               }
   MAX-ACCESS  read-only
   STATUS      current
   DESCRIPTION
      "Particular Role which is existing for the Port"
  ::= { dot1sPortRoleTrapNotificationEntry 2 }


-- Dot1s Trap

dot1sTraps OBJECT IDENTIFIER ::= { dot1sMstTraps 0 }

dot1sGlobalErrTrap NOTIFICATION-TYPE
   OBJECTS {
      dot1sBrgAddress,
      dot1sGlobalErrTrapType
   }
   STATUS             current
   DESCRIPTION
      "Generated when any of the error events like memory failure or buffer failure
       or protocol migration or new root or topology change occurs "
   ::= { dot1sTraps 1 }

dot1sGenTrap NOTIFICATION-TYPE
   OBJECTS {
      dot1sBrgAddress,
      dot1sContextName,
      dot1sGenTrapType
   }
   STATUS             current
   DESCRIPTION
      "Generated when any of the general events like protocol up or
       protocol down occurs"
   ::= { dot1sTraps 2 }

dot1sNewRootTrap NOTIFICATION-TYPE
   OBJECTS {
      dot1sBrgAddress,
      dot1sContextName,
      dot1sOldDesignatedRoot,
      dot1sMstiBridgeRegionalRoot
   }
   STATUS             current
   DESCRIPTION
      "Generated whenever a new root bridge is selected in the topology "
   ::= { dot1sTraps 3 }

dot1sTopologyChgTrap NOTIFICATION-TYPE
   OBJECTS {
      dot1sBrgAddress,
      dot1sContextName,
      dot1sMstiTopChanges
   }
   STATUS             current
   DESCRIPTION
      "Generated when topology change is detected "
   ::= { dot1sTraps 4 }

dot1sProtocolMigrationTrap NOTIFICATION-TYPE
   OBJECTS {
      dot1sBrgAddress,
      dot1sContextName,
      dot1sForceProtocolVersion,
      dot1sPortMigrationType
   }
   STATUS             current
   DESCRIPTION
      "Generated when port protocol migration happens in the port "
   ::= { dot1sTraps 5 }

dot1sInvalidBpduRxdTrap NOTIFICATION-TYPE
   OBJECTS {
      dot1sBrgAddress,
      dot1sContextName,
      dot1sPktErrType,
      dot1sPktErrVal
   }
   STATUS             current
   DESCRIPTION
      "Generated when the invalid packet is received for
       bpdu/stp/rstp/maximum age/forward delay/hello time"
   ::= { dot1sTraps 6 }

dot1sRegionConfigChangeTrap NOTIFICATION-TYPE
   OBJECTS {
      dot1sBrgAddress,
      dot1sContextName,
      dot1sMstiConfigIdSel,
      dot1sMstiRegionName,
      dot1sMstiRegionVersion,
      dot1sMstiConfigDigest
   }
   STATUS             current
   DESCRIPTION
      "Generated when the MST region's configuration
       identifier changes."
   ::= { dot1sTraps 7 }

dot1sNewPortRoleTrap NOTIFICATION-TYPE
   OBJECTS {
      dot1sBrgAddress,
      dot1sPortRoleType,
      dot1sOldRoleType
   }
   STATUS             current
   DESCRIPTION
      "Generated whenever a new role is selected for the port "
   ::= { dot1sTraps 8 }





dot1wRst                   OBJECT IDENTIFIER   ::= { l2Rst 1 }
dot1wRstTrapsControl       OBJECT IDENTIFIER ::= { l2Rst 2 }
dot1wRstTraps              OBJECT IDENTIFIER ::= { l2Rst 3 }


-- Dot1w RST

dot1wRstTable OBJECT-TYPE
   SYNTAX SEQUENCE OF TabDot1wRstEntry
   MAX-ACCESS  not-accessible
   STATUS      current
   DESCRIPTION
      "List of per virtual context RstModule Parameters"
   ::= { dot1wRst 3}

dot1wRstEntry OBJECT-TYPE
   SYNTAX      TabDot1wRstEntry
   MAX-ACCESS  not-accessible
   STATUS      current
   DESCRIPTION
      "Virtual Bridge RstModule Parameters."
   INDEX { dot1wRstContextId }
   ::= { dot1wRstTable 1 }

TabDot1wRstEntry ::=
   SEQUENCE {
      dot1wRstContextId
         Integer32,
      dot1wSystemControl
         INTEGER,
      dot1wModuleStatus
         EnabledStatus,
      dot1wTraceOption
         Integer32,
      dot1wDebugOption
         Integer32,
      dot1wRstpUpCount
         Counter32,
      dot1wRstpDownCount
         Counter32,
      dot1wBufferFailureCount
         Counter32,
      dot1wMemAllocFailureCount
         Counter32,
      dot1wNewRootIdCount
         Counter32,
      dot1wPortRoleSelSmState
         INTEGER,
      dot1wOldDesignatedRoot
         BridgeId,
      dot1wDynamicPathcostCalculation
         TruthValue,
      dot1wContextName
         DisplayString
   }

dot1wRstContextId OBJECT-TYPE
   SYNTAX      Integer32 (0..65535)
   MAX-ACCESS  not-accessible
   STATUS      current
   DESCRIPTION
      "Identifies the Virtual Bridge Context."
   ::= { dot1wRstEntry 1 }

dot1wSystemControl OBJECT-TYPE
   SYNTAX      INTEGER { start(1), shutdown(2) }
   MAX-ACCESS  read-write
   STATUS      current
   DESCRIPTION
      "The administrative system control status requested by management for
       the RSTP feature. The value 'start'(1) indicates that all resources
       required by RSTP should be allocated and RSTP should be supported
       in the device on all ports. The value shutdown(2) indicates that RSTP
       should be shutdown in the device on all ports and all allocated memory
       must be released."
   ::= { dot1wRstEntry 2 }

dot1wModuleStatus OBJECT-TYPE
   SYNTAX      EnabledStatus
   MAX-ACCESS  read-write
   STATUS      current
   DESCRIPTION
      "The administrative module status requested by management for the RSTP
       Module. This enables or disables RSTP in the system. A value of 'enabled'
       (1) indicates that RSTP must be enabled in the device on all the ports.
       A value of 'disabled'(2) indicates that RSTP must be disabled in the
       device on all the ports. This object can be set only after the object
       dot1wSystemControl has been set."
   ::= {dot1wRstEntry 3 }



-- ============================================================================

-- The bit positions within a byte as used in Trace and Debug are as indicated
-- below :

--                -----------------------------
--                | 7 | ..................| 0 |
--                -----------------------------

--The bits are numbered 0 to 7 from right to left."

-- ============================================================================


dot1wTraceOption OBJECT-TYPE
   SYNTAX      Integer32 (0..255)
   MAX-ACCESS  read-write
   STATUS      current
   DESCRIPTION
      "This object is used to enable Trace Statements in the RSTP
       Module.
      
       A FOUR BYTE integer is used for enabling the level of tracing.
       Each BIT in the four byte integer, represents a particular
       level of Trace.
      
       The mapping between the bit positions & the level of trace is
       as follows:
       0 - Init and Shutdown Traces
       1 - Management Traces
       2 - Data Path Traces
       3 - Control Plane Traces
       4 - Packet Dump Traces
       5 - Traces related to All Resources except Buffers
       6 - All Failure Traces
       7 - Buffer Traces
      
       The remaining bits are unused. Combination of trace levels are
       also allowed.
      
       For example if the bits 0 and 1 are set, then the Trace
       statements related to Init-Shutdown and management
       will be printed.
      
       The user has to enter the corresponding INTEGER VALUE for the
       bits set. For example if bits 0 and 1 are to be set then user has
       to give the value for this object as 3.
      
       Setting the Trace Option to any value will cause the Debug Option
       to be set to 0 (i.e.) the Trace Option and Debug Option are mutually
       exclusive."
   DEFVAL { 0 }
   ::= { dot1wRstEntry 4 }

dot1wDebugOption OBJECT-TYPE
   SYNTAX      Integer32 (0..262143)
   MAX-ACCESS  read-write
   STATUS      current
   DESCRIPTION
      "This object is used to enable Debug Statements in the RSTP
       Module.
     
       A FOUR BYTE integer is used for enabling the level of debugging.
       Each BIT in the four byte integer, represents a particular
       level of Debug.
     
       The mapping between the bit positions & the level of debug is
       as follows:
       0 - Init and Shutdown Debug statements
       1 - Management Debug statements
       2 - Memory related Debug statements
       3 - BPDU related Debug statements
       4 - Event Handling Debug statements
       5 - Timer Module Debug statements
       6 - Port Information SEM Debug statements
       7 - Port Receive SEM Debug statements
       8 - Role Selection SEM Debug statements
       9 - Role Transition SEM Debug statements
       10 - State Transition SEM Debug statements
       11 - Protocol Migration SEM Debug statements
       12 - Topology Change SEM Debug statements
       13 - Port Transmit SEM Debug statements
       14 - Bridge Detection SEM Debug statements
       15 - All Failure Debug statements
       16 - Redundancy code flow Debug statements
       17 - State Machine variable changes debug statements
     
       The remaining bits are unused. Combination of debug levels are
       also allowed.
     
       For example if the bits 0 and 1 are set, then the Debug
       statements related to Init-Shutdown and management
       will be printed.
     
       The user has to enter the corresponding INTEGER VALUE for the
       bits set. For example if bits 0 and 1 are to be set then user has
       to give the value for this object as 3.
     
       Setting the Debug Option to any value will cause the Trace Option
       to be set to 0 (i.e.) the Trace Option and Debug Option are mutually
       exclusive."
   DEFVAL { 0 }
   ::= { dot1wRstEntry 5 }

dot1wRstpUpCount OBJECT-TYPE
   SYNTAX      Counter32
   MAX-ACCESS  read-only
   STATUS      current
   DESCRIPTION
      "The number of times RSTP Module has been enabled."
   ::= { dot1wRstEntry 6 }

dot1wRstpDownCount OBJECT-TYPE
   SYNTAX      Counter32
   MAX-ACCESS  read-only
   STATUS      current
   DESCRIPTION
      "The number of times RSTP Module has been disabled."
   ::= { dot1wRstEntry 7 }

dot1wBufferFailureCount OBJECT-TYPE
   SYNTAX      Counter32
   MAX-ACCESS  read-only
   STATUS      current
   DESCRIPTION
      "The number of times buffer overflows/failures have occurred.
       A Trap is generated on the occurrence of this event."
   ::= { dot1wRstEntry 8 }

dot1wMemAllocFailureCount OBJECT-TYPE
   SYNTAX      Counter32
   MAX-ACCESS  read-only
   STATUS      current
   DESCRIPTION
      "The number of times memory allocation failures have occurred.
       A Trap is generated on the occurrence of this event."
   ::= { dot1wRstEntry 9 }

dot1wNewRootIdCount OBJECT-TYPE
   SYNTAX      Counter32
   MAX-ACCESS  read-only
   STATUS      current
   DESCRIPTION
      "The number of times this Bridge has detected a new Root in the topology.
       A Trap is generated on the occurrence of this event."
   ::= { dot1wRstEntry 10 }

dot1wPortRoleSelSmState OBJECT-TYPE
   SYNTAX      INTEGER {
                initbridge (0),
                roleselection (1)
               }
   MAX-ACCESS  read-only
   STATUS      current
   DESCRIPTION
      "This indicates the current state of the Port Role Selection State
       Machine. This object will hold the value 'initbridge' when the
       Port Role Selection state machine is in the INIT_BRIDGE state and
       the value of 'roleselection' when the state machine is in the
       ROLE_SELECTION state."
   ::= { dot1wRstEntry 11 }

dot1wOldDesignatedRoot OBJECT-TYPE
   SYNTAX  BridgeId
   MAX-ACCESS  read-only
   STATUS  current
   DESCRIPTION
      "The bridge identifier of the old root of the spanning
       tree as determined by the Spanning Tree Protocol
       as executed by this node. "
   ::= { dot1wRstEntry 12 }

dot1wDynamicPathcostCalculation OBJECT-TYPE
   SYNTAX      TruthValue
   MAX-ACCESS  read-write
   STATUS      current
   DESCRIPTION
      "This object is used to determine whether dynamic pathcost
       calculation is allowed or not.The value is determined by
       management. If set to true, pathcost is calculated dynamically
       from port speed, otherwise the link speed at the time of port
       creation is used for calculating the path cost. In both cases
       if the user has configured a pathcost for the port that will be
       used. By default dynamic pathcost calculation is set to false."
   DEFVAL { false }
   ::= { dot1wRstEntry 13 }

 dot1wContextName OBJECT-TYPE
   SYNTAX   DisplayString (SIZE (1..32))
   MAX-ACCESS   read-only
   STATUS   current
   DESCRIPTION
      "This object is used to identity the context-name."
   ::= { dot1wRstEntry 14 }

dot1wPortExtTable OBJECT-TYPE
   SYNTAX SEQUENCE OF TabDot1wPortExtEntry
   MAX-ACCESS not-accessible
   STATUS     current
   DESCRIPTION
      "This is a table that is an extension to the dot1dStpExtPortTable.
      This contains object(s) that are Port-based."
   ::= { dot1wRst 4 }

dot1wPortExtEntry OBJECT-TYPE
   SYNTAX      TabDot1wPortExtEntry
   MAX-ACCESS  not-accessible
   STATUS      current
   DESCRIPTION
      "Each entry in this table is for each port present in the system.
       This table is indexed by the dot1wPort."
   INDEX { dot1wPort }
   ::= { dot1wPortExtTable 1 }

TabDot1wPortExtEntry ::=
   SEQUENCE {
      dot1wPort
         Integer32,
      dot1wPortRole
         INTEGER,
      dot1wPortOperVersion
         INTEGER,
      dot1wPortInfoSmState
         INTEGER,
      dot1wPortMigSmState
         INTEGER,
      dot1wPortRoleTransSmState
         INTEGER,
      dot1wPortStateTransSmState
         INTEGER,
      dot1wPortTopoChSmState
         INTEGER,
      dot1wPortTxSmState
         INTEGER,
      dot1wPortRxRstBpduCount
         Counter32,
      dot1wPortRxConfigBpduCount
         Counter32,
      dot1wPortRxTcnBpduCount
         Counter32,
      dot1wPortTxRstBpduCount
         Counter32,
      dot1wPortTxConfigBpduCount
         Counter32,
      dot1wPortTxTcnBpduCount
         Counter32,
      dot1wPortInvalidRstBpduRxCount
         Counter32,
      dot1wPortInvalidConfigBpduRxCount
         Counter32,
      dot1wPortInvalidTcnBpduRxCount
         Counter32,
      dot1wPortProtocolMigrationCount
         Counter32,
      dot1wPortEffectivePortState
         TruthValue,
      dot1wPortAutoEdge
         TruthValue,
      dot1wPortRestrictedRole
          TruthValue,
      dot1wPortRestrictedTCN
          TruthValue
   }

dot1wPort OBJECT-TYPE
   SYNTAX      Integer32 (1..4096)
   MAX-ACCESS  not-accessible
   STATUS      current
   DESCRIPTION
      "A unique value, greater than zero, indicating the Port number."
   ::= { dot1wPortExtEntry 1 }

dot1wPortRole OBJECT-TYPE
   SYNTAX      INTEGER {
                disabledPort(0),
                alternatePort(1),
                backupPort(2),
                rootPort(3),
                designatedPort(4)
               }
   MAX-ACCESS  read-only
   STATUS      current
   DESCRIPTION
      "This indicates the current Port Role assumed by this Port."
   ::= { dot1wPortExtEntry 2 }


dot1wPortOperVersion OBJECT-TYPE
   SYNTAX      INTEGER {
                stpCompatible(0),
                rstp(2)
               }
   MAX-ACCESS  read-only
   STATUS      current
   DESCRIPTION
      "This indicates whether the Port is operationally in the Rstp
       mode or the Stp-compatible mode i.e., whether the Port is
       transmitting RST BPDUs or Config/TCN BPDUs."
   ::= { dot1wPortExtEntry 3 }

dot1wPortInfoSmState OBJECT-TYPE
   SYNTAX      INTEGER {
                disabled (0),
                aged (1),
                update (2),
                superior (3),
                repeat (4),
                notdesignated (5),
                present (6),
                receive (7),
                inferiordesignated (8)
               }
   MAX-ACCESS  read-only
   STATUS      current
   DESCRIPTION
      "This indicates the current state of the Port Information state
       machine. This object will hold the value 'disabled' when the
       Port Information state machine is in the DISABLED state, the value
       'aged' when the state machine is in the AGED state, the value 'update'
       when the state machine is in the UPDATE state, the value 'superior'
       when the state machine is in the SUPERIOR state, the value 'repeat'
       when the state machine is in the REPEAT state, the value
       'notdesignated' when the state machine is in the NOT_DESIGNATED state,
       the value 'present' when the state machine is in the CURRENT state
       and the value 'receive' when the state machine is in the RECEIVE
       state and the value 'inferiordesignated' when the state machine is
       in the INFERIOR_DESIGNATED state."
   ::= { dot1wPortExtEntry 4 }

dot1wPortMigSmState OBJECT-TYPE
   SYNTAX      INTEGER {
                checkingrstp (0),
                selectingstp (1),
                sensing (2)
               }
   MAX-ACCESS  read-only
   STATUS      current
   DESCRIPTION
      "This indicates the current state of the Port Protocol Migration state
       machine. This object will hold the value 'checkingrstp' when the
       Protocol Migration state machine is in the CHECKING_RSTP state,
       the value 'selectingstp' when the state machine is in the
       SELECTING_STP state, the value 'sensing' when the state machine
       is in the SENSING state."
   ::= { dot1wPortExtEntry 5 }

dot1wPortRoleTransSmState OBJECT-TYPE
   SYNTAX      INTEGER {
                init (0),
                disableport (1),
                disabledport (2),
                rootport (3),
                designatedport (4),
                backupport (5),
                rootproposed (6),
                rootagreed(7),
                reroot (8),
                rootforward (9),
                rootlearn (10),
                rerooted (11),
                designatedpropose (12),
                designatedsynced (13),
                designatedretired (14),
                designatedforward (15),
                designatedlearn (16),
                designatedlisten (17)
               }
   MAX-ACCESS  read-only
   STATUS      current
   DESCRIPTION
      "This indicates the current state of the Port Role Transition state
       machine. This object will hold the value 'init' when the Port Role
       Transition state machine is in the INIT state, the value 'disableport'
       when the state machine is in the DISABLE_PORT state, the value
       'disabledport' when the state machine is in the DISABLED_PORT state,
       the value 'rootport' when the state machine is in the ROOT_PORT state,
       the value 'desgport' when the state machine is in the DESIGNATED_PORT
       state, the value 'backupport' when the state machine is in BACKUP_PORT
       state, the value 'rootproposed' when the state machine is in the
       ROOT_PROPOSED state, the value 'rootagreed' when the state machine
       is in the ROOT_AGREED state, the value 'reroot' when the state machine
       is in the REROOT state, the value 'rootforward' when the state machine
       is in the ROOT_FORWARD state, the value 'rootlearn' when the state
       machine is in the ROOT_LEARN state, the value 'rerooted' when the
       state machine is in the REROOTED state, the value 'designatedpropose'
       when the state machine is in the DESIGNATED_PROPOSE state, the value
       'designatedsynced' when the state machine is in the DESIGNATED_SYNCED
       state, the value 'designatedretired' when the state machine is in the
       DESIGNATED_RETIRED state, the value 'designatedforward' when the state
       machine is in the DESIGNATED_FORWARD state, the value 'designatedlearn'
       when the state machine is in the DESIGNATED_LEARN state and the value
       'designatedlisten' when the state machine is in the DESIGNATED_LISTEN
       state."
   ::= { dot1wPortExtEntry 6 }

dot1wPortStateTransSmState OBJECT-TYPE
   SYNTAX      INTEGER {
                discarding (0),
                learning (1),
                forwarding (2)
               }
   MAX-ACCESS  read-only
   STATUS      current
   DESCRIPTION
      "This indicates the current state of the Port State Transition state
       machine. This object will hold the value 'discarding' when the Port
       State Transition state machine is in the DISCARDING state, the value
       'learning' when the state machine is in the LEARNING state and the
       value 'forwarding' when the state machine is in the FORWARDING state."
   ::= { dot1wPortExtEntry 7 }

dot1wPortTopoChSmState OBJECT-TYPE
   SYNTAX      INTEGER {
                inactive (0),
                learning (1),
                detected (2),
                active (3),
                notifiedtcn (4),
                notifiedtc (5),
                propagating (6),
                acknowledged (7)
               }
   MAX-ACCESS  read-only
   STATUS      current
   DESCRIPTION
      "This indicates the current state of the Topology Change state machine.
       This object will hold the value 'inactive' when the Topology Change
       state machine is in the INACTIVE state, the value 'learning' when the
       state machine is in the LEARNING state, the value 'active' when the
       state machine is in the ACTIVE state, the value 'detected' when the
       state machine is in the DETECTED state, the value 'notifiedtcn' when
       the state machine is in the NOTIFIED_TCN state, the value 'notifiedtc'
       when the state machine is in the NOTIFIED_TC state, the value
       'propagating' state when the state machine is in the PROPAGATING
       state and the value 'acknowledged' when the state machine is in the
       ACKNOWLEDGED state."
   ::= { dot1wPortExtEntry 8 }

dot1wPortTxSmState OBJECT-TYPE
   SYNTAX      INTEGER {
                transmitinit (0),
                transmitperiodic (1),
                transmitconfig (2),
                transmittcn (3),
                transmitrstp (4),
                idle (5)
               }
   MAX-ACCESS  read-only
   STATUS      current
   DESCRIPTION
      "This indicates the current state of the Port Transmit state machine.
       This object will hold the value 'transmitinit' when the Port Transmit
       state machine is in the TRANSMIT_INIT state, the value
       'transmitperiodic' when the state machine is in the TRANSMIT_PERIODIC
       state, the value 'transmitconfig' when the state machine is in the
       TRANSMIT_CONFIG state, the value 'transmittcn', when the state machine
       is in the TRANSMIT_TCN state, the value 'transmitrstp', when the state
       machine is in the TRANSMIT_RSTP state and the value 'idle' when
       the state machine is in the IDLE state."
   ::= { dot1wPortExtEntry 9 }


dot1wPortRxRstBpduCount OBJECT-TYPE
   SYNTAX      Counter32
   MAX-ACCESS  read-only
   STATUS      current
   DESCRIPTION
      "The number of RST BPDUs that have been received on this Port."
   ::= { dot1wPortExtEntry 10 }

dot1wPortRxConfigBpduCount OBJECT-TYPE
   SYNTAX      Counter32
   MAX-ACCESS  read-only
   STATUS      current
   DESCRIPTION
      "The number of Config BPDUs that have been received on this Port."
   ::= { dot1wPortExtEntry 11 }

dot1wPortRxTcnBpduCount OBJECT-TYPE
   SYNTAX      Counter32
   MAX-ACCESS  read-only
   STATUS      current
   DESCRIPTION
      "The number of TCN BPDUs that have been received on this Port."
   ::= { dot1wPortExtEntry 12 }

dot1wPortTxRstBpduCount OBJECT-TYPE
   SYNTAX      Counter32
   MAX-ACCESS  read-only
   STATUS      current
   DESCRIPTION
      "The number of RST BPDUs that have been transmitted by this Port."
   ::= { dot1wPortExtEntry 13 }

dot1wPortTxConfigBpduCount OBJECT-TYPE
   SYNTAX      Counter32
   MAX-ACCESS  read-only
   STATUS      current
   DESCRIPTION
      "The number of Config BPDUs that have been transmitted by this Port."
   ::= { dot1wPortExtEntry 14 }

dot1wPortTxTcnBpduCount OBJECT-TYPE
   SYNTAX      Counter32
   MAX-ACCESS  read-only
   STATUS      current
   DESCRIPTION
      "The number of TCN BPDUs that have been transmitted by this Port."
   ::= { dot1wPortExtEntry 15 }

dot1wPortInvalidRstBpduRxCount OBJECT-TYPE
   SYNTAX      Counter32
   MAX-ACCESS  read-only
   STATUS      current
   DESCRIPTION
      "The number of invalid RSTP BPDUs that have been received on this Port.
       A Trap is generated on the occurrence of this event."
   ::= { dot1wPortExtEntry 16 }

dot1wPortInvalidConfigBpduRxCount OBJECT-TYPE
   SYNTAX      Counter32
   MAX-ACCESS  read-only
   STATUS      current
   DESCRIPTION
      "The number of invalid Configuration BPDUs that have been received on
       this Port. A Trap is generated on the occurrence of this event."
   ::= { dot1wPortExtEntry 17 }

dot1wPortInvalidTcnBpduRxCount OBJECT-TYPE
   SYNTAX      Counter32
   MAX-ACCESS  read-only
   STATUS      current
   DESCRIPTION
      "The number of invalid TCN BPDUs that have been received on this Port.
       A Trap is generated on the occurrence of this event."
   ::= { dot1wPortExtEntry 18 }

dot1wPortProtocolMigrationCount OBJECT-TYPE
   SYNTAX      Counter32
   MAX-ACCESS  read-only
   STATUS      current
   DESCRIPTION
      "The number of times this Port has migrated from one STP protocol
       version to another. The relevant protocols are STP-COMPATIBLE and RSTP.
       A Trap is generated on the occurrence of this event."
   ::= { dot1wPortExtEntry 19 }

dot1wPortEffectivePortState OBJECT-TYPE
   SYNTAX      TruthValue
   MAX-ACCESS  read-only
   STATUS      current
   DESCRIPTION
      "The effective Operational state of the port. This object will be
       set to TRUE only when the port is operationally up in the
       interface manager and the force Port State for this port and
       specified port state is enabled. Otherwise this object is set
       to FALSE."

   ::= { dot1wPortExtEntry 20 }

dot1wPortAutoEdge OBJECT-TYPE
    SYNTAX      TruthValue
    MAX-ACCESS  read-write
    STATUS      current
    DESCRIPTION
      "This parameter when TRUE(1) indicates that detection of a port
       as Edge Port happens automatically and FALSE(2)
       indicates that this feature is disabled."
    ::= { dot1wPortExtEntry 21 }

dot1wPortRestrictedRole OBJECT-TYPE
   SYNTAX      TruthValue
   MAX-ACCESS  read-write
   STATUS      current
   DESCRIPTION
      "A Boolean value set by management. If TRUE causes the Port not
       to be selected as Root Port for the CIST or any MSTI, even it has
       the best spanning tree priority vector. Such a Port will be selected
       as an Alternate Port after the Root Port has been selected. This
       parameter should be FALSE by default. If set it can cause lack of
       spanning tree connectivity. It is set by a network administrator to
       prevent bridges external to a core region of the network influencing
       the spanning tree active topology, possibly because those bridges are
       not under the full control of the administrator.
       This administrator configuration is also known as 'Root Guard'."
   ::= {dot1wPortExtEntry 22}

dot1wPortRestrictedTCN OBJECT-TYPE
   SYNTAX      TruthValue
   MAX-ACCESS  read-write
   STATUS      current
   DESCRIPTION
      "A Boolean value set by management. If TRUE causes the Port not
       to propagate received topology change notifications and topology
       changes to other Ports. This parameter should be FALSE by default.
       If set it can cause temporary loss of connectivity after changes in
       a spanning trees active topology as a result of persistent
       incorrectly learnt station location information. It is set by a
       network administrator to prevent bridges external to a core region of
       the network causing address flushing in that region, possibly because
       those bridges are not under the full control of the administrator or
       MAC_Operational for the attached LANs transitions frequently."
   ::= {dot1wPortExtEntry 23}


-- Dot1w Trap

dot1wSetGlobalTraps OBJECT-TYPE
   SYNTAX       Integer32 (0..1)
   MAX-ACCESS   read-write
   STATUS       current
   DESCRIPTION
      "This object is used to enable and disable RSTP traps for memory
       failure or buffer failure irrespective of the context in which
       the failure occurs.
       0 - Traps are not enabled.
       1 - Memory and buffer failure traps enabled"
   ::= { dot1wRstTrapsControl 1 }

dot1wGlobalErrTrapType OBJECT-TYPE
   SYNTAX       INTEGER   {
                 none (0),
                 memfail (1),
                 bufffail (2)
                }
   MAX-ACCESS  read-only
   STATUS      current
   DESCRIPTION
      "Used within the Trap Notification PDU.
       It returns the following values
       none - none of the below values
       memfail - memory allocation failure
       bufffail - buffer allocation failure"
   ::= { dot1wRstTrapsControl 2 }

dot1wRstTrapsControlTable OBJECT-TYPE
   SYNTAX        SEQUENCE OF TabDot1wRstTrapsControlEntry
   MAX-ACCESS    not-accessible
   STATUS        current
   DESCRIPTION
      "List of per virtual bridge TrapsControl Info."
   ::= { dot1wRstTrapsControl 3 }

dot1wRstTrapsControlEntry OBJECT-TYPE
   SYNTAX        TabDot1wRstTrapsControlEntry
   MAX-ACCESS    not-accessible
   STATUS        current
   DESCRIPTION
      "Virtual bridge TrapsControl information."
   INDEX { dot1wRstContextId }
   ::= { dot1wRstTrapsControlTable 1 }

TabDot1wRstTrapsControlEntry ::=
   SEQUENCE {
      dot1wSetTraps
         Integer32,
      dot1wGenTrapType
         INTEGER
   }

dot1wSetTraps OBJECT-TYPE
   SYNTAX       Integer32 (0..3)
   MAX-ACCESS   read-write
   STATUS       current
   DESCRIPTION
      "This object is used to enable and  disable context-specific
       RSTP traps. Currently the following are defined
       0 - Traps are not enabled.
       1 - Protocol up or down traps.
       2 - Exception Traps like port protocol migration or invalid packet
           rcvd in port
       3 - All the above Traps "
   ::= { dot1wRstTrapsControlEntry 1 }


dot1wGenTrapType OBJECT-TYPE
   SYNTAX      INTEGER   {
                none (0),
                up (1),
                down (2)
               }
   MAX-ACCESS  read-only
   STATUS      current
   DESCRIPTION
      "Used within the Trap Notification PDU.
       It denotes general events like
       none - none of the below values
       up - protocol UP,
       down - protocol DOWN"
   ::= { dot1wRstTrapsControlEntry 2 }


-- Dot1w Trap Control

dot1wPortTrapNotificationTable OBJECT-TYPE
   SYNTAX     SEQUENCE OF TabDot1wPortTrapNotificationEntry
   MAX-ACCESS not-accessible
   STATUS     current
   DESCRIPTION
      "This table is used to store the notification information
       occurred in each of the port for protocol migration and
       invalid packet received  "
   ::= { dot1wRstTrapsControl 4 }

dot1wPortTrapNotificationEntry OBJECT-TYPE
   SYNTAX      TabDot1wPortTrapNotificationEntry
   MAX-ACCESS  not-accessible
   STATUS      current
   DESCRIPTION
      "This entry is used to store the notification information"
   INDEX { dot1wPortTrapIndex}
   ::= { dot1wPortTrapNotificationTable 1 }

TabDot1wPortTrapNotificationEntry ::=
   SEQUENCE {
      dot1wPortTrapIndex
         Integer32,
      dot1wPortMigrationType
         INTEGER,
      dot1wPktErrType
         INTEGER,
      dot1wPktErrVal
         Integer32,
      dot1wPortRoleType
         INTEGER,
      dot1wOldRoleType
         INTEGER
   }

dot1wPortTrapIndex OBJECT-TYPE
   SYNTAX      Integer32 (1..4096)
   MAX-ACCESS  not-accessible
   STATUS      current
   DESCRIPTION
      "A unique value, greater than zero, indicating the Port number."
   ::= { dot1wPortTrapNotificationEntry 1 }

dot1wPortMigrationType OBJECT-TYPE
   SYNTAX      INTEGER {
                sendstp (0),
                sendrstp (1)
               }
   MAX-ACCESS  read-only
   STATUS      current
   DESCRIPTION
      "Port Protocol migration type occurred in the port"
   ::= { dot1wPortTrapNotificationEntry 2 }

dot1wPktErrType OBJECT-TYPE
   SYNTAX      INTEGER {
                protocolIdErr(0),
                invalidBpdu(1),
                configLengthErr(2),
                tcnLengthErr(3),
                rstpLengthErr(4),
                maxAgeErr(5),
                fwdDelayErr(6),
                helloTimeErr(7)
               }
   MAX-ACCESS  read-only
   STATUS      current
   DESCRIPTION
      "Type of invalid packet received in each of the port "
   ::= { dot1wPortTrapNotificationEntry 3 }

dot1wPktErrVal OBJECT-TYPE
   SYNTAX      Integer32
   MAX-ACCESS  read-only
   STATUS      current
   DESCRIPTION
      "Packet error value corresponding to the above type "
   ::= { dot1wPortTrapNotificationEntry 4 }

dot1wPortRoleType OBJECT-TYPE
  SYNTAX       INTEGER {
                disabledPort(0),
                alternatePort(1),
                backupPort(2),
                rootPort(3),
                designatedPort(4)
               }
   MAX-ACCESS  read-only
   STATUS      current
   DESCRIPTION
      "Particular Role Selected for the Port"
   ::= { dot1wPortTrapNotificationEntry 5 }

dot1wOldRoleType OBJECT-TYPE
  SYNTAX       INTEGER {
                disabledPort(0),
                alternatePort(1),
                backupPort(2),
                rootPort(3),
                designatedPort(4)
               }
   MAX-ACCESS  read-only
   STATUS      current
   DESCRIPTION
      "Particular Role which is existing for the Port"
   ::= { dot1wPortTrapNotificationEntry 6 }

dot1wTraps OBJECT IDENTIFIER ::= { dot1wRstTraps 0 }

dot1wGlobalErrTrap NOTIFICATION-TYPE
   OBJECTS {
      dot1dBaseBridgeAddress,
      dot1wGlobalErrTrapType
   }
   STATUS             current
   DESCRIPTION
      "Generated when any of the error events like memory failure or
       buffer failure or protocol migration or new root or topology
       change occurrs "
   ::= { dot1wTraps 1 }
   
dot1wGenTrap NOTIFICATION-TYPE
   OBJECTS {
      dot1dBaseBridgeAddress,
      dot1wContextName,
      dot1wGenTrapType
   }
   STATUS             current
   DESCRIPTION
      "Generated when any of the general events like protocol up or
       protocol down occurrs"
   ::= { dot1wTraps 2 }

dot1wNewRootTrap NOTIFICATION-TYPE
   OBJECTS {
      dot1dBaseBridgeAddress,
      dot1wContextName,
      dot1wOldDesignatedRoot,
      dot1dStpDesignatedRoot
   }
   STATUS             current
   DESCRIPTION
      "Generated whenever a new root bridge is selected in the topology "
   ::= { dot1wTraps 3 }

dot1wTopologyChgTrap NOTIFICATION-TYPE
   OBJECTS {
      dot1dBaseBridgeAddress,
      dot1wContextName
   }
   STATUS             current
   DESCRIPTION
      "Generated when topology change is detected "
   ::= { dot1wTraps 4 }

dot1wProtocolMigrationTrap NOTIFICATION-TYPE
   OBJECTS {
      dot1dBaseBridgeAddress,
      dot1wContextName,
      dot1dStpVersion,
      dot1wPortMigrationType
   }
   STATUS             current
   DESCRIPTION
      "Generated when port protocol migration happens in the port "
   ::= { dot1wTraps 5 }

dot1wInvalidBpduRxdTrap NOTIFICATION-TYPE
   OBJECTS {
      dot1dBaseBridgeAddress,
      dot1wContextName,
      dot1wPktErrType,
      dot1wPktErrVal
   }
   STATUS             current
   DESCRIPTION
      "Generated when the invalid packet is received for
       bpdu/stp/rstp/maximum age/forward delay/hello time"
   ::= { dot1wTraps 6 }

dot1wNewPortRoleTrap NOTIFICATION-TYPE
   OBJECTS {
      dot1dBaseBridgeAddress,
      dot1wPortRoleType,
      dot1wOldRoleType
   }
   STATUS             current
   DESCRIPTION
      "Generated whenever a new role is selected for the port "
   ::= { dot1wTraps 7 }





l2Dot1qVlan                    OBJECT IDENTIFIER  ::= { l2Vlan 1 }
portBaseVlan				OBJECT IDENTIFIER  ::= { l2Vlan 3 }
portBaseStatic     			OBJECT IDENTIFIER ::= { l2Vlan 4 }

-- Dot1q VLAN

dot1qVlanGlobalTrace OBJECT-TYPE
   SYNTAX        TruthValue
   MAX-ACCESS    read-write
   STATUS        current
   DESCRIPTION
      "Enable/Disable the global trace in VLAN."
   ::= { l2Dot1qVlan 1 }

dot1qVlanGlobalsTable OBJECT-TYPE
   SYNTAX        SEQUENCE OF TabDot1qVlanGlobalsEntry
   MAX-ACCESS    not-accessible
   STATUS        current
   DESCRIPTION
      "List of per virtual context Vlan Module Parameters."
   ::= { l2Dot1qVlan 2 }

dot1qVlanGlobalsEntry OBJECT-TYPE
   SYNTAX       TabDot1qVlanGlobalsEntry
   MAX-ACCESS   not-accessible
   STATUS       current
   DESCRIPTION
      "Per virtual context Vlan module parmaters."
   INDEX { dot1qVlanGlobalsContextId }
   ::= { dot1qVlanGlobalsTable 1 }

TabDot1qVlanGlobalsEntry ::=
   SEQUENCE {
      dot1qVlanGlobalsContextId
         Integer32,
      dot1qGarpShutdownStatus
         TruthValue,
      dot1qVlanDebug
         Integer32,
      dot1qVlanLearningMode
         INTEGER,
      dot1qVlanOperStatus
         EnabledStatus,
      dot1qGvrpOperStatus
         EnabledStatus
   }

dot1qVlanGlobalsContextId OBJECT-TYPE
   SYNTAX        Integer32 (0..65535)
   MAX-ACCESS    not-accessible
   STATUS        current
   DESCRIPTION
      "Identifies the virtual context in the system."
   ::= { dot1qVlanGlobalsEntry 1 }
   
dot1qGarpShutdownStatus OBJECT-TYPE
   SYNTAX      TruthValue
   MAX-ACCESS  read-write
   STATUS      current
   DESCRIPTION
      "The administrative status requested by management for GARP
       The value true(1) indicates that GARP should be shutdown
       in the device on all ports. All memory will be released.
       The value false(2) indicates that GARP should be active in
       the device on all ports. This object can be set to true only
       when none of the Garp applications (GVRP, GMRP) are enabled.
       Whenever Garp is enabled after shutdown, Gvrp and Gmrp must
       be enabled explicitly."
   DEFVAL   { false }
   ::= { dot1qVlanGlobalsEntry 6 }   

dot1qVlanDebug OBJECT-TYPE
   SYNTAX      Integer32 (0..524287)
   MAX-ACCESS  read-write
   STATUS      current
   DESCRIPTION
      "Enables the tracing in the selected submodule in VLAN. A 32 bit
       integer is used to store the Tracing level in the specified module.
       Different Tracing Levels -
         BIT 0 - Initialisation and Shutdown Trace.
         BIT 1 - Management trace.
         BIT 2 - Data path trace.
         BIT 3 - Control Plane trace.
         BIT 4 - Packet Dump.
         BIT 5 - OS Resource trace.
         BIT 6 - All Failure trace (All failures including Packet Validation)
         BIT 7 - Buffer Trace.

       Different submodule Tracing -
         BIT 16 - Tracing in VLAN module.
         BIT 17 - Tracing in VLAN Priority module.
         BIT 18 - Tracing in VLAN Redundancy module.

       The remaining bits are reserved. The combination of levels and
       submodules are allowed i.e. Tracing can be allowed at all failure
       and data path level in All submodules by setting the BIT
       appropriately.
       For Example, setting the debug value to the following bit stream,
          00000000000000010000000000000100 will enable data path trace
       prints in VLAN module. Multiple submodules and multiple levels can
       be combined by setting the corresponding bits.
       For Example, setting the debug value to the following bit stream,
          00000000000000110000000000001100 will enable data path and
       control plane trace prints in VLAN and VLAN Priority modules.

       Note : BIT0 is the least significant bit and BIT31 is the most
       significant bit."
   ::= { dot1qVlanGlobalsEntry 7 }

dot1qVlanLearningMode OBJECT-TYPE
   SYNTAX      INTEGER {
                ivl(1),
                svl(2)
               }
   MAX-ACCESS  read-write
   STATUS      current
   DESCRIPTION
      "The type of VLAN learning mode."
   DEFVAL { ivl }
   ::= { dot1qVlanGlobalsEntry 8 }

dot1qVlanOperStatus OBJECT-TYPE
   SYNTAX      EnabledStatus
   MAX-ACCESS  read-only
   STATUS      current
   DESCRIPTION
      "The operational status of the Vlan module.
       The value enabled(1) indicates that Vlan module is currently enabled
       in the device.
       The value disabled(2) indicates that Vlan module is currently disabled
       in the device."
   ::= { dot1qVlanGlobalsEntry 10 }

dot1qGvrpOperStatus OBJECT-TYPE
   SYNTAX      EnabledStatus
   MAX-ACCESS  read-only
   STATUS      current
   DESCRIPTION
      "The operational status of the GVRP module.
       The value enabled(1) indicates that GVRP module is currently enabled
       in the device.
       The value disabled(2) indicates that GVRP module is currently disabled
       in the device."
   ::= { dot1qVlanGlobalsEntry 11 }

 -- -------------------------------------------------------------
-- The Current VLAN Database
-- -------------------------------------------------------------

portBaseVlanEnablePerPort OBJECT-TYPE
    SYNTAX     PortList
    MAX-ACCESS read-write
    STATUS     current
    DESCRIPTION
        "The set of ports which are in port-based VLAN mode."
    ::= { portBaseVlan 1 }

portBaseVlanCurrentTable OBJECT-TYPE
    SYNTAX      SEQUENCE OF TabPortBaseVlanCurrentEntry
    MAX-ACCESS  not-accessible
    STATUS      current
    DESCRIPTION
        "A table containing current configuration information
        for each VLAN currently configured into the device by
        (local or network) management, or dynamically created
        as a result of GVRP requests received."
    ::= { portBaseVlan 2 }

tabPortBaseVlanCurrentEntry OBJECT-TYPE
    SYNTAX      TabPortBaseVlanCurrentEntry
    MAX-ACCESS  not-accessible
    STATUS      current
    DESCRIPTION
        "Information for a VLAN configured into the device by
        (local or network) management, or dynamically created
        as a result of GVRP requests received."
    INDEX   { portBaseVlanIndex }
    ::= { portBaseVlanCurrentTable 1 }

TabPortBaseVlanCurrentEntry ::=
    SEQUENCE {
		portBaseVlanIndex
            Integer32,
		portBaseVlanName
            OCTET STRING,
        portBaseVlanCurrentEgressPorts
            PortList,
        portBaseVlanStatus
            INTEGER,
        portBaseVlanCreationTime
            TimeTicks,
		portBaseVlanRowStatus
            RowStatus
    }

portBaseVlanIndex OBJECT-TYPE
    SYNTAX      Integer32 (0..65535)
    MAX-ACCESS  not-accessible
    STATUS      current
    DESCRIPTION
        "The VLAN-ID or other identifier referring to this VLAN."
    ::= { tabPortBaseVlanCurrentEntry 1 }
	
portBaseVlanName OBJECT-TYPE
    SYNTAX      OCTET STRING
    MAX-ACCESS  read-write
    STATUS      current
    DESCRIPTION
        "The VLAN-Name referring to this VLAN."
    ::= { tabPortBaseVlanCurrentEntry 2 }

portBaseVlanCurrentEgressPorts OBJECT-TYPE
    SYNTAX      PortList
    MAX-ACCESS  read-write
    STATUS      current
    DESCRIPTION
        "The set of ports which are transmitting traffic for
        this VLAN as either tagged or untagged frames."
    REFERENCE
        "IEEE 802.1Q/D11 Section 12.10.2.1"
    ::= { tabPortBaseVlanCurrentEntry 3 }

portBaseVlanStatus OBJECT-TYPE
    SYNTAX      INTEGER {
                    other(1),
                    permanent(2),
                    dynamicGvrp(3)
                }
    MAX-ACCESS  read-write
    STATUS      current
    DESCRIPTION
        "This object indicates the status of this entry.
            other(1) - this entry is currently in use but the
                conditions under which it will remain so differ
                from the following values.
            permanent(2) - this entry, corresponding to an entry
                in portBaseVlanStaticTable, is currently in use and
                will remain so after the next reset of the
                device.  The port lists for this entry include
                ports from the equivalent portBaseVlanStaticTable
                entry and ports learnt dynamically.
            dynamicGvrp(3) - this entry is currently in use
                and will remain so until removed by GVRP.  There
                is no static entry for this VLAN and it will be
                removed when the last port leaves the VLAN."
    ::= { tabPortBaseVlanCurrentEntry 4 }

portBaseVlanCreationTime OBJECT-TYPE
    SYNTAX      TimeTicks
    MAX-ACCESS  read-write
    STATUS      current
    DESCRIPTION
        "The value of sysUpTime when this VLAN was created."
    ::= { tabPortBaseVlanCurrentEntry 5 }

portBaseVlanRowStatus OBJECT-TYPE
   SYNTAX      RowStatus
   MAX-ACCESS  read-create
   STATUS      current
   DESCRIPTION
      "The status of this concsystual row. All writable objects in this
       row may be modified only when the row status is not active."
   ::= { tabPortBaseVlanCurrentEntry 6 }

   
-- -------------------------------------------------------------
-- The Static (Destination-Address Filtering) Database
-- -------------------------------------------------------------

portBaseStaticUnicastTable OBJECT-TYPE
    SYNTAX      SEQUENCE OF TabPortBaseStaticUnicastEntry
    MAX-ACCESS  not-accessible
    STATUS      current
    DESCRIPTION
        "A table containing filtering information for Unicast
        MAC addresses for each Filtering Database, configured
        into the device by (local or network) management
        specifying the set of ports to which frames received
        from specific ports and containing specific unicast
        destination addresses are allowed to be forwarded.  A
        value of zero in this table as the port number from
        which frames with a specific destination address are
        received, is used to specify all ports for which there
        is no specific entry in this table for that particular
        destination address.  Entries are valid for unicast
        addresses only."
    REFERENCE
        "IEEE 802.1Q/D11 Section 12.7.7,
        ISO/IEC 15802-3 Section 7.9.1"
    ::= { portBaseStatic 1 }

tabPortBaseStaticUnicastEntry OBJECT-TYPE
    SYNTAX      TabPortBaseStaticUnicastEntry
    MAX-ACCESS  not-accessible
    STATUS      current
    DESCRIPTION
        "Filtering information configured into the device by
        (local or network) management specifying the set of
        ports to which frames received from a specific port and
        containing a specific unicast destination address are
        allowed to be forwarded."
    INDEX   { portBaseStaticUnicastIndex }
    ::= { portBaseStaticUnicastTable 1 }

TabPortBaseStaticUnicastEntry ::=
    SEQUENCE {
		portBaseStaticUnicastIndex
            Integer32,
		portBaseStaticUnicastVlanIndex
            Integer32,
        portBaseStaticUnicastAddress
            MacAddress,
        portBaseStaticUnicastAllowedToGoTo
            PortList,
        portBaseStaticUnicastStatus
            INTEGER,
		portBaseStaticUnicastRowStatus
            RowStatus
    }
	
portBaseStaticUnicastIndex OBJECT-TYPE
    SYNTAX      Integer32 (0..65535)
    MAX-ACCESS  not-accessible
    STATUS      current
    DESCRIPTION
        "The index of entries int this table."
    ::= { tabPortBaseStaticUnicastEntry 1 }
	
portBaseStaticUnicastVlanIndex OBJECT-TYPE
    SYNTAX      Integer32
    MAX-ACCESS  read-write
    STATUS      current
    DESCRIPTION
        "The VLAN-ID or other identifier referring to this VLAN."
    ::= { tabPortBaseStaticUnicastEntry 2 }
	
portBaseStaticUnicastAddress OBJECT-TYPE
    SYNTAX      MacAddress
    MAX-ACCESS  read-write
    STATUS      current
    DESCRIPTION
        "The destination MAC address in a frame to which this
        entry's filtering information applies.  This object must
        take the value of a unicast address."
    ::= { tabPortBaseStaticUnicastEntry 3 }

portBaseStaticUnicastAllowedToGoTo OBJECT-TYPE
    SYNTAX      PortList
    MAX-ACCESS  read-write
    STATUS      current
    DESCRIPTION
        "The set of ports for which a frame with a specific
        unicast address will be flooded in the event that it
        has not been learned.  It also specifies the set of
        ports a specific unicast address may be dynamically
        learnt on.  The portBaseTpFdbTable will have an equivalent
        entry with a portBaseTpFdbPort value of '0' until this
        address has been learnt, when it will be updated with
        the port the address has been seen on.  This only
        applies to ports that are members of the VLAN, defined
        by portBaseVlanCurrentEgressPorts.  The default value of
        this object is a string of ones of appropriate length."
    REFERENCE
        "IEEE 802.1Q/D11 Table 8-5, ISO/IEC 15802-3 Table 7-5"
    ::= { tabPortBaseStaticUnicastEntry 4 }

portBaseStaticUnicastStatus OBJECT-TYPE
    SYNTAX      INTEGER {
                    other(1),
                    invalid(2),
                    permanent(3),
                    deleteOnReset(4),
                    deleteOnTimeout(5)
                }
    MAX-ACCESS  read-write
    STATUS      current
    DESCRIPTION
        "This object indicates the status of this entry.
            other(1) - this entry is currently in use but
                the conditions under which it will remain
                so differ from the following values.
            invalid(2) - writing this value to the object
                removes the corresponding entry.
            permanent(3) - this entry is currently in use
                and will remain so after the next reset of
                the bridge.
            deleteOnReset(4) - this entry is currently in
                use and will remain so until the next
                reset of the bridge.
            deleteOnTimeout(5) - this entry is currently in
                use and will remain so until it is aged out."
    DEFVAL      { permanent }
    ::= { tabPortBaseStaticUnicastEntry 5 }
	
portBaseStaticUnicastRowStatus OBJECT-TYPE
   SYNTAX      RowStatus
   MAX-ACCESS  read-create
   STATUS      current
   DESCRIPTION
      "The status of this concsystual row. All writable objects in this
       row may be modified only when the row status is not active."
   ::= { tabPortBaseStaticUnicastEntry 6 }
   
 portBaseStaticMulticastTable OBJECT-TYPE
    SYNTAX      SEQUENCE OF TabPortBaseStaticMulticastEntry
    MAX-ACCESS  not-accessible
    STATUS      current
    DESCRIPTION
        "A table containing filtering information for Multicast
        and Broadcast MAC addresses for each VLAN, configured
        into the device by (local or network) management
        specifying the set of ports to which frames received
        from specific ports and containing specific Multicast
        and Broadcast destination addresses are allowed to be
        forwarded.  A value of zero in this table as the port
        number from which frames with a specific destination
        address are received, is used to specify all ports for
        which there is no specific entry in this table for that
        particular destination address.  Entries are valid for
        Multicast and Broadcast addresses only."
    REFERENCE
        "IEEE 802.1Q/D11 Section 12.7.7,
        ISO/IEC 15802-3 Section 7.9.1"
    ::= { portBaseStatic 2 }

tabPortBaseStaticMulticastEntry OBJECT-TYPE
    SYNTAX      TabPortBaseStaticMulticastEntry
    MAX-ACCESS  not-accessible
    STATUS      current
    DESCRIPTION
        "Filtering information configured into the device by
        (local or network) management specifying the set of
        ports to which frames received from this specific port
        for this VLAN and containing this Multicast or Broadcast
        destination address are allowed to be forwarded."
    INDEX   { portBaseStaticMulticastIndex }
    ::= { portBaseStaticMulticastTable 1 }

TabPortBaseStaticMulticastEntry ::=
    SEQUENCE {
		portBaseStaticMulticastIndex
            Integer32,
		portBaseStaticMulticastVlanIndex
            Integer32,
        portBaseStaticMulticastAddress
            MacAddress,
        portBaseStaticMulticastStaticEgressPorts
            PortList,
        portBaseStaticMulticastStatus
            INTEGER,
		portBaseStaticMulticastRowStatus
            RowStatus
    }

portBaseStaticMulticastIndex OBJECT-TYPE
    SYNTAX      Integer32 (0..65535)
    MAX-ACCESS  not-accessible
    STATUS      current
    DESCRIPTION
        "The index of entries int this table."
    ::= { tabPortBaseStaticMulticastEntry 1 }
	
portBaseStaticMulticastVlanIndex OBJECT-TYPE
    SYNTAX      Integer32
    MAX-ACCESS  read-write
    STATUS      current
    DESCRIPTION
        "The VLAN-ID or other identifier referring to this VLAN."
    ::= { tabPortBaseStaticMulticastEntry 2 }
	
portBaseStaticMulticastAddress OBJECT-TYPE
    SYNTAX      MacAddress
    MAX-ACCESS  read-write
    STATUS      current
    DESCRIPTION
        "The destination MAC address in a frame to which this
        entry's filtering information applies.  This object must
        take the value of a Multicast or Broadcast address."
    ::= { tabPortBaseStaticMulticastEntry 3 }

portBaseStaticMulticastStaticEgressPorts OBJECT-TYPE
    SYNTAX      PortList
    MAX-ACCESS  read-write
    STATUS      current
    DESCRIPTION
        "The set of ports to which frames received from a
        specific port and destined for a specific Multicast or
        Broadcast MAC address must be forwarded, regardless of
        any dynamic information e.g. from GMRP.  A port may not
        be added in this set if it is already a member of the
        set of ports in portBaseStaticMulticastForbiddenEgressPorts.
        The default value of this object is a string of ones of
        appropriate length."
    ::= { tabPortBaseStaticMulticastEntry 4 }

portBaseStaticMulticastStatus OBJECT-TYPE
    SYNTAX      INTEGER {
                    other(1),
                    invalid(2),
                    permanent(3),
                    deleteOnReset(4),
                    deleteOnTimeout(5)
                }
    MAX-ACCESS  read-write
    STATUS      current
    DESCRIPTION
        "This object indicates the status of this entry.
            other(1) - this entry is currently in use but
                the conditions under which it will remain
                so differ from the following values.
            invalid(2) - writing this value to the object
                removes the corresponding entry.
            permanent(3) - this entry is currently in use
                and will remain so after the next reset of
                the bridge.
            deleteOnReset(4) - this entry is currently in
                use and will remain so until the next
                reset of the bridge.
            deleteOnTimeout(5) - this entry is currently in
                use and will remain so until it is aged out."
    DEFVAL      { permanent }
    ::= { tabPortBaseStaticMulticastEntry 5 }
	
portBaseStaticMulticastRowStatus OBJECT-TYPE
   SYNTAX      RowStatus
   MAX-ACCESS  read-create
   STATUS      current
   DESCRIPTION
      "The status of this concsystual row. All writable objects in this
       row may be modified only when the row status is not active."
   ::= { tabPortBaseStaticMulticastEntry 6 }


-- Aricent LLDP Proprietary MIB Definition  
-- This MIB contains tables used to configure a switch running 
-- Aricent LLDP in addition to the standard MIB.
 
 
  
-- ------------------------------------------------------------  
-- groups in the MIB  
-- ------------------------------------------------------------ 
 
      fsLldpSystem        OBJECT IDENTIFIER ::= { fslldp 1 } 
      fsLldpTLV           OBJECT IDENTIFIER ::= { fslldp 2 } 
      fsLldpStatistics    OBJECT IDENTIFIER ::= { fslldp 3 }
      fsLldpNotification  OBJECT IDENTIFIER ::= { fslldp 4 }
 
-- ------------------------------------------------------------------ 
-- The LLDP System Group 
-- ------------------------------------------------------------------ 
 
      fsLldpSystemControl OBJECT-TYPE 
          SYNTAX      INTEGER  {
                        start(1),
                        shutdownInProgress(2),
                        shutdown(3)
                      } 
          MAX-ACCESS  read-write 
          STATUS      current 
          DESCRIPTION 
              "The administrative system control status of LLDP 
               module. The value 'start' (1) indicates that all
               resources required by LLDP module should be allocated 
               and LLDP should be supported in the device on all ports. 
               The value 'shutdown' (3) indicates that LLDP should be 
               shutdown in the device on all ports and all allocated 
               memory must be released.

              Here, start and shutdown are configurable values.
              shutdownInProgress can only be read and cannot be wriiten.
              When 'shutdown' (3)is configured, the value is changed to
              'shutdownInProgress' (2). This is because shutdownInProgress
              is used to indicate that shutdown process has been initiated
              by setting the object as shutdown but the process is not
              comitted. The value should be changed to shutdown once
              LLDP is shut on all ports and memory is released."
          DEFVAL  { start }
          ::= { fsLldpSystem 1 } 
          
      fsLldpModuleStatus OBJECT-TYPE 
          SYNTAX      INTEGER  { enabled(1), disabled(2) } 
          MAX-ACCESS  read-write
          STATUS      current 
          DESCRIPTION 
             "The administrative module status of LLDP module. 
              This enables or disables LLDP in the system. A value of 
              'enabled' (1) indicates that LLDP is enabled in the device
              and can be enabled port-wise. A value of 'disabled' (2) 
              indicates that LLDP is disabled in the device and also
              disabled on all ports.
             
              When LLLDP module status is changed from enabled to disabled, 
              a global timer (instead of port specific timers) is started 
              to ensure the successful transmission of shutdown frame on 
              all ports. Module status change from disabled to enabled is 
              not allowed when the global timer is running (i.e., when disable
              is in progress)."
          DEFVAL  { disabled }
          ::= { fsLldpSystem 2 } 

      fsLldpTraceInput OBJECT-TYPE 
          SYNTAX      OCTET STRING (SIZE(1..280))
          MAX-ACCESS  read-write 
          STATUS      current 
          DESCRIPTION
            "This object stores the trace option string input given by the user.
             To enable particular trace the user has to enter
             the corresponding string(given below) assigned for that. 
             And for enabling more than once traces the user has to enter the 
             corresponding strings with SPACE delimiter between each string. 

             For example, to enable
                 - Init and Shutdown traces
                 - Management traces
                 - Neighbor delete traces
                 - LLDP Port-descr TLV traces and
                 - LLDP Power-via-mdi TLV traces
             The input string is,
             enable init-shut mgmt neigh-del port-descr pwr-mdi
             For example to disable 
                 - Init and Shutdown traces
                 - Management traces
                 - Neighbor delete traces
                 - LLDP Port-descr TLV traces and
                 - LLDP Power-via-mdi TLV traces
             The input string is,
             disable init-shut mgmt neigh-del port-descr pwr-mdi
             first value should be either enable or disable.

             The entered input string is parsed to get the trace options. 
             And the corresponding bits of the trace options are set in 
             fsLldpTraceOption object.
                               
             enable          - Enables the corresponding option.
             disable         - Disables the corresponding option.
             init-shut       - Init and Shutdown traces
             mgmt            - Management traces
             data            - Data Path traces
             ctrl            - Control Plane traces
             pkt-dump        - Packet Dump traces
             resource        - Traces related to all
                               resources except buffers
             all-fail        - All Failure traces
             buf             - Buffer allocation/
                               release traces          

             neigh-add       - Neighbor add traces
             neigh-del       - Neighbor delete traces
             neigh-updt      - Neighbor update traces
             neigh-drop      - Neighbor drop traces
             neigh-ageout    - Neighbor ageout traces
             critical        - LLDP Critical traces
             all-tlv         - LLDP All TLV traces
             chassis-id      - LLDP Chassis-id TLV traces
                 
             port-id         - LLDP Port-id TLV trace
             ttl             - LLDP Ttl TLV trace
             port-descr      - LLDP Port-descr TLV traces
             sys-name        - LLDP Sys-name TLV traces
             sys-descr       - LLDP Sys-descr TLV traces
             sys-capab       - LLDP Sys-capab TLV traces
             mgmt-addr       - LLDP Mgmt-addr TLV traces
             port-vlan       - LLDP Port-vlan TLV traces
             ppvlan          - LLDP Port-proto-vlan
                               TLV traces 
             vlan-name       - LLDP Vlan-name TLV traces
             proto-id        - LLDP Proto-id TLV traces
             mac-phy         - LLDP Mac-phy TLV traces
             pwr-mdi         - LLDP Power-via-mdi TLV traces
             lagg            - LLDP Link-agg TLV traces 
             max-frame       - LLDP Max-frame-size TLV traces
             -               - Reserved

             By default critical trace is enabled." 

          DEFVAL  { "critical" }
          ::= { fsLldpSystem 3 } 

    fsLldpTraceOption OBJECT-TYPE 
          SYNTAX      Integer32          
          MAX-ACCESS  read-only
          STATUS      current 
          DESCRIPTION 
             "This object is used to store the trace options that are enabled
             by the user. The bit positions of the traces is shown below
             
             Bit 0  - init-shut
             Bit 1  - mgmt
             Bit 2  - data
             Bit 3  - ctrl
             Bit 4  - pkt-dump
             Bit 5  - resource
             Bit 6  - all-fail
             Bit 7  - buf

             Bit 8  - neigh-add
             Bit 9  - neigh-del
             Bit 10 - neigh-updt
             Bit 11 - neigh-drop
             Bit 12 - neigh-ageout
             Bit 13 - critical
             Bit 14 - all-tlv
             Bit 15 - chassis-id

             Bit 16 - port-id
             Bit 17 - ttl
             Bit 18 - port-descr
             Bit 19 - sys-name
             Bit 20 - sys-descr
             Bit 21 - sys-capab
             Bit 22 - mgmt-addr
             Bit 23 - port-vlan
             
             Bit 24 - ppvlan
             Bit 25 - vlan-name
             Bit 26 - proto-id
             Bit 27 - mac-phy
             Bit 28 - pwr-mdi
             Bit 29 - lagg
             Bit 30 - max-frame
             Bit 31 - -

             By default critical trace(Bit 13) is set."
             
          DEFVAL { '00002000'H }
          ::= { fsLldpSystem 4 } 

-- ------------------------------------------------------------------ 
-- The LLDP TLV Group 
-- ------------------------------------------------------------------ 

   fsLldpLocChassisIdSubtype  OBJECT-TYPE
      SYNTAX      INTEGER { chassiscomp(1), ifalias(2), portcomp(3),
                            macaddr(4), nwaddr(5), ifname(6), local(7) }
      MAX-ACCESS  read-only
      STATUS      current
      DESCRIPTION
         "The type of encoding used to identify the chassis component
          associated with the local system. 
          
          When chassis id subtype is configured as chassiscomp/portcomp/local
          it is mandatory to configure the fsLldpLocChassisId object. 
          If fsLldpLocChassisId object is not configured then current value of
          fsLldpLocChassisId is advertised.
          
          When chassis id subtype is configured as ifalias/macaddr/nwaddr/
          ifname it is not required to configure fsLldpLocChassisId object. 
          System specific values are used for setting fsLldpLocChassisId 
          object."
      REFERENCE
          "IEEE 802.1AB-2005 9.5.2.2"
      DEFVAL  { macaddr }
      ::= { fsLldpTLV 1 }

   fsLldpLocChassisId  OBJECT-TYPE
      SYNTAX      OCTET STRING (SIZE (1..255))
      MAX-ACCESS  read-only
      STATUS      current
      DESCRIPTION
         "The string value used to identify the chassis component
         associated with the local system. 
         
         Write operation to this object is allowed only when the chassis id 
         subtype is configured as chassiscomp/portcomp/local.

         When chassis id subtype is configured as ifalias/macaddr/nwaddr/ifname
         system specific values are used and hence write operation to this 
         object is not allowed."
      REFERENCE
         "IEEE 802.1AB-2005 9.5.2.3"
         ::= { fsLldpTLV 2}
fsLldpLocPortTable OBJECT-TYPE
	SYNTAX SEQUENCE OF FsLldpLocPortEntry
	MAX-ACCESS         not-accessible
	STATUS             current
	DESCRIPTION
  	  "This table contains one or more rows per port information
 	  associated with the local system known to this agent."
	::= { fsLldpTLV 3 }

     fsLldpLocPortEntry OBJECT-TYPE
	SYNTAX             FsLldpLocPortEntry
	MAX-ACCESS         not-accessible
	STATUS             current
	DESCRIPTION
  	  "Information about a particular port component.
	  Entries may be created and deleted in this table by the
   	  agent."
	INDEX {lldpLocPortNum }
	::= { fsLldpLocPortTable 1 }

     FsLldpLocPortEntry ::= SEQUENCE {
	fsLldpLocPortIdSubtype INTEGER,
	fsLldpLocPortId        OCTET STRING,
        fsLldpPortConfigNotificationType       INTEGER
	}
	
     fsLldpLocPortIdSubtype OBJECT-TYPE
	SYNTAX         INTEGER {ifalias(1), portcomp(2), macaddr(3), nwaddr(4), 
                                ifname(5), agentcircuitid(6), local(7) }
	MAX-ACCESS     read-write
	STATUS         current
	DESCRIPTION
     	  "The type of port identifier encoding used to identify the port 
          component associated with the local port.

          When port id subtype is configured as portcomp/local it is mandatory
          to configure the fsLldpLocPortId object. If fsLldpLocPortId 
          object is not configured then current value of fsLldpLocPortId is
          advertised.

          When chassis id subtype is configured as ifalias/macaddr/nwaddr/
          ifname/agentcircuitid it is not required to configure fsLldpLocPortId
          object. System specific values are used for setting fsLldpLocPortId
          object."
        REFERENCE
 	  "IEEE Std 802.1AB-2005 9.5.3.2"
        DEFVAL  { ifalias }
	::= { fsLldpLocPortEntry 1 }

     fsLldpLocPortId OBJECT-TYPE
	SYNTAX         OCTET STRING (SIZE (1..255))
	MAX-ACCESS     read-write
	STATUS         current
	DESCRIPTION
          "TThe string value used to identify the port component associated 
    with the local port.

    Write operation to this object is allowed only when the chassis id 
    subtype is configured as chassiscomp/portcomp/local.

    When chassis id subtype is configured as ifalias/macaddr/nwaddr/ifname
    system specific values are used and hence write operation to this 
    object is not allowed."
	REFERENCE
   	  "IEEE Std 802.1AB-2005 9.5.3.3"
	::= { fsLldpLocPortEntry 2 }
      fsLldpPortConfigNotificationType       OBJECT-TYPE
      SYNTAX      INTEGER  {
                             remTabChg (1), 
                             misCfg(2),
                             remTabChgAndMisCfg(3)
      } 
      MAX-ACCESS  read-write
      STATUS      current
      DESCRIPTION
             "This object is used to set the notification type. 
    
              If the associated fsLldpNotificationType object has a value of  
              remTabChg (1),then LLDP agent sends trap notification to NMS 
              whenever remote table change occurs.

              If the associated fsLldpNotificationType object has a value of  
              misCfg (1),then LLDP agent sends trap notification to NMS 
              whenever mis-configuration is identified.

              If the associated fsLldpNotificationType object has a value of  
              remTabChgAndMisCfg(3),then LLDP agent sends trap notification to 
              NMS whenever remote table change occurs or/and whenever 
              mis-configuration is identified.

              LLDP agent send the trap messages only when  MIB Object 
              lldpPortConfigNotificationEnable is true.So 
              fsLldpNotificationType Object is valid when 
              lldpPortConfigNotificationEnable Object is true."

       DEFVAL  { misCfg }
	::= { fsLldpLocPortEntry 3 }
   
   
-- ------------------------------------------------------------------ 
-- The LLDP stastics Group 
-- ------------------------------------------------------------------ 
    
   fsLldpMemAllocFailure  OBJECT-TYPE
      SYNTAX      Integer32
      MAX-ACCESS  read-only
      STATUS      current
      DESCRIPTION
         "This object gives the count of total memory allocation failures"
      ::= { fsLldpStatistics 1 }

   fsLldpInputQOverFlows  OBJECT-TYPE
      SYNTAX      Integer32
      MAX-ACCESS  read-only
      STATUS      current
      DESCRIPTION
         "This object gives the count of total input queue overflows"
      ::= {fsLldpStatistics 2}

   fsLldpStatsRemTablesUpdates  OBJECT-TYPE
     SYNTAX      ZeroBasedCounter32
     UNITS       "table entries"
     MAX-ACCESS  read-only
     STATUS      current
     DESCRIPTION
         "The number of times any information advertised by a particular 
          MSAP is updated in tables contained in lldpRemoteSystemsData and
          lldpExtensions objects."
     ::= { fsLldpStatistics 3 }

-- ------------------------------------------------------------------ 
-- The LLDP Notification Group 
-- ------------------------------------------------------------------ 
    fsLldpTraps OBJECT IDENTIFIER ::= { fsLldpNotification 0 }

    fsLldpRemTablesChange NOTIFICATION-TYPE
    OBJECTS {
        lldpStatsRemTablesInserts,
        lldpStatsRemTablesDeletes,
        lldpStatsRemTablesDrops,
        lldpStatsRemTablesAgeouts,
        fsLldpStatsRemTablesUpdates
    }
    STATUS      current
    DESCRIPTION
        "A fsLldpRemTablesChange notification is sent when the value
         of lldpStatsRemTableLastChangeTime changes.  It can be
         utilized by an NMS to trigger LLDP remote systems table
         maintenance polls.

         Note that transmission of fsLldpRemTablesChange
         notifications are throttled by the agent, as specified by the
         'lldpNotificationInterval' object.
          
         The first four objects are already mentioned in the standard
         LLDP mib. As the Table Updation notification is also sent in the
         same notification PDU these objects are moved to proprietary mib."
    ::= { fsLldpTraps 1 }

    fsLldpExceedsMaxFrameSize NOTIFICATION-TYPE
    OBJECTS {
        lldpLocPortId
    }
    STATUS      current
    DESCRIPTION
           "A fsLldpExceedsMaxFrameSize notification is sent if the size of LLDP
           frame to be transmitted exceeds the maximum frame size (1522 bytes).
           This can occur if many number of TLVs need to be included in a single
           frame .

           It notifies the NMS that the information obtained about this system
           from its neighbor is not complete."
    ::= { fsLldpTraps 2 }


    fsLldpDupChasisId NOTIFICATION-TYPE
    OBJECTS {
        lldpRemChassisId,
        lldpRemPortId        
    }
    STATUS      current
    DESCRIPTION
           "A fsLldpDupChasisId notification sent if the configured 
            chasisId and Received chasisId from the neighbor is same.

            It notifies the NMS that the information obtained from its neighbor 
            is Duplicate."
       ::= {fsLldpTraps 3}

    fsLldpDupSystemName NOTIFICATION-TYPE
    OBJECTS {
        lldpRemChassisId ,
        lldpRemPortId, 
        lldpRemSysName    
    }
    STATUS      current
    DESCRIPTION
           "A fsLldpDupSystemName notification sent if the configured 
            system name and Received system name from the neighbor is same.

            It notifies the NMS that the information obtained from its neighbor 
            is Duplicate."
       ::= {fsLldpTraps 4}

    fsLldpDupManagmentAddress NOTIFICATION-TYPE
    OBJECTS {
        lldpRemChassisId ,
        lldpRemPortId, 
        lldpRemManAddr
    }
    STATUS      current
    DESCRIPTION
           "A fsLldpDupManagementAddress notification sent if the configured 
            management address and Received management address from the neighbor is same.

            It notifies the NMS that the information obtained from its neighbor 
            is Duplicate."
       ::= {fsLldpTraps 5}

    fsLldpMisConfigPortVlanID NOTIFICATION-TYPE
    OBJECTS {
        lldpRemChassisId ,
        lldpRemPortId, 
        lldpXdot1RemPortVlanId
    }
    STATUS      current
    DESCRIPTION
           "A fsLldpMisConfigPortVlanID notification sent if the Port VlanId of 
            two systems connected to the same link is different.

            It notifies the NMS that the information obtained from its neighbor 
            is mis-configured."
       ::= {fsLldpTraps 6}

    fsLldpMisConfigPortProtoVlanID NOTIFICATION-TYPE
    OBJECTS {
        lldpRemChassisId ,
        lldpRemPortId, 
        lldpXdot1RemProtoVlanSupported
    }
    STATUS      current
    DESCRIPTION
           "A fsLldpMisConfigPortProtoVlanID notification sent if the Port and 
            protocol VlanId of two systems connected to the same link is different.
        
            lldpRemPortId and lldpRemChassisId information sent to identify
            the remote system.
            lldpXdot1RemProtoVlanId is not accesiable since it is the index,
            so sending the lldpXdot1RemProtoVlanSupported information,
            to know which Port and Protocol VlanId is MisConfigured. PPVID will
            be sent along with the OID.

            It notifies the NMS that the information obtained from its neighbor 
            is mis-configured."
       ::= {fsLldpTraps 7}

    fsLldpMisConfigVlanName NOTIFICATION-TYPE
    OBJECTS {
        lldpRemChassisId ,
        lldpRemPortId, 
        lldpXdot1RemVlanName        
    }
    STATUS      current
    DESCRIPTION
           "A fsLldpMisConfigVlanName notification sent if the vlan name 
            of two systems connected to the same link is different.

            It notifies the NMS that the information obtained from its neighbor 
            is mis-configured."
       ::= {fsLldpTraps 8}

    fsLldpMisConfigProtocolIdentity NOTIFICATION-TYPE
    OBJECTS {
        lldpRemChassisId ,
        lldpRemPortId, 
       lldpXdot1RemProtocolId 
    }
    STATUS      current
    DESCRIPTION
           "A fsLldpMisConfigProtocolIdentity notification sent if the protocol 
            identity information (example spanning Tree protocol, 
            the Link Aggregation protocol and proprietary protocol) of 
            two systems connected to the same link is different.

            It notifies the NMS that the information obtained from its neighbor 
            is mis-configured."
       ::= {fsLldpTraps 9}

    fsLldpMisConfigLinkAggStatus NOTIFICATION-TYPE
    OBJECTS {
        lldpRemChassisId ,
        lldpRemPortId, 
        lldpXdot3RemLinkAggStatus       
    }
    STATUS      current
    DESCRIPTION
           "A fsLldpMisConfigLinkAggStatus notification sent if the 
            Link aggregation configuration of two systems connected to the same link 
            is different.
            It is possible that if one system formed a link aggregation with
            a remote port while the other system is unaware of the aggregation.
            This type of configuration may cause network loops or 
            unpredictable communication.

            It notifies the NMS that the information obtained from its neighbor 
            is mis-configured."
       ::= {fsLldpTraps 10}

    fsLldpMisConfigPowerMDI NOTIFICATION-TYPE
    OBJECTS {
        lldpRemChassisId ,
        lldpRemPortId, 
        lldpXdot3RemPowerClass        
    }
    STATUS      current
    DESCRIPTION
           "A fsLldpMisConfigPowerMDI notification sent if the power class
            configuration of two systems connected to the same link is different.

            It notifies the NMS that the information obtained from its neighbor 
            is mis-configured."
       ::= {fsLldpTraps 11}

    fsLldpMisConfigMaxFrameSize NOTIFICATION-TYPE
    OBJECTS {
        lldpRemChassisId ,
        lldpRemPortId, 
        lldpXdot3RemMaxFrameSize
    }
    STATUS      current
    DESCRIPTION
           "A fsLldpMisConfigMaxFrameSize notification sent if the 
            maximum frame size configuration of two systems connected to 
            the same link is different.
            
            Difference in maximum frame size can result in loss of frames if 
            the sending station advertised maximum frame size is larger 
            than the receiveing station.

            It notifies the NMS that the information obtained from its neighbor 
            is mis-configured."
       ::= {fsLldpTraps 12}
       
    fsLldpMisConfigOperMauType NOTIFICATION-TYPE
    OBJECTS {
        lldpRemChassisId ,
        lldpRemPortId, 
        lldpXdot3RemPortOperMauType         
    }
    STATUS      current
    DESCRIPTION
           "A fsLldpMisConfigOperMauType  notification sent if the 
           Operational MauType of the two systems connected to the same link is different.

            It notifies the NMS that the information obtained from its neighbor 
            is mis-configured."
       ::= {fsLldpTraps 13}

 



-- ----------------------------------------------------------------- -- 
-- groups in the MIB  
-- ----------------------------------------------------------------- -- 
-- start title 
--     l2VoiceVlan                   OBJECT IDENTIFIER ::= { at-GS95016v3 163 }
-- end title 
-- ---------------------------------------------------------------- --
-- start body
    -- ---------------------------------------------------------------------
    -- voicevlan Function
    -- ---------------------------------------------------------------------
          
      voicevlanSystem          OBJECT IDENTIFIER ::= { l2VoiceVlan 1 }
      voicevlanOUI             OBJECT IDENTIFIER ::= { l2VoiceVlan 2 }
 
    -- ------------------------------------------------------------------
    -- The Voice Vlan Group
    -- ------------------------------------------------------------------

      voiceVlanMode OBJECT-TYPE
           SYNTAX      INTEGER { enabled(1), disabled(2) }
           MAX-ACCESS  read-write
           STATUS      current
           DESCRIPTION
               "Voice VLAN is a feature that allows you to automatically place 
               the voice traffic from IP phone to an assigned VLAN to enhance 
               the VoIP service. 
               This object is for enabling or disabling Voice Vlan function 
               in the system. 
               If the Vlan mode is in Asymmetric VLAN mode, Voice VLAN can not 
               be enabled."

           ::= { voicevlanSystem 2 }

      voiceVlanId OBJECT-TYPE
            SYNTAX Integer32
            MAX-ACCESS read-write
            STATUS current
            DESCRIPTION
                "The ID of VLAN that you want the voice traffic to be in. 
                It must be a exist vlan id."
            ::= { voicevlanSystem 3 }

      voiceVlanTimeout OBJECT-TYPE
            SYNTAX Integer32
            MAX-ACCESS read-write
            STATUS current
            DESCRIPTION
                "A period of time in hour to remove a port from voice VLAN 
                if the port is an automatic VLAN member.
                The Timeout range is 1~120 hours.
                Default aging time is 1 hour."
            ::= { voicevlanSystem 4}

      voiceVlanPriority OBJECT-TYPE
            SYNTAX INTEGER { highest(0), high(1), medium(2), low(3) }
            MAX-ACCESS read-write
            STATUS current
            DESCRIPTION
                "The 802.1p priority levels of the traffic in the Voice VLAN."
            ::= { voicevlanSystem 5}

        --
        -- Voice Vlan Port Control Table
        --          

        voicevlanPortControlTable OBJECT-TYPE
          SYNTAX      SEQUENCE OF VoiceVlanPortControlEntry
          MAX-ACCESS  not-accessible
           STATUS      current
           DESCRIPTION
                      "A table that contains Voice Vlan Port Control
                       configuration information."
          ::= { voicevlanSystem 6 }


        voicevlanPortControlEntry OBJECT-TYPE
          SYNTAX      VoiceVlanPortControlEntry
          MAX-ACCESS  not-accessible
          STATUS      current
          DESCRIPTION
                      "A list of Voice Vlan Control configuration
                       parameters for each Port on this device."
          INDEX      { voicevlanPortControlIndex }
          ::= { voicevlanPortControlTable 1 }  

        VoiceVlanPortControlEntry ::=
          SEQUENCE {
            voicevlanPortControlIndex
                InterfaceIndex,
            voicevlanPortAutoDetection
                INTEGER,    
            voicevlanPortState
                INTEGER        
        }
        
        voicevlanPortControlIndex OBJECT-TYPE
          SYNTAX       InterfaceIndex
          MAX-ACCESS   read-only
          STATUS       current
          DESCRIPTION
              "The voice vlan port index."
          ::= { voicevlanPortControlEntry 1 }            
          
        voicevlanPortAutoDetection  OBJECT-TYPE
          SYNTAX       INTEGER { enabled(1), disabled(2) }
          MAX-ACCESS   read-write
          STATUS       current
          DESCRIPTION
            "This object is for enabling or disabling Voice Vlan Auto 
             Detection in the port.
             If the auto detection is enable, switch will add this port 
             to the voice VLAN automatically if it detects the device OUI 
             matches the Telephony OUI.
             If the port is a static member of voice vlan or a LA member,
             it can not enable voice vlan auto detection."
          ::= { voicevlanPortControlEntry 2 }
                
        voicevlanPortState      OBJECT-TYPE 
            SYNTAX INTEGER  {
        		 manual(1),
        		 dynamic(2),
                 none(3)
            }
           MAX-ACCESS  read-only 
           STATUS      current 
           DESCRIPTION 
                "This object indicates Voice vlan state to this Port.
                manual - this port is a static member of voice vlan.
                dynamic - this port is a dynamic member of voice vlan.
                none - this port is not a member of voice vlan."
                 
           ::= { voicevlanPortControlEntry 3 }    

    -- ------------------------------------------------------------------
    -- The Voice Vlan OUI Group
    -- ------------------------------------------------------------------

    --
    -- Voice Vlan OUI Table
    --
    
    voicevlanOUITable  OBJECT-TYPE
        SYNTAX     SEQUENCE OF VoicevlanOUIEntry 
        MAX-ACCESS not-accessible
        STATUS     current
        DESCRIPTION
           "A voice vlan OUI entry containing the description and mac."

        ::= { voicevlanOUI 1 }

    voicevlanOUIEntry OBJECT-TYPE
        SYNTAX     VoicevlanOUIEntry 
        MAX-ACCESS not-accessible
        STATUS     current
        DESCRIPTION
              "A voice vlan OUI entry containing the description and mac."

        INDEX { voicevlanOUITelephonyOUI }
        ::= { voicevlanOUITable 1 }

    VoicevlanOUIEntry  ::= 
            SEQUENCE {
              voicevlanOUITelephonyOUI          MacAddress,
              voicevlanOUIDescription           OCTET STRING,
              voicevlanOUIMask                  MacAddress,
              voicevlanOUIStatus                RowStatus          
              }

    voicevlanOUITelephonyOUI OBJECT-TYPE
       SYNTAX       MacAddress
       MAX-ACCESS   read-only
       STATUS       current
       DESCRIPTION
         "An Organizationally Unique Identifier (OUI) is a 24-bit number 
         that is purchased from the IEEE Registration Authority. This identifier 
         uniquely identifies a vendor, manufacturer, or other organization.
         This object indicates the voice traffic's OUI that user created." 
        ::= { voicevlanOUIEntry  1 }

    voicevlanOUIDescription OBJECT-TYPE
        SYNTAX      OCTET STRING
        MAX-ACCESS  read-write
        STATUS      current
        DESCRIPTION
              "The Description for the OUI."
        ::= { voicevlanOUIEntry  2 }
        
    voicevlanOUIMask OBJECT-TYPE
       SYNTAX       MacAddress
       MAX-ACCESS   read-only
       STATUS       current
       DESCRIPTION
         "Voice vlan OUI Mask. Always be FF:FF:FF:00:00:00."
        ::= { voicevlanOUIEntry  3 }
        
    voicevlanOUIStatus OBJECT-TYPE
       SYNTAX RowStatus
       MAX-ACCESS read-create
       STATUS current
       DESCRIPTION
         "This object indicates the status of this entry. 
         To create a new entry, you must set the voicevlanOUIStatus 
         to be CreateAndGo, then this entry will turn to be Active."
       ::= { voicevlanOUIEntry 4 }    

-- end body

     
    --
    -- Port Map Table
    --
    
    trafficSegTable  OBJECT-TYPE
        SYNTAX     SEQUENCE OF TrafficSegEntry 
        MAX-ACCESS not-accessible
        STATUS     current
        DESCRIPTION
           "A Port-channel is created through ifMain table.
           After the creation of the port-channel, corresponding logical
           interface will be created in the ifMain table. 
           This Port-channel table is indexed through Key values and allows to 
           configure link selection policy and the Mac address for 
           the port-channel. All other objects in this table displays 
           the details of the port-channel"

        ::= { trafficSeg 1 }

    trafficSegEntry OBJECT-TYPE
        SYNTAX     TrafficSegEntry 
        MAX-ACCESS not-accessible
        STATUS     current
        DESCRIPTION
              "There is one entry in this table for each created
               port-channel port"

        INDEX { trafficSegIfIndex }
        ::= { trafficSegTable 1 }

    TrafficSegEntry ::= 
            SEQUENCE {
              trafficSegIfIndex                InterfaceIndex,
              trafficSegMemberList             PortList
              }

    trafficSegIfIndex OBJECT-TYPE
        SYNTAX      InterfaceIndex
        MAX-ACCESS  read-only
        STATUS      current
        DESCRIPTION
              "The ifIndex of the port-channel(Aggregator's 
               interface index). "
        ::= { trafficSegEntry 1 }

  	trafficSegMemberList OBJECT-TYPE
	   SYNTAX       PortList
	   MAX-ACCESS   read-write
	   STATUS       current
	   DESCRIPTION
	       "List of the member port of the port-channel."
	   ::= { trafficSegEntry 2 }

        
    
-- end body
              

atiAcl                    OBJECT IDENTIFIER  ::= { atiAclMib 1 }
atiMacFilter              OBJECT IDENTIFIER  ::= { atiAclMib 2 }

--======================= Classifier =======================--
 
atiAclClassifierTable OBJECT-TYPE
   SYNTAX        SEQUENCE OF AtiAclClassifierEntry
   MAX-ACCESS    not-accessible
   STATUS        current
   DESCRIPTION
      "ACL Classifier entry table."
   ::= { atiAcl 1 }

atiAclClassifierEntry OBJECT-TYPE
   SYNTAX       AtiAclClassifierEntry
   MAX-ACCESS   not-accessible
   STATUS       current
   DESCRIPTION
      "Classifier is used to specify a packet type for Policies."
   INDEX { atiAclClassifierIndex }
   ::= { atiAclClassifierTable 1 }

AtiAclClassifierEntry ::=
   SEQUENCE {
		atiAclClassifierIndex
         Integer32,   
-- L2 --         
		atiAclClassifierSrcMac
         MacAddress, 
		atiAclClassifierSrcMacMaskLen
         Integer32,            
		atiAclClassifierDstMac
         MacAddress,
		atiAclClassifierDstMacMaskLen
         Integer32,
		atiAclClassifierVlanId
         Integer32,
		atiAclClassifierCos
         Integer32,         
		atiAclClassifierEtherType
         Integer32,          
-- L3 --       
		atiAclClassifierSrcIp
         IpAddress, 
		atiAclClassifierSrcIpMaskLen
         Integer32,            
		atiAclClassifierDstIp
         IpAddress,
		atiAclClassifierDstIpMaskLen
         Integer32,
		atiAclClassifierDscp
         Integer32,
		atiAclClassifierProtocol
         Integer32, 
-- L4 --
		atiAclClassifierSrcPort
         Integer32,                  
		atiAclClassifierDstPort
         Integer32,          
--
		atiAclClassifierRowStatus
         RowStatus
   }

atiAclClassifierIndex OBJECT-TYPE
   SYNTAX        Integer32 (1..65535)
   MAX-ACCESS    read-only
   STATUS    current
   DESCRIPTION
      "The index of the Classifier entry."
   ::=  { atiAclClassifierEntry 1 }        
  
atiAclClassifierSrcMac OBJECT-TYPE
   SYNTAX        MacAddress
   MAX-ACCESS    read-write
   STATUS    current
   DESCRIPTION
      "Source MAC address."
   ::=  { atiAclClassifierEntry 2 } 
   
atiAclClassifierSrcMacMaskLen OBJECT-TYPE
   SYNTAX        Integer32 (0..48)
   MAX-ACCESS    read-write
   STATUS    current
   DESCRIPTION
      "Source MAC mask length.
      	1-48: length in bits
      	0: Ignored"      
   ::=  { atiAclClassifierEntry 3 }          
   
atiAclClassifierDstMac OBJECT-TYPE
   SYNTAX        MacAddress
   MAX-ACCESS    read-write
   STATUS    current
   DESCRIPTION
      "Destination MAC address."
   ::=  { atiAclClassifierEntry 4 }   

atiAclClassifierDstMacMaskLen OBJECT-TYPE
   SYNTAX        Integer32 (0..48)
   MAX-ACCESS    read-write
   STATUS    current
   DESCRIPTION
      "Destination MAC mask length.
      	1-48: length in bits
      	0: Ignored"      
   ::=  { atiAclClassifierEntry 5 }      
   
atiAclClassifierVlanId OBJECT-TYPE
   SYNTAX        Integer32 (-1..4000)
   MAX-ACCESS    read-write
   STATUS    current
   DESCRIPTION
      "802.1Q Vlan Id.
     	1-4000: Vlan Id
      	-1: Ignored"	  
   ::=  { atiAclClassifierEntry 6 } 
   
atiAclClassifierCos OBJECT-TYPE
   SYNTAX        Integer32 (-1..7)
   MAX-ACCESS    read-write
   STATUS    current
   DESCRIPTION
      "802.1p priority. 
      	0-7: 802.1p priority value      
		-1: Ignored"	  
   ::=  { atiAclClassifierEntry 7 }      
   
atiAclClassifierEtherType OBJECT-TYPE
   SYNTAX        Integer32 (-1..65535)
   MAX-ACCESS    read-write
   STATUS    current
   DESCRIPTION
      "EtherType. 
      	0-65535: EtherType number 
		-1: Ignored"	  
   ::=  { atiAclClassifierEntry 8 }   

atiAclClassifierSrcIp OBJECT-TYPE
   SYNTAX        IpAddress
   MAX-ACCESS    read-write
   STATUS    current
   DESCRIPTION
      "Source IP address."
   ::=  { atiAclClassifierEntry 10 }   
   
atiAclClassifierSrcIpMaskLen OBJECT-TYPE
   SYNTAX        Integer32 (0..32)
   MAX-ACCESS    read-write
   STATUS    current
   DESCRIPTION
      "Source IP mask length.
      	1-32: length in bits
      	0: Ignored"      
   ::=  { atiAclClassifierEntry 11 }       
   
atiAclClassifierDstIp OBJECT-TYPE
   SYNTAX        IpAddress
   MAX-ACCESS    read-write
   STATUS    current
   DESCRIPTION
      "Destination IP address."
   ::=  { atiAclClassifierEntry 12 }    
   
atiAclClassifierDstIpMaskLen OBJECT-TYPE
   SYNTAX        Integer32 (0..32)
   MAX-ACCESS    read-write
   STATUS    current
   DESCRIPTION
      "Destination IP mask length.
      	1-32: length in bits
      	0: Ignored"
   ::=  { atiAclClassifierEntry 13 }   
   
atiAclClassifierDscp OBJECT-TYPE
   SYNTAX        Integer32 (-1..63)
   MAX-ACCESS    read-write
   STATUS    current
   DESCRIPTION
      "Differentiated Services Code Point. 
        0-63: DSCP value      
		-1: Ignored"	  
   ::=  { atiAclClassifierEntry 14 }    
   
atiAclClassifierProtocol OBJECT-TYPE
   SYNTAX        Integer32 (-1..255)
   MAX-ACCESS    read-write
   STATUS    current
   DESCRIPTION
      "Layer 4 protocol type.
        0-255: Layer 4 protocol number
		-1: Ignored"   
   ::=  { atiAclClassifierEntry 15 }  
   
atiAclClassifierSrcPort OBJECT-TYPE
   SYNTAX        Integer32 (-1..65535)
   MAX-ACCESS    read-write
   STATUS    current
   DESCRIPTION
      "TCP/UDP Source port.
        0-65535: port number
		-1: Ignored"	  
   ::=  { atiAclClassifierEntry 20 } 
   
atiAclClassifierDstPort OBJECT-TYPE
   SYNTAX        Integer32 (-1..65535)
   MAX-ACCESS    read-write
   STATUS    current
   DESCRIPTION
      "TCP/UDP Destination port.  
        0-65535: port number
		-1: Ignored"	  
   ::=  { atiAclClassifierEntry 21 }  
      
atiAclClassifierRowStatus OBJECT-TYPE
   SYNTAX    		RowStatus
   MAX-ACCESS   read-create
   STATUS    current
   DESCRIPTION
      "The row status of the entry.
       1: write - enable the entry 
       	  read - entry is enabled   
       2: write - disable the entry
       	  read - entry is disabled
       3: read - entry is not ready
       5: write - create the entry
       6: write - delete the entry"
   ::= { atiAclClassifierEntry 30 } 

--======================= Profile Action =======================--

atiAclProfileActionTable OBJECT-TYPE
   SYNTAX        SEQUENCE OF AtiAclProfileActionEntry
   MAX-ACCESS    not-accessible
   STATUS        current
   DESCRIPTION
      "ACL Profile Action entry table."
   ::= { atiAcl 2 }

atiAclProfileActionEntry OBJECT-TYPE
   SYNTAX       AtiAclProfileActionEntry
   MAX-ACCESS   not-accessible
   STATUS       current
   DESCRIPTION
      "Profile Action is used to manipulate the DSCP or CoS values in a packet."
   INDEX { atiAclProfileActionIndex }
   ::= { atiAclProfileActionTable 1 }

AtiAclProfileActionEntry ::=
   SEQUENCE {
		atiAclProfileActionIndex
         Integer32,  
		atiAclProfileActionCos
         Integer32,		 
		atiAclProfileActionDscp
         Integer32, 		  
		atiAclProfileActionRowStatus
         RowStatus
   }
   
atiAclProfileActionIndex OBJECT-TYPE
   SYNTAX        Integer32 (1..72)
   MAX-ACCESS    read-only
   STATUS    current
   DESCRIPTION
      "The index of the Action entry."
   ::=  { atiAclProfileActionEntry 1 }

atiAclProfileActionCos OBJECT-TYPE
   SYNTAX        Integer32 (-1..7)
   MAX-ACCESS    read-write
   STATUS    current
   DESCRIPTION
      "Policied-Cos.
        0-7: 802.1p priority value
		-1: Ignored"
   ::=  { atiAclProfileActionEntry 2 }

atiAclProfileActionDscp OBJECT-TYPE
   SYNTAX        Integer32 (-1..63)
   MAX-ACCESS    read-write
   STATUS    current
   DESCRIPTION
      "Policied-DSCP.  
        0-63: DSCP value      
		-1: Ignored"
   ::=  { atiAclProfileActionEntry 3 }
   
atiAclProfileActionRowStatus OBJECT-TYPE
   SYNTAX    RowStatus
   MAX-ACCESS   read-create
   STATUS    current
   DESCRIPTION
      "The row status of the entry.
       1: write - enable the entry 
       	  read - entry is enabled   
       2: write - disable the entry
       	  read - entry is disabled
       3: read - entry is not ready
       5: write - create the entry
       6: write - delete the entry"
   ::= { atiAclProfileActionEntry 4 }    
   
--======================= In-profile Action =======================--   

atiAclInProfileActionTable OBJECT-TYPE
   SYNTAX        SEQUENCE OF AtiAclInProfileActionEntry
   MAX-ACCESS    not-accessible
   STATUS        current
   DESCRIPTION
      "ACL In-Profile Action entry table."
   ::= { atiAcl 3 }

atiAclInProfileActionEntry OBJECT-TYPE
   SYNTAX       AtiAclInProfileActionEntry
   MAX-ACCESS   not-accessible
   STATUS       current
   DESCRIPTION
      "In-Profile Action is used to assign an action to a policy."
   INDEX { atiAclInProfileActionIndex }
   ::= { atiAclInProfileActionTable 1 }

AtiAclInProfileActionEntry ::=
   SEQUENCE {
		atiAclInProfileActionIndex
         Integer32,  
		atiAclInProfileActionPermitDeny
         Integer32,		 
		atiAclInProfileActionActionId
         Integer32, 		  
		atiAclInProfileActionRowStatus
         RowStatus
   }
   
atiAclInProfileActionIndex OBJECT-TYPE
   SYNTAX        Integer32 (1..65535)
   MAX-ACCESS    read-only
   STATUS    current
   DESCRIPTION
      "The index of the In-Profile Action entry."
   ::=  { atiAclInProfileActionEntry 1 }

atiAclInProfileActionPermitDeny OBJECT-TYPE
   SYNTAX        Integer32 (0..1)
   MAX-ACCESS    read-write
   STATUS    current
   DESCRIPTION
      "Permit/Deny action.
		0: Permit
		1: Deny"
   ::=  { atiAclInProfileActionEntry 2 }

atiAclInProfileActionActionId OBJECT-TYPE
   SYNTAX        Integer32 (0..72)
   MAX-ACCESS    read-write
   STATUS    current
   DESCRIPTION
      "The index of Action entry used by this In-Profile entry.
      	1-72: Action entry index
		0: Ignored"
   ::=  { atiAclInProfileActionEntry 3 }
   
atiAclInProfileActionRowStatus OBJECT-TYPE
   SYNTAX    RowStatus
   MAX-ACCESS   read-create
   STATUS    current
   DESCRIPTION
      "The row status of the entry.
       1: write - enable the entry 
       	  read - entry is enabled   
       2: write - disable the entry
       	  read - entry is disabled
       3: read - entry is not ready
       5: write - create the entry
       6: write - delete the entry"
   ::= { atiAclInProfileActionEntry 4 }  

--======================= Out-profile Action =======================--

atiAclOutProfileActionTable OBJECT-TYPE
   SYNTAX        SEQUENCE OF AtiAclOutProfileActionEntry
   MAX-ACCESS    not-accessible
   STATUS        current
   DESCRIPTION
      "ACL Out-Profile Action entry table."
   ::= { atiAcl 4 }

atiAclOutProfileActionEntry OBJECT-TYPE
   SYNTAX       AtiAclOutProfileActionEntry
   MAX-ACCESS   not-accessible
   STATUS       current
   DESCRIPTION  
      "Out-Profile Action is used to assign a classifier index to a profile action ID 
      as well as a committed rate and a burst size"      
   INDEX { atiAclOutProfileActionIndex }
   ::= { atiAclOutProfileActionTable 1 }

AtiAclOutProfileActionEntry ::=
   SEQUENCE {
		atiAclOutProfileActionIndex
         Integer32,  
		atiAclOutProfileActionPermitDeny
         Integer32,
		atiAclOutProfileActionCommittedRate
         Integer32,
		atiAclOutProfileActionBurstSize
         Integer32,		 
		atiAclOutProfileActionActionId
         Integer32, 		  
		atiAclOutProfileActionRowStatus
         RowStatus
   }
   
atiAclOutProfileActionIndex OBJECT-TYPE
   SYNTAX        Integer32 (1..65535)
   MAX-ACCESS    read-only
   STATUS    current
   DESCRIPTION
      "The index of the Out-Profile Action entry."
   ::=  { atiAclOutProfileActionEntry 1 }

atiAclOutProfileActionPermitDeny OBJECT-TYPE
   SYNTAX        Integer32 (0..1)
   MAX-ACCESS    read-write
   STATUS    current
   DESCRIPTION
      "Permit/Deny action.
		0: Permit
		1: Deny"
   ::=  { atiAclOutProfileActionEntry 2 }
   
   
atiAclOutProfileActionCommittedRate OBJECT-TYPE
   SYNTAX        Integer32 (64..1000000)
   MAX-ACCESS    read-write
   STATUS    current
   DESCRIPTION
      "Committed rate in Kbps."
   ::=  { atiAclOutProfileActionEntry 3 }

atiAclOutProfileActionBurstSize OBJECT-TYPE
   SYNTAX        Integer32 (16..64)
   MAX-ACCESS    read-write
   STATUS    current
   DESCRIPTION
      "Max burst size which is the maximum amount of data in KB."
   ::=  { atiAclOutProfileActionEntry 4 }   

atiAclOutProfileActionActionId OBJECT-TYPE
   SYNTAX        Integer32 (0..72)
   MAX-ACCESS    read-write
   STATUS    current
   DESCRIPTION
      "The index of Action entry used by this Out-Profile entry.  
      	1-72: Action entry index      
		0: Ignored"
   ::=  { atiAclOutProfileActionEntry 5 }
   
atiAclOutProfileActionRowStatus OBJECT-TYPE
   SYNTAX    RowStatus
   MAX-ACCESS   read-create
   STATUS    current
   DESCRIPTION
      "The row status of the entry.
       1: write - enable the entry 
       	  read - entry is enabled   
       2: write - disable the entry
       	  read - entry is disabled
       3: read - entry is not ready
       5: write - create the entry
       6: write - delete the entry"
   ::= { atiAclOutProfileActionEntry 6 }     

--======================= Port-List =======================--

atiAclPortListTable OBJECT-TYPE
   SYNTAX        SEQUENCE OF AtiAclPortListEntry
   MAX-ACCESS    not-accessible
   STATUS        current
   DESCRIPTION
      "ACL Port-List entry table."
   ::= { atiAcl 5 }

atiAclPortListEntry OBJECT-TYPE
   SYNTAX       AtiAclPortListEntry
   MAX-ACCESS   not-accessible
   STATUS       current
   DESCRIPTION
      "Port-List is used to specify a list of ports."
   INDEX { atiAclPortListIndex }
   ::= { atiAclPortListTable 1 }

AtiAclPortListEntry ::=
   SEQUENCE {
		atiAclPortListIndex
         Integer32,  
		atiAclPortListString
         DisplayString,		 	  
		atiAclPortListRowStatus
         RowStatus
   }
   
atiAclPortListIndex OBJECT-TYPE
   SYNTAX        Integer32 (1..65535)
   MAX-ACCESS    read-only
   STATUS    current
   DESCRIPTION
      "The index of the Port-List entry."
   ::=  { atiAclPortListEntry 1 }

atiAclPortListString OBJECT-TYPE
   SYNTAX        DisplayString (SIZE (1..63))
   MAX-ACCESS    read-write
   STATUS    current
   DESCRIPTION
      "Port-list string. e.g. 1,3,5-8"
   ::=  { atiAclPortListEntry 2 }
   
atiAclPortListRowStatus OBJECT-TYPE
   SYNTAX    RowStatus
   MAX-ACCESS   read-create
   STATUS    current
   DESCRIPTION
      "The row status of the entry.
       1: write - enable the entry 
       	  read - entry is enabled   
       2: write - disable the entry
       	  read - entry is disabled
       3: read - entry is not ready
       5: write - create the entry
       6: write - delete the entry"
   ::= { atiAclPortListEntry 3 }       
   
--======================= Policy =======================--

atiAclPolicyTable OBJECT-TYPE
   SYNTAX        SEQUENCE OF AtiAclPolicyEntry
   MAX-ACCESS    not-accessible
   STATUS        current
   DESCRIPTION
      "ACL Policy entry table."
   ::= { atiAcl 6 }

atiAclPolicyEntry OBJECT-TYPE
   SYNTAX       AtiAclPolicyEntry
   MAX-ACCESS   not-accessible
   STATUS       current
   DESCRIPTION
      "Policy controls the ingress traffic on a port. 
      It defines a category of traffic and the action of the port when it receives 
      packets of the category."
   INDEX { atiAclPolicyIndex }
   ::= { atiAclPolicyTable 1 }

AtiAclPolicyEntry ::=
   SEQUENCE {
		atiAclPolicyIndex
         Integer32,  
		atiAclPolicyClassifierIndex
         Integer32,	
		atiAclPolicySequence
         Integer32,		 
		atiAclPolicyInProfileIndex
         Integer32,	
		atiAclPolicyOutProfileIndex
         Integer32,	
		atiAclPolicyPortListIndex
         Integer32,			 
		atiAclPolicyRowStatus
         RowStatus
   }
   
atiAclPolicyIndex OBJECT-TYPE
   SYNTAX        Integer32 (1..65535)
   MAX-ACCESS    read-only
   STATUS    current
   DESCRIPTION
		"The index of the Policy entry."
   ::=  { atiAclPolicyEntry 1 }

atiAclPolicyClassifierIndex OBJECT-TYPE
   SYNTAX        Integer32 (1..65535)
   MAX-ACCESS    read-write
   STATUS    current
   DESCRIPTION
		"The index of Classifier entry used by this Policy entry."
   ::=  { atiAclPolicyEntry 2 }
   
atiAclPolicySequence OBJECT-TYPE
   SYNTAX        Integer32 (1..64)
   MAX-ACCESS    read-write
   STATUS    current
   DESCRIPTION
		"The sequence of the Policy entry."
   ::=  { atiAclPolicyEntry 3 }
   
atiAclPolicyInProfileIndex OBJECT-TYPE
   SYNTAX        Integer32 (1..65535)
   MAX-ACCESS    read-write
   STATUS    current
   DESCRIPTION
		"The index of In-Profile entry used by this Policy entry."
   ::=  { atiAclPolicyEntry 4 }

atiAclPolicyOutProfileIndex OBJECT-TYPE
   SYNTAX        Integer32 (0..65535)
   MAX-ACCESS    read-write
   STATUS    current
   DESCRIPTION
		"The index of Out-Profile entry used by this Policy entry.
		0: Ignored"
   ::=  { atiAclPolicyEntry 5 }   
   
atiAclPolicyPortListIndex OBJECT-TYPE
   SYNTAX        Integer32 (1..65535)
   MAX-ACCESS    read-write
   STATUS    current
   DESCRIPTION
		"The index of Port-List entry used by this Policy entry."
   ::=  { atiAclPolicyEntry 6 } 
 
atiAclPolicyRowStatus OBJECT-TYPE
   SYNTAX    RowStatus
   MAX-ACCESS   read-create
   STATUS    current
   DESCRIPTION
      "The row status of the entry.
       1: write - enable the entry 
       	  read - entry is enabled   
       2: write - disable the entry
       	  read - entry is disabled
       3: read - entry is not ready
       5: write - create the entry
       6: write - delete the entry"
   ::= { atiAclPolicyEntry 7 }      
   
--======================= Destnation MAC Filter =======================--

atiDstMacFilterTable OBJECT-TYPE
   SYNTAX        SEQUENCE OF AtiDstMacFilterEntry
   MAX-ACCESS    not-accessible
   STATUS        current
   DESCRIPTION
      "DstMacFilter entry table."
   ::= { atiMacFilter 1 }

atiDstMacFilterEntry OBJECT-TYPE
   SYNTAX       AtiDstMacFilterEntry
   MAX-ACCESS   not-accessible
   STATUS       current
   DESCRIPTION
      "DstMacFilter is used to filter the packets by the specific Destination MAC."
   INDEX { atiDstMacFilterIndex }
   ::= { atiDstMacFilterTable 1 }

AtiDstMacFilterEntry ::=
   SEQUENCE {
		atiDstMacFilterIndex
         Integer32,  
		atiDstMacFilterAddress
         MacAddress,		 	  
		atiDstMacFilterRowStatus
         RowStatus
   }
   
atiDstMacFilterIndex OBJECT-TYPE
   SYNTAX        Integer32 (1..40)
   MAX-ACCESS    read-only
   STATUS    current
   DESCRIPTION
      "The index of the DstMacFilter entry."
   ::=  { atiDstMacFilterEntry 1 }

atiDstMacFilterAddress OBJECT-TYPE
   SYNTAX        MacAddress
   MAX-ACCESS    read-write
   STATUS    current
   DESCRIPTION
      "Destnation MAC address"
   ::=  { atiDstMacFilterEntry 2 }

atiDstMacFilterRowStatus OBJECT-TYPE
   SYNTAX    RowStatus
   MAX-ACCESS   read-create
   STATUS    current
   DESCRIPTION
      "The row status of the entry.
       1: write - enable the entry 
       	  read - entry is enabled   
       2: write - disable the entry
       	  read - entry is disabled
       3: read - entry is not ready
       5: write - create the entry
       6: write - delete the entry"
   ::= { atiDstMacFilterEntry 3 }       
   


                 
dhcpSnoopSystemStatus OBJECT-TYPE
   SYNTAX      INTEGER {
                 disabled (0),
                 enabled (1)
               }
   MAX-ACCESS  read-write
   STATUS      current
   DESCRIPTION
      "Enable/Disable DHCP Snooping."
   ::= { l2DhcpSnoop 1 }

dhcpSnoopOption82Insertion OBJECT-TYPE
   SYNTAX      INTEGER {
                 disabled (0),
                 enabled (1)
               }
   MAX-ACCESS  read-write
   STATUS      current
   DESCRIPTION
      "Determine if to insert DHCP option 82 into packets."
   ::= { l2DhcpSnoop 2 }

dhcpSnoopPassThroughOption82 OBJECT-TYPE
   SYNTAX      INTEGER {
                 disabled (0),
                 enabled (1)
               }
   MAX-ACCESS  read-write
   STATUS      current
   DESCRIPTION
      "Determine if to pass through DHCP packets with option 82."
   ::= { l2DhcpSnoop 3 }
                                       
dhcpSnoopVerifyMACAddress OBJECT-TYPE
   SYNTAX      INTEGER {
                 disabled (0),
                 enabled (1)
               }
   MAX-ACCESS  read-write
   STATUS      current
   DESCRIPTION
      "Determine if to verify MAC address for incoming DHCP packets."
   ::= { l2DhcpSnoop 4 }

dhcpSnoopBackupDatabase OBJECT-TYPE
   SYNTAX      INTEGER {
                 disabled (0),
                 enabled (1)
               }
   MAX-ACCESS  read-write
   STATUS      current
   DESCRIPTION
      "Determine if to backup database to flash memory."
   ::= { l2DhcpSnoop 5 }

dhcpSnoopBackupDatabaseInterval OBJECT-TYPE
   SYNTAX      Integer32 (600..86400)
   MAX-ACCESS  read-write
   STATUS      current
   DESCRIPTION
      "Determine the period to backup database."
   ::= { l2DhcpSnoop 6 }
                                         
dhcpSnoopVLANSettingTable OBJECT-TYPE
   SYNTAX      SEQUENCE OF TabDhcpSnoopVLANSettingEntry
   MAX-ACCESS  not-accessible
   STATUS      current
   DESCRIPTION
      "A table of DHCP snooping VLAN settings."
   ::= { l2DhcpSnoop 7 }

dhcpSnoopVLANSettingEntry OBJECT-TYPE
   SYNTAX      TabDhcpSnoopVLANSettingEntry
   MAX-ACCESS  not-accessible
   STATUS      current
   DESCRIPTION
      "The entry of DHCP snooping VLAN setting table."
   INDEX { dhcpSnoopVLANSettingVID }
   ::= { dhcpSnoopVLANSettingTable 1 }

TabDhcpSnoopVLANSettingEntry ::=
   SEQUENCE {
      dhcpSnoopVLANSettingVID
         Unsigned32,
      dhcpSnoopVLANSettingStatus
         INTEGER
   }

dhcpSnoopVLANSettingVID OBJECT-TYPE
   SYNTAX      Unsigned32 (1..4094)
   MAX-ACCESS  read-only
   STATUS      current
   DESCRIPTION
      "The VLAN ID."
   ::= { dhcpSnoopVLANSettingEntry 1 }

dhcpSnoopVLANSettingStatus OBJECT-TYPE
   SYNTAX      INTEGER {
                 disabled (0),
                 enabled (1)
               }
   MAX-ACCESS  read-write
   STATUS      current
   DESCRIPTION
      "The VLAN status."
   ::= { dhcpSnoopVLANSettingEntry 2 }

dhcpSnoopPortSettingTable OBJECT-TYPE
   SYNTAX      SEQUENCE OF TabDhcpSnoopPortSettingEntry
   MAX-ACCESS  not-accessible
   STATUS      current
   DESCRIPTION
      "A table of DHCP snooping port settings."
   ::= { l2DhcpSnoop 8 }

dhcpSnoopPortSettingEntry OBJECT-TYPE
   SYNTAX      TabDhcpSnoopPortSettingEntry
   MAX-ACCESS  not-accessible
   STATUS      current
   DESCRIPTION
      "The entry of DHCP snooping port setting table."
   INDEX { dhcpSnoopPortSettingIndex }
   ::= { dhcpSnoopPortSettingTable 1 }

TabDhcpSnoopPortSettingEntry ::=
   SEQUENCE {
      dhcpSnoopPortSettingIndex
         Integer32,
      dhcpSnoopPortSettingStatus
         INTEGER
   }

dhcpSnoopPortSettingIndex OBJECT-TYPE
   SYNTAX      Integer32 (1..65535)
   MAX-ACCESS  read-only
   STATUS      current
   DESCRIPTION
      "The port number."
   ::= { dhcpSnoopPortSettingEntry 1 }

dhcpSnoopPortSettingStatus OBJECT-TYPE
   SYNTAX      INTEGER {
                 untrusted (0),
                 trusted (1)
               }
   MAX-ACCESS  read-write
   STATUS      current
   DESCRIPTION
      "The port status."
   ::= { dhcpSnoopPortSettingEntry 2 }

dhcpSnoopBindindDatabaseTable OBJECT-TYPE
   SYNTAX      SEQUENCE OF TabDhcpSnoopBindindDatabaseEntry
   MAX-ACCESS  not-accessible
   STATUS      current
   DESCRIPTION
      "A table of DHCP snooping bindind database."
   ::= { l2DhcpSnoop 9 }

dhcpSnoopBindindDatabaseEntry OBJECT-TYPE
   SYNTAX      TabDhcpSnoopBindindDatabaseEntry
   MAX-ACCESS  not-accessible
   STATUS      current
   DESCRIPTION
      "The entry of DHCP snooping bindind database table."
   INDEX { dhcpSnoopBindindDBMacAddress }
   ::= { dhcpSnoopBindindDatabaseTable 1 }

TabDhcpSnoopBindindDatabaseEntry ::=
   SEQUENCE {
      dhcpSnoopBindindDBMacAddress
         MacAddress,
      dhcpSnoopBindindDBVLANID
         Unsigned32,
      dhcpSnoopBindindDBIPAddress
         IpAddress,
      dhcpSnoopBindindDBPortNumber
         Integer32,
      dhcpSnoopBindindDBType
         INTEGER,
      dhcpSnoopBindindDBLeaseTime
         Unsigned32,
      dhcpSnoopBindindDBRowStatus
         RowStatus
   }

dhcpSnoopBindindDBMacAddress OBJECT-TYPE
   SYNTAX      MacAddress
   MAX-ACCESS  read-only
   STATUS      current
   DESCRIPTION
      "The MAC address."
   ::= { dhcpSnoopBindindDatabaseEntry 1 }

dhcpSnoopBindindDBVLANID OBJECT-TYPE
   SYNTAX      Unsigned32 (1..4094)
   MAX-ACCESS  read-write
   STATUS      current
   DESCRIPTION
      "The VLAN ID."
   ::= { dhcpSnoopBindindDatabaseEntry 2 }

dhcpSnoopBindindDBIPAddress OBJECT-TYPE
   SYNTAX      IpAddress
   MAX-ACCESS  read-write
   STATUS      current
   DESCRIPTION
      "The IP address."
   ::= { dhcpSnoopBindindDatabaseEntry 3 }

dhcpSnoopBindindDBPortNumber OBJECT-TYPE
   SYNTAX      Integer32
   MAX-ACCESS  read-write
   STATUS      current
   DESCRIPTION
      "The port number."
   ::= { dhcpSnoopBindindDatabaseEntry 4 }

dhcpSnoopBindindDBType OBJECT-TYPE
   SYNTAX      INTEGER {
                 dynamic (0),
                 static (1)
               }
   MAX-ACCESS  read-write
   STATUS      current
   DESCRIPTION
      "The entry type."
   ::= { dhcpSnoopBindindDatabaseEntry 5 }

dhcpSnoopBindindDBLeaseTime OBJECT-TYPE
   SYNTAX      Unsigned32
   MAX-ACCESS  read-write
   STATUS      current
   DESCRIPTION
      "The DHCP lease time."
   ::= { dhcpSnoopBindindDatabaseEntry 6 }

dhcpSnoopBindindDBRowStatus OBJECT-TYPE
   SYNTAX      RowStatus
   MAX-ACCESS  read-create
   STATUS      current
   DESCRIPTION
      "The entry row status."
   ::= { dhcpSnoopBindindDatabaseEntry 7 }

END
