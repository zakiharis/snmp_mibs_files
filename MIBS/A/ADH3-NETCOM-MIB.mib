ADH3-NETCOM-MIB DEFINITIONS ::= BEGIN

IMPORTS
	MODULE-IDENTITY,
	OBJECT-IDENTITY,
	OBJECT-TYPE,
	Integer32,
	enterprises
		FROM SNMPv2-SMI
	DisplayString
		FROM SNMPv2-TC;

 

environmentalTechnology MODULE-IDENTITY
	LAST-UPDATED "200811230000Z"
	ORGANIZATION "Environmental Technology Inc."
	CONTACT-INFO
		"	Environmental Technology Inc.
			Product Support

		Postal: 1850 N. Sheridan St.
			South Bend, IN 46628
			USA

		   Tel: +1 574 233 1202

		E-mail: cgartland@networketi.com"
	DESCRIPTION
		"The Structure of Management Information for 
		  Environmental Technology Inc. SNMP devices"
	REVISION      "200811230000Z"
	DESCRIPTION
		"ADH-3 NETCOM: Ethernet-enabled air dehydrator.
		 This is for preliminary version (NCTEST4)"
	::= { enterprises 32185 }	--  assigned by IANA


netcom OBJECT-IDENTITY
	STATUS current
	DESCRIPTION
		" ADH-3 NETCOM"
	::= { environmentalTechnology 2 }

-- this is the MIB for the ADH3-NETCOM air dehydrator family
-- this is a preliminary version, for testing

statusInfo  OBJECT IDENTIFIER ::= { netcom 1 }
paramsInfo  OBJECT IDENTIFIER ::= { netcom 2 }


-- statusInfo: gives state of the ADH-3 NETCOM device
-- these change fairly frequently

allStatuses OBJECT-TYPE
        SYNTAX     DisplayString (SIZE (80))
        MAX-ACCESS read-only
        STATUS     current
        DESCRIPTION
                "Summary: same as objects 2-7, separated by semicolons"
        ::= { statusInfo 1 }
-- this is included as a convenience
-- if you are concerned that all the information you get is valid at exactly
-- the same time, use this instead of individual objects

pressurePSI OBJECT-TYPE
        SYNTAX     DisplayString (SIZE (10))
        MAX-ACCESS read-only
        STATUS     current
        DESCRIPTION
                "Pressure, in PSI"
        ::= { statusInfo 2 }

dutycycle OBJECT-TYPE
        SYNTAX     DisplayString (SIZE (10))
        MAX-ACCESS read-only
        STATUS     current
        DESCRIPTION
                "Current duty cycle, in percent; --- if none available"
        ::= { statusInfo 3 }

statusVars OBJECT-TYPE
        SYNTAX     DisplayString (SIZE (6))
        MAX-ACCESS read-only
        STATUS     current
        DESCRIPTION
                "Summary of the status of the unit.
		 Is always 6 characters
                 Character 1 is major state: N=normal, S=standby, L=leaky
                 Character 2 is environment: N=normal, C=cold, H=hot
                 Character 3 is canister 1 condition:
                      O=OK (ie dry), F=full (wet), U=unknown, D=dead
                 Character 4 is canister 1 usage:
                      I=idle, U=in use, R=regenerating
                 Character 5 is canister 2 condition, as in character 3
                 Character 5 is canister 2 usage, as in character 4"
        ::= { statusInfo 4 }

temperature OBJECT-TYPE
        SYNTAX     DisplayString (SIZE (10))
        MAX-ACCESS read-only
        STATUS     current
        DESCRIPTION
                "Current temperature, in degrees F"
        ::= { statusInfo 5 }

alarms OBJECT-TYPE
        SYNTAX     DisplayString (SIZE (30))
        MAX-ACCESS read-only
        STATUS     current
        DESCRIPTION
                "Current alarm conditions: is a list of them
                 Each character has a - for no alarm, or an A or W if there
                 is an alarm.  A means alarm (serious), W means a warning
                 (not so serious)."
        ::= { statusInfo 6 }

compressorHours OBJECT-TYPE
        SYNTAX     DisplayString (SIZE (30))
        MAX-ACCESS read-only
        STATUS     current
        DESCRIPTION
                "Number of hours that the compressor has been running;
		 resolution is tenths of an hour."
        ::= { statusInfo 7 }


majorState OBJECT-TYPE
        SYNTAX INTEGER {
          online (1),
          standby (2),
          leaky (3)
          }
        MAX-ACCESS read-write
        STATUS current
        DESCRIPTION
	  "Major state of the dehydrator.
           Online: currently pressurizing.
           Standby: not pressurizing.
           Leaky: shut down because of inability to pressurize."
        ::= { statusInfo 8 }

--  This is the only writable variable in this MIB
--  Setting it will change the state of the system, if allowed.
--  The only valid changes are between online and standby.


-- paramsInfo: operating parameters of the ADH3-NETCOM
-- these change infrequently if at all; mostly set at initialization
-- these will be settable via the configuration option of the web interface

lowerLimit OBJECT-TYPE
        SYNTAX     DisplayString (SIZE (10))
        MAX-ACCESS read-only
        STATUS     current
        DESCRIPTION
                "The pressure, in PSI, at which the unit starts to pump"
        ::= { paramsInfo 1 }

upperLimit OBJECT-TYPE
        SYNTAX     DisplayString (SIZE (10))
        MAX-ACCESS read-only
        STATUS     current
        DESCRIPTION
                "The pressure, in PSI, which the unit pressurizes to"
        ::= { paramsInfo 2 }

lowerAlarmLimit OBJECT-TYPE
        SYNTAX     DisplayString (SIZE (10))
        MAX-ACCESS read-only
        STATUS     current
        DESCRIPTION
                "The pressure, in PSI, below which the unit declares a
		 low pressure alarm"
        ::= { paramsInfo 3 }

upperAlarmLimit OBJECT-TYPE
        SYNTAX     DisplayString (SIZE (10))
        MAX-ACCESS read-only
        STATUS     current
        DESCRIPTION
                "The pressure, in PSI, above which the unit declares a
		 high pressure alarm"
        ::= { paramsInfo 4 }


END
