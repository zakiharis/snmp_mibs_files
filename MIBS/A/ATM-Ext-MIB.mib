-- automatically generated by mosy 7.1 #379 (dbc), do not edit!

ATM-Ext-MIB DEFINITIONS ::= BEGIN


IMPORTS
        DisplayString
                FROM RFC1213-MIB
        OBJECT-TYPE
                FROM RFC-1212
        Counter, enterprises
                FROM RFC1155-SMI
        ifIndex
                FROM RFC1213-MIB
        RowStatus
                FROM SNMPv2-TC;

bellcore OBJECT IDENTIFIER ::= { enterprises  148 }

requirements OBJECT IDENTIFIER ::= { bellcore  1 }

-- created from atmExtMIB (9312101200Z)

atmExtMIB OBJECT IDENTIFIER ::= { requirements  6 }

atmExtObjects OBJECT IDENTIFIER ::= { atmExtMIB  1 }

atmExtContactTable OBJECT-TYPE
    SYNTAX  SEQUENCE OF AtmExtContactEntry
    ACCESS  not-accessible
    STATUS  mandatory
    DESCRIPTION
           "A table with contact information for ATM
interfaces. "
    ::= { atmExtObjects  1 }

atmExtContactEntry OBJECT-TYPE
    SYNTAX  AtmExtContactEntry
    ACCESS  not-accessible
    STATUS  mandatory
    DESCRIPTION
           "An entry in the Contact table."
    INDEX   { ifIndex }
    ::= { atmExtContactTable  1 }

AtmExtContactEntry ::=
    SEQUENCE {
        atmExtContactIfInfo
            DisplayString,

        atmExtContactIfLocation
            DisplayString
    }

atmExtContactIfInfo OBJECT-TYPE
    SYNTAX  DisplayString
    ACCESS  read-only
    STATUS  mandatory
    DESCRIPTION
           "The service provider contact information for
                                  this interface."
    ::= { atmExtContactEntry  2 }

atmExtContactIfLocation OBJECT-TYPE
    SYNTAX  DisplayString
    ACCESS  read-only
    STATUS  mandatory
    DESCRIPTION
           "The serving location of this interface."
    ::= { atmExtContactEntry  3 }

atmExtVclTable OBJECT-TYPE
    SYNTAX  SEQUENCE OF AtmExtVclEntry
    ACCESS  not-accessible
    STATUS  mandatory
    DESCRIPTION
           "A table with performance information for VCLs. "
    ::= { atmExtObjects  2 }

atmExtVclEntry OBJECT-TYPE
    SYNTAX  AtmExtVclEntry
    ACCESS  not-accessible
    STATUS  mandatory
    DESCRIPTION
           "An entry in the VCL table."
    INDEX   { ifIndex,  atmExtVclVpi,  atmExtVclVci }
    ::= { atmExtVclTable  1 }

AtmExtVclEntry ::=
    SEQUENCE {
        atmExtVclVpi
            INTEGER (-2147483648..2147483647),

        atmExtVclVci
            INTEGER (-2147483648..2147483647),

        atmExtVclUpcViolations
            Counter,

        atmExtVclRowStatus
            RowStatus
    }

atmExtVclVpi OBJECT-TYPE
    SYNTAX  INTEGER (-2147483648..2147483647)
    ACCESS  not-accessible
    STATUS  mandatory
    DESCRIPTION
           "The VCL's VPI value."
    ::= { atmExtVclEntry  1 }

atmExtVclVci OBJECT-TYPE
    SYNTAX  INTEGER (-2147483648..2147483647)
    ACCESS  not-accessible
    STATUS  mandatory
    DESCRIPTION
           "The VCL's VCI value."
    ::= { atmExtVclEntry  2 }

atmExtVclUpcViolations OBJECT-TYPE
    SYNTAX  Counter
    ACCESS  read-only
    STATUS  mandatory
    DESCRIPTION
           "The number of cells discarded due
                                to UPC violations on this link."
    ::= { atmExtVclEntry  3 }

atmExtVclRowStatus OBJECT-TYPE
    SYNTAX  RowStatus
    ACCESS  read-write
    STATUS  mandatory
    DESCRIPTION
           "The status of this entry."
    ::= { atmExtVclEntry  4 }

atmExtVplTable OBJECT-TYPE
    SYNTAX  SEQUENCE OF AtmExtVplEntry
    ACCESS  not-accessible
    STATUS  mandatory
    DESCRIPTION
           "A table with performance information for
VPLs. "
    ::= { atmExtObjects  3 }

atmExtVplEntry OBJECT-TYPE
    SYNTAX  AtmExtVplEntry
    ACCESS  not-accessible
    STATUS  mandatory
    DESCRIPTION
           "An entry in the VPL table."
    INDEX   { ifIndex,  atmExtVplVpi }
    ::= { atmExtVplTable  1 }

AtmExtVplEntry ::=
    SEQUENCE {
        atmExtVplVpi
            INTEGER (-2147483648..2147483647),

        atmExtVplUpcViolations
            Counter,

        atmExtVplRowStatus
            RowStatus
    }

atmExtVplVpi OBJECT-TYPE
    SYNTAX  INTEGER (-2147483648..2147483647)
    ACCESS  not-accessible
    STATUS  mandatory
    DESCRIPTION
           "The VPL's VPI value."
    ::= { atmExtVplEntry  1 }

atmExtVplUpcViolations OBJECT-TYPE
    SYNTAX  Counter
    ACCESS  read-only
    STATUS  mandatory
    DESCRIPTION
           "The number of cells discarded due
                                to UPC violations on this link."
    ::= { atmExtVplEntry  2 }

atmExtVplRowStatus OBJECT-TYPE
    SYNTAX  RowStatus
    ACCESS  read-write
    STATUS  mandatory
    DESCRIPTION
           "The status of this entry."
    ::= { atmExtVplEntry  3 }

atmExtConformance OBJECT IDENTIFIER ::= { atmExtMIB  2 }

atmExtGroups OBJECT IDENTIFIER ::= { atmExtConformance  1 }

atmExtCompliances OBJECT IDENTIFIER ::= { atmExtConformance  2 }

atmExtCompliance OBJECT IDENTIFIER ::= { atmExtCompliances  1 }

atmExtContactGroup OBJECT IDENTIFIER ::= { atmExtGroups  1 }

atmExtVCCGroup OBJECT IDENTIFIER ::= { atmExtGroups  2 }

atmExtVPCGroup OBJECT IDENTIFIER ::= { atmExtGroups  3 }

END



--_/_/_/_/_/_/_/_/_/_/_/_/_/_/_/_/_/_/_/_/_/_/_/_/_/_/_/_/_/_/_/_/_/_/_/_/_/
--_/                                                                      _/
--_/  Kaj Tesink                                                          _/
--_/  Bellcore                                                            _/
--_/  - Broadband Data Services & Consulting  vmail (908) 758-5254        _/
--_/    331 Newman Springs Rd.                email kaj@cc.bellcore.com   _/
--_/    Red Bank, NJ 07701                  faxmail (908) 758-4196        _/
--_/                                                                      _/
--_/_/_/_/_/_/_/_/_/_/_/_/_/_/_/_/_/_/_/_/_/_/_/_/_/_/_/_/_/_/_/_/_/_/_/_/_/
