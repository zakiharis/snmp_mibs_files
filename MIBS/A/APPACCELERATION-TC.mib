-- *******************************************************************
-- APPACCELERATION-TC.txt: Citrix Systems Application Acceleration
--                         MIB Textual Conventions
--
--
-- Copyright (c) 2004-2009 by Citrix Systems, Inc.
-- All rights reserved.
--
-- *******************************************************************
--

APPACCELERATION-TC DEFINITIONS ::= BEGIN

IMPORTS
    MODULE-IDENTITY,
    Integer32
        FROM SNMPv2-SMI
    TEXTUAL-CONVENTION,
    DisplayString
        FROM SNMPv2-TC
    appAccelerationModules
        FROM APPACCELERATION-SMI;


appAccelerationTextualConventions MODULE-IDENTITY
    LAST-UPDATED    "200905110000Z"
    ORGANIZATION    "www.citrix.com"
    CONTACT-INFO
            "       Citrix Systems, Inc.
                                                                                
            Postal: 851 West Cypress Creek Road
                    Fort Lauderdale, Florida  33309
                    United States"

    DESCRIPTION
        "This module defines the textual conventions used throughout
        Application Acceleration enterprise mibs."
    ::= { appAccelerationModules 1 }

--
-- General TCs for all Sub-systems
--

AppAccelerationYesNo   ::= TEXTUAL-CONVENTION
    STATUS       current
    DESCRIPTION
        "Textual convention for yes/no enum.
        "
    SYNTAX INTEGER
    { 
        no(0),
        yes(1)
    }

AppAccelerationDescription ::= TEXTUAL-CONVENTION
    STATUS       current
    DESCRIPTION
        "Represents a string description used for any MIB object.
         Currently used for alarms sent out as trap notifications.
         "
    SYNTAX DisplayString (SIZE(0..255))


--
-- TCs for Alarm Sub-system
--
AppAccelerationAlarmSeverity ::= TEXTUAL-CONVENTION
    STATUS       current
    DESCRIPTION
        "Represents the perceived alarm condition associated with a
        service affecting condition and/or event.

            cleared(1) -
                Indicates a previous alarm condition has been
                cleared.  It is not required (unless specifically
                stated elsewhere on a case by case basis) that an
                alarm condition that has been cleared will produce
                a notification or other event containing an
                alarm severity with this value.

            indeterminate(2) -
                Indicates that the severity level cannot be
                determined. 

            critical(3) -
                Indicates that a service or safety affecting
                condition has occurred and an immediate
                corrective action is required.

            major(4) -
                Indicates that a service affecting condition has
                occurred and an urgent corrective action is
                required.

            minor(5) -
                Indicates the existence of a non-service affecting
                condition and that corrective action should be
                taken in order to prevent a more serious (for
                example, service or safety affecting) condition.

            warning(6) -
                Indicates the detection of a potential or impending
                service or safety affecting condition, before any
                significant effects have been felt.

            info(7) -
                Indicates an alarm condition that does not
                meet any other severity definition.  This can
                include important, but non-urgent, notices or
                informational events.
         "
    REFERENCE
        "ITU-X.733"
    SYNTAX INTEGER
    {
        cleared(1),
        indeterminate(2),
        critical(3),
        major(4),
        minor(5),
        warning(6),
        info(7)
    }

AppAccelerationSeqNum ::= TEXTUAL-CONVENTION
    STATUS       current
    DESCRIPTION
        "Represents the unique sequence number associated with each
         generated trap.
         "
    SYNTAX INTEGER (1..2147483647)


END
