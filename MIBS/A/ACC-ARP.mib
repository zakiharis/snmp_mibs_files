ACC-ARP DEFINITIONS ::= BEGIN

    IMPORTS
	OBJECT-TYPE, IpAddress, Counter FROM RFC1155-SMI
	 TRAP-TYPE FROM RFC-1215
    	 accTrapLogSeqNum FROM ACC-SYSTEM
	accBRG, DisplayString, RowStatus, IfIndex, SmdsAddress
            FROM ACC-MIB
				ipAdEntAddr FROM RFC1213-MIB
--        frCircuitDlci, DLCI FROM RFC1315-MIB;
        frCircuitDlci, DLCI FROM ACC-FAKE;

-- ARP Group
      accArp     OBJECT IDENTIFIER ::=   { accBRG 11 }
	accArpTimeout	OBJECT-TYPE   
			SYNTAX	INTEGER (1..1440)
			ACCESS	read-write
			STATUS	mandatory
			DESCRIPTION
                 " Aging timer value (in minutes) for ARP table entries."
			::= { accArp 1 }
	accArpTable	OBJECT-TYPE
			SYNTAX SEQUENCE OF AccArpEntry
			ACCESS not-accessible
			STATUS mandatory
			DESCRIPTION
                   " The ARP (Address Resolution Protocol) table.
                     This is an alternate view of the atTable."
			::= { accArp 2 }
	  accArpEntry	OBJECT-TYPE
			SYNTAX AccArpEntry
			ACCESS not-accessible
			STATUS mandatory
			DESCRIPTION
                            " A correspondence between logical (IP) 
                              and physical (MAC) addresses."
                        INDEX { accArpNetAddress }
			::= { accArpTable 1 }
		AccArpEntry  ::= SEQUENCE {
			accArpPhysAddress	OCTET STRING,
			accArpNetAddress	IpAddress,
			accArpEntStatus		INTEGER
			}
	    accArpPhysAddress	OBJECT-TYPE   
			SYNTAX	OCTET STRING -- (SIZE(6))
			ACCESS	read-only
			STATUS	mandatory
			DESCRIPTION
                	 " The Ethernet address of the ARP table entry."
			::= { accArpEntry 1  }
	    accArpNetAddress	OBJECT-TYPE   
			SYNTAX	IpAddress
			ACCESS	read-only
			STATUS	mandatory
			DESCRIPTION
                	 " IP address of this entry.
			   Set this object to NULL to delete an entry."
			::= { accArpEntry 2 }
	    accArpEntStatus	OBJECT-TYPE   
			SYNTAX	INTEGER {
				pending(1),
				dynamic(2),
                                static(4),
				permanent(8),
                                apepending(16),
                                stepending(32),
                                confirmpending(64),
                                confirmsrpending(128)
				}
			ACCESS	read-only
			STATUS	mandatory
			DESCRIPTION
                	 " Status of the ARP table entry."
                        DEFVAL { static }
			::= { accArpEntry 3 }
	accArpType	OBJECT-TYPE   
			SYNTAX	INTEGER {
				normal(0),
				proxy(2)
				}
			ACCESS	read-write
			STATUS	mandatory
			DESCRIPTION
               		 " State of proxy ARP capability.
			"
			::= { accArp 3 }
	accArpReqRcvds	OBJECT-TYPE   
			SYNTAX	Counter
			ACCESS	read-only
			STATUS	mandatory
			DESCRIPTION
             		 "  Number of ARP Requests received."
			::= { accArp 4 }
	accArpReqSents	OBJECT-TYPE   
			SYNTAX	Counter
			ACCESS	read-only
			STATUS	mandatory
			DESCRIPTION
             		 "  Number of ARP Requests sent."
			::= { accArp 5 }
	accArpRspRcvds	OBJECT-TYPE   
			SYNTAX	Counter
			ACCESS	read-only
			STATUS	mandatory
			DESCRIPTION
              		 " Number of ARP Responses received."
			::= { accArp 6 }
	accArpRspSents	OBJECT-TYPE   
			SYNTAX	Counter
			ACCESS	read-only
			STATUS	mandatory
			DESCRIPTION
              		 " Number of ARP Responses sent."
			::= { accArp 7 }
	accArpInErrs	OBJECT-TYPE   
			SYNTAX	Counter
			ACCESS	read-only
			STATUS	mandatory
			DESCRIPTION
              		 " Number of ARP input errors encountered."
			::= { accArp 8 }
	accArpOutErrs	OBJECT-TYPE   
			SYNTAX	Counter
			ACCESS	read-only
			STATUS	mandatory
			DESCRIPTION
             		 "  Number of ARP output errors encountered."
			::= { accArp 9 }
	accArpUnknownProtos	OBJECT-TYPE   
			SYNTAX	Counter
			ACCESS	read-only
			STATUS	mandatory
			DESCRIPTION
              		 " Number of address resolution requests for which
              		   this ARP implementation did not recognize the protocol."
			::= { accArp 10 }
	accArpPromiscuous	OBJECT-TYPE   
			SYNTAX	INTEGER {
				promiscuous(1),
				nonpromiscuous(2)
				}
			ACCESS	read-write
			STATUS	mandatory
			DESCRIPTION
               		 " When operating promiscuously, the device will
                           learn ARP information from all ARP packets
                           received.  When non-promiscuous, the device
                           will learn information only from ARP packets
                           addressed to the IP address of the device.
			"
			::= { accArp 11 }
	accArpRefresh	OBJECT-TYPE   
			SYNTAX	INTEGER {
				refresh(1),
				norefresh(2)
				}
			ACCESS	read-write
			STATUS	mandatory
			DESCRIPTION
               		 " When operating in refresh mode, when it is
                           time for an entry to age out, the device
                           will refresh the entry by ARPing for it
                           again.  Devices will thus stay in the ARP
                           table until disconnected, even if they are
                           not communicating via the router.  In norefresh 
                           mode, the entry will simply be aged out, and
                           refreshed only if traffic warrants. 
			"
			::= { accArp 12 }
	accArpAddressCheck OBJECT IDENTIFIER ::= { accArp 13 }
-- Dummy object for oArpAddressCheck object in ng_mib.c
        accArpTraps   OBJECT IDENTIFIER ::= { accArp 14 }
        accArpTrapMsg   OBJECT-TYPE
                        SYNTAX  DisplayString 
                        ACCESS  read-write
                        STATUS  mandatory
                        DESCRIPTION
                         " Trap Message object for level-1 traps of ARP module "
                        ::= { accArpTraps 1 }

        accArpDuplicateAddrTrap TRAP-TYPE
        ENTERPRISE   accArpTraps 
        VARIABLES  { accArpTrapMsg,
		     ipAdEntAddr,
		     frCircuitDlci ,
accTrapLogSeqNum}
        DESCRIPTION
                "Indicates that Duplicate addresss specified as value of second
		 varbind received on the DLCI number specified as the value of
		 third varbind.
SEVERITY-DEFAULT: Warning 
EVENTTYPE-DEFAULT: 10 
ADDITIONAL-TEXT-VARIABLES: { accTrapLogSeqNum,accArpTrapMsg }
PCAUSE-DEFAULT: 5 " 
 
        ::= 1
        accArpInvDevTypeTrap TRAP-TYPE
        ENTERPRISE   accArpTraps 
        VARIABLES  { accArpTrapMsg ,
                      accTrapLogSeqNum}
        DESCRIPTION
		" Invalid device type was received
SEVERITY-DEFAULT: Warning 
EVENTTYPE-DEFAULT: 10 
ADDITIONAL-TEXT-VARIABLES: { accTrapLogSeqNum,accArpTrapMsg }
PCAUSE-DEFAULT: 5 " 
 
        ::= 2
        accArpDuplIpOnMacTrap TRAP-TYPE
        ENTERPRISE   accArpTraps 
        VARIABLES  { accArpTrapMsg,
		     accArpNetAddress ,
        accTrapLogSeqNum}
        DESCRIPTION
                " Duplicate IP address for a mac address
SEVERITY-DEFAULT: Warning 
EVENTTYPE-DEFAULT: 10 
ADDITIONAL-TEXT-VARIABLES: { accTrapLogSeqNum,accArpTrapMsg }
PCAUSE-DEFAULT: 5 " 
 
        ::= 3
END
