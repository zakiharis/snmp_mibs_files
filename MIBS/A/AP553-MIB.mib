-- ****************************************************************************
--                             FRProbe.mib
-- ****************************************************************************

-- Copyright 1998 General DataComm Ind., Inc. All Rights Reserved.
--
-- Reproduction of this document is authorized on condition that the
-- foregoing copyright notice is included. This General DataComm, GDC,
-- SNMP Management Information Base Specification embodies GDCs'
-- confidential and proprietary intellectual property. GDC retains all
-- title and ownership in the Specification, including any revisions.
--
-- It is GDCs intent to encourage the widespread use of this Specification
-- in connection with the management of GDC's products. GDC grants vendors,
-- end-users, and other interested parties a non-exclusive license to use
-- this Specification in connection with the management of GDC's products.
--
-- This Specification is supplied "AS IS," and GDC makes no warranty,
-- either expressed or implied, as to the use operation, condition, or
-- performance of the Specification.

-- ****************************************************************************


--
-- ****************************************************************************
--                        Revision History
-- ****************************************************************************

--  Version   Date        Name/Comments

--  1.00A     09-Sept-98  A. Limoncelli
--                        Initial Revision 

--  1.00B     18-Sept-98  A. Limoncelli
--                        removed exceptions and endException traps
--                        added trapStatus object                        
--

--  1.00C     22-Sept-98  A. Limoncelli
--                        added exceptions traps and modified MIB object's 
--                        naming conventions

--  1.00D     22-Oct-98   A. Limoncelli
--                        add a realtime performance table, changed order of
--                        trap thres. objects and traps for consistency

--  1.00E     27-Oct-98   A. Limoncelli
--                        changed TRAP-TYPEs - made one enterprise trap
--                        for all traps 

--  1.00F     28-Oct-98   A. Limoncelli
--                        changed OBJECT-TYPEs - currentStatusBitsMap and
--                        alarmCurrentStatusBitsMap to read-only

--  1.00G     28-Oct-98   A. Limoncelli
--                        changed arguments for the trap, added two more 
--                        objects in trap config. - sysNameObj, sysUpTimeObj

--  1.00H      8-Dec-98   A. Limoncelli
--                        deleted two objects in trap config. - sysNameObj,
--                        sysUpTimeObj,  delete pvcTrapCtlBitsMap object
--                        added two objects in trap config. - 
--                        trapSeverityTableIndex and trapSeverity
--                        added probe version object
--                        added imports - sysUpTime, sysName

--  1.00I      3-Jan-99   A. Limoncelli
--                        changed trapSeverityTableIndex and trapSeverity 
--                        object from bit map to individual objects
--                        changed front end by importing linkProbe

--  1.00J      7-Jan-99   R. Zawislak
--                        changed object names in probeStat and probePerform 
--                        groups


--  1.00K      7-Jan-99   A. Limoncelli
--                        documented unitType object to proFunConfig group

--
-- ****************************************************************************
--                        Revision History   (con't)
-- ****************************************************************************

--  Version   Date        Name/Comments

--  1.00L      2-Feb-99   S. Veillette
--                        1) changes to Channel Stats for Current Intvl Group
--                        2) in probeStat 1 group: replaced chCurrLmiTimeout
--                           with chCurrDTELmiTimeout & chCurrDCELmiTimeout
--                        3) in probeStat 2 group: replaced chIntvLmiTimeout
--                           with chIntvDTELmiTimeout & chIntvDCELmiTimeout

--  1.00M      4-Feb-99   S. Veillette
--                        1) changes to Channel Stats for Current Intvl Group

--  1.00N      2-Feb-99   S. Veillette
--                        1) Add WEBFLAG/WEBEND tokens to description text of
--                           enumerated objects for web page support.
--                        2) Reorder & improve naming convention of 
--                           TrapConfiguration group objects.

--  1.00P      5-Feb-99   A. Liomncelli
--                        1) change ipDLCI oject to read-write


--  1.00Q     23-Feb-99   S. Veillette
--                        1) correct WEBFLAG tokens for ipEncapp object.

--  1.00R     26-Mar-99   S. Veillette
--                        1) correct WEBFLAG tokens for pvcOperation object.

--  1.00S     12-Apr-99   S. Veillette
--                        1) correct WEBFLAG tokens for lmiOperation object.
--                        2) add lmiConfig object:  max_Info_Length
--                        3) add chanConfig object: chanAggregateRate

--  1.00T     13-Apr-99   A. Limoncelli
--                        1) changed probeTokenSize from read-only to r/w

--  1.00U     28-May-99   S. Veillette
--                        1) change object size - pvcIdentifier: 255 => 32

--  1.00V     15-June-99  R. Zawislak
--			  Change the upper limit of realTimeChanLoadToDCEThresh,
--			  avgChanLoadToDCEThresh, realTimeChanLoadToDTEThresh,
--			  and avgChanLoadToDTEThresh from 2048% to 100%

--  1.00W     24-AUG-99   K. Nell
--                        Removed LMI DLCI 1023 because we don't support
--			  consortium LMI at this time
--               
--  1.00X     15-Sept-99   A. Limoncelli
--                        1) removed  probeTokenSize and pollPeriod objects
--               
--  1.00Y     15-Sept-99   A. Limoncelli
--                        1) added  probeTokenSize and pollPeriod objects

--
-- ****************************************************************************
--                          mib definitions begin
-- ****************************************************************************


AP553-MIB DEFINITIONS ::= BEGIN

IMPORTS
Counter			FROM RFC1155-SMI
DisplayString		FROM RFC1213-MIB
OBJECT-TYPE	     	FROM RFC-1212
linkProbe		FROM INNOVX-CORE-MIB;	


probeConfig		OBJECT IDENTIFIER ::={ linkProbe 1 }
probeStat		OBJECT IDENTIFIER ::={ linkProbe 2 }
probePerform   		OBJECT IDENTIFIER ::={ linkProbe 3 }
trapStatus   		OBJECT IDENTIFIER ::={ linkProbe 4 }


chanConfig 		OBJECT IDENTIFIER ::={ probeConfig 1 }
lmiConfig 		OBJECT IDENTIFIER ::={ probeConfig 2 }
proFunConfig 		OBJECT IDENTIFIER ::={ probeConfig 3 }
trapConfig 		OBJECT IDENTIFIER ::={ probeConfig 4 }
pvcConfig  		OBJECT IDENTIFIER ::={ probeConfig 5 }
probeVersion  		OBJECT IDENTIFIER ::={ probeConfig 6 }


alarmStatus 		OBJECT IDENTIFIER ::={ trapStatus 1 }



--
-- ****************************************************************************
--                          PROBE VERSION GROUP
-- ****************************************************************************


frProbeMIBversion OBJECT-TYPE
    SYNTAX  DisplayString (SIZE (0..5))
    ACCESS  read-write
    STATUS  mandatory
    DESCRIPTION
    "Identifies the version of the MIB as 'X.YZT' where:
    
        X: Major Revision (1-9)
        Y: Minor Revision (0-9)
        Z: Typographical Revision (0-9)
        T: Test Revision (A-Z) "

    ::= {probeVersion 1}





--
-- ****************************************************************************
--                          CHANNEL CONFIGURATION GROUP
-- ****************************************************************************


lmiOperation OBJECT-TYPE
    SYNTAX INTEGER
    {
        off  (1),
        on   (2)
    }
    ACCESS read-write
    STATUS mandatory
    DESCRIPTION
    " LMI operation, on -- enabled,  off -- disabled 
    WEBFLAG
    Off
    On
    WEBEND
    "

    ::= { chanConfig 1 }


lmiDLCI OBJECT-TYPE
    SYNTAX INTEGER 
    {
	dlci-0     (1)
    }
    ACCESS read-write
    STATUS mandatory
    DESCRIPTION
    "The DLCI # used for LMI polls, the default value is dlci-0
    WEBFLAG
    DLCI-0
    WEBEND
    "

    ::= { chanConfig 2 }


ipDLCI OBJECT-TYPE
    SYNTAX INTEGER (16..991)
    ACCESS read-write
    STATUS mandatory
    DESCRIPTION
    "Valid Inband IP DLCI ranges from 16 to 991"

    ::= { chanConfig 3 }


ipEncapp OBJECT-TYPE
    SYNTAX INTEGER
    {
	rawIP    (1),
	ietf-IP  (2),
	snap-IP  (3)
    }
    ACCESS read-write
    STATUS mandatory
    DESCRIPTION
    " Defines the IP DLCI Encapsulation method
    WEBFLAG
    RAW
    IETF
    SNAP
    WEBEND
    "

    ::= { chanConfig 4 }

          
chanAggregateRate OBJECT-TYPE
    SYNTAX INTEGER (56000..2048000)
    ACCESS read-only
    STATUS mandatory
    DESCRIPTION
    "Displays the current aggregate channel rate."
		    
    ::= { chanConfig 5 }


--
-- ****************************************************************************
--                          LMI Configuration Group
-- ****************************************************************************


lmiType OBJECT-TYPE
    SYNTAX INTEGER
    {
         annexA  (1),
         annexD  (2)
    }
    ACCESS read-write
    STATUS mandatory
    DESCRIPTION
    "Defines the network's LMI type.
    WEBFLAG
    Annex-A
    Annex-D
    WEBEND
    "

    ::= { lmiConfig 1 }


lmiN391 OBJECT-TYPE
    SYNTAX INTEGER ( 1..255 )
    ACCESS read-write
    STATUS mandatory
    DESCRIPTION
    " N391 Full Enquiry Interval Counter ranges from 1 to 255,
    the default value is 6."
   
    ::= { lmiConfig 2 }


lmiNet392 OBJECT-TYPE
    SYNTAX INTEGER ( 1..10 )
    ACCESS read-write
    STATUS mandatory
    DESCRIPTION
    " N392 Network Interface Down Threshold Counter 
    ranges from 1 to 10, the default value is 3."
  
    ::= { lmiConfig 3 }


lmiUser392 OBJECT-TYPE
    SYNTAX INTEGER ( 1..10 )
    ACCESS read-write
    STATUS mandatory
    DESCRIPTION
    " N392 User Interface Down Threshold Counter 
    ranges from 1 to 10, the default value is 3."
  
    ::= { lmiConfig 4 }


lmiNet393 OBJECT-TYPE
    SYNTAX INTEGER ( 1..10 )
    ACCESS read-write
    STATUS mandatory
    DESCRIPTION
    " N393 Network Interface Down Window  Counter ranges
    from 1 to 10, the default value is 4."

    ::= { lmiConfig 5 }


lmiUser393 OBJECT-TYPE
    SYNTAX INTEGER ( 1..10 )
    ACCESS read-write
    STATUS mandatory
    DESCRIPTION
    " N393 User Interface Down Window Counter ranges from
    1 to 10, the default value is 4."
  
    ::= { lmiConfig 6 }


t391Timer OBJECT-TYPE
    SYNTAX INTEGER ( 5..30 )
    ACCESS read-write
    STATUS mandatory
    DESCRIPTION
    " T391 Status Poll Interval Timer ranges from 5 to 30,
    the default value is 10, which would always less than to T392 Timer."

    ::= { lmiConfig 7 }


t392Timer OBJECT-TYPE
    SYNTAX INTEGER ( 5..30 )
    ACCESS read-write
    STATUS mandatory
    DESCRIPTION
    " T392 Polling Verification Interval Timer ranges from 5 to 30,
    the default value is 15 should always be greater than T391 Timer."

    ::= { lmiConfig 8 }

maxInfoLength OBJECT-TYPE
    SYNTAX INTEGER ( 400..4000 )
    ACCESS read-write
    STATUS mandatory
    DESCRIPTION
    "Maximum supported frame information length ranges from
    400 to 4000, the default value is 4000."
     
    ::= { lmiConfig 9 }




--
-- ****************************************************************************
--                          Probe Function Configuration Group
-- ****************************************************************************


unitType OBJECT-TYPE
    SYNTAX INTEGER
    {
        master  (1),                    
        remote  (2)                 
    }
    ACCESS read-write
    STATUS mandatory
    DESCRIPTION
    "Defines the ap553 as a master or remote unit in the network.  
    This option is used to define the probe(s) installed on the local 
    management network. As a master, PVC hiding is disabled, which allows
    discovery of remotely managed probes.
    WEBFLAG
    Master
    Remote
    WEBEND
    "

    ::= { proFunConfig 1}


probeMode OBJECT-TYPE
    SYNTAX INTEGER
    {
	generator(1),
        responder(2),
	both(3),
	disabled(4)
    }
    ACCESS read-write
    STATUS mandatory
    DESCRIPTION
    " Defines the probe mode as a generator, responder, or both or disabled.
    WEBFLAG
    Generator
    Responder
    Generator & Responder
    Disabled
    WEBEND
    "
    
	::={ proFunConfig 2 }



pollPeriod OBJECT-TYPE
    SYNTAX INTEGER ( 1..60 )
    ACCESS read-only
    STATUS mandatory
    DESCRIPTION
    "Defines the frequency of sending the polling frame by the link probe,
    from 1 to 60 seconds. pollPeriod applies to all PVCs that are probed."
	::={ proFunConfig 3 }



globalTC OBJECT-TYPE
    SYNTAX INTEGER (1..100)
    ACCESS read-only
    STATUS mandatory
    DESCRIPTION
    "This parameter defines the committed rate measurement
    time interval (in seconds) which can be calculated as
    Bc/CIR, currently we only allow this value to be 1 sec."

    ::={ proFunConfig 4 }


pvcCount OBJECT-TYPE
    SYNTAX INTEGER ( 1..127 )
    ACCESS read-only
    STATUS mandatory
    DESCRIPTION
    "PVC count defines the total number of PVCs which are being
    probed. The value is between 1 to 127. "
    
    ::={ proFunConfig 5 }


probeTokenSize OBJECT-TYPE
    SYNTAX INTEGER ( 19..4096 )
    ACCESS read-only
    STATUS mandatory
    DESCRIPTION
    "Defines the probe token size."

    ::={ proFunConfig 6 }



pvcAdd OBJECT-TYPE
    SYNTAX INTEGER ( 16..991 )
    ACCESS write-only
    STATUS mandatory
    DESCRIPTION
    "This object allows for manual addition of a PVC to the existing PVC
    table, the added PVC must not exist before it is added."

    ::={ proFunConfig 7 }


pvcDelete OBJECT-TYPE
    SYNTAX INTEGER ( 16..991 )
    ACCESS write-only
    STATUS mandatory
    DESCRIPTION
    "This object allows for manual deletion of a PVC from the existing 
    PVC table, the deleted PVC must exist before it was deleted."
  
    ::={ proFunConfig 8 }


pvcDiscovery OBJECT-TYPE
    SYNTAX INTEGER
    {
        initiate    (1),  -- write only
	inProgress  (2),  -- read only
	complete    (3)   -- read only
    }
    ACCESS read-write
    STATUS mandatory
    DESCRIPTION
    "This object automatically adds PVCs as seen by the LMI protocol.
    It controls the probe ability to read all pvcs as reported by the LMI
    process and update the probe pvc data table as controlled by the 
    pvcCirEirTable. Values of 2 and 3 cannot be set and have no affect."

    ::={ proFunConfig 9 }


--
-- ****************************************************************************
--                     Trap Threshold Configuration Group
-- ****************************************************************************


pvcOperStateChangeTrapSeverity OBJECT-TYPE
    SYNTAX INTEGER
    {
        inhibit   (1),
        critical  (2),
        major     (3),
        minor     (4),
        warning   (5),
        info      (6)
    }
    ACCESS read-write
    STATUS mandatory
    DESCRIPTION
    "Controls the reporting of and defines the severity of the pvc
    state change trap which may be sent when a PVC's operational status
    is changed via the pvcOperation object.
    WEBFLAG
    Inhibit
    Critical
    Major
    Minor
    Warning
    Info
    WEBEND
    "

    ::={ trapConfig 1 }


realTimeTrapSeverity OBJECT-TYPE
    SYNTAX INTEGER
    {
        inhibit   (1),
        critical  (2),
        major     (3),
        minor     (4),
        warning   (5),
        info      (6)
    }
    ACCESS read-write
    STATUS mandatory
    DESCRIPTION
    "Controls the reporting of and defines the severity of ALL real time
    alarm conditions: Channel Load To DTE, Channel Load TO DCE,
    PVC Load To DCE, PVC Load To DTE, and PVC Round Trip Delay.
    WEBFLAG
    Inhibit
    Critical
    Major
    Minor
    Warning
    Info
    WEBEND
    "

    ::={ trapConfig 2 }


--
--***************************************************************************
--                            CHANNEL LOAD TO DCE

realTimeChanLoadToDCEThresh OBJECT-TYPE
    SYNTAX INTEGER (0..100)
    ACCESS read-write
    STATUS mandatory
    DESCRIPTION
    "Defines the maximum allowed real-time channel load calculated every
    second, expressed in percentage. If the actual load is more than this
    threshold, a realTimeTrapSeverity exception trap may be sent as specified
    by the realTimeTrapSeverity object value."

    ::={ trapConfig 3 }


realTimeChanLoadToDCEThreshVar OBJECT-TYPE
    SYNTAX INTEGER (0..100)
    ACCESS read-write
    STATUS mandatory
    DESCRIPTION
    "Defines the variation range for real-time channel load, expressed in 
    percentage.. If within the current TC interval, the variation of the
    actual utilization is more than that range compared with the previous 
    trap value, another realTimeTrapSeverity exception trap may be sent as
    specified by the realTimeTrapSeverity object value."

    ::={ trapConfig 4}


avgChanLoadToDCETrapSeverity OBJECT-TYPE
    SYNTAX INTEGER
    {
        inhibit   (1),
        critical  (2),
        major     (3),
        minor     (4),
        warning   (5),
        info      (6)
    }
    ACCESS read-write
    STATUS mandatory
    DESCRIPTION
    "Controls the reporting of and defines severity of the 15 minute average
    load exception trap.
    WEBFLAG
    Inhibit
    Critical
    Major
    Minor
    Warning
    Info
    WEBEND
    "

    ::={ trapConfig 5 }


avgChanLoadToDCEThresh OBJECT-TYPE
    SYNTAX INTEGER (0..100)
    ACCESS read-write
    STATUS mandatory
    DESCRIPTION
    "Defines the maximum allowed frame relay channel utilization in a 15
    minute period, expressed in percentage. If the actual average utilization
    is more than this threshold, an avgChanLoadToDCETrap trap may be sent as
    specified by the avgChanLoadToDCETrapSeverity object value."

    ::={ trapConfig 6 }


--
--***************************************************************************
--                            CHANNEL LOAD TO DTE

realTimeChanLoadToDTEThresh OBJECT-TYPE
    SYNTAX INTEGER (0..100)
    ACCESS read-write
    STATUS mandatory
    DESCRIPTION
    "Defines the maximum allowed real-time channel load calculated every
    second, expressed in percentage. If the actual load is more than this
    threshold, a realTimeTrapSeverity exception trap may be sent as specified
    by the realTimeTrapSeverity object value."

    ::={ trapConfig 7 }


realTimeChanLoadToDTEThreshVar OBJECT-TYPE
    SYNTAX INTEGER (0..100)
    ACCESS read-write
    STATUS mandatory
    DESCRIPTION
    "Defines the variation range for real-time channel load, expressed in 
    percentage.. If within the current TC interval, the variation of the
    actual utilization is more than that range compared with the previous 
    trap value, another realTimeTrapSeverity exception trap may be sent as
    specified by the realTimeTrapSeverity object value."

    ::={ trapConfig 8 }


avgChanLoadToDTETrapSeverity OBJECT-TYPE
    SYNTAX INTEGER
    {
        inhibit   (1),
        critical  (2),
        major     (3),
        minor     (4),
        warning   (5),
        info      (6)
    }
    ACCESS read-write
    STATUS mandatory
    DESCRIPTION
    "Controls the reporting of and defines severity of the 15 minute average
    load exception trap.
    WEBFLAG
    Inhibit
    Critical
    Major
    Minor
    Warning
    Info
    WEBEND
    "

    ::={ trapConfig 9 }


avgChanLoadToDTEThresh OBJECT-TYPE
    SYNTAX INTEGER (0..100)
    ACCESS read-write
    STATUS mandatory
    DESCRIPTION
    "Defines the maximum allowed frame relay channel utilization in a 15
    minute period, expressed in percentage. If the actual average utilization
    is more than this threshold, an avgChanLoadToDTETrap trap may be sent as
    specified by the avgChanLoadToDTETrapSeverity object value."

    ::={ trapConfig 10 }


--
--***************************************************************************
--                           PVC LOAD TO DCE

realTimePvcLoadToDCEThresh OBJECT-TYPE
    SYNTAX INTEGER (0..2048)
    ACCESS read-write
    STATUS mandatory
    DESCRIPTION
    "Defines the maximum allowed real-time PVC load calculated every
    second, expressed in percentage. If the actual load is more than this
    threshold, a realTimeTrapSeverity exception trap may be sent as specified
    by the realTimeTrapSeverity object value."

    ::={ trapConfig 11 }


realTimePvcLoadToDCEThreshVar OBJECT-TYPE
    SYNTAX INTEGER (0..100)
    ACCESS read-write
    STATUS mandatory
    DESCRIPTION
    "Defines the variation range for real-time PVC load, expressed in 
    percentage.. If within the current TC interval, the variation of the
    actual utilization is more than that range compared with the previous 
    trap value, another realTimeTrapSeverity exception trap may be sent as
    specified by the realTimeTrapSeverity object value."

    ::={ trapConfig 12 }


avgPvcLoadToDCETrapSeverity OBJECT-TYPE
    SYNTAX INTEGER
    {
        inhibit   (1),
        critical  (2),
        major     (3),
        minor     (4),
        warning   (5),
        info      (6)
    }
    ACCESS read-write
    STATUS mandatory
    DESCRIPTION
    "Controls the reporting of and defines severity of the 15 minute average
    load exception trap.
    WEBFLAG
    Inhibit
    Critical
    Major
    Minor
    Warning
    Info
    WEBEND
    "

    ::={ trapConfig 13 }


avgPvcLoadToDCEThresh OBJECT-TYPE
    SYNTAX INTEGER (0..2048)
    ACCESS read-write
    STATUS mandatory
    DESCRIPTION
    "Defines the maximum allowed PVC load in a 15 minute period, expressed in
    percentage. If the actual average PVC loading is more than this threshold,
    an avgPvcLoadToDCETrap trap may be sent as specified by the
    avgPvcLoadToDCETrapSeverity object value."

    ::={ trapConfig 14 }


--
--***************************************************************************
--                            PVC LOAD TO DTE

realTimePvcLoadToDTEThresh OBJECT-TYPE
    SYNTAX INTEGER (0..2048)
    ACCESS read-write
    STATUS mandatory
    DESCRIPTION
    "Defines the maximum allowed real-time PVC load calculated every
    second, expressed in percentage. If the actual load is more than this
    threshold, a realTimeTrapSeverity exception trap may be sent as specified
    by the realTimeTrapSeverity object value."

    ::={ trapConfig 15 }


realTimePvcLoadToDTEThreshVar OBJECT-TYPE
    SYNTAX INTEGER (0..100)
    ACCESS read-write
    STATUS mandatory
    DESCRIPTION
    "Defines the variation range for real-time PVC load, expressed in 
    percentage. If within the current TC interval, the variation of the
    actual utilization is more than that range compared with the previous 
    trap value, another realTimeTrapSeverity exception trap may be sent as
    specified by the realTimeTrapSeverity object value."

    ::={ trapConfig 16 }


avgPvcLoadToDTETrapSeverity OBJECT-TYPE
    SYNTAX INTEGER
    {
        inhibit   (1),
        critical  (2),
        major     (3),
        minor     (4),
        warning   (5),
        info      (6)
    }
    ACCESS read-write
    STATUS mandatory
    DESCRIPTION
    "Controls the reporting of and defines severity of the 15 minute average
    load exception trap.
    WEBFLAG
    Inhibit
    Critical
    Major
    Minor
    Warning
    Info
    WEBEND
    "

    ::={ trapConfig 17 }


avgPvcLoadToDTEThresh OBJECT-TYPE
    SYNTAX INTEGER (0..2048)
    ACCESS read-write
    STATUS mandatory
    DESCRIPTION
    "Defines the maximum allowed PVC load in a 15 minute period, expressed in
    percentage. If the actual average utilization is more than this threshold,
    an avgPvcLoadToDTETrap trap may be sent as specified by the
    avgPvcLoadToDTETrapSeverity object value."

    ::={ trapConfig 18 }


--
--***************************************************************************
--                            PVC ROUND TRIP DELAY

realTimePvcRoundTripDelayThresh OBJECT-TYPE
    SYNTAX INTEGER (0..2048)
    ACCESS read-write
    STATUS mandatory
    DESCRIPTION
    "Defines the maximum allowed real-time PVC round trip delay, calculated
    every second, expressed in percentage. If the actual load is more than
    this threshold, a realTimeTrapSeverity exception trap may be sent as
    specified by the realTimeTrapSeverity object value."

    ::={ trapConfig 19 }


realTimePvcRoundTripDelayThreshVar OBJECT-TYPE
    SYNTAX INTEGER (0..100)
    ACCESS read-write
    STATUS mandatory
    DESCRIPTION
    "Defines the variation range for real-time PVC round trip delay, expressed
    in percentage.. If within the current TC interval, the variation of the
    actual round trip delay is more than that range compared with the previous 
    trap value, another realTimeTrapSeverity exception trap may be sent as
    specified by the realTimeTrapSeverity object value."

    ::={ trapConfig 20 }


avgPvcRoundTripDelayTrapSeverity OBJECT-TYPE
    SYNTAX INTEGER
    {
        inhibit   (1),
        critical  (2),
        major     (3),
        minor     (4),
        warning   (5),
        info      (6)
    }
    ACCESS read-write
    STATUS mandatory
    DESCRIPTION
    "Controls the reporting of and defines severity of the 15 minute average
    round trip delay exception trap.
    WEBFLAG
    Inhibit
    Critical
    Major
    Minor
    Warning
    Info
    WEBEND
    "

    ::={ trapConfig 21 }


avgPvcRoundTripDelayThresh OBJECT-TYPE
    SYNTAX INTEGER (0..2048)
    ACCESS read-write
    STATUS mandatory
    DESCRIPTION
    "Defines the maximum allowed PVC round trip delay in a 15 minute period,
    expressed in percentage. If the actual average PVC round trip delay
    is more than this threshold, an avgPvcRoundTripDelayTrap trap may be sent
    as specified by the avgPvcRoundTripDelayTrapSeverity object value."

    ::={ trapConfig 22 }


--
--***************************************************************************
--                   15 MINUTE AVERAGE ALARMS & THRESHOLDS


avgPvcNotAvailToDCETrapSeverity OBJECT-TYPE
    SYNTAX INTEGER
    {
        inhibit   (1),
        critical  (2),
        major     (3),
        minor     (4),
        warning   (5),
        info      (6)
	    }
    ACCESS read-write
    STATUS mandatory
    DESCRIPTION
    "Controls the reporting of and defines severity of the 
    avgPvcNotAvailToDCE exception trap.  This condition may be reported when
    the avgPvcNotAvailToDCEThresh object value is exceeded within a 15 minute
    period.
    WEBFLAG
    Inhibit
    Critical
    Major
    Minor
    Warning
    Info
    WEBEND
    "

    ::={ trapConfig 23 }


avgPvcNotAvailToDCEThresh OBJECT-TYPE
    SYNTAX INTEGER (0..100)
    ACCESS read-write
    STATUS mandatory
    DESCRIPTION
    "Defines the maximum allowed average unavailability in a 15 minute period,
    expressed in percentage. If the actual value is more than this threshold,
    an avgPvcNotAvailToDCE trap may be sent as specified by the 
    avgPvcNotAvailToDCETrapSeverity object value."

    ::={ trapConfig 24 }


avgPvcNotAvailToDTETrapSeverity OBJECT-TYPE
    SYNTAX INTEGER
    {
        inhibit   (1),
        critical  (2),
        major     (3),
        minor     (4),
        warning   (5),
        info      (6)
    }
    ACCESS read-write
    STATUS mandatory
    DESCRIPTION
    "Controls the reporting of and defines severity of the
    avgPvcNotAvailToDTE exception trap.  This condition may be reported when
    the avgPvcNotAvailToDTEThresh object value is exceeded within a 15 minute
    period.
    WEBFLAG
    Inhibit
    Critical
    Major
    Minor
    Warning
    Info
    WEBEND
    "

    ::={ trapConfig 25 }


avgPvcNotAvailToDTEThresh OBJECT-TYPE
    SYNTAX INTEGER (0..100)
    ACCESS read-write
    STATUS mandatory
    DESCRIPTION
    "Defines the maximum allowed average unavailability in a 15 minute period,
    expressed in percentage. If the actual value is more than this threshold,
    an avgPvcNotAvailToDTE trap may be sent as specified by the 
    avgPvcNotAvailToDTETrapSeverity object value."

    ::={ trapConfig 26 }


avgPvcFecnFramesTrapSeverity OBJECT-TYPE
    SYNTAX INTEGER
    {
        inhibit   (1),
        critical  (2),
        major     (3),
        minor     (4),
        warning   (5),
        info      (6)
    }
    ACCESS read-write
    STATUS mandatory
    DESCRIPTION
    "Controls the reporting of and defines severity of the avgPvcFecnFrames
    exception trap. This condition may be reported when the 
    avgPvcFecnFramesThresh object value is exceeded within a 15 minute period.
    WEBFLAG
    Inhibit
    Critical
    Major
    Minor
    Warning
    Info
    WEBEND
    "

    ::={ trapConfig 27 }


avgPvcFecnFramesThresh OBJECT-TYPE
    SYNTAX INTEGER (0..2048)
    ACCESS read-write
    STATUS mandatory
    DESCRIPTION
    "Defines the maximum allowed number of FECN frames which may be received
    in a 15 minute period."

    ::={ trapConfig 28 }


avgPvcBecnFramesTrapSeverity OBJECT-TYPE
    SYNTAX INTEGER
    {
        inhibit   (1),
        critical  (2),
        major     (3),
        minor     (4),
        warning   (5),
        info      (6)
    }
    ACCESS read-write
    STATUS mandatory
    DESCRIPTION
    "Controls the reporting of and defines severity of the avgPvcBecnFrames
    exception trap. This condition may be reported when the 
    avgPvcFecnFramesThresh object value is exceeded within a 15 minute period.
    WEBFLAG
    Inhibit
    Critical
    Major
    Minor
    Warning
    Info
    WEBEND
    "

    ::={ trapConfig 29 }


avgPvcBecnFramesThresh OBJECT-TYPE
    SYNTAX INTEGER (0..2048)
    ACCESS read-write
    STATUS mandatory
    DESCRIPTION
    "Defines the maximum allowed number of BECN frames which may be received
    in a 15 minute period."

    ::={ trapConfig 30 }


--
--***************************************************************************
--                   15 MINUTE AVERAGE ALARMS



avgPvcCIRExceedToDTETrapSeverity OBJECT-TYPE
    SYNTAX INTEGER
    {
        inhibit   (1),
        critical  (2),
        major     (3),
        minor     (4),
        warning   (5),
        info      (6)
    }
    ACCESS read-write
    STATUS mandatory
    DESCRIPTION
    "Controls the reporting of and defines severity of the
    avgPvcCIRExceedToDTE exception trap. This trap may be reported if
    this condition occurs over a 15 minute period.
    WEBFLAG
    Inhibit
    Critical
    Major
    Minor
    Warning
    Info
    WEBEND
    "

    ::={ trapConfig 31 }


avgPvcEIRExceedToDTETrapSeverity OBJECT-TYPE
    SYNTAX INTEGER
    {
        inhibit   (1),
        critical  (2),
        major     (3),
        minor     (4),
        warning   (5),
        info      (6)
    }
    ACCESS read-write
    STATUS mandatory
    DESCRIPTION
    "Controls the reporting of and defines severity of the
    avgPvcEIRExceedToDTE exception trap. This trap may be reported if
    this condition occurs over a 15 minute period.
    WEBFLAG
    Inhibit
    Critical
    Major
    Minor
    Warning
    Info
    WEBEND
    "

    ::={ trapConfig 32 }


avgPvcLossFrameTxTrapSeverity OBJECT-TYPE
    SYNTAX INTEGER
    {
        inhibit   (1),
        critical  (2),
        major     (3),
        minor     (4),
        warning   (5),
        info      (6)
    }
    ACCESS read-write
    STATUS mandatory
    DESCRIPTION
    "Controls the reporting of and defines severity of the
    avgPvcLossFrameTx exception trap. This trap may be reported if
    this condition occurs over a 15 minute period.
    WEBFLAG
    Inhibit
    Critical
    Major
    Minor
    Warning
    Info
    WEBEND
    "

    ::={ trapConfig 33 }


avgPvcLossFrameRxTrapSeverity OBJECT-TYPE
    SYNTAX INTEGER
    {
        inhibit   (1),
        critical  (2),
        major     (3),
        minor     (4),
        warning   (5),
        info      (6)
    }
    ACCESS read-write
    STATUS mandatory
    DESCRIPTION
    "Controls the reporting of and defines severity of the
    avgPvcLossFrameTx exception trap. This trap may be reported if
    this condition occurs over a 15 minute period.
    WEBFLAG
    Inhibit
    Critical
    Major
    Minor
    Warning
    Info
    WEBEND
    "

    ::={ trapConfig 34 }


--
--***************************************************************************
--                         LMI ALARMS


networkLmiInterfaceDownTrapSeverity OBJECT-TYPE
    SYNTAX INTEGER
    {
        inhibit   (1),
        critical  (2),
        major     (3),
        minor     (4),
        warning   (5),
        info      (6)
    }
    ACCESS read-write
    STATUS mandatory
    DESCRIPTION
    "Controls the reporting of and defines severity of the
    networkLmiInterfaceDown exception trap.
    WEBFLAG
    Inhibit
    Critical
    Major
    Minor
    Warning
    Info
    WEBEND
    "

    ::={ trapConfig 35 }


userLmiInterfaceDownTrapSeverity OBJECT-TYPE
    SYNTAX INTEGER
    {
        inhibit   (1),
        critical  (2),
        major     (3),
        minor     (4),
        warning   (5),
        info      (6)
    }
    ACCESS read-write
    STATUS mandatory
    DESCRIPTION
    "Controls the reporting of and defines severity of the
    userLmiInterfaceDown exception trap.
    WEBFLAG
    Inhibit
    Critical
    Major
    Minor
    Warning
    Info
    WEBEND
    "

    ::={ trapConfig 36 }


--
-- ****************************************************************************
--                         PVC Configuration Group
-- ****************************************************************************


pvcCirEirTable OBJECT-TYPE
    SYNTAX SEQUENCE OF PvcCirEirEntry
    ACCESS not-accessible
    STATUS mandatory
    DESCRIPTION
    "PVC table, which lists PVCs for which the statistic data are collected."

    ::={ pvcConfig 1 }

pvcCirEirEntry OBJECT-TYPE
    SYNTAX PvcCirEirEntry
    ACCESS not-accessible
    STATUS mandatory
    DESCRIPTION
    "Identifies an entry (row) in PVC CIR/EIR table."
    INDEX { pvcCirEirTableIndex }
    
    ::={ pvcCirEirTable 1 }

PvcCirEirEntry ::=
    SEQUENCE
    {
        pvcCirEirTableIndex	INTEGER,
        pvcCirToDTE		INTEGER,
        pvcCirToDCE		INTEGER,
        pvcEirToDTE		INTEGER,
        pvcEirToDCE		INTEGER,
	pvcOperation		INTEGER,	
	pvcState		INTEGER,	
	pvcIdentifier		DisplayString	
    }

pvcCirEirTableIndex OBJECT-TYPE
    SYNTAX INTEGER ( 16..991 )
    ACCESS read-only
    STATUS mandatory
    DESCRIPTION
    "Identifies an entry (row) in PVC table."

    ::={ pvcCirEirEntry    1 }

pvcCirToDTE OBJECT-TYPE
    SYNTAX INTEGER (1..2048000)
    ACCESS read-write
    STATUS mandatory
    DESCRIPTION
    "Defines the committed information rate, in bps, under normal 
    conditions in the direction of to DTE."

    ::={ pvcCirEirEntry    2 }

pvcCirToDCE OBJECT-TYPE
    SYNTAX INTEGER (1..2048000)
    ACCESS read-write
    STATUS mandatory
    DESCRIPTION
    "Defines the committed information rate, in bps, under normal
    conditions in the direction of to DCE."

    ::={ pvcCirEirEntry    3 }

pvcEirToDTE OBJECT-TYPE
    SYNTAX INTEGER (0..2048000)
    ACCESS read-write
    STATUS mandatory
    DESCRIPTION
    "Defines the maximum transfer information rate, in bps, which the
    network is accepting in the direction of to DTE."

    ::={ pvcCirEirEntry    4 }

pvcEirToDCE OBJECT-TYPE
    SYNTAX INTEGER (0..2048000)
    ACCESS read-write
    STATUS mandatory
    DESCRIPTION
    "Defines the maximum transfer information rate, in bps, which the
    network is accepting in the direction of to DCE."

    ::={ pvcCirEirEntry    5 }

pvcOperation OBJECT-TYPE
    SYNTAX INTEGER
    {
        pvcNotProbed     (1),   -- not probed
        pvcWaitForProbe  (2),   -- waiting to be probed in next 15 min cycle
        pvcProbed        (3)    -- probed for stats and perform.  (read only)
    }
    ACCESS read-write
    STATUS mandatory
    DESCRIPTION
    "Defines the monitored state of a PVC. pvcNotProbed - specifies that 
    the PVC will not be probed, round trip delay and frame loss measurements
    will not be tabulated. pvcWaitForProbe specifies that this PVC is in a
    transition state, and will be probed at the start of the next 15 minute
    poll cycle for statistic data collection. pvcProbed is a read only value
    that indicates this PVC is used for both statistic data and probing.
    WEBFLAG
    Not Probed
    Probe Pending
    Probed
    WEBEND
    "

    ::={ pvcCirEirEntry    6 }

pvcState OBJECT-TYPE
    SYNTAX INTEGER
    {
	unavailable  (1),
	inactive     (2),
        active       (3)
    }
    ACCESS read-only
    STATUS mandatory
    DESCRIPTION
    "Reflects the state of the PVC as seen by the probe. 
    `unavailable' indicates that the PVC is not included in the DLCI list.
    `inactive indicates that the PVC is no longer responding.
    `active' indicates that the PVC is in operational state. "

    ::={ pvcCirEirEntry    7 }

pvcIdentifier
    OBJECT-TYPE
    SYNTAX  DisplayString (SIZE (0..32))
    ACCESS  read-write
    STATUS  mandatory
    DESCRIPTION
    "Comment field for annotation."

    ::= { pvcCirEirEntry   8 }





--
-- ****************************************************************************

--	LINK PROBE STATISTICS GROUP
--	four sub-groups are defined in this group
--	1. Channel statistics for current interval
--	2. Channel statistics interval table
--	3. PVC statistics current interval table
--	4. PVC statistics interval table
--

--
--	The following chStCurrent group contains various statistics being
--	collected for the current 15 minutes interval.
--

--
-- ****************************************************************************
--                Channel Statistics for Current Interval Group
-- ****************************************************************************


	chStCurrent OBJECT IDENTIFIER ::={ probeStat 1 }

	chCurrDteFrames OBJECT-TYPE
		SYNTAX Counter
		ACCESS read-only
		STATUS mandatory
		DESCRIPTION
		" Identifies total frames received from DTE device within
		  current 15 minutes interval. "
		::={ chStCurrent 1 }

	chCurrDceFrames OBJECT-TYPE
		SYNTAX Counter
		ACCESS read-only
		STATUS mandatory
		DESCRIPTION
		" Identifies total frames received from DCE device within
		  current 15 minutes interval. "
		::={ chStCurrent 2 }

	chCurrDteOctets OBJECT-TYPE
		SYNTAX Counter
		ACCESS read-only
		STATUS mandatory
		DESCRIPTION
		" Identifies total octets received from DTE device within
		  current 15 minutes interval. "
		::={ chStCurrent 3 }

	chCurrDceOctets OBJECT-TYPE
		SYNTAX Counter
		ACCESS read-only
		STATUS mandatory
		DESCRIPTION
		" Identifies total octets received from DTE device within
		  current 15 minutes interval. "
		::={ chStCurrent 4 }

	 chCurrLmiTxEnq OBJECT-TYPE
		SYNTAX Counter
		ACCESS read-only
		STATUS mandatory
		DESCRIPTION
               " Identifies the total number of LMI enquiries sent to DCE
		  within current 15 minutes interval. "
		::={ chStCurrent 5 }

	chCurrLmiTxResp OBJECT-TYPE
		SYNTAX Counter
		ACCESS read-only
		STATUS mandatory
		DESCRIPTION
                " Identifies the total number of LMI responses sent to DTE
		  within current 15 minutes interval. "
		::={ chStCurrent 6 }

	chCurrLmiRxEnq OBJECT-TYPE
		SYNTAX Counter
		ACCESS read-only
		STATUS mandatory
		DESCRIPTION
                " Identifies the total number of LMI enquiries from the DTE
		  within current 15  minutes interval. "
		::={ chStCurrent 7 }

	chCurrLmiRxResp OBJECT-TYPE
		SYNTAX Counter
		ACCESS read-only
		STATUS mandatory
		DESCRIPTION
		" Identifies the total number of LMI status responses received
		  from the DCE within current 15 minutes interval. "
		::={ chStCurrent 8 }

	chCurrDTELmiTimeout OBJECT-TYPE
		SYNTAX Counter
		ACCESS read-only
		STATUS mandatory
		DESCRIPTION
		" Identifies the total number of lmi timeouts received
		  within current 15 minutes interval. "
		::={ chStCurrent 9 }

	chCurrDCELmiTimeout OBJECT-TYPE
		SYNTAX Counter
		ACCESS read-only
		STATUS mandatory
		DESCRIPTION
		" Identifies the total number of lmi timeouts received
		  within current 15 minutes interval. "
		::={ chStCurrent 10}

	chCurrFecnFrames OBJECT-TYPE
		SYNTAX Counter
		ACCESS read-only
		STATUS mandatory
		DESCRIPTION
		" Identifies total number of frames with FECN  set received
		  within current 15 minutes interval. "
		::={ chStCurrent 11 }

	chCurrBecnFrames OBJECT-TYPE
		SYNTAX Counter
		ACCESS read-only
		STATUS mandatory
		DESCRIPTION
		" Identifies total number of frames with BECN  set received
		  within current 15 minutes interval. "
		::={ chStCurrent 12 }

	chCurrTxIp OBJECT-TYPE
		SYNTAX Counter
		ACCESS read-only
		STATUS mandatory
		DESCRIPTION
		" Identifies total number of IP packets sent on inband DLCI
		  within current 15 minutes interval. "
		::={ chStCurrent 13 }

	chCurrRxIp OBJECT-TYPE
		SYNTAX Counter
		ACCESS read-only
		STATUS mandatory
		DESCRIPTION
		" Identifies total number of IP packets received on inband
		  DLCI within current 15 minutes interval. "
		::={ chStCurrent 14 }

	chCurrTxPoll OBJECT-TYPE
		SYNTAX Counter
		ACCESS read-only
		STATUS mandatory
		DESCRIPTION
		" Identifies total number of probe polls sent to DCE within
		  current 15 minutes interval. "
		::={ chStCurrent 15 }

	chCurrTxResp OBJECT-TYPE
		SYNTAX Counter
		ACCESS read-only
		STATUS mandatory
		DESCRIPTION
		" Identifies total number of probe responses sent to DCE
		  within current 15 minutes interval. "
		::={ chStCurrent 16 }

	chCurrRxPoll OBJECT-TYPE
		SYNTAX Counter
		ACCESS read-only
		STATUS mandatory
		DESCRIPTION
		" Identifies total number of probe polls received from DCE
		  within current 15 minutes interval. "
		::={ chStCurrent 17 }

	chCurrRxResp OBJECT-TYPE
		SYNTAX Counter
		ACCESS read-only
		STATUS mandatory
		DESCRIPTION
		" Identifies total number of probe responses received from
		  DCE within current 15 minutes interval. "
		::={ chStCurrent 18 }


	intervalComplete OBJECT-TYPE
		SYNTAX INTEGER ( 1..100 )
		ACCESS read-only
		STATUS mandatory
		DESCRIPTION
		" This object identifies the the percent completeion 
		  of the interval. "
		::={ chStCurrent 19 }







--^L
-- ****************************************************************************
--	The channel statistic interval table contains various statistics
--      collected over the previous 24 hours of operation.  The past
--	24 hours are broken into 96 completed 15-minute intervals.
-- ****************************************************************************

	chStIntervalTable OBJECT-TYPE
		SYNTAX SEQUENCE OF ChStIntervalEntry
		ACCESS not-accessible
		STATUS mandatory
		DESCRIPTION
		" probe statistic table, row 1 to row 96,
		  which defines the time interval for every 15
		  minutes. "
		::={ probeStat 2 }

	chStIntervalEntry OBJECT-TYPE
		SYNTAX ChStIntervalEntry
		ACCESS not-accessible
		STATUS mandatory
		DESCRIPTION
		" Identifies an entry (row) in probe statistic table."
		INDEX { chIntvIndex }
		::={ chStIntervalTable 1 }

	ChStIntervalEntry ::=
		SEQUENCE {
		  chIntvIndex		INTEGER,
		  chIntvDteFrames	Counter,
		  chIntvDceFrames	Counter,
		  chIntvDteOctets	Counter,
		  chIntvDceOctets	Counter,
		  chIntvLmiTxEnq	Counter,
		  chIntvLmiTxResp	Counter,
		  chIntvLmiRxEnq	Counter,
                  chIntvLmiRxResp	Counter,
		  chIntvDTELmiTimeout	Counter, 
		  chIntvDCELmiTimeout	Counter, 
		  chIntvFecnFrames	Counter,
		  chIntvBecnFrames	Counter,
		  chIntvTxIp		Counter,
		  chIntvRxIp		Counter,
		  chIntvTxPoll		Counter,
		  chIntvTxResp		Counter,
		  chIntvRxPoll		Counter,
		  chIntvRxResp		Counter
                	}

	chIntvIndex OBJECT-TYPE
                SYNTAX INTEGER ( 1..96 )
                ACCESS read-only
                STATUS mandatory
                DESCRIPTION
               " Identifies an entry (row) in channel statistic table,
                  1-96 time intervals. "
                ::={ chStIntervalEntry 1 }

	chIntvDteFrames OBJECT-TYPE
                SYNTAX Counter
                ACCESS read-only
                STATUS mandatory
                DESCRIPTION
                " Identifies total frames received from DTE device within a 15
                  minutes interval. "
                ::={ chStIntervalEntry 2 }

	chIntvDceFrames OBJECT-TYPE
                SYNTAX Counter
               ACCESS read-only
                STATUS mandatory
                DESCRIPTION
                " Identifies total frames received from DCE device within a 15
                  minutes interval. "
               ::={ chStIntervalEntry 3 }

	chIntvDteOctets OBJECT-TYPE
                SYNTAX Counter
                ACCESS read-only
                STATUS mandatory
                DESCRIPTION
                " Identifies total octets received from DTE device within a 15
                  minutes interval. "
                ::={ chStIntervalEntry 4 }

	chIntvDceOctets OBJECT-TYPE
                SYNTAX Counter
                ACCESS read-only
                STATUS mandatory
                DESCRIPTION
                " Identifies total octets received from DTE device within a 15
                  minutes interval. "
                ::={ chStIntervalEntry 5 }

	chIntvLmiTxEnq OBJECT-TYPE
                SYNTAX Counter
                ACCESS read-only
                STATUS mandatory
                DESCRIPTION
                " Identifies the total number of LMI enquiries sent to DCE
                 within a 15 minutes interval. "
                ::={ chStIntervalEntry 6 }

	chIntvLmiTxResp OBJECT-TYPE
                SYNTAX Counter
                ACCESS read-only
                STATUS mandatory
                DESCRIPTION
                " Identifies the total number of LMI responses send to
                  DTE within a 15 minutes interval. "
                ::={ chStIntervalEntry 7 }

	chIntvLmiRxEnq OBJECT-TYPE
                SYNTAX Counter
                ACCESS read-only
                STATUS mandatory
                DESCRIPTION
               " Identifies the total number of LMI enquiries received
                 within a 15 minutes interval. "
                ::={ chStIntervalEntry 8 }

	chIntvLmiRxResp OBJECT-TYPE
                SYNTAX Counter
                ACCESS read-only
                STATUS mandatory
                DESCRIPTION
                " Identifies the total number of LMI status responses received
                  from the DCE within a 15 minutes interval. "
                ::={ chStIntervalEntry 9 }

	chIntvDTELmiTimeout OBJECT-TYPE
                SYNTAX Counter
                ACCESS read-only
                STATUS mandatory
                DESCRIPTION
                " Identifies the total number of LMI timeouts received
                  within a 15 minutes interval. "
                ::={ chStIntervalEntry 10 }

	chIntvDCELmiTimeout OBJECT-TYPE
                SYNTAX Counter
                ACCESS read-only
                STATUS mandatory
                DESCRIPTION
                " Identifies the total number of LMI timeouts received
                  within a 15 minutes interval. "
                ::={ chStIntervalEntry 11 }

	chIntvFecnFrames OBJECT-TYPE
                SYNTAX Counter
                ACCESS read-only
                STATUS mandatory
                DESCRIPTION
                " Identifies total number of frames with FECN  set received 
		  within a 15 minutes interval. "
                ::={ chStIntervalEntry 12 }

	chIntvBecnFrames OBJECT-TYPE
                SYNTAX Counter
               ACCESS read-only
                STATUS mandatory
                DESCRIPTION
               " Identifies total number of frames with BECN  set received 
		 within a 15 minutes interval. "
                ::={ chStIntervalEntry 13 }

	chIntvTxIp OBJECT-TYPE
                SYNTAX Counter
                ACCESS read-only
                STATUS mandatory
                DESCRIPTION
               " Identifies total number of IP packets sent on inband DLCI
                 within a 15 minutes interval. "
               ::={ chStIntervalEntry 14 }

	chIntvRxIp OBJECT-TYPE
                SYNTAX Counter
                ACCESS read-only
                STATUS mandatory
                DESCRIPTION
                " Identifies total number of IP packets received on inband
                  DLCI within a 15 minutes interval. "
                ::={ chStIntervalEntry 15 }

	chIntvTxPoll OBJECT-TYPE
                SYNTAX Counter
                ACCESS read-only
               STATUS mandatory
                DESCRIPTION
                " Identifies total number of probe polls sent to DCE within
                  a 15 minutes interval. "
                ::={ chStIntervalEntry 16 }

	chIntvTxResp OBJECT-TYPE
                SYNTAX Counter
                ACCESS read-only
                STATUS mandatory
                DESCRIPTION
                " Identifies total number of probe response sent to DCE within
                  a 15 minutes interval. "
                ::={ chStIntervalEntry 17 }

	chIntvRxPoll OBJECT-TYPE
                SYNTAX Counter
                ACCESS read-only
                STATUS mandatory
                DESCRIPTION
                " Identifies total number of probe polls received from DCE
                  within a 15 minutes interval. "
                ::={ chStIntervalEntry 18 }

	chIntvRxResp OBJECT-TYPE
                SYNTAX Counter
                ACCESS read-only
                STATUS mandatory
                DESCRIPTION
                " Identifies total number of probe responses received from
                  DCE within a 15 minutes interval. "
                ::={ chStIntervalEntry 19 }

--^L
-- ****************************************************************************
--	The  current PVC statistic table contains various statistics being
--	collected by each PVC for the current 15 minutes interval.
-- ****************************************************************************

	pvcStCurrentTable OBJECT-TYPE
               SYNTAX SEQUENCE OF PVCStCurrentEntry
                ACCESS not-accessible
                STATUS mandatory
                DESCRIPTION
                " PVC statistic table."
                ::={ probeStat 3 }

	pvcStCurrentEntry OBJECT-TYPE
                SYNTAX PVCStCurrentEntry
                ACCESS not-accessible
                STATUS mandatory
                DESCRIPTION
                " Identifies an entry (row) in PVC statistic table"
                INDEX { pvcCurrDlciIndex }
                ::={ pvcStCurrentTable 1 }

	PVCStCurrentEntry ::=
                SEQUENCE {
                  pvcCurrDlciIndex		INTEGER,
                  pvcCurrDteFrames		Counter,
                  pvcCurrDceFrames		Counter,
                  pvcCurrDteOctets		Counter,
                  pvcCurrDceOctets		Counter,
                  pvcCurrDteFramesWithDE	Counter,
                  pvcCurrDceFramesWithDE	Counter,
                  pvcCurrFecnFrames		Counter,
                  pvcCurrBecnFrames		Counter,
                  pvcCurrTxPoll			Counter,
                  pvcCurrTxResp			Counter,
                  pvcCurrRxPoll			Counter,
                  pvcCurrRxResp			Counter,
                  pvcCurrLoopback		INTEGER
		}

	pvcCurrDlciIndex OBJECT-TYPE
               SYNTAX INTEGER ( 16..991 )
                ACCESS read-only
                STATUS mandatory
                DESCRIPTION
                " Index in PVC statistics table, which identifies
                  the PVC number, up to 20 PVCs can exist. "
                ::={ pvcStCurrentEntry 1 }

	pvcCurrDteFrames OBJECT-TYPE
                SYNTAX Counter
                ACCESS read-only
                STATUS mandatory
                DESCRIPTION
                " Identifies total frames received from DTE device for a
                  specific PVC within current 15 minutes interval. "
                ::={ pvcStCurrentEntry 2 }

	pvcCurrDceFrames OBJECT-TYPE
                SYNTAX Counter
                ACCESS read-only
                STATUS mandatory
                DESCRIPTION
                " Identifies total frames received from DCE device for a
                 specific PVC within current 15 minutes interval. "
                ::={ pvcStCurrentEntry 3 }

	pvcCurrDteOctets OBJECT-TYPE
               SYNTAX Counter
                ACCESS read-only
                STATUS mandatory
                DESCRIPTION
               " Identifies total octets received from DTE device for a
                  specific PVC within current 15 minutes interval. "
                ::={ pvcStCurrentEntry 4 }

	pvcCurrDceOctets OBJECT-TYPE
                SYNTAX Counter
                ACCESS read-only
                STATUS mandatory
               DESCRIPTION
                " Identifies total octets received from DTE device for a
                  specific PVC within current 15 minutes interval. "
                ::={ pvcStCurrentEntry 5 }

	pvcCurrDteFramesWithDE OBJECT-TYPE
                SYNTAX Counter
                ACCESS read-only
                STATUS mandatory
                DESCRIPTION
                " Identifies total frames with DE bit set received from DTE
		  device for a specific PVC within current 15 minutes
		  interval. "
                ::={ pvcStCurrentEntry 6 }

	pvcCurrDceFramesWithDE OBJECT-TYPE
                SYNTAX Counter
                ACCESS read-only
                STATUS mandatory
                DESCRIPTION
                " Identifies total frames with DE bit set received from DCE
		  device for a specific PVC within current 15 minutes 
		  interval. "
                ::={ pvcStCurrentEntry 7 }

	pvcCurrFecnFrames OBJECT-TYPE
                SYNTAX Counter
                ACCESS read-only
                STATUS mandatory
                DESCRIPTION
                " Identifies total number of frames for a specific PVC
                  with FECN  set received within current 15 minutes interval. "
                ::={ pvcStCurrentEntry 8 }

	pvcCurrBecnFrames OBJECT-TYPE
                SYNTAX Counter
                ACCESS read-only
                STATUS mandatory
                DESCRIPTION
                " Identifies total number of frames for a specific PVC
                  with BECN  set received within current 15 minutes interval. "
                ::={ pvcStCurrentEntry 9 }

	pvcCurrTxPoll OBJECT-TYPE
                SYNTAX Counter
                ACCESS read-only
                STATUS mandatory
                DESCRIPTION
                " Identifies total number of probe polls sent to DCE within
                  current 15  minutes interval. "
                ::={ pvcStCurrentEntry 10 }

	pvcCurrTxResp OBJECT-TYPE
                SYNTAX Counter
                ACCESS read-only
                STATUS mandatory
                DESCRIPTION
                " Identifies total number of probe responses sent to DCE
                  within current 15  minutes interval. "
                ::={ pvcStCurrentEntry 11 }

	pvcCurrRxPoll OBJECT-TYPE
                SYNTAX Counter
                ACCESS read-only
                STATUS mandatory
                DESCRIPTION
                " Identifies total number of probe polls received from DCE
                  on a specific PVC within current 15 minutes interval. "
                ::={ pvcStCurrentEntry 12 }

	pvcCurrRxResp OBJECT-TYPE
                SYNTAX Counter
                ACCESS read-only
                STATUS mandatory
                DESCRIPTION
                " Identifies total number of probe responses received from DCE
                  on a specific PVC within current 15 minutes interval. "
                ::={ pvcStCurrentEntry 13 }

	pvcCurrLoopback OBJECT-TYPE
                SYNTAX INTEGER {
                        loopback(1),
                        noLoopback(2)
                }
                ACCESS read-only
                STATUS mandatory
                DESCRIPTION
                " Identifies whether the specific PVC has been found to be in
		  a loop back state by link probe's generator process. "
                ::={ pvcStCurrentEntry 14 }

--^L
-- ****************************************************************************
--	The PVC statistic interval table contains various statistics
--      collected for each PVC over the previous 24 hours of operation.
--	The past 24 hours are broken into 96 completed 15-minute intervals.
-- ****************************************************************************

	pvcStIntervalTable OBJECT-TYPE
		SYNTAX SEQUENCE OF PVCStIntervalEntry
		ACCESS not-accessible
		STATUS mandatory
		DESCRIPTION
		" PVC statistic interval table: "
		::={ probeStat 4 }

	pvcStIntervalEntry OBJECT-TYPE
		SYNTAX PVCStIntervalEntry
		ACCESS not-accessible
		STATUS mandatory
		DESCRIPTION
		" Identifies an entry (row) in pvc statistic table"
		INDEX { pvcIntvDlciIndex, pvcIntvIndex }
		::={ pvcStIntervalTable 1 }

	PVCStIntervalEntry ::=
		SEQUENCE {
		  pvcIntvDlciIndex		INTEGER,
		  pvcIntvIndex			INTEGER,
		  pvcIntvDteFrames		Counter,
		  pvcIntvDceFrames		Counter,
		  pvcIntvDteOctets		Counter,
		  pvcIntvDceOctets		Counter,
                  pvcIntvDteFramesWithDE	Counter,
                  pvcIntvDceFramesWithDE	Counter,
                  pvcIntvFecnFrames		Counter,
		  pvcIntvBecnFrames		Counter,
		  pvcIntvTxPoll			Counter,
		  pvcIntvTxResp			Counter,
		  pvcIntvRxPoll			Counter,
		  pvcIntvRxResp			Counter,
                  pvcIntvLoopback		INTEGER
		}

	pvcIntvDlciIndex OBJECT-TYPE
		SYNTAX INTEGER ( 16..991 )
		ACCESS read-only
		STATUS mandatory
		DESCRIPTION
		" This index value which uniquely identifies the PVC
		  number to which this entry is applicable. "
		::={ pvcStIntervalEntry 1 }

	pvcIntvIndex OBJECT-TYPE
		SYNTAX INTEGER ( 1..96 )
		ACCESS read-only
		STATUS mandatory
		DESCRIPTION
		" A number between 1 and 96, where 1 is the most recently
		  completed 15 minutes interval and 96 is the least recently
		 completed 15 minutes interval. "
		::={ pvcStIntervalEntry 2 }

	pvcIntvDteFrames OBJECT-TYPE
		SYNTAX Counter
		ACCESS read-only
		STATUS mandatory
		DESCRIPTION
		" Identifies total frames received from DTE device for a
		  specific PVC within a 15 minutes interval. "
		::={ pvcStIntervalEntry 3 }

	pvcIntvDceFrames OBJECT-TYPE
		SYNTAX Counter
		ACCESS read-only
		STATUS mandatory
		DESCRIPTION
		" Identifies total frames received from DCE device for a
		  specific PVC within a 15 minutes interval. "
		::={ pvcStIntervalEntry 4 }

	pvcIntvDteOctets OBJECT-TYPE
		SYNTAX Counter
		ACCESS read-only
		STATUS mandatory
		DESCRIPTION
		" Identifies total octets received from DTE device for a
		  specific PVC within a 15 minutes interval. "
		::={ pvcStIntervalEntry 5 }

	pvcIntvDceOctets OBJECT-TYPE
		SYNTAX Counter
		ACCESS read-only
		STATUS mandatory
		DESCRIPTION
		" Identifies total octets received from DCE device for a
		  specific PVC within a 15 minutes interval. "
		::={ pvcStIntervalEntry 6 }

	pvcIntvDteFramesWithDE OBJECT-TYPE
		SYNTAX Counter
		ACCESS read-only
		STATUS mandatory
		DESCRIPTION
                " Identifies the frames with DE bit set received from DTE 
		  device for a specific PVC within a 15 minutes interval. "
                ::={ pvcStIntervalEntry 7 }

	pvcIntvDceFramesWithDE OBJECT-TYPE
		SYNTAX Counter
		ACCESS read-only
		STATUS mandatory
		DESCRIPTION
                " Identifies the frames with DE bit set received from DCE 
		  device for a specific PVC within a 15 minutes interval. "
                ::={ pvcStIntervalEntry 8 }

	pvcIntvFecnFrames OBJECT-TYPE
		SYNTAX Counter
		ACCESS read-only
		STATUS mandatory
		DESCRIPTION
		" Identifies total number of frames for a specific PVC
		  with FECN  set received within a 15 minutes interval. "
                ::={ pvcStIntervalEntry 9 }

	pvcIntvBecnFrames OBJECT-TYPE
		SYNTAX Counter
		ACCESS read-only
		STATUS mandatory
		DESCRIPTION
		" Identifies total number of frames for a specific PVC
		  with BECN  set received within a 15 minutes interval. "
                ::={ pvcStIntervalEntry 10 }

	pvcIntvTxPoll OBJECT-TYPE
		SYNTAX Counter
		ACCESS read-only
		STATUS mandatory
		DESCRIPTION
		" Identifies total number of probe polls sent to DCE within
		  a 15 minutes interval. "
                ::={ pvcStIntervalEntry 11 }

	pvcIntvTxResp OBJECT-TYPE
		SYNTAX Counter
		ACCESS read-only
		STATUS mandatory
		DESCRIPTION
		" Identifies total number of probe responses sent to DCE
		  within a 15 minutes interval. "
                ::={ pvcStIntervalEntry 12 }

	pvcIntvRxPoll OBJECT-TYPE
		SYNTAX Counter
		ACCESS read-only
		STATUS mandatory
		DESCRIPTION
		" Identifies total number of probe polls received from DCE
		  on a specific PVC within a 15 minutes interval. "
                ::={ pvcStIntervalEntry 13 }

	pvcIntvRxResp OBJECT-TYPE
		SYNTAX Counter
		ACCESS read-only
		STATUS mandatory
		DESCRIPTION
		" Identifies total number of probe responses received from
		  DCE on a specific PVC within a 15 minutes interval. "
                ::={ pvcStIntervalEntry 14 }

	pvcIntvLoopback OBJECT-TYPE
                SYNTAX INTEGER {
                        loopback(1),
                        noLoopback(2)
                }
		ACCESS read-only
		STATUS mandatory
		DESCRIPTION
                " Identifies whether the specific PVC has been found to be 
		  in a loop back state by link probe's generator process. "
               ::={ pvcStIntervalEntry 15 }

--^L
-- ****************************************************************************

-- Subgroup in probe performance group
--
-- 1. Channel Performance Current 15 Minutes Data
-- 2. Channel Performance Historical Data (up to 96 15-min. interval)
-- 3. PVC performance Current 15 Minutes Data
-- 4. PVC Performance Historical Data (up to 96 15-min. interval)
--

-- ****************************************************************************
-- 1. Current Channel Performance Group displays the statistic data which
--    measure the channel performance within the latest 15 minutes.
--
-- ****************************************************************************

	chanPerfCurr OBJECT IDENTIFIER ::={ probePerform 1 }

	chPerfCurrUnavailToDte OBJECT-TYPE
                SYNTAX INTEGER
                ACCESS  read-only
		STATUS mandatory
		DESCRIPTION
               " This object identifies the channel unavailability due to 
		 remote DTE fault within the latest 15 minutes. This 
		 statistic datum is calculated by the channel unavailable
		 time over the full time interval."
                ::={ chanPerfCurr 1 }

	chPerfCurrUnavailToDce OBJECT-TYPE
                SYNTAX INTEGER
                ACCESS read-only
		STATUS mandatory
		DESCRIPTION
                " This object identifies the channel unavailability due to
		  local DTE fault within the latest 15 minutes. This 
		  statistic datum is calculated by the channel unavailable 
		  time over the full time interval."
                ::={ chanPerfCurr 2 }

	chPerfCurrTxLoad OBJECT-TYPE
                SYNTAX INTEGER
               ACCESS  read-only
		STATUS mandatory
		DESCRIPTION
                " channel average user tx load within the latest 15 minutes,
                  this statistic datum is calculated by user data octets 
		  sent by the channel within the 15 minutes over the total
		  channel available load ( which depends on physical
		  interface speed). "
                ::={ chanPerfCurr 3 }

	chPerfCurrRxLoad OBJECT-TYPE
                SYNTAX INTEGER
                ACCESS  read-only
		STATUS mandatory
		DESCRIPTION
                " Channel average user rx load within the latest 15 minutes,
                  this statistic datum is calculated by user data octets 
		  received by the channel within the 15 minutes over the 
		  total channel available load ( which depends on physical 
		  interface speed). "
                ::={ chanPerfCurr 4 }

	chPerfCurrTotalTxLoad OBJECT-TYPE
                SYNTAX INTEGER
                ACCESS  read-only
		STATUS mandatory
		DESCRIPTION
                " channel total tx load within the latest 15 minutes,
                  this statistic datum is calculated by the total data octets
                  sent by the channel within the 15 minutes over the channel
                  available load ( which depends on physical interface 
		  speed). "
                ::={ chanPerfCurr 5 }

	chPerfCurrTotalRxLoad OBJECT-TYPE
                SYNTAX INTEGER
                ACCESS  read-only
		STATUS mandatory
		DESCRIPTION
                "channel total rx load within the latest 15 minutes,
                 this statistic datum is calculated by total data octets
		 received by the channel within the 15 minutes over the 
		 channel total available load ( which depends on physical 
		 interface speed). "
                ::={ chanPerfCurr 6 }

	chPerfCurrLoadToDceRealTime OBJECT-TYPE
               SYNTAX INTEGER
                ACCESS read-only
		STATUS mandatory
		DESCRIPTION
                " This object displays the channel load tx within current TC
                  ( 1 sec.), this variable is calculated by total octets
                  transmitted over the capacity of this channel. "
                ::={ chanPerfCurr 7 }

	chPerfCurrLoadToDteRealTime OBJECT-TYPE
                SYNTAX INTEGER
                ACCESS read-only
		STATUS mandatory
		DESCRIPTION
                " This object displays the channel load rx within current TC
                  ( 1 sec.), this variable is calculated by total octets
                  received over the capacity of this channel. "
                ::={ chanPerfCurr 8 }

--^L
-- ****************************************************************************
-- 2. Channel Performance Interval Group displays the statistic data which
--    measure the channel performance over the previous 24 hours of operation.
--    The past 24 hours are broken into 96 completed 15 minutes intervals.
-- ****************************************************************************
--

	chanPerfIntvTable OBJECT-TYPE
                SYNTAX SEQUENCE OF ChanPerfIntvEntry
		ACCESS not-accessible
		STATUS mandatory
		DESCRIPTION
                " Probe channel performance table, which displays
                  the performance statistic data based on the probe
                  channel within previous 24 hours."
                ::={ probePerform 2 }

	chanPerfIntvEntry OBJECT-TYPE
                SYNTAX ChanPerfIntvEntry
		ACCESS not-accessible
		STATUS mandatory
		DESCRIPTION
                " Identifies an entry (row) in probe channel performance
                  table."
                INDEX { chPerfIntvIndex }
                ::={ chanPerfIntvTable 1 }

	ChanPerfIntvEntry ::=
		SEQUENCE {
                  chPerfIntvIndex		INTEGER,
                  chPerfIntvUnavailToDte	INTEGER,
                  chPerfIntvUnavailToDce	INTEGER,
                  chPerfIntvTxLoad		INTEGER,
                  chPerfIntvRxLoad		INTEGER,
                  chPerfIntvTotalTxLoad		INTEGER,
                  chPerfIntvTotalRxLoad		INTEGER
               	}

	chPerfIntvIndex OBJECT-TYPE
                SYNTAX INTEGER (1..96)
                ACCESS  read-only
		STATUS mandatory
		DESCRIPTION
                " Identifies an entry (row) in historical PVC performance
		  table, total 96 time intervals, where 1 is the most 
		  recently completed 15 minutes interval and 96 is the 
		  least recently completed 15 minutes interval (assuming 
		  that all 96 intervals are valid).  "
              ::={ chanPerfIntvEntry 1 }

	chPerfIntvUnavailToDte OBJECT-TYPE
                SYNTAX INTEGER
                ACCESS  read-only
		STATUS mandatory
		DESCRIPTION
                " This object identifies the channel unavailability due to
		  remote DTE fault within a 15 minutes interval. This 
		  statistic datum is calculated by the channel unavailable
		  time over the full time interval."
                ::={ chanPerfIntvEntry 2 }

	chPerfIntvUnavailToDce OBJECT-TYPE
                SYNTAX INTEGER
                ACCESS  read-only
		STATUS mandatory
		DESCRIPTION
                " This object identifies the channel unavailability due to
		  local DTE fault within a 15 minutes interval. This
		  statistic datum is calculated by the channel unavailable
		  time over the full time interval."
                ::={ chanPerfIntvEntry 3 }

	chPerfIntvTxLoad OBJECT-TYPE
                SYNTAX INTEGER
                ACCESS  read-only
		STATUS mandatory
		DESCRIPTION
                " channel average user tx load within a 15 minutes 
		  interval,this statistic datum is calculated by user data
		  octets sent by the channel within the 15 minutes over the
		  total channel available load ( which depends on physical
		  interface speed). "
                ::={ chanPerfIntvEntry 4 }

	chPerfIntvRxLoad OBJECT-TYPE
                SYNTAX INTEGER
                ACCESS  read-only
		STATUS mandatory
		DESCRIPTION
                " channel average user rx load within a 15 minutes interval,
                  this statistic datum is calculated by user data octets
		  received by the channel within the 15 minutes over the 
		  total channel available load( which depends on physical 
		  interface speed). "
                ::={ chanPerfIntvEntry 5 }

	chPerfIntvTotalTxLoad OBJECT-TYPE
                SYNTAX INTEGER
                ACCESS  read-only
		STATUS mandatory
		DESCRIPTION
                " channel total tx load within a 15 minutes interval,
                  this statistic datum is calculated by the total data octets
                  sent by the channel within the 15 minutes over the total
                  channel available load ( which depends on physical 
 		  interface speed). "
                ::={ chanPerfIntvEntry 6 }

	chPerfIntvTotalRxLoad OBJECT-TYPE
                SYNTAX INTEGER
                ACCESS  read-only
		STATUS mandatory
		DESCRIPTION
                " Channel total rx load within a 15 minutes interval,
                  this statistic datum is calculated by the total data octets
                  received by the channel within the 15 minutes over the total
		  channel available load ( which depends on physical interface
		  speed). "
                ::={ chanPerfIntvEntry 7 }

--^L
-- ****************************************************************************
-- 3. Current PVC Performance Table displays the statistic data
--    for every PVC within the current 15 minutes.
-- ****************************************************************************
--

	pvcPerfCurrTable OBJECT-TYPE
                SYNTAX SEQUENCE OF PvcPerfCurrEntry
		ACCESS not-accessible
		STATUS mandatory
		DESCRIPTION
              " PVC performance table, which displays
                  the performance statistic data based on
                  each PVC."
                ::={ probePerform 3 }

	pvcPerfCurrEntry OBJECT-TYPE
                SYNTAX PvcPerfCurrEntry
		ACCESS not-accessible
		STATUS mandatory
		DESCRIPTION
               " Identifies an entry (row) in pvc statistic table"
                INDEX { pvcPerfCurrDlciIndex}
                ::={ pvcPerfCurrTable 1 }

	PvcPerfCurrEntry ::=
		SEQUENCE {
                  pvcPerfCurrDlciIndex		INTEGER,
                  pvcPerfCurrRtd		INTEGER,
                  pvcPerfCurrUnavailToDte	INTEGER,
                  pvcPerfCurrUnavailToDce	INTEGER,
                  pvcPerfCurrTxLoad		INTEGER,
                  pvcPerfCurrRxLoad		INTEGER,
                  pvcPerfCurrTotalTxLoad	INTEGER,
                  pvcPerfCurrTotalRxLoad	INTEGER,
                  pvcPerfCurrCirToNetExceed	INTEGER,
                  pvcPerfCurrEirToNetExceed	INTEGER,
                  pvcPerfCurrTxFrameLoss	INTEGER,
                  pvcPerfCurrRxFrameLoss	INTEGER
               	}

	pvcPerfCurrDlciIndex OBJECT-TYPE
                SYNTAX INTEGER ( 16..991 )
		ACCESS read-only
		STATUS mandatory
		DESCRIPTION
		" This index value which uniquely identifies the PVC
		  number to which this entry is applicable. "
                ::={ pvcPerfCurrEntry 1 }

	pvcPerfCurrRtd OBJECT-TYPE
                SYNTAX INTEGER
               ACCESS read-only
		STATUS mandatory
		DESCRIPTION
                " Probe token average round trip time within the latest
                  15 minutes for a specific PVC. "
                ::={ pvcPerfCurrEntry 2 }

	pvcPerfCurrUnavailToDte OBJECT-TYPE
               SYNTAX INTEGER
                ACCESS  read-only
		STATUS mandatory
		DESCRIPTION
                " This object identifies the PVC average unavailability
                  within the latest 15 minutes. This statistic datum is
                  calculated by a PVC unavailable time due to the network
                  or remote DTE fault over the full time interval."
                ::={ pvcPerfCurrEntry 3 }

	pvcPerfCurrUnavailToDce OBJECT-TYPE
                SYNTAX INTEGER
                ACCESS  read-only
		STATUS mandatory
		DESCRIPTION
                " This object identifies the PVC average unavailability
                  within the latest 15 minutes. This statistic datum is
                  calculated by a PVC unavailable time due to the local
                  DTE fault over the full time interval."
                ::={ pvcPerfCurrEntry 4 }

	pvcPerfCurrTxLoad OBJECT-TYPE
                SYNTAX INTEGER
                ACCESS  read-only
		STATUS mandatory
		DESCRIPTION
                " This object identifies the PVC average user tx load within
		  the latest 15 minutes.  This statistic datum is calculated
		  by user data octets sent by a specific PVC within the 15 
		  minutes over the PVC total available load. If the CIR is 
		  correctly defined for this PVC, PVC available load will 
		  depend on CIR, otherwise, it will get from interface
                  speed. "
                ::={ pvcPerfCurrEntry 5 }

	pvcPerfCurrRxLoad OBJECT-TYPE
                SYNTAX INTEGER
                ACCESS  read-only
		STATUS mandatory
		DESCRIPTION
                " This object identifies the PVC average user rx load within
		  the latest 15 minutes.  This statistic datum is calculated
		  by user data octets received by a specific PVC within the 
		  15 minutes over the PVC total available load. If the CIR
		  is correctly defined for this PVC, PVC available load will
		  depend on CIR, otherwise, it will get from interface
                  speed. "
                ::={ pvcPerfCurrEntry 6 }

	pvcPerfCurrTotalTxLoad OBJECT-TYPE
                SYNTAX INTEGER
                ACCESS  read-only
		STATUS mandatory
		DESCRIPTION
                " This object identifies the PVC total tx load within the
                  latest 15 minutes.  This statistic datum is calculated by
                  total data octets sent by a specific PVC within the 15
		  minutes over the PVC total available load. If the CIR is 
		  correctly defined for this PVC, PVC available load will 
		  depend on CIR, otherwise, it will get from interface
                  speed. "
                ::={ pvcPerfCurrEntry 7 }

	pvcPerfCurrTotalRxLoad OBJECT-TYPE
                SYNTAX INTEGER
                ACCESS  read-only
		STATUS mandatory
		DESCRIPTION
               "  This object identifies the PVC total rx load within the
                  latest 15 minutes.  This statistic datum is calculated by
                  total data octets received by a specific PVC within the 15 
		  minutes over the PVC total available load. If the CIR is
		  correctly defined for this PVC, PVC available load will
		  depend on CIR, otherwise, it will get from interface
                  speed. "
                ::={ pvcPerfCurrEntry 8 }

	pvcPerfCurrCirToNetExceed OBJECT-TYPE
                SYNTAX INTEGER
                ACCESS read-only
		STATUS mandatory
		DESCRIPTION
                " This object identifies the number of exceeding CIR times 
		  that the network detected within the current interval. 
		  The measurement is done for every Tc, and the direction 
		  is to the network."
                ::={ pvcPerfCurrEntry 9 }

	pvcPerfCurrEirToNetExceed OBJECT-TYPE
                SYNTAX INTEGER
                ACCESS read-only
		STATUS mandatory
		DESCRIPTION
                " This object identifies the number of exceeding EIR times
		  that the network detected within the current interval.
		  The measurement is done for every Tc, and the direction
		  is to the network."
               ::={ pvcPerfCurrEntry 10 }

	pvcPerfCurrTxFrameLoss OBJECT-TYPE
                SYNTAX INTEGER {
                       notAvail(255)
               }
                ACCESS read-only
		STATUS mandatory
		DESCRIPTION
                " This object identifies the percentage of tx loss of frames
		  within the total tx frames for this PVC."
                ::={ pvcPerfCurrEntry 11 }

	pvcPerfCurrRxFrameLoss OBJECT-TYPE
                SYNTAX INTEGER {
                        notAvail(255)
                }
                ACCESS read-only
		STATUS mandatory
		DESCRIPTION
                " This object identifies the percentage of rx loss of frames
		  within the total rx frames for this PVC."
                ::={ pvcPerfCurrEntry 12 }

--^L
-- ****************************************************************************
-- 4. PVC Performance Interval Table displays the statistic data
--    for every PVC over the previous 24 hours of operation.
--    The past 24 hours are broken into 96 completed 15 minutes
--    intervals.
-- ****************************************************************************
--

	pvcPerfIntvTable OBJECT-TYPE
                SYNTAX SEQUENCE OF PvcPerfIntvEntry
		ACCESS not-accessible
		STATUS mandatory
		DESCRIPTION
                " PVC performance interval table, which displays
                  the performance statistic data based on  each
                  PVC in previous 24 hours."
                ::={ probePerform 4 }

	pvcPerfIntvEntry OBJECT-TYPE
                SYNTAX PvcPerfIntvEntry
		ACCESS not-accessible
		STATUS mandatory
		DESCRIPTION
                " Identifies an entry (row) in pvc statistic table"
                INDEX { pvcPerfIntvDlciIndex, pvcPerfIntvIndex }
                ::={ pvcPerfIntvTable 1 }

	PvcPerfIntvEntry ::=
		SEQUENCE {
                  pvcPerfIntvDlciIndex		INTEGER,
                  pvcPerfIntvIndex		INTEGER,
                  pvcPerfIntvRtd		INTEGER,
                  pvcPerfIntvUnavailToDte	INTEGER,
                  pvcPerfIntvUnavailToDce	INTEGER,
                  pvcPerfIntvTxLoad		INTEGER,
                  pvcPerfIntvRxLoad		INTEGER,
                  pvcPerfIntvTotalTxLoad	INTEGER,
                  pvcPerfIntvTotalRxLoad	INTEGER,
                  pvcPerfIntvCirToNetExceed	INTEGER,
                  pvcPerfIntvEirToNetExceed	INTEGER,
                  pvcPerfIntvTxFrameLoss	INTEGER,
                  pvcPerfIntvRxFrameLoss	INTEGER
       		}

	pvcPerfIntvDlciIndex OBJECT-TYPE
                SYNTAX INTEGER ( 16..991 )
		ACCESS read-only
		STATUS mandatory
		DESCRIPTION
		" This index value which uniquely identifies the PVC
		  number to which this entry is applicable. "
               ::={ pvcPerfIntvEntry 1 }

	pvcPerfIntvIndex OBJECT-TYPE
                SYNTAX INTEGER (1..96)
		ACCESS read-only
		STATUS mandatory
		DESCRIPTION
                " Identifies an entry (row) in historical PVC performance
		  table,total 96 time intervals, where 1 is the most
		  recently completed 15 minutes interval and 96 is the 
		  least recently completed 15 minutes interval (assuming 
		  that all 96 intervals are valid). "
                ::={ pvcPerfIntvEntry 2 }

	pvcPerfIntvRtd OBJECT-TYPE
                SYNTAX INTEGER
                ACCESS read-only
		STATUS mandatory
		DESCRIPTION
                " Probe token average round trip time within a
                  15 minutes interval for a specific PVC. "
                ::={ pvcPerfIntvEntry 3 }

	pvcPerfIntvUnavailToDte OBJECT-TYPE
                SYNTAX INTEGER
                ACCESS read-only
		STATUS mandatory
		DESCRIPTION
               " This object identifies the PVC average unavailability
                 within a 15 minutes. This statistic datum is
                  calculated by a PVC unavailable time due to the network
                or remote DTE fault over the full time interval."
                ::={ pvcPerfIntvEntry 4 }

	pvcPerfIntvUnavailToDce OBJECT-TYPE
               SYNTAX INTEGER
                ACCESS read-only
		STATUS mandatory
		DESCRIPTION
                " This object identifies the PVC average unavailability
                  within a 15 minutes. This statistic datum is
                  calculated by a PVC unavailable time due to the local DTE
                  fault over the full time interval."
                ::={ pvcPerfIntvEntry 5 }

	pvcPerfIntvTxLoad OBJECT-TYPE
                SYNTAX INTEGER
                ACCESS read-only
		STATUS mandatory
		DESCRIPTION
                " This object identifies the PVC average user tx load within
                  a 15 minutes interval.  This statistic datum is calculated
		  by user data octets sent by a specific PVC within the 15 
		  minutes over the PVC total available load. If the CIR is 
		  correctly defined for this PVC, PVC available load will
		  depend on CIR, otherwise, it will get from interface
                  speed. "
                ::={ pvcPerfIntvEntry 6 }

	pvcPerfIntvRxLoad OBJECT-TYPE
                SYNTAX INTEGER
                ACCESS read-only
		STATUS mandatory
		DESCRIPTION
                " This object identifies the PVC average user rx load within
                  a 15 minutes interval.  This statistic datum is calculated 
		  by user data octets received by a specific PVC within the 
		  15 minutes over the PVC total available load. If the CIR
		  is correctly defined for this PVC, PVC available load will
		  depend on CIR, otherwise, it will get from interface
                  speed. "
               ::={ pvcPerfIntvEntry 7 }

	pvcPerfIntvTotalTxLoad OBJECT-TYPE
                SYNTAX INTEGER
                ACCESS read-only
		STATUS mandatory
		DESCRIPTION
                " This object identifies the PVC total tx load within
                  a 15 minutes interval.  This statistic datum is calculated
		  by total data octets sent by a specific PVC within the 15
		  minutes over the PVC total available load. If the CIR is
		  correctly defined for this PVC, PVC available load will 
		  depend on CIR, otherwise, it will get from interface
                  speed. "
                ::={ pvcPerfIntvEntry 8 }

	pvcPerfIntvTotalRxLoad OBJECT-TYPE
                SYNTAX INTEGER
                ACCESS read-only
		STATUS mandatory
		DESCRIPTION
                " This object identifies the PVC total rx load within
                  a 15 minutes interval.  This statistic datum is calculated
		  by total data octets received by a specific PVC within 
		  the 15 minutes over the PVC total available load. If the 
		  CIR is correctly defined for this PVC, PVC available
                  load will depend on CIR, otherwise, it will get from 
		  interface speed. "
                ::={ pvcPerfIntvEntry 9 }

	pvcPerfIntvCirToNetExceed OBJECT-TYPE
                SYNTAX INTEGER
                ACCESS read-only
		STATUS mandatory
		DESCRIPTION
                " This object identifies the number of exceeding CIR times
		  that the network detected within an interval. The 
		  measurement is done for every Tc, and the direction is 
		  to the network."
                ::={ pvcPerfIntvEntry 10 }

	pvcPerfIntvEirToNetExceed OBJECT-TYPE
                SYNTAX INTEGER
                ACCESS read-only
		STATUS mandatory
		DESCRIPTION
                " This object identifies the number of exceeding EIR times
		  that the network detected within an interval. The 
		  measurement is done for every Tc, and the direction is to
		  the network."
               ::={ pvcPerfIntvEntry 11 }

	pvcPerfIntvTxFrameLoss OBJECT-TYPE
                SYNTAX INTEGER {
                        notAvail(255)
               }
                ACCESS read-only
		STATUS mandatory
		DESCRIPTION
                " This object identifies the percentage of tx loss of frames
		  within the total tx frames for this PVC in this interval."
                ::={ pvcPerfIntvEntry 12 }

	pvcPerfIntvRxFrameLoss OBJECT-TYPE
                SYNTAX INTEGER {
                        notAvail(255)
                }
                ACCESS read-only
		STATUS mandatory
		DESCRIPTION
                " This object identifies the percentage of rx loss of frames
		  within the total rx frames for this PVC in this interval."
                ::={ pvcPerfIntvEntry 13 }


--^L
-- ****************************************************************************
-- 5. Current realtime PVC Performance Table displays the statistic data
--    for every PVC within the current 15 minutes.
-- ****************************************************************************
--

	pvcPerfRealTimeTable OBJECT-TYPE
                SYNTAX SEQUENCE OF PvcPerfRealTimeEntry
		ACCESS not-accessible
		STATUS mandatory
		DESCRIPTION
              " PVC performance table, which displays
                  the performance statistic data based on
                  each PVC."
                ::={ probePerform 5 }

	pvcPerfRealTimeEntry OBJECT-TYPE
                SYNTAX PvcPerfRealTimeEntry
		ACCESS not-accessible
		STATUS mandatory
		DESCRIPTION
               " Identifies an entry (row) in pvc statistic table"
                INDEX { pvcPerfRealTimeDlciIndex}
                ::={ pvcPerfRealTimeTable 1 }

	PvcPerfRealTimeEntry ::=
		SEQUENCE {
		  pvcPerfRealTimeDlciIndex	INTEGER,
                  pvcPerfRealTimeRtd		INTEGER,
                  pvcPerfRealTimeLoadToDCE	INTEGER,
 		  pvcPerfRealTimeLoadToDTE	INTEGER
               	}

	pvcPerfRealTimeDlciIndex OBJECT-TYPE
                SYNTAX INTEGER ( 16..991 )
		ACCESS read-only
		STATUS mandatory
		DESCRIPTION
		" This index value which uniquely identifies the PVC
		  number to which this entry is applicable. "
                ::={ pvcPerfRealTimeEntry 1 }

	pvcPerfRealTimeRtd OBJECT-TYPE
                SYNTAX INTEGER
                ACCESS read-only
		STATUS mandatory
		DESCRIPTION
                " Probe token real time round trip delay in msec. for a PVC,
		  it is calculated every Probe Poll interval
		  (1 to 60 sec.). "
                ::={ pvcPerfRealTimeEntry 2 }

	pvcPerfRealTimeLoadToDCE OBJECT-TYPE
                SYNTAX INTEGER
                ACCESS  read-only
		STATUS mandatory
		DESCRIPTION
                " This object displays the PVC load to DCE within current TC
                  ( 1 sec.), this variable is calculated by total octets
                  transmitted to DTE over the CIR of this PVC."
                ::={ pvcPerfRealTimeEntry 3 }

	pvcPerfRealTimeLoadToDTE OBJECT-TYPE
                SYNTAX INTEGER
                ACCESS  read-only
		STATUS mandatory
		DESCRIPTION
                " This object displays the PVC load to DTE within current TC
                  ( 1 sec.), this variable is calculated by total octets
                  transmitted to DCE over the CIR of this PVC."
                ::={ pvcPerfRealTimeEntry 4 }

--^L
-- ****************************************************************************
--
--                           TRAP STATUS GROUP
--			     
-- ****************************************************************************

-- These are a snapshot of the current alarm status.



        alarmCurrentStatusBitsMap OBJECT-TYPE
                SYNTAX INTEGER (0..4095)
		ACCESS read-only
		STATUS mandatory
		DESCRIPTION
                "This parameter is a bitmap for the 6 enterprise specific 
		 traps. A bit value of one means the trap is active. A
		 bit value of zero means the trap is clear.

                 1st bit = avgChanLoadToDTE_trap;
		 2nd bit = realTimeChanLoadToDTE_trap;
                 3rd bit = avgChanLoadToDCE_trap;
		 4th bit = realTimeChanLoadToDCE_trap;
                 5th bit = networkLmiInterfaceDown_trap;
                 6th bit = userLmiInterfaceDown_trap; "
                ::={ alarmStatus 1}


        alarmCurrentStatusTable OBJECT-TYPE
                SYNTAX SEQUENCE OF AlarmStatusEntry
		ACCESS not-accessible
		STATUS mandatory
		DESCRIPTION
                " PVC table which lists PVCs and alarm status. "
                ::={ alarmStatus 2 }

        alarmStatusEntry OBJECT-TYPE
                SYNTAX AlarmStatusEntry
		ACCESS not-accessible
		STATUS mandatory
		DESCRIPTION
                " Identifies an entry (row) in PVC alarm status table."
		INDEX { alarmStatusTableIndex }
                ::={ alarmCurrentStatusTable 1 }

        AlarmStatusEntry ::=
		SEQUENCE {
                  alarmStatusTableIndex		INTEGER,
                  currentStatusBitsMap		INTEGER
		  	}


        alarmStatusTableIndex OBJECT-TYPE
		SYNTAX INTEGER ( 16..991 )
		ACCESS read-only
		STATUS mandatory
		DESCRIPTION
                " Identifies an entry (row) in the alarm status 
		  table. "
                ::={ alarmStatusEntry    1 }




currentStatusBitsMap OBJECT-TYPE
    SYNTAX INTEGER (0..4095)
    ACCESS read-only
    STATUS mandatory
    DESCRIPTION
    "This parameter is a bitmap for the 14 enterprise specific traps. A bit
    value of one means the trap is active. A bit value of zero means the trap
    is clear.
  
     1st bit = avgPvcNotAvailToDCE_trap;
     2nd bit = avgPvcNotAvailToDTE_trap;
     3rd bit = avgPvcRoundTripDelay_trap;
     4th bit = realTimePvcRoundTripDelay_trap;
     5th bit = avgPvcBecnFrames_trap;
     6th bit = avgPvcFecnFrames_trap;
     7th bit = avgPvcLoadToDTE_trap;
     8th bit = realTimePvcLoadToDTE_trap;
     9th bit = avgPvcLoadToDCE_trap;
    10th bit = realTimePvcLoadToDCE_trap;
    11th bit = avgPvcCIRExceedToDTE_trap;
    12th bit = avgPvcEIRExceedToDTE_trap;
    13th bit = avgPvcLossFrameTx_trap;
    14th bit = avgPvcLossFrameRx_trap;  "
 
    ::={ alarmStatusEntry 2 }



--^L
-- ****************************************************************************
--
--                           TRAP GENERATION GROUP
--			     SYSTEM TRAP EVENTS
-- ****************************************************************************
--
-- These are unsolicited messages sent by the SNMP Agent to alert the NMS
-- of critical System errors that would require immediate attention.
--


--
-- ****************************************************************************
--                     General Alarm Object Information for Default Values
-- ****************************************************************************


--       Alarm                 Maskable     Window and     Reportable Type
--                                           Threshold      of Alarm
--                                                          
--   pvcOperStateChange         yes            no             Info

--   realTimePvcLoadToDCE       yes            yes            Info
--        avgPvcLoadToDCE       yes            yes            Info

--   realTimePvcLoadToDTE       yes            yes            Info
--        avgPvcLoadToDTE       yes            yes            Info

--   realTimePvcRoundTripDelay  yes            yes            Info
--        avgPvcRoundTripDelay  yes            yes            Info



--   avgPvcNotAvailToDCE        yes            yes            Minor

--   avgPvcNotAvailToDTE        yes            yes            Minor

--   avgPvcFecnFrames           yes            yes            Info

--   avgPvcBecnFrames         	yes            yes            Info



--   avgPvcCIRExceedToDTE       yes            no             Info

--   avgPvcEIRExceedToDTE     	yes            no             Info
 
--   avgPvcLossFrameTx        	yes            no             Info

--   avgPvcLossFrameRx          yes            no             Info
 

--   realTimeChanLoadToDCE      yes            yes            Info
--        avgChanLoadToDCE      yes            yes            Info

--   realTimeChanLoadToDTE      yes            yes            Info
--        avgChanLoadToDTE      yes            yes            Info

--   networkLmiInterfaceDown    yes            yes            Info

--   userLmiInterfaceDown       yes            yes            Info





-- ****************************************************************************
--                          mib definitions end
-- ****************************************************************************

END
