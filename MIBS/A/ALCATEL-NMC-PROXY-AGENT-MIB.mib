-- The Alcatel NMC proxy agent MIB


-- Revision: 1.6


-- Date:     01/05/29


-- /* RA CDHva56260 */





ALCATEL-NMC-PROXY-AGENT-MIB DEFINITIONS ::= BEGIN





IMPORTS


    enterprises, OBJECT-TYPE	FROM SNMPv2-SMI


    TRAP-TYPE			FROM RFC-1215


    openViewSeverity		FROM HPOV-NNM-MIB;





alcatel OBJECT IDENTIFIER ::= { enterprises 637 }


abs OBJECT IDENTIFIER ::= { alcatel 64 }


nmc4755 OBJECT IDENTIFIER ::= { abs 0 }


notification OBJECT IDENTIFIER ::= { nmc4755 10 }


nmcProxyAgent OBJECT IDENTIFIER ::= { notification 1 }


nmcProxyTraps OBJECT IDENTIFIER ::= { nmcProxyAgent 2 }





cmipEventArg OBJECT IDENTIFIER ::= { nmcProxyAgent 1 }


objectClass OBJECT IDENTIFIER ::= { cmipEventArg 1 }


objectInstance OBJECT IDENTIFIER ::= { cmipEventArg 2 }





topClass OBJECT-TYPE


    SYNTAX INTEGER


    ACCESS read-only


    STATUS mandatory


    DESCRIPTION


	"identifier which allows the identification of the system.


	For instance an Alcatel 4400"


    ::= { objectClass 1 }





baseClass OBJECT-TYPE


    SYNTAX INTEGER


    ACCESS read-only


    STATUS mandatory


    DESCRIPTION


	"identifier which allows to identify the impacted object


	without ambiguity for a given system. For instance


	a board of a 4400"


    ::= { objectClass 2 }





containmentTree OBJECT IDENTIFIER ::= { objectInstance 1 }


a4400 OBJECT IDENTIFIER ::= { containmentTree 89 }


shelf OBJECT IDENTIFIER ::= { a4400 29 }


board OBJECT IDENTIFIER ::= { shelf 23 }


actOrSuEvents OBJECT IDENTIFIER ::= { board 175 }


terminal OBJECT IDENTIFIER ::= { actOrSuEvents 82 }


logicalLinks OBJECT IDENTIFIER ::= { a4400 101 }


dect OBJECT IDENTIFIER ::= { a4400 201 }





rdnDepth OBJECT-TYPE


    SYNTAX INTEGER


    ACCESS read-only


    STATUS mandatory


    DESCRIPTION


	"value that specifies the depth of the impacted object class


	inside the containment tree"


    ::= { objectInstance 2 }





rdnValues OBJECT IDENTIFIER


	::= { objectInstance 3 }





rdn1 OBJECT IDENTIFIER ::= { rdnValues 1 }





classId1 OBJECT-TYPE


    SYNTAX INTEGER


    ACCESS read-only


    STATUS mandatory


    DESCRIPTION "object class, level one"


    ::= { rdn1 1 }


rdnValue1 OBJECT-TYPE


    SYNTAX OCTET STRING


    ACCESS read-only


    STATUS mandatory


    DESCRIPTION "value, level one"


    ::= { rdn1 2 }





rdn2 OBJECT IDENTIFIER ::= { rdnValues 2 }





classId2 OBJECT-TYPE


    SYNTAX INTEGER


    ACCESS read-only


    STATUS mandatory


    DESCRIPTION "object class, level two"


    ::= { rdn2 1 }


rdnValue2 OBJECT-TYPE


    SYNTAX OCTET STRING


    ACCESS read-only


    STATUS mandatory


    DESCRIPTION "value, level two"


    ::= { rdn2 2 }





rdn3 OBJECT IDENTIFIER ::= { rdnValues 3 }





classId3 OBJECT-TYPE


    SYNTAX INTEGER


    ACCESS read-only


    STATUS mandatory


    DESCRIPTION "object class, level three"


    ::= { rdn3 1 }


rdnValue3 OBJECT-TYPE


    SYNTAX OCTET STRING


    ACCESS read-only


    STATUS mandatory


    DESCRIPTION "value, level three"


    ::= { rdn3 2 }





rdn4 OBJECT IDENTIFIER ::= { rdnValues 4 }





classId4 OBJECT-TYPE


    SYNTAX INTEGER


    ACCESS read-only


    STATUS mandatory


    DESCRIPTION "object class, level four"


    ::= { rdn4 1 }


rdnValue4 OBJECT-TYPE


    SYNTAX OCTET STRING


    ACCESS read-only


    STATUS mandatory


    DESCRIPTION "value, level four"


    ::= { rdn4 2 }





rdn5 OBJECT IDENTIFIER ::= { rdnValues 5 }





classId5 OBJECT-TYPE


    SYNTAX INTEGER


    ACCESS read-only


    STATUS mandatory


    DESCRIPTION "object class, level five"


    ::= { rdn5 1 }


rdnValue5 OBJECT-TYPE


    SYNTAX OCTET STRING


    ACCESS read-only


    STATUS mandatory


    DESCRIPTION "value, level five"


    ::= { rdn5 2 }





eventTime OBJECT-TYPE


    SYNTAX OCTET STRING


    ACCESS read-only


    STATUS mandatory


    DESCRIPTION


	"date and time of detection of the notification


	by the managed system"


    ::= { cmipEventArg 3 }





eventType OBJECT-TYPE


    SYNTAX INTEGER {


        communicationAlarm (2),


        environmentalAlarm (3),


        equipmentAlarm (4),


        processingErrorAlarm (10),


        qualityOfServiceAlarm (11)


    }


    ACCESS read-only


    STATUS mandatory


    DESCRIPTION


	"OSI type of the notification"


    ::= { cmipEventArg 4 }





severity OBJECT-TYPE


    SYNTAX INTEGER {


        indeterminate (1),


        critical (2),


        major (3),


        minor (4),


        warning (5),


        clear (6)


    }


    ACCESS read-only


    STATUS mandatory


    DESCRIPTION


	"OSI severity of the notification"


    ::= { cmipEventArg 5 }





probableCause OBJECT-TYPE


    SYNTAX INTEGER {


	unknown (0),


	adaptererror (1),


	applicationsubsystemfailure (2),


	bandwidthreduced (3),


	callestablishmenterror (4),


	communicationsprotocolerror (5),


	communicationssubsystemfailure (6),


	configurationorcustomizationerror (7),


	congestion (8),


	corruptdata (9),


	cpucycleslimitexceeded (10),


	datasetormodemerror (11),


	degradedsignal (12),


	dtedceinterfaceerror (13),


	enclosuredooropen (14),


	equipmentmalfunction (15),


	excessivevibration (16),


	fileerror (17),


	firedetected (18),


	flooddetected (19),


	framingerror (20),


	heatingventilationcoolingsystemproblem (21),


	humidityunacceptable (22),


	inputoutputdeviceerror (23),


	inputdeviceerror (24),


	lanerror (25),


	leakdetected (26),


	localnodetransmissionerror (27),


	lossofframe (28),


	lossofsignal (29),


	materialsupplyexhausted (30),


	multiplexerproblem (31),


	outofmemory (32),


	outputdeviceerror (33),


	performancedegraded (34),


	powerproblem (35),


	pressureunacceptable (36),


	processorproblem (37),


	pumpfailure (38),


	queuesizeexceeded (39),


	receivefailure (40),


	receiverfailure (41),


	remotenodetransmissionfailure (42),


	resourceatornearingcapacity (43),


	responsetimeexcessive (44),


	retransmissionrateexcessive (45),


	softwareerror (46),


	softwareprogramabnormallyterminated (47),


	softwareprogramerror (48),


	storagecapacityproblem (49),


	temperatureunacceptable (50),


	thresholdcrossed (51),


	timingproblem (52),


	toxicleakdetected (53),


	transmitfailure (54),


	transmitterfailure (55),


	underlyingresourceunavailable (56),


	versionmismatch (57)


    }


    ACCESS read-only


    STATUS mandatory


    DESCRIPTION


	"probable cause of the notification"


    ::= { cmipEventArg 6 }





voiceIds OBJECT IDENTIFIER ::= { objectInstance 4 }





objectNumber OBJECT-TYPE


    SYNTAX INTEGER


    ACCESS read-only


    STATUS optional


    DESCRIPTION "Object numeric identifier"


    ::= { voiceIds 1 }





parentNumber OBJECT-TYPE


    SYNTAX INTEGER


    ACCESS read-only


    STATUS optional


    DESCRIPTION "Parent object numeric identifier"


    ::= { voiceIds 2 }





packedForm OBJECT-TYPE


    SYNTAX OCTET STRING


    ACCESS read-only


    STATUS mandatory


    DESCRIPTION


	"contains the packed form of a part (or all) of the arguments


	of a CMIP notification"


    ::= { cmipEventArg 7 }





notificationId OBJECT-TYPE


    SYNTAX INTEGER


    ACCESS read-only


    STATUS mandatory


    DESCRIPTION


	"number that permits the exact identification of the


	alarm that occured"


    ::= { cmipEventArg 8 }





addText OBJECT-TYPE


    SYNTAX OCTET STRING


    ACCESS read-only


    STATUS optional


    DESCRIPTION


	"contains text information"


    ::= { cmipEventArg 9 }





packedCmipTrap TRAP-TYPE


    ENTERPRISE nmcProxyTraps


    VARIABLES { openViewSeverity, packedForm }


    DESCRIPTION 


	"packed forwarded trap :


	contains a part (or all) of the arguments of the CMIP notification


	inside one variable binding.


	The arguments are selected with the NMC.


	This form suits well to a simple display of informations.


	HP OpenView Display=> Packed form: $2"


    ::= 1





startOfResyncTrap TRAP-TYPE


    ENTERPRISE nmcProxyTraps


    DESCRIPTION 


	"start of resynchronization :


	this trap announces the beginning of the reemission of all


	the traps corresponding to the active alarms of


	the managed nodes.


	HP OpenView Display=> Start of resynchronization: $*"


    ::= 2





cmipTrap TRAP-TYPE


    ENTERPRISE nmcProxyTraps


    VARIABLES { topClass, baseClass, rdnDepth, classId1, rdnValue1, classId2, rdnValue2, classId3, rdnValue3, classId4, rdnValue4, classId5, rdnValue5, eventTime, eventType, severity, probableCause, notificationId, addText }


    DESCRIPTION 


	"developped form trap :


	contains all arguments of the CMIP notification, each of them


	is placed in one independant variable binding.


	This form suits well for the processing of informations on


	a supervision station in a view to build an application,


	like a topology presentation and animation.


	HP OpenView Display=> Top class: $1 | Base Class: $2 | Hierarchy height: $3 | ClassId: $4-$6-$8-$10-$12 Values: $5-$7-$9-$11-$13 | Date: $14 | Event type: $15 | Severity: $16 | Probable cause: $17 | Notification ID: $18 | Add Text: $19"


    ::= 3





startProxyTrap TRAP-TYPE


    ENTERPRISE nmcProxyTraps


    DESCRIPTION 


	"proxy started :


	this trap announces that a proxy has just been started


	HP OpenView Display=> Start of NMC proxy $A"


    ::= 4





stopProxyTrap TRAP-TYPE


    ENTERPRISE nmcProxyTraps


    DESCRIPTION 


	"proxy stopped :


	this trap announces that a proxy has just been stopped


	HP OpenView Display=> End of proxy: $A"


    ::= 5





eventLostTrap TRAP-TYPE


    ENTERPRISE nmcProxyTraps


    DESCRIPTION 


	"event lost :


	this trap announces that a proxy didn't succeed to send all


	events and that the operator should perform a resynchronization.


	HP OpenView Display=> Event lost from $A"


    ::= 6





topClassStateTrap TRAP-TYPE


    ENTERPRISE nmcProxyTraps


    VARIABLES { classId1, rdnValue1, severity, objectNumber, parentNumber }


    DESCRIPTION 


	"state trap :


	contains arguments that describe the current state of a top class


	object.


	HP OpenView Display=> Voice element $2 of class $1 has state $3"


    ::= 7





END
