OSBRiDGE5XLi-MIB DEFINITIONS ::= BEGIN

IMPORTS
    DisplayString
	FROM SNMPv2-TC
	IpAddress, OBJECT-TYPE FROM SNMPv2-SMI;



org            OBJECT IDENTIFIER ::= { iso 3 }
dod            OBJECT IDENTIFIER ::= { org 6 }
internet       OBJECT IDENTIFIER ::= { dod 1 }
directory      OBJECT IDENTIFIER ::= { internet 1 }
mgmt           OBJECT IDENTIFIER ::= { internet 2 }
mib-2          OBJECT IDENTIFIER ::= { mgmt 1 }
transmission   OBJECT IDENTIFIER ::= { mib-2 10 }
experimental   OBJECT IDENTIFIER ::= { internet 3 }
private        OBJECT IDENTIFIER ::= { internet 4 }
enterprises    OBJECT IDENTIFIER ::= { private 1 }
security       OBJECT IDENTIFIER ::= { internet 5 }
snmpV2         OBJECT IDENTIFIER ::= { internet 6 }
snmpDomains    OBJECT IDENTIFIER ::= { snmpV2 1 }
snmpProxys     OBJECT IDENTIFIER ::= { snmpV2 2 }
snmpModules    OBJECT IDENTIFIER ::= { snmpV2 3 }

osbridge      OBJECT IDENTIFIER ::= { enterprises 19025 }
pxlimib       OBJECT IDENTIFIER ::= { osbridge 1 }
pxliSys       OBJECT IDENTIFIER ::= {pxlimib 1}
wireless      OBJECT IDENTIFIER ::= {pxlimib 2}
traps         OBJECT IDENTIFIER ::= {pxlimib 3 }

sysDevInfGRP     OBJECT IDENTIFIER ::= {pxliSys 1}

sysDevType OBJECT-TYPE
    	SYNTAX  OCTET STRING (SIZE (32))
    	ACCESS  read-only
    	STATUS  mandatory
       	DESCRIPTION
        "."
	::= { sysDevInfGRP 1 } 

sysMACAddr OBJECT-TYPE
	SYNTAX  OCTET STRING (SIZE (12))
	ACCESS  read-only
	STATUS  mandatory
	DESCRIPTION       
	"." 
	::= { sysDevInfGRP 2 } 

sysFirmVer OBJECT-TYPE
	SYNTAX  OCTET STRING (SIZE (6))
	ACCESS read-only
	STATUS mandatory
	DESCRIPTION
	"."
	::= {sysDevInfGRP 3}

sysHarRev OBJECT-TYPE
	SYNTAX INTEGER
	ACCESS  read-only
	STATUS  mandatory
	DESCRIPTION       
	"." 
	::= { sysDevInfGRP 4 }

sysRegDom OBJECT-TYPE
	SYNTAX INTEGER {europe(1), usa(2), ukofcomfwa(3), fareastafrica(4)}
	ACCESS read-write
	STATUS mandatory
	DESCRIPTION	 
	"."
	::= {sysDevInfGRP 5 }

sysConnInfGRP OBJECT IDENTIFIER ::= {pxliSys 2}

sysConnect OBJECT-TYPE
	SYNTAX INTEGER {connected(1), notconnected(0)}
	ACCESS  read-only
	STATUS  mandatory
	DESCRIPTION       
	"." 
	::= { sysConnInfGRP 1 } 
                   
sysRemoteBSSID OBJECT-TYPE
	SYNTAX  OCTET STRING (SIZE (24))
	ACCESS  read-only
	STATUS  mandatory
	DESCRIPTION       
	"." 
	::= { sysConnInfGRP 2 } 

sysSigStr OBJECT-TYPE
	SYNTAX  INTEGER
	ACCESS  read-only
	STATUS  mandatory
	DESCRIPTION       
	"." 
	::= { sysConnInfGRP 3 } 

sysNoise OBJECT-TYPE
	SYNTAX  INTEGER
	ACCESS  read-only
	STATUS  mandatory
	DESCRIPTION       
	"." 
	::= { sysConnInfGRP 4 } 

sysOperRate OBJECT-TYPE
	SYNTAX  OCTET STRING (SIZE (24))
	ACCESS  read-only
	STATUS  mandatory
	DESCRIPTION       
	"." 
	::= { sysConnInfGRP 5 } 
	
sysTxPack OBJECT-TYPE
	SYNTAX  OCTET STRING (SIZE (24))
	ACCESS  read-only
	STATUS  mandatory
	DESCRIPTION       
	"." 
	::= { sysConnInfGRP 7 } 

sysTxByte OBJECT-TYPE
	SYNTAX  OCTET STRING (SIZE (24))
	ACCESS  read-only
	STATUS  mandatory
	DESCRIPTION       
	"." 
	::= { sysConnInfGRP 8 } 

sysRxPack OBJECT-TYPE
	SYNTAX  OCTET STRING (SIZE (24))
	ACCESS  read-only
	STATUS  mandatory
	DESCRIPTION       
	"." 
	::= { sysConnInfGRP 9 } 

sysRxByte OBJECT-TYPE
	SYNTAX  OCTET STRING (SIZE (24))
	ACCESS  read-only
	STATUS  mandatory
	DESCRIPTION       
	"." 
	::= { sysConnInfGRP 10 }

sysEthSpeed OBJECT-TYPE
	SYNTAX  INTEGER
	ACCESS  read-write
	STATUS  mandatory
	DESCRIPTION       
	"." 
	::= { sysConnInfGRP 11 }

sysChaWidh OBJECT-TYPE
	SYNTAX  INTEGER
	ACCESS  read-write
	STATUS  mandatory
	DESCRIPTION       
	"." 
	::= { sysConnInfGRP 12 }
	 
sysOperSettGRP OBJECT IDENTIFIER ::= {pxliSys 3}

sysDevNam OBJECT-TYPE
    	SYNTAX  OCTET STRING (SIZE (32))
    	ACCESS  read-write    
    	STATUS  mandatory
    	DESCRIPTION
    	"."
    	::= {sysOperSettGRP 1 } 
	      
sysWlanOperMode OBJECT-TYPE
    	SYNTAX  INTEGER {infrastructureclient(0), pollingclient(1)}
    	ACCESS  read-write    
    	STATUS  mandatory
    	DESCRIPTION
    	"."
    	::= {sysOperSettGRP 2 } 
	    
sysTurboMode OBJECT-TYPE
	SYNTAX INTEGER {n80211a(0), n80211aTurbo(1)}  
	ACCESS read-write
	STATUS mandatory
	DESCRIPTION	 
	"."
	::= {sysOperSettGRP 3 }	    
   
sysIpOperMode OBJECT-TYPE
    	SYNTAX  INTEGER {bridge(1), router(2), nat-router(3)}
    	ACCESS  read-write    
    	STATUS  mandatory
    	DESCRIPTION
    	"."
    	::= {sysOperSettGRP 4 } 	
	 
sysUptime OBJECT-TYPE
    	SYNTAX  OCTET STRING (SIZE (32))
    	ACCESS  read-only    
    	STATUS  mandatory
    	DESCRIPTION
    	"."
    	::= {sysOperSettGRP 5 } 
    
sysLoad OBJECT-TYPE
    	SYNTAX  OCTET STRING (SIZE (32))
    	ACCESS  read-only    
    	STATUS  mandatory
    	DESCRIPTION
    	"."
    	::= {sysOperSettGRP 6 }

sysESSID OBJECT-TYPE
    	SYNTAX  OCTET STRING (SIZE (32))
    	ACCESS  read-write   
    	STATUS  mandatory
    	DESCRIPTION
    	"."
    	::= {sysOperSettGRP 7 }

sysFrequency OBJECT-TYPE
	SYNTAX	INTEGER  
	ACCESS read-only
	STATUS mandatory
	DESCRIPTION	 
	"."
	::= {sysOperSettGRP 8 }

sysPrefBSSID OBJECT-TYPE
    	SYNTAX  OCTET STRING (SIZE (32))
    	ACCESS  read-write    
    	STATUS  mandatory
    	DESCRIPTION
    	"."
    	::= {sysOperSettGRP 9 }	
 	   
sysPPPoEAuthorization OBJECT-TYPE
	SYNTAX	INTEGER  {disabled(0), enabled(1)}
	ACCESS read-write
	STATUS mandatory
	DESCRIPTION	 
	"."
	::= {sysOperSettGRP 11 }		    
	
sysPPPoELinkStatus OBJECT-TYPE
	SYNTAX	INTEGER  {notconnected(0), connected(1)}
	ACCESS read-only
	STATUS mandatory
	DESCRIPTION	 
	"."
	::= {sysOperSettGRP 12 }		    	

sysRTSThreshold OBJECT-TYPE
	SYNTAX	INTEGER  
	ACCESS read-write
	STATUS mandatory
	DESCRIPTION	 
	"."
	::= {sysOperSettGRP 13 }	
	
sysFragmenationThreshold OBJECT-TYPE
	SYNTAX	INTEGER  
	ACCESS read-write
	STATUS mandatory
	DESCRIPTION	 
	"."
	::= {sysOperSettGRP 14 }	    	
	    
sysSupportedDataRates OBJECT-TYPE
    	SYNTAX  OCTET STRING (SIZE (128))
    	ACCESS  read-only    
    	STATUS  mandatory
    	DESCRIPTION
    	"."
    	::= {sysOperSettGRP 15 }		    
	    
sysSupportedFrequencies OBJECT-TYPE
    	SYNTAX  OCTET STRING (SIZE (128))
    	ACCESS  read-only    
    	STATUS  mandatory
    	DESCRIPTION
    	"."
    	::= {sysOperSettGRP 16 }		    
  
sysDistancetotheAP OBJECT-TYPE
	SYNTAX	INTEGER  
	ACCESS read-write
	STATUS mandatory
	DESCRIPTION	 
	"."
	::= {sysOperSettGRP 17 }

sysWlanSpeed OBJECT-TYPE
    	SYNTAX  INTEGER {sAuto(0),s54Mbsps(1),s48Mbps(2),s36Mbps(3),s24Mbps(4),s18Mbps(5),s12Mbps(6),s9Mbps(7),s6Mbps(8)}
    	ACCESS  read-write    
    	STATUS  mandatory
    	DESCRIPTION
    	"."
    	::= {sysOperSettGRP 18 }	

sysWLANIPAddr OBJECT-TYPE
	SYNTAX	IpAddress  
	ACCESS read-only
	STATUS mandatory
	DESCRIPTION	 
	"."
	::= {sysOperSettGRP 19 }
 
sysWLANIPMask OBJECT-TYPE
	SYNTAX	IpAddress  
	ACCESS read-only
	STATUS mandatory
	DESCRIPTION	 
	"."
	::= {sysOperSettGRP 20 }
	
sysETHIPAddr OBJECT-TYPE
	SYNTAX	IpAddress  
	ACCESS read-write
	STATUS mandatory
	DESCRIPTION	 
	"."
	::= {sysOperSettGRP 21 }

sysETHIPMask OBJECT-TYPE
	SYNTAX	IpAddress  
	ACCESS read-write
	STATUS mandatory
	DESCRIPTION	 
	"."
	::= {sysOperSettGRP 22 }

sysDefGat OBJECT-TYPE
	SYNTAX	IpAddress  
	ACCESS read-write
	STATUS mandatory
	DESCRIPTION	 
	"."
	::= {sysOperSettGRP 23 }		

sysDHCP OBJECT-TYPE
	SYNTAX INTEGER {disabled(0), enabled(1)}
	ACCESS read-write
	STATUS mandatory
	DESCRIPTION	 
	"."
	::= {sysOperSettGRP 24 }								
		
sysTrafficShaping OBJECT-TYPE
	SYNTAX INTEGER {disabled(0), enabled(1)}
	ACCESS read-write
	STATUS mandatory
	DESCRIPTION	 
	"."
	::= {sysOperSettGRP 25 }						
		
sysFirewall OBJECT-TYPE
	SYNTAX INTEGER {disabled(0), enabled(1)}
	ACCESS read-write
	STATUS mandatory
	DESCRIPTION	 
	"."
	::= {sysOperSettGRP 26 }				
		
sysWebPort OBJECT-TYPE
	SYNTAX INTEGER
	ACCESS read-write
	STATUS mandatory
	DESCRIPTION	 
	"."
	::= {sysOperSettGRP 27 }		
		
sysWatchdog OBJECT-TYPE
	SYNTAX INTEGER  {disabled(0), enabled(1)}  
	ACCESS read-write
	STATUS mandatory
	DESCRIPTION	 
	"."
	::= {sysOperSettGRP 32 }
		
sysWatchdogIp OBJECT-TYPE
	SYNTAX	IpAddress  
	ACCESS read-write
	STATUS mandatory
	DESCRIPTION	 
	"."
	::= {sysOperSettGRP 33 }

sysWebTimeout OBJECT-TYPE
	SYNTAX INTEGER
	ACCESS read-write
	STATUS mandatory
	DESCRIPTION	 
	"."
	::= {sysOperSettGRP 34 }

sysTxPower OBJECT-TYPE
	SYNTAX INTEGER  {full(0), half(1), quarter(2), eight(3)}  
	ACCESS read-write
	STATUS mandatory
	DESCRIPTION	 
	"."
	::= {sysOperSettGRP 35 }

sysWepEnc OBJECT-TYPE
	SYNTAX INTEGER
	ACCESS read-write
	STATUS mandatory
	DESCRIPTION	 
	"."
	::= {sysOperSettGRP 39 }
	
sysall OBJECT-TYPE
    	SYNTAX  OCTET STRING (SIZE (512))
    	ACCESS  read-write    
    	STATUS  mandatory
    	DESCRIPTION
    	"."
    	::= {sysOperSettGRP 40 }
		
	
sysChangeSettGRP OBJECT IDENTIFIER ::= {pxliSys 5}
		
sysApplyCfg OBJECT-TYPE
	SYNTAX INTEGER
	ACCESS read-write
	STATUS mandatory
	DESCRIPTION	 
	"."
	::= {sysChangeSettGRP 1 }

sysReboot OBJECT-TYPE
	SYNTAX INTEGER
	ACCESS read-write
	STATUS mandatory
	DESCRIPTION
	"."
	::= {sysChangeSettGRP 2 }

END
