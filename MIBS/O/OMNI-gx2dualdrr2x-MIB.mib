OMNI-gx2dualdrr2x-MIB DEFINITIONS ::= BEGIN

    IMPORTS
	IpAddress, TimeTicks, Counter            
					      FROM RFC1155-SMI
	
	OBJECT-TYPE                     
					      FROM RFC-1212
	DisplayString        
					      FROM RFC1213-MIB
	TRAP-TYPE                       
					      FROM RFC-1215
	gx2DualDrr2x
					      FROM GX2HFC-MIB

	trapIdentifier,trapNetworkElemModelNumber,
	trapNetworkElemSerialNum, trapPerceivedSeverity,
	trapNetworkElemOperState, trapNetworkElemAlarmStatus,
	trapNetworkElemAdminState, trapNetworkElemAvailStatus,
	trapText, trapNETrapLastTrapTimeStamp, trapChangedObjectId,
	trapChangedValueInteger, trapChangedValueDisplayString
					      FROM NLSBBN-TRAPS-MIB;



	       -- This MIB module uses the extended OBJECT-TYPE macro as
	       -- defined in RFC1212 and the TRAP-TYPE macro as defined
	       -- in RFC 1215.

      -- ********************************************************************************
      -- *                                                                              *  
      -- * REVISION history:                                                            *
      -- *	      MIB at Rev 0 to support Firmware at Rev A3 and below, May 31, 2012    * 
      -- *	      MIB at Rev 1 to support Firmware at Rev B, June 9 2012                * 
      -- *                                                                              *
      -- ********************************************************************************

	-- OMNISTAR Digital Receiver Return 2X Module MIB MODULE

	-- This MIB module defines information for management of HFC networks
		-- 
		-- The MIB module assumes that all generic (static) network element
		-- information is defined in a different module such as the HFC module
		-- The MIB consists of two groups:
		-- the device type descriptor subgroup and 
		-- gx2dualdrr2x Network Elements subgroup.
		-- The device type descriptor subgroup is used to define 
		-- parameters specific to gx2dualdrr2x device type.
		-- These parameters are common across all network elements
		-- from gx2dualdrr2x device type.
		--
		-- The gx2dualdrr2x Network Elements subgroup is
		-- a list of gx2dualdrr2x type elements in the
		-- current network topology with nominal
		-- and current parameter values for the
		-- individual network elements; the individual
		-- network elements are identified by  
		-- index from hfcCommonTable.
		-- That implies the hfcCommonTableIndex and
		-- gx2dualdrr2xTableIndex are equal for each individual
		-- network element.
		-- This table is an extension of the hfcCommonTable
		-- for all elements of gx2dualdrr2x type.
		--
		-- Both groups are mandatory for management of gx2dualdrr2x devices.

-- ****************************************************************************
		--
		-- All floating point numbers will be represented by an IEEE 32 Bit number.
		-- Conversion of this number must be done on the user interface to view the 
		-- actual floating point number. 
		--

		Float ::= Counter  -- UNSIGNED (32 BITS) 

-- ****************************************************************************

		-- gx2dualdrr2x Device Descriptor subgroup.

		-- The device type descriptor subgroup is used to define 
		-- parameters specific to gx2dualdrr2x device type.
		-- These parameters are common across all network elements
		-- from gx2dualdrr2x device type.


		 gx2dualdrr2xDescriptor OBJECT IDENTIFIER ::= {gx2DualDrr2x 1}



--*****************************************************************************
		--              gx2dualdrr2x Table
		
		--
		-- The individual network elements indentified by  
		-- index from hfcCommonTable.
		-- That implies what hfcCommonTableIndex and
		-- gx2dualdrr2xTableIndex are equal for each individual
		-- nettwork element.
		-- This table should be used as an extension of the hfcCommonTable
		-- for all elements of gx2dualdrr2x type.

	-- ANALOG TABLE:
	-- Analog table hold analog parameters. 
	--    For each analog parameter, there are following alarm limits:
      --       major high, major low, minor high and minor low.
      --    Firmware use these limits to determine alarm related to this parameter. Based on 
	--    individual parameter, certain alarm limit may not be populated.   
      --    For the unused entry, this MIB provides the following comment:
 	--    "This object is not used by this module and always returns invalid float value 
	--	of 0xFFFFFFFF . This object is kept here for persistence." 

	       gx2dualdrr2xAnalogTable                    OBJECT-TYPE
			 SYNTAX             SEQUENCE OF Gx2dualdrr2xAnalogEntry
			 ACCESS             not-accessible
			 STATUS             mandatory
			 DESCRIPTION
			 "This table contains gx2dualdrr2x specific analog parameters with
			  nominal,limits and current values."
			 ::= { gx2DualDrr2x 2 }


	       gx2dualdrr2xAnalogEntry               OBJECT-TYPE
			 SYNTAX             Gx2dualdrr2xAnalogEntry
			 ACCESS             not-accessible
			 STATUS             mandatory
			 DESCRIPTION
			 "This list contains the analog parameters and descriptions."
			 INDEX { gx2dualdrr2xAnalogTableIndex }
			 ::= { gx2dualdrr2xAnalogTable  1}

--*****************************************************************************
	       gx2dualdrr2xDigitalTable                    OBJECT-TYPE
			 SYNTAX             SEQUENCE OF Gx2dualdrr2xDigitalEntry
			 ACCESS             not-accessible
			 STATUS             mandatory
			 DESCRIPTION
			 "This table contains gx2dualdrr2x specific digital parameters with
			  nominal and current values."
			 ::= { gx2DualDrr2x 3 }

	       gx2dualdrr2xDigitalEntry               OBJECT-TYPE
			 SYNTAX             Gx2dualdrr2xDigitalEntry
			 ACCESS             not-accessible
			 STATUS             mandatory
			 DESCRIPTION
			 "This list contains individual digital parameters and descriptions."
			 INDEX { gx2dualdrr2xDigitalTableIndex }
			 ::= { gx2dualdrr2xDigitalTable  2}

--*****************************************************************************
	       gx2dualdrr2xStatusTable                    OBJECT-TYPE
			 SYNTAX             SEQUENCE OF Gx2dualdrr2xStatusEntry
			 ACCESS             not-accessible
			 STATUS             mandatory
			 DESCRIPTION
			 "This table contains gx2dualdrr2x specific status parameters with
			  nominal and current values."
			 ::= { gx2DualDrr2x 4 }

	       gx2dualdrr2xStatusEntry               OBJECT-TYPE
			 SYNTAX             Gx2dualdrr2xStatusEntry
			 ACCESS             not-accessible
			 STATUS             mandatory
			 DESCRIPTION
			 "This list contains Status parameters and descriptions."
			 INDEX { gx2dualdrr2xStatusTableIndex }
			 ::= { gx2dualdrr2xStatusTable  3}

--*****************************************************************************
	       gx2dualdrr2xFactoryTable                    OBJECT-TYPE
			 SYNTAX             SEQUENCE OF Gx2dualdrr2xFactoryEntry
			 ACCESS             not-accessible
			 STATUS             mandatory
			 DESCRIPTION
			 "This table contains gx2dualdrr2x specific factory setting parameters with
			  nominal and current values."
			 ::= { gx2DualDrr2x 5 }

	       gx2dualdrr2xFactoryEntry               OBJECT-TYPE
			 SYNTAX             Gx2dualdrr2xFactoryEntry
			 ACCESS             not-accessible
			 STATUS             mandatory
			 DESCRIPTION
			 "This list contains Factory setting parameters and descriptions."
			 INDEX { gx2dualdrr2xFactoryTableIndex }
			 ::= { gx2dualdrr2xFactoryTable  4}

--************************* ANALOG PARAMETERS ****************************************************


	      Gx2dualdrr2xAnalogEntry    ::= SEQUENCE  
	       {
		gx2dualdrr2xAnalogTableIndex      		INTEGER,
 		
		dualdrr2xlabelRecdOptPwr1			DisplayString (SIZE (0..80)),
		dualdrr2xuomRecdOptPwr1				DisplayString (SIZE (0..80)),
		dualdrr2xmajorHighRecdOptPwr1		Float,
		dualdrr2xmajorLowRecdOptPwr1		Float, 
		dualdrr2xminorHighRecdOptPwr1		Float,
		dualdrr2xminorLowRecdOptPwr1		Float, 
		dualdrr2xcurrentValueRecdOptPwr1	Float, 
		dualdrr2xstateFlagRecdOptPwr1		INTEGER,
		dualdrr2xminValueRecdOptPwr1		Float,
		dualdrr2xmaxValueRecdOptPwr1 		Float,
		dualdrr2xalarmStateRecdOptPwr1		INTEGER,
		
		dualdrr2xlabelRecdOptPwr2			DisplayString (SIZE (0..80)),
		dualdrr2xuomRecdOptPwr2				DisplayString (SIZE (0..80)),
		dualdrr2xmajorHighRecdOptPwr2		Float,
		dualdrr2xmajorLowRecdOptPwr2		Float, 
		dualdrr2xminorHighRecdOptPwr2		Float,
		dualdrr2xminorLowRecdOptPwr2		Float, 
		dualdrr2xcurrentValueRecdOptPwr2	Float, 
		dualdrr2xstateFlagRecdOptPwr2		INTEGER,
		dualdrr2xminValueRecdOptPwr2		Float,
		dualdrr2xmaxValueRecdOptPwr2 		Float,
		dualdrr2xalarmStateRecdOptPwr2		INTEGER,
		
		dualdrr2xlabelModTemp			    	DisplayString (SIZE (0..80)),
		dualdrr2xuomModTemp						DisplayString (SIZE (0..80)),
		dualdrr2xmajorHighModTemp				Float, 
		dualdrr2xmajorLowModTemp				Float, 
		dualdrr2xminorHighModTemp				Float,
		dualdrr2xminorLowModTemp				Float, 
		dualdrr2xcurrentValueModTemp			Float, 
		dualdrr2xstateFlagModTemp				INTEGER,
		dualdrr2xminValueModTemp				Float,
		dualdrr2xmaxValueModTemp				Float,
		dualdrr2xalarmStateModTemp				INTEGER,    
			
		dualdrr2xlabel12VCurrent				DisplayString (SIZE (0..80)),
		dualdrr2xuom12VCurrent					DisplayString (SIZE (0..80)),
		dualdrr2xmajorHigh12VCurrent			Float, 
		dualdrr2xmajorLow12VCurrent				Float, 
		dualdrr2xminorHigh12VCurrent			Float,
		dualdrr2xminorLow12VCurrent				Float, 
		dualdrr2xcurrentValue12VCurrent			Float, 
		dualdrr2xstateFlag12VCurrent			INTEGER,
		dualdrr2xminValue12VCurrent				Float,
		dualdrr2xmaxValue12VCurrent 			Float,
		dualdrr2xalarmState12VCurrent			INTEGER, 
		
		dualdrr2xlabelFanSpeed					DisplayString (SIZE (0..80)),
		dualdrr2xuomFanSpeed					DisplayString (SIZE (0..80)),
		dualdrr2xmajorHighFanSpeed				Float, 
		dualdrr2xmajorLowFanSpeed				Float, 
		dualdrr2xminorHighFanSpeed				Float,
		dualdrr2xminorLowFanSpeed				Float, 
		dualdrr2xcurrentValueFanSpeed			Float, 
		dualdrr2xstateFlagFanSpeed				INTEGER,
		dualdrr2xminValueFanSpeed				Float,
		dualdrr2xmaxValueFanSpeed 				Float,
		dualdrr2xalarmStateFanSpeed				INTEGER,
				
		dualdrr2xlabelTx0SFPWave				DisplayString (SIZE (0..80)),
		dualdrr2xuomTx0SFPWave					DisplayString (SIZE (0..80)),
		dualdrr2xmajorHighTx0SFPWave			Float, 
		dualdrr2xmajorLowTx0SFPWave				Float, 
		dualdrr2xminorHighTx0SFPWave			Float,
		dualdrr2xminorLowTx0SFPWave				Float, 
		dualdrr2xcurrentValueTx0SFPWave			Float, 
		dualdrr2xstateFlagTx0SFPWave			INTEGER,
		dualdrr2xminValueTx0SFPWave				Float,
		dualdrr2xmaxValueTx0SFPWave 			Float,
		dualdrr2xalarmStateTx0SFPWave			INTEGER,
				
		dualdrr2xlabelTx0OptPwr					DisplayString (SIZE (0..80)),
		dualdrr2xuomTx0OptPwr					DisplayString (SIZE (0..80)),
		dualdrr2xmajorHighTx0OptPwr				Float, 
		dualdrr2xmajorLowTx0OptPwr				Float, 
		dualdrr2xminorHighTx0OptPwr				Float,
		dualdrr2xminorLowTx0OptPwr				Float, 
		dualdrr2xcurrentValueTx0OptPwr			Float, 
		dualdrr2xstateFlagTx0OptPwr				INTEGER,
		dualdrr2xminValueTx0OptPwr				Float,
		dualdrr2xmaxValueTx0OptPwr 				Float,
		dualdrr2xalarmStateTx0OptPwr			INTEGER,
				
		dualdrr2xlabelTx024vCurr				DisplayString (SIZE (0..80)),
		dualdrr2xuomTx024vCurr					DisplayString (SIZE (0..80)),
		dualdrr2xmajorHighTx024vCurr			Float, 
		dualdrr2xmajorLowTx024vCurr				Float, 
		dualdrr2xminorHighTx024vCurr			Float,
		dualdrr2xminorLowTx024vCurr				Float, 
		dualdrr2xcurrentValueTx024vCurr			Float, 
		dualdrr2xstateFlagTx024vCurr			INTEGER,
		dualdrr2xminValueTx024vCurr				Float,
		dualdrr2xmaxValueTx024vCurr 			Float,
		dualdrr2xalarmStateTx024vCurr			INTEGER,
				
		dualdrr2xlabelTx024Volt					DisplayString (SIZE (0..80)),
		dualdrr2xuomTx024Volt					DisplayString (SIZE (0..80)),
		dualdrr2xmajorHighTx024Volt				Float, 
		dualdrr2xmajorLowTx024Volt				Float, 
		dualdrr2xminorHighTx024Volt				Float,
		dualdrr2xminorLowTx024Volt				Float, 
		dualdrr2xcurrentValueTx024Volt			Float, 
		dualdrr2xstateFlagTx024Volt				INTEGER,
		dualdrr2xminValueTx024Volt				Float,
		dualdrr2xmaxValueTx024Volt 				Float,
		dualdrr2xalarmStateTx024Volt			INTEGER,
				
		dualdrr2xlabelTx0ModTemp				DisplayString (SIZE (0..80)),
		dualdrr2xuomTx0ModTemp					DisplayString (SIZE (0..80)),
		dualdrr2xmajorHighTx0ModTemp			Float, 
		dualdrr2xmajorLowTx0ModTemp				Float, 
		dualdrr2xminorHighTx0ModTemp			Float,
		dualdrr2xminorLowTx0ModTemp				Float, 
		dualdrr2xcurrentValueTx0ModTemp			Float, 
		dualdrr2xstateFlagTx0ModTemp			INTEGER,
		dualdrr2xminValueTx0ModTemp				Float,
		dualdrr2xmaxValueTx0ModTemp 			Float,
		dualdrr2xalarmStateTx0ModTemp			INTEGER,
				
		dualdrr2xlabelTx1SFPWave				DisplayString (SIZE (0..80)),
		dualdrr2xuomTx1SFPWave					DisplayString (SIZE (0..80)),
		dualdrr2xmajorHighTx1SFPWave			Float, 
		dualdrr2xmajorLowTx1SFPWave				Float, 
		dualdrr2xminorHighTx1SFPWave			Float,
		dualdrr2xminorLowTx1SFPWave				Float, 
		dualdrr2xcurrentValueTx1SFPWave			Float, 
		dualdrr2xstateFlagTx1SFPWave			INTEGER,
		dualdrr2xminValueTx1SFPWave				Float,
		dualdrr2xmaxValueTx1SFPWave 			Float,
		dualdrr2xalarmStateTx1SFPWave			INTEGER,
				
		dualdrr2xlabelTx1OptPwr					DisplayString (SIZE (0..80)),
		dualdrr2xuomTx1OptPwr					DisplayString (SIZE (0..80)),
		dualdrr2xmajorHighTx1OptPwr				Float, 
		dualdrr2xmajorLowTx1OptPwr				Float, 
		dualdrr2xminorHighTx1OptPwr				Float,
		dualdrr2xminorLowTx1OptPwr				Float, 
		dualdrr2xcurrentValueTx1OptPwr			Float, 
		dualdrr2xstateFlagTx1OptPwr				INTEGER,
		dualdrr2xminValueTx1OptPwr				Float,
		dualdrr2xmaxValueTx1OptPwr 				Float,
		dualdrr2xalarmStateTx1OptPwr			INTEGER,
				
		dualdrr2xlabelTx124vCurr				DisplayString (SIZE (0..80)),
		dualdrr2xuomTx124vCurr					DisplayString (SIZE (0..80)),
		dualdrr2xmajorHighTx124vCurr			Float, 
		dualdrr2xmajorLowTx124vCurr				Float, 
		dualdrr2xminorHighTx124vCurr			Float,
		dualdrr2xminorLowTx124vCurr				Float, 
		dualdrr2xcurrentValueTx124vCurr			Float, 
		dualdrr2xstateFlagTx124vCurr			INTEGER,
		dualdrr2xminValueTx124vCurr				Float,
		dualdrr2xmaxValueTx124vCurr 			Float,
		dualdrr2xalarmStateTx124vCurr			INTEGER,
				
		dualdrr2xlabelTx124Volt					DisplayString (SIZE (0..80)),
		dualdrr2xuomTx124Volt					DisplayString (SIZE (0..80)),
		dualdrr2xmajorHighTx124Volt				Float, 
		dualdrr2xmajorLowTx124Volt				Float, 
		dualdrr2xminorHighTx124Volt				Float,
		dualdrr2xminorLowTx124Volt				Float, 
		dualdrr2xcurrentValueTx124Volt			Float, 
		dualdrr2xstateFlagTx124Volt				INTEGER,
		dualdrr2xminValueTx124Volt				Float,
		dualdrr2xmaxValueTx124Volt 				Float,
		dualdrr2xalarmStateTx124Volt			INTEGER,
				
		dualdrr2xlabelTx1ModTemp				DisplayString (SIZE (0..80)),
		dualdrr2xuomTx1ModTemp					DisplayString (SIZE (0..80)),
		dualdrr2xmajorHighTx1ModTemp			Float, 
		dualdrr2xmajorLowTx1ModTemp				Float, 
		dualdrr2xminorHighTx1ModTemp			Float,
		dualdrr2xminorLowTx1ModTemp				Float, 
		dualdrr2xcurrentValueTx1ModTemp			Float, 
		dualdrr2xstateFlagTx1ModTemp			INTEGER,
		dualdrr2xminValueTx1ModTemp				Float,
		dualdrr2xmaxValueTx1ModTemp 			Float,
		dualdrr2xalarmStateTx1ModTemp			INTEGER
				
		}

		-- ****************  Digital Parameters ***********************
	     Gx2dualdrr2xDigitalEntry    ::= SEQUENCE  
	     {
		gx2dualdrr2xDigitalTableIndex       	INTEGER,    
		               
        dualdrr2xlabelTrippoint1Value   		DisplayString (SIZE (0..80)),
		dualdrr2xenumTrippoint1Value 			DisplayString (SIZE (0..80)),
		dualdrr2xvalueTrippoint1Value 			INTEGER,
		dualdrr2xstateflagTrippoint1Value 		INTEGER,
		    							         
        dualdrr2xlabelTrippoint1Mode   			DisplayString (SIZE (0..80)),
		dualdrr2xenumTrippoint1Mode		    	DisplayString (SIZE (0..80)),
		dualdrr2xvalueTrippoint1Mode			INTEGER,
		dualdrr2xstateflagTrippoint1Mode    	INTEGER,
		    							         
        dualdrr2xlabelTrippoint2Value   		DisplayString (SIZE (0..80)),
		dualdrr2xenumTrippoint2Value 			DisplayString (SIZE (0..80)),
		dualdrr2xvalueTrippoint2Value 			INTEGER,
		dualdrr2xstateflagTrippoint2Value 		INTEGER,
		    							         
        dualdrr2xlabelTrippoint2Mode   			DisplayString (SIZE (0..80)),
		dualdrr2xenumTrippoint2Mode		    	DisplayString (SIZE (0..80)),
		dualdrr2xvalueTrippoint2Mode			INTEGER,
		dualdrr2xstateflagTrippoint2Mode    	INTEGER,
		    							         
        dualdrr2xlabelGainChannel1A   			DisplayString (SIZE (0..80)),
		dualdrr2xenumGainChannel1A		    	DisplayString (SIZE (0..80)),
		dualdrr2xvalueGainChannel1A				INTEGER,
		dualdrr2xstateflagGainChannel1A    		INTEGER,
		    							         
        dualdrr2xlabelGainChannel1B   			DisplayString (SIZE (0..80)),
		dualdrr2xenumGainChannel1B		    	DisplayString (SIZE (0..80)),
		dualdrr2xvalueGainChannel1B				INTEGER,
		dualdrr2xstateflagGainChannel1B    		INTEGER,
		    							         
        dualdrr2xlabelGainChannel2A   			DisplayString (SIZE (0..80)),
		dualdrr2xenumGainChannel2A		    	DisplayString (SIZE (0..80)),
		dualdrr2xvalueGainChannel2A				INTEGER,
		dualdrr2xstateflagGainChannel2A    		INTEGER,
		    							         
        dualdrr2xlabelGainChannel2B   			DisplayString (SIZE (0..80)),
		dualdrr2xenumGainChannel2B		    	DisplayString (SIZE (0..80)),
		dualdrr2xvalueGainChannel2B				INTEGER,
		dualdrr2xstateflagGainChannel2B    		INTEGER,
		    							         
        dualdrr2xlabelTestpointSelect           DisplayString (SIZE (0..80)),
		dualdrr2xenumTestpointSelect	    	DisplayString (SIZE (0..80)),
		dualdrr2xvalueTestpointSelect			INTEGER,
		dualdrr2xstateflagTestpointSelect  		INTEGER,
		    							         
        dualdrr2xlabelOpFrequency           	DisplayString (SIZE (0..80)),
		dualdrr2xenumOpFrequency	    		DisplayString (SIZE (0..80)),
		dualdrr2xvalueOpFrequency				INTEGER,
		dualdrr2xstateflagOpFrequency  		INTEGER,
		    							         
        dualdrr2xlabelActChanSelect           	DisplayString (SIZE (0..80)),
		dualdrr2xenumActChanSelect	    		DisplayString (SIZE (0..80)),
		dualdrr2xvalueActChanSelect				INTEGER,
		dualdrr2xstateflagActChanSelect  		INTEGER,
		    							         
		dualdrr2xlabelFactoryDefaultReset	    DisplayString (SIZE (0..80)),
		dualdrr2xenumFactoryDefaultReset		DisplayString (SIZE (0..80)),
		dualdrr2xvalueFactoryDefaultReset		INTEGER,
		dualdrr2xstateflagFactoryDefaultReset 	INTEGER                             
	    }

		-- ****************  Status Parameters ************************************
	     Gx2dualdrr2xStatusEntry    ::= SEQUENCE  
	     {
		gx2dualdrr2xStatusTableIndex      		INTEGER,

		dualdrr2xlabelBoot						DisplayString (SIZE (0..80)),
		dualdrr2xvalueBoot						INTEGER,
		dualdrr2xstateflagBoot					INTEGER,
		
		dualdrr2xlabelFlash						DisplayString (SIZE (0..80)),
		dualdrr2xvalueFlash						INTEGER,
		dualdrr2xstateflagFlash					INTEGER,

		dualdrr2xlabelFactoryDataCRC 			DisplayString (SIZE (0..80)),
		dualdrr2xvalueFactoryDataCRC			INTEGER,
		dualdrr2xstateflagFactoryDataCRC		INTEGER,

		dualdrr2xlabelAlarmDataCrc				DisplayString (SIZE (0..80)),
		dualdrr2xvalueAlarmDataCrc				INTEGER,
		dualdrr2xstateflagAlarmDataCrc			INTEGER,

		dualdrr2xlabelCalibrationDataCrc		DisplayString (SIZE (0..80)),
		dualdrr2xvalueCalibrationDataCrc		INTEGER,
		dualdrr2xstateflagCalibrationDataCrc	INTEGER,

		dualdrr2xlabelHardwareStatus			DisplayString (SIZE (0..80)),
		dualdrr2xvalueHardwareStatus			INTEGER,
		dualdrr2xstateflagHardwareStatus		INTEGER, 
	
		dualdrr2xlabelCh1TripPointStatus		DisplayString (SIZE (0..80)),
		dualdrr2xvalueCh1TripPointStatus		INTEGER,
		dualdrr2xstateflagCh1TripPointStatus	INTEGER,
			
		dualdrr2xlabelLink1Status               DisplayString (SIZE (0..80)),
		dualdrr2xvalueLink1Status	            INTEGER,
		dualdrr2xstateflagLink1Status			INTEGER,     

		dualdrr2xlabelCh2TripPointStatus		DisplayString (SIZE (0..80)),
		dualdrr2xvalueCh2TripPointStatus		INTEGER,
		dualdrr2xstateflagCh2TripPointStatus	INTEGER,
			
		dualdrr2xlabelLink2Status               DisplayString (SIZE (0..80)),
		dualdrr2xvalueLink2Status	            INTEGER,
		dualdrr2xstateflagLink2Status			INTEGER,     
			
		dualdrr2xlabelDRT1Status               DisplayString (SIZE (0..80)),
		dualdrr2xvalueDRT1Status	            INTEGER,
		dualdrr2xstateflagDRT1Status			INTEGER,     
			
		dualdrr2xlabelSFP0Status               DisplayString (SIZE (0..80)),
		dualdrr2xvalueSFP0Status	            INTEGER,
		dualdrr2xstateflagSFP0Status			INTEGER,     
			
		dualdrr2xlabelDRT2Status               DisplayString (SIZE (0..80)),
		dualdrr2xvalueDRT2Status	            INTEGER,
		dualdrr2xstateflagDRT2Status			INTEGER,     

		dualdrr2xlabelSFP1Status               DisplayString (SIZE (0..80)),
		dualdrr2xvalueSFP1Status	            INTEGER,
		dualdrr2xstateflagSFP1Status			INTEGER     
			
		}


		-- ****************  Factory Parameters *************************************
       Gx2dualdrr2xFactoryEntry    ::= SEQUENCE  
       {
		gx2dualdrr2xFactoryTableIndex       	INTEGER,
		dualdrr2xbootControlByte  				INTEGER,
		dualdrr2xbootStatusByte   				INTEGER,
		dualdrr2xbank1CRC    			        INTEGER,
		dualdrr2xbank2CRC    			        INTEGER,
		dualdrr2xprgEEPROMByte    				INTEGER,
		dualdrr2xfactoryCRC    			    	INTEGER,
		dualdrr2xcalculateCRC    				INTEGER,
		dualdrr2xhourMeter    					INTEGER,
		dualdrr2xflashPrgCntA    				INTEGER,
		dualdrr2xflashPrgCntB    				INTEGER,
		dualdrr2xflashBankARev    				DisplayString (SIZE (0..80)),
		dualdrr2xflashBankBRev    				DisplayString (SIZE (0..80)),
		dualdrr2xSubAgentRev					DisplayString (SIZE (0..80)),   
		dualdrr2xFPGA0FwRev						DisplayString (SIZE (0..80)),   
		dualdrr2xFPGA1FwRev						DisplayString (SIZE (0..80)),   
		dualdrr2xDRT1SerialNo					DisplayString (SIZE (0..80)),   
		dualdrr2xDRT1FwRev						DisplayString (SIZE (0..80)),   
		dualdrr2xDRT1FpgaFwRev					DisplayString (SIZE (0..80)),   
		dualdrr2xDRT1SFPSerialNo				DisplayString (SIZE (0..80)),   
		dualdrr2xDRT1SFPPartNo  				DisplayString (SIZE (0..80)),   
		dualdrr2xDRT2SerialNo					DisplayString (SIZE (0..80)),   
		dualdrr2xDRT2FwRev						DisplayString (SIZE (0..80)),   
		dualdrr2xDRT2FpgaFwRev					DisplayString (SIZE (0..80)),   
		dualdrr2xDRT2SFPSerialNo				DisplayString (SIZE (0..80)),   
		dualdrr2xDRT2SFPPartNo  				DisplayString (SIZE (0..80))   
		}
            -- ************** Analog Parameters ****************************
		gx2dualdrr2xAnalogTableIndex              OBJECT-TYPE
			   SYNTAX           INTEGER (1..2147483647)
			   ACCESS           read-only
			   STATUS           mandatory
			   DESCRIPTION
			   "The value of this object identifies the network
			    element. This index is equal to the
			    hfcCommonTableIndex for the same element."
			   ::= { gx2dualdrr2xAnalogEntry 1}
			   
 -- RecdOptPwr1         
        dualdrr2xlabelRecdOptPwr1           OBJECT-TYPE
			   SYNTAX           DisplayString (SIZE (0..80))
			   ACCESS           read-only
			   STATUS           optional
			   DESCRIPTION
			   "The value of this object provides the label of the
			    Channel 1 Received Opt power Analog parameter."
			   ::= { gx2dualdrr2xAnalogEntry 2}

		dualdrr2xuomRecdOptPwr1             OBJECT-TYPE
			   SYNTAX           DisplayString (SIZE (0..80))
			   ACCESS           read-only
			   STATUS           optional
			   DESCRIPTION
			   "The value of this object provides the Unit of Measure of the
			    Channel 1 Received Opt power Analog parameter."
			   ::= { gx2dualdrr2xAnalogEntry 3}

		dualdrr2xmajorHighRecdOptPwr1       OBJECT-TYPE
			   SYNTAX           Float 
			   ACCESS           read-only
			   STATUS           obsolete
			   DESCRIPTION
			   "This object is not used by this module and always returns the value of the
			    Channel 1 Received Opt power Major High Alarm Limit Analog parameter."
			   ::= { gx2dualdrr2xAnalogEntry 4}

		dualdrr2xmajorLowRecdOptPwr1        OBJECT-TYPE
			   SYNTAX           Float 
			   ACCESS           read-only
			   STATUS           obsolete
			   DESCRIPTION
			   "This object is not used by this module and always returns the value of the
			    Channel 1 Received Opt power Major High Alarm Limit Analog parameter."
			   ::= { gx2dualdrr2xAnalogEntry 5}

		dualdrr2xminorHighRecdOptPwr1       OBJECT-TYPE
			   SYNTAX           Float
			   ACCESS           read-only
			   STATUS           obsolete
			   DESCRIPTION
			   "This object is not used by this module and always returns the value
			    of 10^e10 . It is kept here for persistence."
			   ::= { gx2dualdrr2xAnalogEntry 6}

		dualdrr2xminorLowRecdOptPwr1        OBJECT-TYPE
			   SYNTAX           Float 
			   ACCESS           read-only
			   STATUS           obsolete
			   DESCRIPTION
			   "This object is not used by this module and always returns the value
			    of 10^e10 . It is kept here for persistence."
			   ::= { gx2dualdrr2xAnalogEntry 7}

		dualdrr2xcurrentValueRecdOptPwr1    OBJECT-TYPE
			   SYNTAX           Float 
			   ACCESS           read-write
			   STATUS           mandatory
			   DESCRIPTION
			   "The value of this object provides the Current value of the
			    Channel 1 Received Opt power."
			   ::= { gx2dualdrr2xAnalogEntry 8}

		dualdrr2xstateFlagRecdOptPwr1       OBJECT-TYPE
			   SYNTAX           INTEGER
								{
								hidden(1),
								read-only(2),
								updateable(3)
								}
			   ACCESS           read-only
			   STATUS           mandatory
			   DESCRIPTION
			   "The value of this object provides the state of the 
			    Channel 1 Received Opt power Analog parameter. (1-hidden	
			          2-read-only, 3-updateable)."
			   ::= { gx2dualdrr2xAnalogEntry 9}

		dualdrr2xminValueRecdOptPwr1        OBJECT-TYPE
			   SYNTAX           Float
			   ACCESS           read-only
			   STATUS           mandatory
			   DESCRIPTION
			   "The value of this object provides the minimum value of the
			    Channel 1 Received Opt power."
			    ::= { gx2dualdrr2xAnalogEntry 10}

		dualdrr2xmaxValueRecdOptPwr1        OBJECT-TYPE
			   SYNTAX           Float
			   ACCESS           read-only
			   STATUS           mandatory
			   DESCRIPTION
			   "The value of this object provides the maximum value of the
			    Channel 1 Received Opt power."
			   ::= { gx2dualdrr2xAnalogEntry 11}

        dualdrr2xalarmStateRecdOptPwr1      OBJECT-TYPE
			   SYNTAX           INTEGER
									{
									noAlarm(1),
									majorLowAlarm(2),
									minorLowAlarm(3),
									minorHighAlarm(4),
									majorHighAlarm(5),
									informational(6)
									}
			   ACCESS           read-only
			   STATUS           mandatory
			   DESCRIPTION
			   "The value of this object provides the curent alarm state of the
			    Channel 1 Received Opt power."
			   ::= { gx2dualdrr2xAnalogEntry 12}
			   
			   
 -- RecdOptPwr2         

        dualdrr2xlabelRecdOptPwr2           OBJECT-TYPE
			   SYNTAX           DisplayString (SIZE (0..80))
			   ACCESS           read-only
			   STATUS           optional
			   DESCRIPTION
			   "The value of this object provides the label of the
			    Channel 2 Received Opt power Analog parameter."
			   ::= { gx2dualdrr2xAnalogEntry 13}

		dualdrr2xuomRecdOptPwr2             OBJECT-TYPE
			   SYNTAX           DisplayString (SIZE (0..80))
			   ACCESS           read-only
			   STATUS           optional
			   DESCRIPTION
			   "The value of this object provides the Unit of Measure of the
			    Channel 2 Received Opt power Analog parameter."
			   ::= { gx2dualdrr2xAnalogEntry 14}

		dualdrr2xmajorHighRecdOptPwr2       OBJECT-TYPE
			   SYNTAX           Float 
			   ACCESS           read-only
			   STATUS           obsolete
			   DESCRIPTION
			   "This object is not used by this module and always returns the value of the
			    Channel 2 Received Opt power Major High Alarm Limit Analog parameter."
			   ::= { gx2dualdrr2xAnalogEntry 15}

		dualdrr2xmajorLowRecdOptPwr2        OBJECT-TYPE
			   SYNTAX           Float 
			   ACCESS           read-only
			   STATUS           obsolete
			   DESCRIPTION
			   "This object is not used by this module and always returns the value of the
			    Channel 2 Received Opt power Major High Alarm Limit Analog parameter."
			   ::= { gx2dualdrr2xAnalogEntry 16}

		dualdrr2xminorHighRecdOptPwr2       OBJECT-TYPE
			   SYNTAX           Float
			   ACCESS           read-only
			   STATUS           obsolete
			   DESCRIPTION
			   "This object is not used by this module and always returns the value
			    of 10^e10 . It is kept here for persistence."
			   ::= { gx2dualdrr2xAnalogEntry 17}

		dualdrr2xminorLowRecdOptPwr2        OBJECT-TYPE
			   SYNTAX           Float 
			   ACCESS           read-only
			   STATUS           obsolete
			   DESCRIPTION
			   "This object is not used by this module and always returns the value
			    of 10^e10 . It is kept here for persistence."
			   ::= { gx2dualdrr2xAnalogEntry 18}

		dualdrr2xcurrentValueRecdOptPwr2    OBJECT-TYPE
			   SYNTAX           Float 
			   ACCESS           read-write
			   STATUS           mandatory
			   DESCRIPTION
			   "The value of this object provides the Current value of the
			    Channel 2 Received Opt power."
			   ::= { gx2dualdrr2xAnalogEntry 19}

		dualdrr2xstateFlagRecdOptPwr2       OBJECT-TYPE
			   SYNTAX           INTEGER
								{
								hidden(1),
								read-only(2),
								updateable(3)
								}
			   ACCESS           read-only
			   STATUS           mandatory
			   DESCRIPTION
			   "The value of this object provides the state of the 
			    Channel 2 Received Opt power Analog parameter. (1-hidden	
			          2-read-only, 3-updateable)."
			   ::= { gx2dualdrr2xAnalogEntry 20}

		dualdrr2xminValueRecdOptPwr2        OBJECT-TYPE
			   SYNTAX           Float
			   ACCESS           read-only
			   STATUS           mandatory
			   DESCRIPTION
			   "The value of this object provides the minimum value of the
			    Channel 2 Received Opt power."
			    ::= { gx2dualdrr2xAnalogEntry 21}

		dualdrr2xmaxValueRecdOptPwr2        OBJECT-TYPE
			   SYNTAX           Float
			   ACCESS           read-only
			   STATUS           mandatory
			   DESCRIPTION
			   "The value of this object provides the maximum value of the
			    Channel 2 Received Opt power."
			   ::= { gx2dualdrr2xAnalogEntry 22}

        dualdrr2xalarmStateRecdOptPwr2      OBJECT-TYPE
			   SYNTAX           INTEGER
									{
									noAlarm(1),
									majorLowAlarm(2),
									minorLowAlarm(3),
									minorHighAlarm(4),
									majorHighAlarm(5),
									informational(6)
									}
			   ACCESS           read-only
			   STATUS           mandatory
			   DESCRIPTION
			   "The value of this object provides the curent alarm state of the
			    Channel 2 Received optical power."
			   ::= { gx2dualdrr2xAnalogEntry 23}
			   
-- Module Temperature 

		dualdrr2xlabelModTemp              OBJECT-TYPE
			   SYNTAX           DisplayString (SIZE (0..80))
			   ACCESS           read-only
			   STATUS           optional
			   DESCRIPTION
			   "The value of this object provides the label of the
			    Module Temperature Analog parameter."
			   ::= { gx2dualdrr2xAnalogEntry 24}

		dualdrr2xuomModTemp                OBJECT-TYPE
			   SYNTAX           DisplayString (SIZE (0..80))
			   ACCESS           read-only
			   STATUS           optional
			   DESCRIPTION
			   "The value of this object provides the Unit of Measure of the
			    Module Temperature Analog parameter."
			   ::= { gx2dualdrr2xAnalogEntry 25}

		dualdrr2xmajorHighModTemp          OBJECT-TYPE
			   SYNTAX           Float 
			   ACCESS           read-only
			   STATUS           mandatory
			   DESCRIPTION
			   "The value of this object provides the Major High alarm value
			    of the Module Temperature Analog parameter."
			   ::= { gx2dualdrr2xAnalogEntry 26}


		dualdrr2xmajorLowModTemp           OBJECT-TYPE
			   SYNTAX           Float 
			   ACCESS           read-only
			   STATUS           mandatory
			   DESCRIPTION
			   "The value of this object provides the Major Low alarm value
			    of the Module Temperature Analog parameter."
			     ::= { gx2dualdrr2xAnalogEntry 27}

		dualdrr2xminorHighModTemp          OBJECT-TYPE
			   SYNTAX           Float
			   ACCESS           read-only
			   STATUS           mandatory
			   DESCRIPTION
			   "The value of this object provides the Minor High alarm value
			    of the Module Temperature Analog parameter."
			    ::= { gx2dualdrr2xAnalogEntry 28}

		dualdrr2xminorLowModTemp           OBJECT-TYPE
			   SYNTAX           Float 
			   ACCESS           read-only
			   STATUS           mandatory
			   DESCRIPTION
			   "The value of this object provides the Minor Low alarm value
			    of the Module Temperature Analog parameter."
			    ::= { gx2dualdrr2xAnalogEntry 29}

		dualdrr2xcurrentValueModTemp       OBJECT-TYPE
			   SYNTAX           Float 
			   ACCESS           read-only
			   STATUS           mandatory
			   DESCRIPTION
			   "The value of this object provides the Current value
			    of the Module Temperature Analog parameter."
			   ::= { gx2dualdrr2xAnalogEntry 30}

		dualdrr2xstateFlagModTemp          OBJECT-TYPE
			   SYNTAX           INTEGER
								{
								hidden(1),
								read-only(2),
								updateable(3)
								}
			   ACCESS           read-only
			   STATUS           mandatory
			   DESCRIPTION
			   "The value of this object provides the state
			    of the Module Temperature Analog parameter. (1-hidden	
			          2-read-only, 3-updateable)."
			   ::= { gx2dualdrr2xAnalogEntry 31}

		dualdrr2xminValueModTemp           OBJECT-TYPE
			   SYNTAX           Float
			   ACCESS           read-only
			   STATUS           mandatory
			   DESCRIPTION
			   "The value of this object provides the minimum value
			    the Module Temperature Analog parameter can achive."
			    ::= { gx2dualdrr2xAnalogEntry 32}

		dualdrr2xmaxValueModTemp           OBJECT-TYPE
			   SYNTAX           Float
			   ACCESS           read-only
			   STATUS           mandatory
			   DESCRIPTION
			   "The value of this object provides the maximum value
			    the Module Temperature Analog parameter can achive."
			   ::= { gx2dualdrr2xAnalogEntry 33}

		dualdrr2xalarmStateModTemp         OBJECT-TYPE
			   SYNTAX           INTEGER
									{
									noAlarm(1),
									majorLowAlarm(2),
									minorLowAlarm(3),
									minorHighAlarm(4),
									majorHighAlarm(5),
									informational(6)
									}
			   ACCESS           read-only
			   STATUS           mandatory
			   DESCRIPTION
			   "The value of this object provides the curent alarm state of
			    the Module Temperature Analog parameter."
			   ::= { gx2dualdrr2xAnalogEntry 34}
			     
			   
-- 12V current 

    	dualdrr2xlabel12VCurrent           OBJECT-TYPE
			   SYNTAX           DisplayString (SIZE (0..80))
			   ACCESS           read-only
			   STATUS           optional
			   DESCRIPTION
			   "The value of this object provides the label of the
			    12v power supply Current Analog parameter."
			   ::= { gx2dualdrr2xAnalogEntry 35}

		dualdrr2xuom12VCurrent             OBJECT-TYPE
			   SYNTAX           DisplayString (SIZE (0..80))
			   ACCESS           read-only
			   STATUS           optional
			   DESCRIPTION
			   "The value of this object provides the Unit of Measure of the
			    12v power supply Current Analog parameter."
			   ::= { gx2dualdrr2xAnalogEntry 36}

		dualdrr2xmajorHigh12VCurrent       OBJECT-TYPE
			   SYNTAX           Float 
			   ACCESS           read-only
			   STATUS           mandatory
			   DESCRIPTION
			   "The value of this object provides the Major High alarm value
			    of the 12v power supply Current Analog parameter."
			   ::= { gx2dualdrr2xAnalogEntry 37}


		dualdrr2xmajorLow12VCurrent        OBJECT-TYPE
			   SYNTAX           Float 
			   ACCESS           read-only
			   STATUS           mandatory
			   DESCRIPTION
			   "The value of this object provides the Major Low alarm value
			    of the 12v power supply Current Analog parameter."
			   ::= { gx2dualdrr2xAnalogEntry 38}

		dualdrr2xminorHigh12VCurrent       OBJECT-TYPE
			   SYNTAX           Float
			   ACCESS           read-only
			   STATUS           mandatory
			   DESCRIPTION
			   "The value of this object provides the Minor High alarm value
			    of the 12v power supply Current Analog parameter."
			   ::= { gx2dualdrr2xAnalogEntry 39}

		dualdrr2xminorLow12VCurrent        OBJECT-TYPE
			   SYNTAX           Float 
			   ACCESS           read-only
			   STATUS           mandatory
			   DESCRIPTION
			   "The value of this object provides the Minor Low alarm value
			    of the 12v power supply Current Analog parameter."
			   ::= { gx2dualdrr2xAnalogEntry 40}

		dualdrr2xcurrentValue12VCurrent    OBJECT-TYPE
			   SYNTAX           Float 
			   ACCESS           read-only
			   STATUS           mandatory
			   DESCRIPTION
			   "The value of this object provides the Current value
			    of the 12v power supply Current parameter."
			   ::= { gx2dualdrr2xAnalogEntry 41}

		dualdrr2xstateFlag12VCurrent       OBJECT-TYPE
			   SYNTAX           INTEGER
								{
								hidden(1),
								read-only(2),
								updateable(3)
								}
			   ACCESS           read-only
			   STATUS           mandatory
			   DESCRIPTION
			   "The value of this object provides the state
			    of the 12v power supply Current Analog parameter. (1-hidden	
			          2-read-only, 3-updateable)."
			   ::= { gx2dualdrr2xAnalogEntry 42}

		dualdrr2xminValue12VCurrent        OBJECT-TYPE
			   SYNTAX           Float
			   ACCESS           read-only
			   STATUS           mandatory
			   DESCRIPTION
			   "The value of this object provides the minimum value
			    the 12v power supply Current Analog parameter can achive."
			   ::= { gx2dualdrr2xAnalogEntry 43}

		dualdrr2xmaxValue12VCurrent        OBJECT-TYPE
			   SYNTAX           Float
			   ACCESS           read-only
			   STATUS           mandatory
			   DESCRIPTION
			   "The value of this object provides the maximum value
			    the 12v power supply Current Analog parameter can achive."
			   ::= { gx2dualdrr2xAnalogEntry 44}

        dualdrr2xalarmState12VCurrent      OBJECT-TYPE
			   SYNTAX           INTEGER
									{
									noAlarm(1),
									majorLowAlarm(2),
									minorLowAlarm(3),
									minorHighAlarm(4),
									majorHighAlarm(5),
									informational(6)
									}
			   ACCESS           read-only
			   STATUS           mandatory
			   DESCRIPTION
			   "The value of this object provides the curent alarm state of
			    the 12v power supply Current Analog parameter."
			   ::= { gx2dualdrr2xAnalogEntry 45}
			   
-- Fan Speed
		dualdrr2xlabelFanSpeed           OBJECT-TYPE
			   SYNTAX           DisplayString (SIZE (0..80))
			   ACCESS           read-only
			   STATUS           optional
			   DESCRIPTION
			   "The value of this object provides the label of the
			    Fan Speed Analog parameter."
			   ::= { gx2dualdrr2xAnalogEntry 46}

		dualdrr2xuomFanSpeed             OBJECT-TYPE
			   SYNTAX           DisplayString (SIZE (0..80))
			   ACCESS           read-only
			   STATUS           optional
			   DESCRIPTION
			   "The value of this object provides the Unit of Measure of the
			    Fan Speed Analog parameter."
			   ::= { gx2dualdrr2xAnalogEntry 47}

		dualdrr2xmajorHighFanSpeed       OBJECT-TYPE
			   SYNTAX           Float 
			   ACCESS           read-only
			   STATUS           mandatory
			   DESCRIPTION
			   "The value of this object provides the Major High alarm value
			    of the Fan Speed Analog parameter."
			   ::= { gx2dualdrr2xAnalogEntry 48}


		dualdrr2xmajorLowFanSpeed        OBJECT-TYPE
			   SYNTAX           Float 
			   ACCESS           read-only
			   STATUS           mandatory
			   DESCRIPTION
			   "The value of this object provides the Major Low alarm value
			    of the Fan Speed Analog parameter."
			   ::= { gx2dualdrr2xAnalogEntry 49}

		dualdrr2xminorHighFanSpeed       OBJECT-TYPE
			   SYNTAX           Float
			   ACCESS           read-only
			   STATUS           obsolete
			   DESCRIPTION
			   "This object is not used by this module and always returns invalid float value
			    of 0xFFFFFFFF . It is kept here for persistence."
			   ::= { gx2dualdrr2xAnalogEntry 50}

		dualdrr2xminorLowFanSpeed        OBJECT-TYPE
			   SYNTAX           Float 
			   ACCESS           read-only
			   STATUS           obsolete
			   DESCRIPTION
			   "This object is not used by this module and always returns invalid float value
			    of 0xFFFFFFFF . It is kept here for persistence."
			   ::= { gx2dualdrr2xAnalogEntry 51}

		dualdrr2xcurrentValueFanSpeed    OBJECT-TYPE
			   SYNTAX           Float 
			   ACCESS           read-only
			   STATUS           mandatory
			   DESCRIPTION
			   "The value of this object provides the current value
			    of the Fan Speed Analog parameter."
			   ::= { gx2dualdrr2xAnalogEntry 52}

		dualdrr2xstateFlagFanSpeed       OBJECT-TYPE
			   SYNTAX           INTEGER
								{
								hidden(1),
								read-only(2),
								updateable(3)
								}
			   ACCESS           read-only
			   STATUS           mandatory
			   DESCRIPTION
			   "The value of this object provides the state
			    of the Fan Speed Analog parameter. (1-hidden	
			          2-read-only, 3-updateable)."
			   ::= { gx2dualdrr2xAnalogEntry 53}

		dualdrr2xminValueFanSpeed        OBJECT-TYPE
			   SYNTAX           Float
			   ACCESS           read-only
			   STATUS           mandatory
			   DESCRIPTION
			   "The value of this object provides the minimum value
			    the Fan Speed Analog parameter can achive."
			   ::= { gx2dualdrr2xAnalogEntry 54}

		dualdrr2xmaxValueFanSpeed        OBJECT-TYPE
			   SYNTAX           Float
			   ACCESS           read-only
			   STATUS           mandatory
			   DESCRIPTION
			   "The value of this object provides the maximum value
			    the Fan Speed Analog parameter can achive."
			   ::= { gx2dualdrr2xAnalogEntry 55}

        dualdrr2xalarmStateFanSpeed      OBJECT-TYPE
			   SYNTAX           INTEGER
									{
									noAlarm(1),
									majorLowAlarm(2),
									minorLowAlarm(3),
									minorHighAlarm(4),
									majorHighAlarm(5),
									informational(6)
									}
			   ACCESS           read-only
			   STATUS           mandatory
			   DESCRIPTION
			   "The value of this object provides the curent alarm state of
			    the Fan Speed Analog parameter."
			   ::= { gx2dualdrr2xAnalogEntry 56}  
			   
    			   
-- Transmitter 0 SFP Wavelength
		dualdrr2xlabelTx0SFPWave     OBJECT-TYPE
			   SYNTAX           DisplayString (SIZE (0..80))
			   ACCESS           read-only
			   STATUS           optional
			   DESCRIPTION
			   "The value of this object provides the label of the
			    Tx 0 SFP Wavelength Analog parameter."
			   ::= { gx2dualdrr2xAnalogEntry 57}

		dualdrr2xuomTx0SFPWave             OBJECT-TYPE
			   SYNTAX           DisplayString (SIZE (0..80))
			   ACCESS           read-only
			   STATUS           optional
			   DESCRIPTION
			   "The value of this object provides the Unit of Measure of the
			    Tx 0 SFP Wavelength Analog parameter."
			   ::= { gx2dualdrr2xAnalogEntry 58}

		dualdrr2xmajorHighTx0SFPWave       OBJECT-TYPE
			   SYNTAX           Float 
			   ACCESS           read-only
			   STATUS           mandatory
			   DESCRIPTION
			   "The value of this object provides the Major High alarm value
			    of the Tx 0 SFP Wavelength Analog parameter."
			   ::= { gx2dualdrr2xAnalogEntry 59}


		dualdrr2xmajorLowTx0SFPWave        OBJECT-TYPE
			   SYNTAX           Float 
			   ACCESS           read-only
			   STATUS           mandatory
			   DESCRIPTION
			   "The value of this object provides the Major Low alarm value
			    of the Tx 0 SFP Wavelength Analog parameter."
			   ::= { gx2dualdrr2xAnalogEntry 60}

		dualdrr2xminorHighTx0SFPWave       OBJECT-TYPE
			   SYNTAX           Float
			   ACCESS           read-only
			   STATUS           obsolete
			   DESCRIPTION
			   "This object is not used by this module and always returns invalid float value
			    of 0xFFFFFFFF . It is kept here for persistence."
			   ::= { gx2dualdrr2xAnalogEntry 61}

		dualdrr2xminorLowTx0SFPWave        OBJECT-TYPE
			   SYNTAX           Float 
			   ACCESS           read-only
			   STATUS           obsolete
			   DESCRIPTION
			   "This object is not used by this module and always returns invalid float value
			    of 0xFFFFFFFF . It is kept here for persistence."
			   ::= { gx2dualdrr2xAnalogEntry 62}

		dualdrr2xcurrentValueTx0SFPWave    OBJECT-TYPE
			   SYNTAX           Float 
			   ACCESS           read-only
			   STATUS           mandatory
			   DESCRIPTION
			   "The value of this object provides the current value
			    of the Tx 0 SFP Wavelength Analog parameter."
			   ::= { gx2dualdrr2xAnalogEntry 63}

		dualdrr2xstateFlagTx0SFPWave       OBJECT-TYPE
			   SYNTAX           INTEGER
								{
								hidden(1),
								read-only(2),
								updateable(3)
								}
			   ACCESS           read-only
			   STATUS           mandatory
			   DESCRIPTION
			   "The value of this object provides the state
			    of the Tx 0 SFP Wavelength Analog parameter. (1-hidden	
			          2-read-only, 3-updateable)."
			   ::= { gx2dualdrr2xAnalogEntry 64}

		dualdrr2xminValueTx0SFPWave        OBJECT-TYPE
			   SYNTAX           Float
			   ACCESS           read-only
			   STATUS           mandatory
			   DESCRIPTION
			   "The value of this object provides the minimum value
			    the Tx 0 SFP Wavelength Analog parameter can achive."
			   ::= { gx2dualdrr2xAnalogEntry 65}

		dualdrr2xmaxValueTx0SFPWave        OBJECT-TYPE
			   SYNTAX           Float
			   ACCESS           read-only
			   STATUS           mandatory
			   DESCRIPTION
			   "The value of this object provides the maximum value
			    the Tx 0 SFP Wavelength Analog parameter can achive."
			   ::= { gx2dualdrr2xAnalogEntry 66}

        dualdrr2xalarmStateTx0SFPWave      OBJECT-TYPE
			   SYNTAX           INTEGER
									{
									noAlarm(1),
									majorLowAlarm(2),
									minorLowAlarm(3),
									minorHighAlarm(4),
									majorHighAlarm(5),
									informational(6)
									}
			   ACCESS           read-only
			   STATUS           mandatory
			   DESCRIPTION
			   "The value of this object provides the curent alarm state of
			    the Tx 0 SFP Wavelength Analog parameter."
			   ::= { gx2dualdrr2xAnalogEntry 67}  
			   
    			   
-- Transmitter 0 Optical power
		dualdrr2xlabelTx0OptPwr           OBJECT-TYPE
			   SYNTAX           DisplayString (SIZE (0..80))
			   ACCESS           read-only
			   STATUS           optional
			   DESCRIPTION
			   "The value of this object provides the label of the
			    Tx 0 Optical Power Analog parameter."
			   ::= { gx2dualdrr2xAnalogEntry 68}

		dualdrr2xuomTx0OptPwr             OBJECT-TYPE
			   SYNTAX           DisplayString (SIZE (0..80))
			   ACCESS           read-only
			   STATUS           optional
			   DESCRIPTION
			   "The value of this object provides the Unit of Measure of the
			    Tx 0 Optical Power Analog parameter."
			   ::= { gx2dualdrr2xAnalogEntry 69}

		dualdrr2xmajorHighTx0OptPwr       OBJECT-TYPE
			   SYNTAX           Float 
			   ACCESS           read-only
			   STATUS           mandatory
			   DESCRIPTION
			   "The value of this object provides the Major High alarm value
			    of the Tx 0 Optical Power Analog parameter."
			   ::= { gx2dualdrr2xAnalogEntry 70}


		dualdrr2xmajorLowTx0OptPwr        OBJECT-TYPE
			   SYNTAX           Float 
			   ACCESS           read-only
			   STATUS           mandatory
			   DESCRIPTION
			   "The value of this object provides the Major Low alarm value
			    of the Tx 0 Optical Power Analog parameter."
			   ::= { gx2dualdrr2xAnalogEntry 71}

		dualdrr2xminorHighTx0OptPwr       OBJECT-TYPE
			   SYNTAX           Float
			   ACCESS           read-only
			   STATUS           obsolete
			   DESCRIPTION
			   "This object is not used by this module and always returns invalid float value
			    of 0xFFFFFFFF . It is kept here for persistence."
			   ::= { gx2dualdrr2xAnalogEntry 72}

		dualdrr2xminorLowTx0OptPwr        OBJECT-TYPE
			   SYNTAX           Float 
			   ACCESS           read-only
			   STATUS           obsolete
			   DESCRIPTION
			   "This object is not used by this module and always returns invalid float value
			    of 0xFFFFFFFF . It is kept here for persistence."
			   ::= { gx2dualdrr2xAnalogEntry 73}

		dualdrr2xcurrentValueTx0OptPwr    OBJECT-TYPE
			   SYNTAX           Float 
			   ACCESS           read-only
			   STATUS           mandatory
			   DESCRIPTION
			   "The value of this object provides the current value
			    of the Tx 0 Optical Power Analog parameter."
			   ::= { gx2dualdrr2xAnalogEntry 74}

		dualdrr2xstateFlagTx0OptPwr       OBJECT-TYPE
			   SYNTAX           INTEGER
								{
								hidden(1),
								read-only(2),
								updateable(3)
								}
			   ACCESS           read-only
			   STATUS           mandatory
			   DESCRIPTION
			   "The value of this object provides the state
			    of the Tx 0 Optical Power Analog parameter. (1-hidden	
			          2-read-only, 3-updateable)."
			   ::= { gx2dualdrr2xAnalogEntry 75}

		dualdrr2xminValueTx0OptPwr        OBJECT-TYPE
			   SYNTAX           Float
			   ACCESS           read-only
			   STATUS           mandatory
			   DESCRIPTION
			   "The value of this object provides the minimum value
			    the Tx 0 Optical Power Analog parameter can achive."
			   ::= { gx2dualdrr2xAnalogEntry 76}

		dualdrr2xmaxValueTx0OptPwr        OBJECT-TYPE
			   SYNTAX           Float
			   ACCESS           read-only
			   STATUS           mandatory
			   DESCRIPTION
			   "The value of this object provides the maximum value
			    the Tx 0 Optical Power Analog parameter can achive."
			   ::= { gx2dualdrr2xAnalogEntry 77}

        dualdrr2xalarmStateTx0OptPwr      OBJECT-TYPE
			   SYNTAX           INTEGER
									{
									noAlarm(1),
									majorLowAlarm(2),
									minorLowAlarm(3),
									minorHighAlarm(4),
									majorHighAlarm(5),
									informational(6)
									}
			   ACCESS           read-only
			   STATUS           mandatory
			   DESCRIPTION
			   "The value of this object provides the curent alarm state of
			    the Tx 0 Optical Power Analog parameter."
			   ::= { gx2dualdrr2xAnalogEntry 78}  
			   
    			   
-- Transmitter 0 24 Volt Current           OBJECT-TYPE
		dualdrr2xlabelTx024vCurr             OBJECT-TYPE
			   SYNTAX           DisplayString (SIZE (0..80))
			   ACCESS           read-only
			   STATUS           optional
			   DESCRIPTION
			   "The value of this object provides the label of the
			    Tx 0 24 Volt Current Analog parameter."
			   ::= { gx2dualdrr2xAnalogEntry 79}
   
  
		dualdrr2xuomTx024vCurr             OBJECT-TYPE
			   SYNTAX           DisplayString (SIZE (0..80))
			   ACCESS           read-only
			   STATUS           optional
			   DESCRIPTION
			   "The value of this object provides the Unit of Measure of the
			    Tx 0 24 Volt Current Analog parameter."
			   ::= { gx2dualdrr2xAnalogEntry 80}

		dualdrr2xmajorHighTx024vCurr       OBJECT-TYPE
			   SYNTAX           Float 
			   ACCESS           read-only
			   STATUS           mandatory
			   DESCRIPTION
			   "The value of this object provides the Major High alarm value
			    of the Tx 0 24 Volt Current Analog parameter."
			   ::= { gx2dualdrr2xAnalogEntry 81}


		dualdrr2xmajorLowTx024vCurr        OBJECT-TYPE
			   SYNTAX           Float 
			   ACCESS           read-only
			   STATUS           mandatory
			   DESCRIPTION
			   "The value of this object provides the Major Low alarm value
			    of the Tx 0 24 Volt Current Analog parameter."
			   ::= { gx2dualdrr2xAnalogEntry 82}

		dualdrr2xminorHighTx024vCurr       OBJECT-TYPE
			   SYNTAX           Float
			   ACCESS           read-only
			   STATUS           obsolete
			   DESCRIPTION
			   "This object is not used by this module and always returns invalid float value
			    of 0xFFFFFFFF . It is kept here for persistence."
			   ::= { gx2dualdrr2xAnalogEntry 83}

		dualdrr2xminorLowTx024vCurr        OBJECT-TYPE
			   SYNTAX           Float 
			   ACCESS           read-only
			   STATUS           obsolete
			   DESCRIPTION
			   "This object is not used by this module and always returns invalid float value
			    of 0xFFFFFFFF . It is kept here for persistence."
			   ::= { gx2dualdrr2xAnalogEntry 84}

		dualdrr2xcurrentValueTx024vCurr    OBJECT-TYPE
			   SYNTAX           Float 
			   ACCESS           read-only
			   STATUS           mandatory
			   DESCRIPTION
			   "The value of this object provides the current value
			    of the Tx 0 24 Volt Current Analog parameter."
			   ::= { gx2dualdrr2xAnalogEntry 85}

		dualdrr2xstateFlagTx024vCurr       OBJECT-TYPE
			   SYNTAX           INTEGER
								{
								hidden(1),
								read-only(2),
								updateable(3)
								}
			   ACCESS           read-only
			   STATUS           mandatory
			   DESCRIPTION
			   "The value of this object provides the state
			    of the Tx 0 24 Volt Current Analog parameter. (1-hidden	
			          2-read-only, 3-updateable)."
			   ::= { gx2dualdrr2xAnalogEntry 86}

		dualdrr2xminValueTx024vCurr        OBJECT-TYPE
			   SYNTAX           Float
			   ACCESS           read-only
			   STATUS           mandatory
			   DESCRIPTION
			   "The value of this object provides the minimum value
			    the Tx 0 24 Volt Current Analog parameter can achive."
			   ::= { gx2dualdrr2xAnalogEntry 87}

		dualdrr2xmaxValueTx024vCurr        OBJECT-TYPE
			   SYNTAX           Float
			   ACCESS           read-only
			   STATUS           mandatory
			   DESCRIPTION
			   "The value of this object provides the maximum value
			    the Tx 0 24 Volt Current Analog parameter can achive."
			   ::= { gx2dualdrr2xAnalogEntry 88}

        dualdrr2xalarmStateTx024vCurr      OBJECT-TYPE
			   SYNTAX           INTEGER
									{
									noAlarm(1),
									majorLowAlarm(2),
									minorLowAlarm(3),
									minorHighAlarm(4),
									majorHighAlarm(5),
									informational(6)
									}
			   ACCESS           read-only
			   STATUS           mandatory
			   DESCRIPTION
			   "The value of this object provides the curent alarm state of
			    the Tx 0 24 Volt Current Analog parameter."
			   ::= { gx2dualdrr2xAnalogEntry 89}  
			   
    			   
-- Transmitter 0 24 Volt supply Voltage   OBJECT-TYPE
		dualdrr2xlabelTx024Volt             OBJECT-TYPE
			   SYNTAX           DisplayString (SIZE (0..80))
			   ACCESS           read-only
			   STATUS           optional
			   DESCRIPTION
			   "The value of this object provides the label of the
			    Tx 0 24 Volt supply voltage Analog parameter."
			   ::= { gx2dualdrr2xAnalogEntry 90}

		dualdrr2xuomTx024Volt             OBJECT-TYPE
			   SYNTAX           DisplayString (SIZE (0..80))
			   ACCESS           read-only
			   STATUS           optional
			   DESCRIPTION
			   "The value of this object provides the Unit of Measure of the
			    Tx 0 24 Volt  supply voltage Analog parameter."
			   ::= { gx2dualdrr2xAnalogEntry 91}

		dualdrr2xmajorHighTx024Volt       OBJECT-TYPE
			   SYNTAX           Float 
			   ACCESS           read-only
			   STATUS           mandatory
			   DESCRIPTION
			   "The value of this object provides the Major High alarm value
			    of the Tx 0 24 Volt supply voltage Analog parameter."
			   ::= { gx2dualdrr2xAnalogEntry 92}


		dualdrr2xmajorLowTx024Volt        OBJECT-TYPE
			   SYNTAX           Float 
			   ACCESS           read-only
			   STATUS           mandatory
			   DESCRIPTION
			   "The value of this object provides the Major Low alarm value
			    of the Tx 0 24 Volt supply voltage Analog parameter."
			   ::= { gx2dualdrr2xAnalogEntry 93}

		dualdrr2xminorHighTx024Volt       OBJECT-TYPE
			   SYNTAX           Float
			   ACCESS           read-only
			   STATUS           obsolete
			   DESCRIPTION
			   "This object is not used by this module and always returns invalid float value
			    of 0xFFFFFFFF . It is kept here for persistence."
			   ::= { gx2dualdrr2xAnalogEntry 94}

		dualdrr2xminorLowTx024Volt        OBJECT-TYPE
			   SYNTAX           Float 
			   ACCESS           read-only
			   STATUS           obsolete
			   DESCRIPTION
			   "This object is not used by this module and always returns invalid float value
			    of 0xFFFFFFFF . It is kept here for persistence."
			   ::= { gx2dualdrr2xAnalogEntry 95}

		dualdrr2xcurrentValueTx024Volt    OBJECT-TYPE
			   SYNTAX           Float 
			   ACCESS           read-only
			   STATUS           mandatory
			   DESCRIPTION
			   "The value of this object provides the current value
			    of the Tx 0 24 Volt supply voltage Analog parameter."
			   ::= { gx2dualdrr2xAnalogEntry 96}

		dualdrr2xstateFlagTx024Volt       OBJECT-TYPE
			   SYNTAX           INTEGER
								{
								hidden(1),
								read-only(2),
								updateable(3)
								}
			   ACCESS           read-only
			   STATUS           mandatory
			   DESCRIPTION
			   "The value of this object provides the state
			    of the Tx 0 24 Volt supply voltage Analog parameter. (1-hidden	
			          2-read-only, 3-updateable)."
			   ::= { gx2dualdrr2xAnalogEntry 97}

		dualdrr2xminValueTx024Volt        OBJECT-TYPE
			   SYNTAX           Float
			   ACCESS           read-only
			   STATUS           mandatory
			   DESCRIPTION
			   "The value of this object provides the minimum value
			    the Tx 0 24 Volt supply voltage Analog parameter can achive."
			   ::= { gx2dualdrr2xAnalogEntry 98}

		dualdrr2xmaxValueTx024Volt        OBJECT-TYPE
			   SYNTAX           Float
			   ACCESS           read-only
			   STATUS           mandatory
			   DESCRIPTION
			   "The value of this object provides the maximum value
			    the Tx 0 24 Volt supply voltage Analog parameter can achive."
			   ::= { gx2dualdrr2xAnalogEntry 99}

        dualdrr2xalarmStateTx024Volt      OBJECT-TYPE
			   SYNTAX           INTEGER
									{
									noAlarm(1),
									majorLowAlarm(2),
									minorLowAlarm(3),
									minorHighAlarm(4),
									majorHighAlarm(5),
									informational(6)
									}
			   ACCESS           read-only
			   STATUS           mandatory
			   DESCRIPTION
			   "The value of this object provides the curent alarm state of
			    the Tx 0 24 Volt supply voltage Analog parameter."
			   ::= { gx2dualdrr2xAnalogEntry 100} 
			   
    			   
-- Transmitter 0 Module Temperature           OBJECT-TYPE
		dualdrr2xlabelTx0ModTemp             OBJECT-TYPE
			   SYNTAX           DisplayString (SIZE (0..80))
			   ACCESS           read-only
			   STATUS           optional
			   DESCRIPTION
			   "The value of this object provides the label of the
			    Tx 0 24 Module Temperature Analog parameter."
			   ::= { gx2dualdrr2xAnalogEntry 101}

		dualdrr2xuomTx0ModTemp             OBJECT-TYPE
			   SYNTAX           DisplayString (SIZE (0..80))
			   ACCESS           read-only
			   STATUS           optional
			   DESCRIPTION
			   "The value of this object provides the Unit of Measure of the
			    Tx 0 Module Temperature Analog parameter."
			   ::= { gx2dualdrr2xAnalogEntry 102}

		dualdrr2xmajorHighTx0ModTemp       OBJECT-TYPE
			   SYNTAX           Float 
			   ACCESS           read-only
			   STATUS           mandatory
			   DESCRIPTION
			   "The value of this object provides the Major High alarm value
			    of the Tx 0 Module Temperature Analog parameter."
			   ::= { gx2dualdrr2xAnalogEntry 103}


		dualdrr2xmajorLowTx0ModTemp        OBJECT-TYPE
			   SYNTAX           Float 
			   ACCESS           read-only
			   STATUS           mandatory
			   DESCRIPTION
			   "The value of this object provides the Major Low alarm value
			    of the Tx 0 Module Temperature Analog parameter."
			   ::= { gx2dualdrr2xAnalogEntry 104}

		dualdrr2xminorHighTx0ModTemp       OBJECT-TYPE
			   SYNTAX           Float
			   ACCESS           read-only
			   STATUS           obsolete
			   DESCRIPTION
			   "This object is not used by this module and always returns invalid float value
			    of 0xFFFFFFFF . It is kept here for persistence."
			   ::= { gx2dualdrr2xAnalogEntry 105}

		dualdrr2xminorLowTx0ModTemp        OBJECT-TYPE
			   SYNTAX           Float 
			   ACCESS           read-only
			   STATUS           obsolete
			   DESCRIPTION
			   "This object is not used by this module and always returns invalid float value
			    of 0xFFFFFFFF . It is kept here for persistence."
			   ::= { gx2dualdrr2xAnalogEntry 106}

		dualdrr2xcurrentValueTx0ModTemp    OBJECT-TYPE
			   SYNTAX           Float 
			   ACCESS           read-only
			   STATUS           mandatory
			   DESCRIPTION
			   "The value of this object provides the current value
			    of the Tx 0 Module Temperature Analog parameter."
			   ::= { gx2dualdrr2xAnalogEntry 107}

		dualdrr2xstateFlagTx0ModTemp       OBJECT-TYPE
			   SYNTAX           INTEGER
								{
								hidden(1),
								read-only(2),
								updateable(3)
								}
			   ACCESS           read-only
			   STATUS           mandatory
			   DESCRIPTION
			   "The value of this object provides the state
			    of the Tx 0 Module Temperature Analog parameter. (1-hidden	
			          2-read-only, 3-updateable)."
			   ::= { gx2dualdrr2xAnalogEntry 108}

		dualdrr2xminValueTx0ModTemp        OBJECT-TYPE
			   SYNTAX           Float
			   ACCESS           read-only
			   STATUS           mandatory
			   DESCRIPTION
			   "The value of this object provides the minimum value
			    the Tx 0 Module Temperature Analog parameter can achive."
			   ::= { gx2dualdrr2xAnalogEntry 109}

		dualdrr2xmaxValueTx0ModTemp        OBJECT-TYPE
			   SYNTAX           Float
			   ACCESS           read-only
			   STATUS           mandatory
			   DESCRIPTION
			   "The value of this object provides the maximum value
			    the Tx 0 Module Temperature Analog parameter can achive."
			   ::= { gx2dualdrr2xAnalogEntry 110}

        dualdrr2xalarmStateTx0ModTemp      OBJECT-TYPE
			   SYNTAX           INTEGER
									{
									noAlarm(1),
									majorLowAlarm(2),
									minorLowAlarm(3),
									minorHighAlarm(4),
									majorHighAlarm(5),
									informational(6)
									}
			   ACCESS           read-only
			   STATUS           mandatory
			   DESCRIPTION
			   "The value of this object provides the curent alarm state of
			    the Tx 0 Module Temperature Analog parameter."
			   ::= { gx2dualdrr2xAnalogEntry 111}  
			   
    			   
-- Transmitter 1 SFP Wavelength
		dualdrr2xlabelTx1SFPWave     OBJECT-TYPE
			   SYNTAX           DisplayString (SIZE (0..80))
			   ACCESS           read-only
			   STATUS           optional
			   DESCRIPTION
			   "The value of this object provides the label of the
			    Tx 1 SFP Wavelength Analog parameter."
			   ::= { gx2dualdrr2xAnalogEntry 112}

		dualdrr2xuomTx1SFPWave             OBJECT-TYPE
			   SYNTAX           DisplayString (SIZE (0..80))
			   ACCESS           read-only
			   STATUS           optional
			   DESCRIPTION
			   "The value of this object provides the Unit of Measure of the
			    Tx 1 SFP Wavelength Analog parameter."
			   ::= { gx2dualdrr2xAnalogEntry 113}

		dualdrr2xmajorHighTx1SFPWave       OBJECT-TYPE
			   SYNTAX           Float 
			   ACCESS           read-only
			   STATUS           mandatory
			   DESCRIPTION
			   "The value of this object provides the Major High alarm value
			    of the Tx 1 SFP Wavelength Analog parameter."
			   ::= { gx2dualdrr2xAnalogEntry 114}


		dualdrr2xmajorLowTx1SFPWave        OBJECT-TYPE
			   SYNTAX           Float 
			   ACCESS           read-only
			   STATUS           mandatory
			   DESCRIPTION
			   "The value of this object provides the Major Low alarm value
			    of the Tx 1 SFP Wavelength Analog parameter."
			   ::= { gx2dualdrr2xAnalogEntry 115}

		dualdrr2xminorHighTx1SFPWave       OBJECT-TYPE
			   SYNTAX           Float
			   ACCESS           read-only
			   STATUS           obsolete
			   DESCRIPTION
			   "This object is not used by this module and always returns invalid float value
			    of 0xFFFFFFFF . It is kept here for persistence."
			   ::= { gx2dualdrr2xAnalogEntry 116}

		dualdrr2xminorLowTx1SFPWave        OBJECT-TYPE
			   SYNTAX           Float 
			   ACCESS           read-only
			   STATUS           obsolete
			   DESCRIPTION
			   "This object is not used by this module and always returns invalid float value
			    of 0xFFFFFFFF . It is kept here for persistence."
			   ::= { gx2dualdrr2xAnalogEntry 117}

		dualdrr2xcurrentValueTx1SFPWave    OBJECT-TYPE
			   SYNTAX           Float 
			   ACCESS           read-only
			   STATUS           mandatory
			   DESCRIPTION
			   "The value of this object provides the current value
			    of the Tx 1 SFP Wavelength Analog parameter."
			   ::= { gx2dualdrr2xAnalogEntry 118}

		dualdrr2xstateFlagTx1SFPWave       OBJECT-TYPE
			   SYNTAX           INTEGER
								{
								hidden(1),
								read-only(2),
								updateable(3)
								}
			   ACCESS           read-only
			   STATUS           mandatory
			   DESCRIPTION
			   "The value of this object provides the state
			    of the Tx 1 SFP Wavelength Analog parameter. (1-hidden	
			          2-read-only, 3-updateable)."
			   ::= { gx2dualdrr2xAnalogEntry 119}

		dualdrr2xminValueTx1SFPWave        OBJECT-TYPE
			   SYNTAX           Float
			   ACCESS           read-only
			   STATUS           mandatory
			   DESCRIPTION
			   "The value of this object provides the minimum value
			    the Tx 1 SFP Wavelength Analog parameter can achive."
			   ::= { gx2dualdrr2xAnalogEntry 120}

		dualdrr2xmaxValueTx1SFPWave        OBJECT-TYPE
			   SYNTAX           Float
			   ACCESS           read-only
			   STATUS           mandatory
			   DESCRIPTION
			   "The value of this object provides the maximum value
			    the Tx 1 SFP Wavelength Analog parameter can achive."
			   ::= { gx2dualdrr2xAnalogEntry 121}

        dualdrr2xalarmStateTx1SFPWave      OBJECT-TYPE
			   SYNTAX           INTEGER
									{
									noAlarm(1),
									majorLowAlarm(2),
									minorLowAlarm(3),
									minorHighAlarm(4),
									majorHighAlarm(5),
									informational(6)
									}
			   ACCESS           read-only
			   STATUS           mandatory
			   DESCRIPTION
			   "The value of this object provides the curent alarm state of
			    the Tx 1 SFP Wavelength Analog parameter."
			   ::= { gx2dualdrr2xAnalogEntry 122}  
			   
    			   
-- Transmitter 1 Optical power
		dualdrr2xlabelTx1OptPwr           OBJECT-TYPE
			   SYNTAX           DisplayString (SIZE (0..80))
			   ACCESS           read-only
			   STATUS           optional
			   DESCRIPTION
			   "The value of this object provides the label of the
			    Tx 1 Optical Power Analog parameter."
			   ::= { gx2dualdrr2xAnalogEntry 123}

		dualdrr2xuomTx1OptPwr             OBJECT-TYPE
			   SYNTAX           DisplayString (SIZE (0..80))
			   ACCESS           read-only
			   STATUS           optional
			   DESCRIPTION
			   "The value of this object provides the Unit of Measure of the
			    Tx 1 Optical Power Analog parameter."
			   ::= { gx2dualdrr2xAnalogEntry 124}

		dualdrr2xmajorHighTx1OptPwr       OBJECT-TYPE
			   SYNTAX           Float 
			   ACCESS           read-only
			   STATUS           mandatory
			   DESCRIPTION
			   "The value of this object provides the Major High alarm value
			    of the Tx 1 Optical Power Analog parameter."
			   ::= { gx2dualdrr2xAnalogEntry 125}


		dualdrr2xmajorLowTx1OptPwr        OBJECT-TYPE
			   SYNTAX           Float 
			   ACCESS           read-only
			   STATUS           mandatory
			   DESCRIPTION
			   "The value of this object provides the Major Low alarm value
			    of the Tx 1 Optical Power Analog parameter."
			   ::= { gx2dualdrr2xAnalogEntry 126}

		dualdrr2xminorHighTx1OptPwr       OBJECT-TYPE
			   SYNTAX           Float
			   ACCESS           read-only
			   STATUS           obsolete
			   DESCRIPTION
			   "This object is not used by this module and always returns invalid float value
			    of 0xFFFFFFFF . It is kept here for persistence."
			   ::= { gx2dualdrr2xAnalogEntry 127}

		dualdrr2xminorLowTx1OptPwr        OBJECT-TYPE
			   SYNTAX           Float 
			   ACCESS           read-only
			   STATUS           obsolete
			   DESCRIPTION
			   "This object is not used by this module and always returns invalid float value
			    of 0xFFFFFFFF . It is kept here for persistence."
			   ::= { gx2dualdrr2xAnalogEntry 128}

		dualdrr2xcurrentValueTx1OptPwr    OBJECT-TYPE
			   SYNTAX           Float 
			   ACCESS           read-only
			   STATUS           mandatory
			   DESCRIPTION
			   "The value of this object provides the current value
			    of the Tx 1 Optical Power Analog parameter."
			   ::= { gx2dualdrr2xAnalogEntry 129}

		dualdrr2xstateFlagTx1OptPwr       OBJECT-TYPE
			   SYNTAX           INTEGER
								{
								hidden(1),
								read-only(2),
								updateable(3)
								}
			   ACCESS           read-only
			   STATUS           mandatory
			   DESCRIPTION
			   "The value of this object provides the state
			    of the Tx 1 Optical Power Analog parameter. (1-hidden	
			          2-read-only, 3-updateable)."
			   ::= { gx2dualdrr2xAnalogEntry 130}

		dualdrr2xminValueTx1OptPwr        OBJECT-TYPE
			   SYNTAX           Float
			   ACCESS           read-only
			   STATUS           mandatory
			   DESCRIPTION
			   "The value of this object provides the minimum value
			    the Tx 1 Optical Power Analog parameter can achive."
			   ::= { gx2dualdrr2xAnalogEntry 131}

		dualdrr2xmaxValueTx1OptPwr        OBJECT-TYPE
			   SYNTAX           Float
			   ACCESS           read-only
			   STATUS           mandatory
			   DESCRIPTION
			   "The value of this object provides the maximum value
			    the Tx 1 Optical Power Analog parameter can achive."
			   ::= { gx2dualdrr2xAnalogEntry 132}

        dualdrr2xalarmStateTx1OptPwr      OBJECT-TYPE
			   SYNTAX           INTEGER
									{
									noAlarm(1),
									majorLowAlarm(2),
									minorLowAlarm(3),
									minorHighAlarm(4),
									majorHighAlarm(5),
									informational(6)
									}
			   ACCESS           read-only
			   STATUS           mandatory
			   DESCRIPTION
			   "The value of this object provides the curent alarm state of
			    the Tx 1 Optical Power Analog parameter."
			   ::= { gx2dualdrr2xAnalogEntry 133}  
			   
    			   
-- Transmitter 1 24 Volt Current           OBJECT-TYPE
		dualdrr2xlabelTx124vCurr             OBJECT-TYPE
			   SYNTAX           DisplayString (SIZE (0..80))
			   ACCESS           read-only
			   STATUS           optional
			   DESCRIPTION
			   "The value of this object provides the label of the
			    Tx 1 24 VoltCurrent Analog parameter."
			   ::= { gx2dualdrr2xAnalogEntry 134}

		dualdrr2xuomTx124vCurr             OBJECT-TYPE
			   SYNTAX           DisplayString (SIZE (0..80))
			   ACCESS           read-only
			   STATUS           optional
			   DESCRIPTION
			   "The value of this object provides the Unit of Measure of the
			    Tx 1 24 Volt Current Analog parameter."
			   ::= { gx2dualdrr2xAnalogEntry 135}

		dualdrr2xmajorHighTx124vCurr       OBJECT-TYPE
			   SYNTAX           Float 
			   ACCESS           read-only
			   STATUS           mandatory
			   DESCRIPTION
			   "The value of this object provides the Major High alarm value
			    of the Tx 1 24 Volt Current Analog parameter."
			   ::= { gx2dualdrr2xAnalogEntry 136}


		dualdrr2xmajorLowTx124vCurr        OBJECT-TYPE
			   SYNTAX           Float 
			   ACCESS           read-only
			   STATUS           mandatory
			   DESCRIPTION
			   "The value of this object provides the Major Low alarm value
			    of the Tx 1 24 Volt Current Analog parameter."
			   ::= { gx2dualdrr2xAnalogEntry 137}

		dualdrr2xminorHighTx124vCurr       OBJECT-TYPE
			   SYNTAX           Float
			   ACCESS           read-only
			   STATUS           obsolete
			   DESCRIPTION
			   "This object is not used by this module and always returns invalid float value
			    of 0xFFFFFFFF . It is kept here for persistence."
			   ::= { gx2dualdrr2xAnalogEntry 138}

		dualdrr2xminorLowTx124vCurr        OBJECT-TYPE
			   SYNTAX           Float 
			   ACCESS           read-only
			   STATUS           obsolete
			   DESCRIPTION
			   "This object is not used by this module and always returns invalid float value
			    of 0xFFFFFFFF . It is kept here for persistence."
			   ::= { gx2dualdrr2xAnalogEntry 139}

		dualdrr2xcurrentValueTx124vCurr    OBJECT-TYPE
			   SYNTAX           Float 
			   ACCESS           read-only
			   STATUS           mandatory
			   DESCRIPTION
			   "The value of this object provides the current value
			    of the Tx 1 24 Volt Current Analog parameter."
			   ::= { gx2dualdrr2xAnalogEntry 140}

		dualdrr2xstateFlagTx124vCurr       OBJECT-TYPE
			   SYNTAX           INTEGER
								{
								hidden(1),
								read-only(2),
								updateable(3)
								}
			   ACCESS           read-only
			   STATUS           mandatory
			   DESCRIPTION
			   "The value of this object provides the state
			    of the Tx 1 24 Volt Current Analog parameter. (1-hidden	
			          2-read-only, 3-updateable)."
			   ::= { gx2dualdrr2xAnalogEntry 141}

		dualdrr2xminValueTx124vCurr        OBJECT-TYPE
			   SYNTAX           Float
			   ACCESS           read-only
			   STATUS           mandatory
			   DESCRIPTION
			   "The value of this object provides the minimum value
			    the Tx 1 24 Volt Current Analog parameter can achive."
			   ::= { gx2dualdrr2xAnalogEntry 142}

		dualdrr2xmaxValueTx124vCurr        OBJECT-TYPE
			   SYNTAX           Float
			   ACCESS           read-only
			   STATUS           mandatory
			   DESCRIPTION
			   "The value of this object provides the maximum value
			    the Tx 1 24 Volt Current Analog parameter can achive."
			   ::= { gx2dualdrr2xAnalogEntry 143}

        dualdrr2xalarmStateTx124vCurr      OBJECT-TYPE
			   SYNTAX           INTEGER
									{
									noAlarm(1),
									majorLowAlarm(2),
									minorLowAlarm(3),
									minorHighAlarm(4),
									majorHighAlarm(5),
									informational(6)
									}
			   ACCESS           read-only
			   STATUS           mandatory
			   DESCRIPTION
			   "The value of this object provides the curent alarm state of
			    the Tx 1 24 Volt Current Analog parameter."
			   ::= { gx2dualdrr2xAnalogEntry 144}  
			   
    			   
-- Transmitter 1 24 Volt supply Voltage   OBJECT-TYPE
		dualdrr2xlabelTx124Volt             OBJECT-TYPE
			   SYNTAX           DisplayString (SIZE (0..80))
			   ACCESS           read-only
			   STATUS           optional
			   DESCRIPTION
			   "The value of this object provides the label of the
			    Tx 1 24 Volt supply voltage Analog parameter."
			   ::= { gx2dualdrr2xAnalogEntry 145}

		dualdrr2xuomTx124Volt             OBJECT-TYPE
			   SYNTAX           DisplayString (SIZE (0..80))
			   ACCESS           read-only
			   STATUS           optional
			   DESCRIPTION
			   "The value of this object provides the Unit of Measure of the
			    Tx 1 24 Volt  supply voltage Analog parameter."
			   ::= { gx2dualdrr2xAnalogEntry 146}

		dualdrr2xmajorHighTx124Volt       OBJECT-TYPE
			   SYNTAX           Float 
			   ACCESS           read-only
			   STATUS           mandatory
			   DESCRIPTION
			   "The value of this object provides the Major High alarm value
			    of the Tx 1 24 Volt supply voltage Analog parameter."
			   ::= { gx2dualdrr2xAnalogEntry 147}


		dualdrr2xmajorLowTx124Volt        OBJECT-TYPE
			   SYNTAX           Float 
			   ACCESS           read-only
			   STATUS           mandatory
			   DESCRIPTION
			   "The value of this object provides the Major Low alarm value
			    of the Tx 1 24 Volt supply voltage Analog parameter."
			   ::= { gx2dualdrr2xAnalogEntry 148}

		dualdrr2xminorHighTx124Volt       OBJECT-TYPE
			   SYNTAX           Float
			   ACCESS           read-only
			   STATUS           obsolete
			   DESCRIPTION
			   "This object is not used by this module and always returns invalid float value
			    of 0xFFFFFFFF . It is kept here for persistence."
			   ::= { gx2dualdrr2xAnalogEntry 149}

		dualdrr2xminorLowTx124Volt        OBJECT-TYPE
			   SYNTAX           Float 
			   ACCESS           read-only
			   STATUS           obsolete
			   DESCRIPTION
			   "This object is not used by this module and always returns invalid float value
			    of 0xFFFFFFFF . It is kept here for persistence."
			   ::= { gx2dualdrr2xAnalogEntry 150}

		dualdrr2xcurrentValueTx124Volt    OBJECT-TYPE
			   SYNTAX           Float 
			   ACCESS           read-only
			   STATUS           mandatory
			   DESCRIPTION
			   "The value of this object provides the current value
			    of the Tx 1 24 Volt supply voltage Analog parameter."
			   ::= { gx2dualdrr2xAnalogEntry 151}

		dualdrr2xstateFlagTx124Volt       OBJECT-TYPE
			   SYNTAX           INTEGER
								{
								hidden(1),
								read-only(2),
								updateable(3)
								}
			   ACCESS           read-only
			   STATUS           mandatory
			   DESCRIPTION
			   "The value of this object provides the state
			    of the Tx 1 24 Volt supply voltage Analog parameter. (1-hidden	
			          2-read-only, 3-updateable)."
			   ::= { gx2dualdrr2xAnalogEntry 152}

		dualdrr2xminValueTx124Volt        OBJECT-TYPE
			   SYNTAX           Float
			   ACCESS           read-only
			   STATUS           mandatory
			   DESCRIPTION
			   "The value of this object provides the minimum value
			    the Tx 1 24 Volt supply voltage Analog parameter can achive."
			   ::= { gx2dualdrr2xAnalogEntry 153}

		dualdrr2xmaxValueTx124Volt        OBJECT-TYPE
			   SYNTAX           Float
			   ACCESS           read-only
			   STATUS           mandatory
			   DESCRIPTION
			   "The value of this object provides the maximum value
			    the Tx 1 24 Volt supply voltage Analog parameter can achive."
			   ::= { gx2dualdrr2xAnalogEntry 154}

        dualdrr2xalarmStateTx124Volt      OBJECT-TYPE
			   SYNTAX           INTEGER
									{
									noAlarm(1),
									majorLowAlarm(2),
									minorLowAlarm(3),
									minorHighAlarm(4),
									majorHighAlarm(5),
									informational(6)
									}
			   ACCESS           read-only
			   STATUS           mandatory
			   DESCRIPTION
			   "The value of this object provides the curent alarm state of
			    the Tx 1 24 Volt supply voltage Analog parameter."
			   ::= { gx2dualdrr2xAnalogEntry 155}  
			   
    			   
-- Transmitter 1 Module Temperature           OBJECT-TYPE
		dualdrr2xlabelTx1ModTemp             OBJECT-TYPE
			   SYNTAX           DisplayString (SIZE (0..80))
			   ACCESS           read-only
			   STATUS           optional
			   DESCRIPTION
			   "The value of this object provides the label of the
			    Tx 1 24 Module Temperature Analog parameter."
			   ::= { gx2dualdrr2xAnalogEntry 156}

		dualdrr2xuomTx1ModTemp             OBJECT-TYPE
			   SYNTAX           DisplayString (SIZE (0..80))
			   ACCESS           read-only
			   STATUS           optional
			   DESCRIPTION
			   "The value of this object provides the Unit of Measure of the
			    Tx 1 Module Temperature Analog parameter."
			   ::= { gx2dualdrr2xAnalogEntry 157}

		dualdrr2xmajorHighTx1ModTemp       OBJECT-TYPE
			   SYNTAX           Float 
			   ACCESS           read-only
			   STATUS           mandatory
			   DESCRIPTION
			   "The value of this object provides the Major High alarm value
			    of the Tx 1 Module Temperature Analog parameter."
			   ::= { gx2dualdrr2xAnalogEntry 158}


		dualdrr2xmajorLowTx1ModTemp        OBJECT-TYPE
			   SYNTAX           Float 
			   ACCESS           read-only
			   STATUS           mandatory
			   DESCRIPTION
			   "The value of this object provides the Major Low alarm value
			    of the Tx 1 Module Temperature Analog parameter."
			   ::= { gx2dualdrr2xAnalogEntry 159}

		dualdrr2xminorHighTx1ModTemp       OBJECT-TYPE
			   SYNTAX           Float
			   ACCESS           read-only
			   STATUS           obsolete
			   DESCRIPTION
			   "This object is not used by this module and always returns invalid float value
			    of 0xFFFFFFFF . It is kept here for persistence."
			   ::= { gx2dualdrr2xAnalogEntry 160}

		dualdrr2xminorLowTx1ModTemp        OBJECT-TYPE
			   SYNTAX           Float 
			   ACCESS           read-only
			   STATUS           obsolete
			   DESCRIPTION
			   "This object is not used by this module and always returns invalid float value
			    of 0xFFFFFFFF . It is kept here for persistence."
			   ::= { gx2dualdrr2xAnalogEntry 161}

		dualdrr2xcurrentValueTx1ModTemp    OBJECT-TYPE
			   SYNTAX           Float 
			   ACCESS           read-only
			   STATUS           mandatory
			   DESCRIPTION
			   "The value of this object provides the current value
			    of the Tx 1 Module Temperature Analog parameter."
			   ::= { gx2dualdrr2xAnalogEntry 162}

		dualdrr2xstateFlagTx1ModTemp       OBJECT-TYPE
			   SYNTAX           INTEGER
								{
								hidden(1),
								read-only(2),
								updateable(3)
								}
			   ACCESS           read-only
			   STATUS           mandatory
			   DESCRIPTION
			   "The value of this object provides the state
			    of the Tx 1 Module Temperature Analog parameter. (1-hidden	
			          2-read-only, 3-updateable)."
			   ::= { gx2dualdrr2xAnalogEntry 163}

		dualdrr2xminValueTx1ModTemp        OBJECT-TYPE
			   SYNTAX           Float
			   ACCESS           read-only
			   STATUS           mandatory
			   DESCRIPTION
			   "The value of this object provides the minimum value
			    the Tx 1 Module Temperature Analog parameter can achive."
			   ::= { gx2dualdrr2xAnalogEntry 164}

		dualdrr2xmaxValueTx1ModTemp        OBJECT-TYPE
			   SYNTAX           Float
			   ACCESS           read-only
			   STATUS           mandatory
			   DESCRIPTION
			   "The value of this object provides the maximum value
			    the Tx 1 Module Temperature Analog parameter can achive."
			   ::= { gx2dualdrr2xAnalogEntry 165}

        dualdrr2xalarmStateTx1ModTemp      OBJECT-TYPE
			   SYNTAX           INTEGER
									{
									noAlarm(1),
									majorLowAlarm(2),
									minorLowAlarm(3),
									minorHighAlarm(4),
									majorHighAlarm(5),
									informational(6)
									}
			   ACCESS           read-only
			   STATUS           mandatory
			   DESCRIPTION
			   "The value of this object provides the curent alarm state of
			    the Tx 1 Module Temperature Analog parameter."
			   ::= { gx2dualdrr2xAnalogEntry 166}  
			   
    			   
-- ************************ Digital parameters **********************************
		gx2dualdrr2xDigitalTableIndex              OBJECT-TYPE
			   SYNTAX           INTEGER (1..2147483647)
			   ACCESS           read-only
			   STATUS           mandatory
			   DESCRIPTION
			   "The value of this object identifies the network
			    element. This index is equal to the
			    hfcCommonTableIndex for the same element."
               ::= { gx2dualdrr2xDigitalEntry 1}
               
   -- Trip point Value 1   

         dualdrr2xlabelTrippoint1Value          OBJECT-TYPE
			   SYNTAX       		DisplayString (SIZE (0..80))         
			   ACCESS           	read-only
			   STATUS           	optional
			   DESCRIPTION
			   "The value of this object provides the label of the
			    Trip point Value Digital parameter. The trip point Value defines the RF switch 
                point based on the optical power input to the DRR"
			   ::= { gx2dualdrr2xDigitalEntry 2}

		dualdrr2xenumTrippoint1Value               	OBJECT-TYPE
			   SYNTAX       		DisplayString (SIZE (0..80))         
			   ACCESS           	read-only
			   STATUS           	optional
			   DESCRIPTION
			   "The value of this object represents the Enumeration values
			    possible for the Digital parameter. Each Enumerated values is
			    separated by a common. "
			   ::= { gx2dualdrr2xDigitalEntry 3}

		dualdrr2xvalueTrippoint1Value         	OBJECT-TYPE
			   SYNTAX					INTEGER 			   									    	
			   ACCESS           	read-write
			   STATUS           	mandatory
			   DESCRIPTION
			   "The value of this object reflects the setting of the threshold at 
			    which the Trip point activates. It is in 1 dB increments 
                      ranging from -25 to -5 dB. The user can enter a number from 0 to 20,
			    where 0 = -5db and 19 = -25db"
   			   ::= { gx2dualdrr2xDigitalEntry 4}

		dualdrr2xstateflagTrippoint1Value     	OBJECT-TYPE
			   SYNTAX       		INTEGER
								{
								hidden(1),
								readOnly(2),
								updateable(3)
								}
			   ACCESS           	read-only
			   STATUS           	mandatory
			   DESCRIPTION
			   "The value of this object provides the state
			    of the the parameter. (1-Hidden 2-Read-Only, 3-Updateable)."
			   ::= { gx2dualdrr2xDigitalEntry 5}
			   		   		   		   
   -- Trip point mode 1  

         dualdrr2xlabelTrippoint1Mode          OBJECT-TYPE
			   SYNTAX       		DisplayString (SIZE (0..80))         
			   ACCESS           	read-only
			   STATUS           	optional
			   DESCRIPTION
			   "The value of this object provides the label of the
			    Trip point mode Digital parameter. The trip point mode defines the RF switch 
                      action based on the optical power input to the DRR"
			   ::= { gx2dualdrr2xDigitalEntry 6}

		dualdrr2xenumTrippoint1Mode               	OBJECT-TYPE
			   SYNTAX       		DisplayString (SIZE (0..80))         
			   ACCESS           	read-only
			   STATUS           	optional
			   DESCRIPTION
			   "The value of this object represents the Enumeration values
			    possible for the Digital parameter. Each Enumerated values is
			    separated by a common. "
			   ::= { gx2dualdrr2xDigitalEntry 7}


		dualdrr2xvalueTrippoint1Mode         	OBJECT-TYPE
			   SYNTAX					INTEGER{
			   							off(1),
			   							alarmOnly(2),
			   							alarm-and-Switch(3)
			   							}			   					    	
			   ACCESS           	read-write
			   STATUS           	mandatory
			   DESCRIPTION
			   "The value of this object is the current value of trip point mode.
			   There are three possible value: 1-off, 2-alarm_only, 3-alarm&switch.
			   			   
			   If module input optical power is higher than the preset trippoint value,
			        no operational difference for these three modes. 
			   
			   If module input optical power is less than the preset trippoint value, 
                     1) When trippoint mode is OFF, no trippoint alarm will be generated and RF output impedance 
                     will stay normal as low.
                     2) When tripoint mode is ALARM_ONLY, trip_point alarm will be generated when the input optical power 
                     lower than the preset trippoint level but RF output impedance will stay normal as low. 
                     3) When trippoint mode is ALARM_SWITCH, trip point alarm will be generated and RF output impedance 
                     will switch to abnorml"
			   ::= { gx2dualdrr2xDigitalEntry 8}

		dualdrr2xstateflagTrippoint1Mode     	OBJECT-TYPE
			   SYNTAX       		INTEGER
								{
								hidden(1),
								readOnly(2),
								updateable(3)
								}
			   ACCESS           	read-only
			   STATUS           	mandatory
			   DESCRIPTION
			   "The value of this object provides the state
			    of the the parameter. (1-Hidden 2-Read-Only, 3-Updateable)."
			   ::= { gx2dualdrr2xDigitalEntry 9}
			   		   		   		   
   -- Trip point Value 2   

         dualdrr2xlabelTrippoint2Value          OBJECT-TYPE
			   SYNTAX       		DisplayString (SIZE (0..80))         
			   ACCESS           	read-only
			   STATUS           	optional
			   DESCRIPTION
			   "The value of this object provides the label of the
			    Trip point Value Digital parameter. The trip point Value defines the RF switch 
                point based on the optical power input to the DRR"
			   ::= { gx2dualdrr2xDigitalEntry 10}

		dualdrr2xenumTrippoint2Value               	OBJECT-TYPE
			   SYNTAX       		DisplayString (SIZE (0..80))         
			   ACCESS           	read-only
			   STATUS           	optional
			   DESCRIPTION
			   "The value of this object represents the Enumeration values
			    possible for the Digital parameter. Each Enumerated values is
			    separated by a common. "
			   ::= { gx2dualdrr2xDigitalEntry 11}

		dualdrr2xvalueTrippoint2Value         	OBJECT-TYPE
			   SYNTAX					INTEGER   	
			   ACCESS           	read-write
			   STATUS           	mandatory
			   DESCRIPTION
			   "The value of this object reflects the setting of the threshold at 
			    which the Trip point activates. It is in 1 dB increments 
                      ranging from -25 to -5 dB. The user can enter a number from 0 to 20,
			    where 0 = -5db and 19 = -25db"
   			   ::= { gx2dualdrr2xDigitalEntry 12}

		dualdrr2xstateflagTrippoint2Value     	OBJECT-TYPE
			   SYNTAX       		INTEGER
								{
								hidden(1),
								readOnly(2),
								updateable(3)
								}
			   ACCESS           	read-only
			   STATUS           	mandatory
			   DESCRIPTION
			   "The value of this object provides the state
			    of the the parameter. (1-Hidden 2-Read-Only, 3-Updateable)."
			   ::= { gx2dualdrr2xDigitalEntry 13}
			   		   		   		   
   -- Trip point mode 2  

         dualdrr2xlabelTrippoint2Mode          OBJECT-TYPE
			   SYNTAX       		DisplayString (SIZE (0..80))         
			   ACCESS           	read-only
			   STATUS           	optional
			   DESCRIPTION
			   "The value of this object provides the label of the
			    Trip point mode Digital parameter. The trip point mode defines the RF switch 
                action based on the optical power input to the DRR"
			   ::= { gx2dualdrr2xDigitalEntry 14}

		dualdrr2xenumTrippoint2Mode               	OBJECT-TYPE
			   SYNTAX       		DisplayString (SIZE (0..80))         
			   ACCESS           	read-only
			   STATUS           	optional
			   DESCRIPTION
			   "The value of this object represents the Enumeration values
			    possible for the Digital parameter. Each Enumerated values is
			    separated by a common. "
			   ::= { gx2dualdrr2xDigitalEntry 15}


		dualdrr2xvalueTrippoint2Mode         	OBJECT-TYPE
			   SYNTAX					INTEGER{
			   							off(1),
			   							alarmOnly(2),
			   							alarm-and-Switch(3)
			   							}			   					    	
			   ACCESS           	read-write
			   STATUS           	mandatory
			   DESCRIPTION
			   "The value of this object is the current value of trip point mode.
			   There are three possible value: 1-off, 2-alarm_only, 3-alarm&switch.
			   			   
			   If module input optical power is higher than the preset trippoint value,
			        no operational difference for these three modes. 
			   
			   If module input optical power is less than the preset trippoint value, 
                     1) When trippoint mode is OFF, no trippoint alarm will be generated and RF output impedance 
                     will stay normal as low.
                     2) When tripoint mode is ALARM_ONLY, trip_point alarm will be generated when the input optical power 
                     lower than the preset trippoint level but RF output impedance will stay normal as low. 
                     3) When trippoint mode is ALARM_SWITCH, trip point alarm will be generated and RF output impedance 
                     will switch to abnorml"
			   ::= { gx2dualdrr2xDigitalEntry 16}

		dualdrr2xstateflagTrippoint2Mode     	OBJECT-TYPE
			   SYNTAX       		INTEGER
								{
								hidden(1),
								readOnly(2),
								updateable(3)
								}
			   ACCESS           	read-only
			   STATUS           	mandatory
			   DESCRIPTION
			   "The value of this object provides the state
			    of the the parameter. (1-Hidden 2-Read-Only, 3-Updateable)."
			   ::= { gx2dualdrr2xDigitalEntry 17}
			   		   		   		   
   -- RF Channel 1A Gain  

         dualdrr2xlabelGainChannel1A          OBJECT-TYPE
			   SYNTAX       		DisplayString (SIZE (0..80))         
			   ACCESS           	read-only
			   STATUS           	optional
			   DESCRIPTION
			   "The value of this object provides the label of the
			    RF Channel 1A Gain Digital parameter. "
			   ::= { gx2dualdrr2xDigitalEntry 18}

		dualdrr2xenumGainChannel1A               	OBJECT-TYPE
			   SYNTAX       		DisplayString (SIZE (0..80))         
			   ACCESS           	read-only
			   STATUS           	optional
			   DESCRIPTION
			   "The value of this object represents the Enumeration values
			    possible for the Digital parameter. Each Enumerated values is
			    separated by a common. "
			   ::= { gx2dualdrr2xDigitalEntry 19}


		dualdrr2xvalueGainChannel1A         	OBJECT-TYPE
			   SYNTAX				INTEGER
			   ACCESS           	read-write
			   STATUS           	mandatory
			   DESCRIPTION
			   "The value of this object reflects the setting of the gain for
			    RF Channel 1A. It is in 1 dB increments 
                ranging from 0 to 20dB. The user can enter a number from 0 to 20"
                
			   ::= { gx2dualdrr2xDigitalEntry 20}

		dualdrr2xstateflagGainChannel1A     	OBJECT-TYPE
			   SYNTAX       		INTEGER
								{
								hidden(1),
								readOnly(2),
								updateable(3)
								}
			   ACCESS           	read-only
			   STATUS           	mandatory
			   DESCRIPTION
			   "The value of this object provides the state
			    of the the parameter. (1-Hidden 2-Read-Only, 3-Updateable)."
			   ::= { gx2dualdrr2xDigitalEntry 21}
			   		   		   		   
   -- RF Channel 1B Gain  

         dualdrr2xlabelGainChannel1B          OBJECT-TYPE
			   SYNTAX       		DisplayString (SIZE (0..80))         
			   ACCESS           	read-only
			   STATUS           	optional
			   DESCRIPTION
			   "The value of this object provides the label of the
			    RF Channel 1B Gain Digital parameter. "
			   ::= { gx2dualdrr2xDigitalEntry 22}

		dualdrr2xenumGainChannel1B               	OBJECT-TYPE
			   SYNTAX       		DisplayString (SIZE (0..80))         
			   ACCESS           	read-only
			   STATUS           	optional
			   DESCRIPTION
			   "The value of this object represents the Enumeration values
			    possible for the Digital parameter. Each Enumerated values is
			    separated by a common. "
			   ::= { gx2dualdrr2xDigitalEntry 23}


		dualdrr2xvalueGainChannel1B         	OBJECT-TYPE
			   SYNTAX				INTEGER
			   ACCESS           	read-write
			   STATUS           	mandatory
			   DESCRIPTION
			   "The value of this object reflects the setting of the gain for
			    RF Channel 1B. It is in 1 dB increments 
                ranging from 0 to 20dB. The user can enter a number from 0 to 20"
                
			   ::= { gx2dualdrr2xDigitalEntry 24}

		dualdrr2xstateflagGainChannel1B     	OBJECT-TYPE
			   SYNTAX       		INTEGER
								{
								hidden(1),
								readOnly(2),
								updateable(3)
								}
			   ACCESS           	read-only
			   STATUS           	mandatory
			   DESCRIPTION
			   "The value of this object provides the state
			    of the the parameter. (1-Hidden 2-Read-Only, 3-Updateable)."
			   ::= { gx2dualdrr2xDigitalEntry 25}
			   		   		   		   
   -- RF Channel 2A Gain  

         dualdrr2xlabelGainChannel2A          OBJECT-TYPE
			   SYNTAX       		DisplayString (SIZE (0..80))         
			   ACCESS           	read-only
			   STATUS           	optional
			   DESCRIPTION
			   "The value of this object provides the label of the
			    RF Channel 2A Gain Digital parameter. "
			   ::= { gx2dualdrr2xDigitalEntry 26}

		dualdrr2xenumGainChannel2A               	OBJECT-TYPE
			   SYNTAX       		DisplayString (SIZE (0..80))         
			   ACCESS           	read-only
			   STATUS           	optional
			   DESCRIPTION
			   "The value of this object represents the Enumeration values
			    possible for the Digital parameter. Each Enumerated values is
			    separated by a common. "
			   ::= { gx2dualdrr2xDigitalEntry 27}


		dualdrr2xvalueGainChannel2A         	OBJECT-TYPE
			   SYNTAX				INTEGER
			   ACCESS           	read-write
			   STATUS           	mandatory
			   DESCRIPTION
			   "The value of this object reflects the setting of the gain for
			    RF Channel 2A. It is in 1 dB increments 
                ranging from 0 to 20dB. The user can enter a number from 0 to 20"
                
			   ::= { gx2dualdrr2xDigitalEntry 28}

		dualdrr2xstateflagGainChannel2A     	OBJECT-TYPE
			   SYNTAX       		INTEGER
								{
								hidden(1),
								readOnly(2),
								updateable(3)
								}
			   ACCESS           	read-only
			   STATUS           	mandatory
			   DESCRIPTION
			   "The value of this object provides the state
			    of the the parameter. (1-Hidden 2-Read-Only, 3-Updateable)."
			   ::= { gx2dualdrr2xDigitalEntry 29}
			   		   		   		   
   -- RF Channel 2B Gain  

         dualdrr2xlabelGainChannel2B          OBJECT-TYPE
			   SYNTAX       		DisplayString (SIZE (0..80))         
			   ACCESS           	read-only
			   STATUS           	optional
			   DESCRIPTION
			   "The value of this object provides the label of the
			    RF Channel 2B Gain Digital parameter. "
			   ::= { gx2dualdrr2xDigitalEntry 30}

		dualdrr2xenumGainChannel2B               	OBJECT-TYPE
			   SYNTAX       		DisplayString (SIZE (0..80))         
			   ACCESS           	read-only
			   STATUS           	optional
			   DESCRIPTION
			   "The value of this object represents the Enumeration values
			    possible for the Digital parameter. Each Enumerated values is
			    separated by a common. "
			   ::= { gx2dualdrr2xDigitalEntry 31}


		dualdrr2xvalueGainChannel2B         	OBJECT-TYPE
			   SYNTAX				INTEGER
			   ACCESS           	read-write
			   STATUS           	mandatory
			   DESCRIPTION
			   "The value of this object reflects the setting of the gain for
			    RF Channel 2B. It is in 1 dB increments 
                ranging from 0 to 20dB. The user can enter a number from 0 to 20"
                
			   ::= { gx2dualdrr2xDigitalEntry 32}

		dualdrr2xstateflagGainChannel2B     	OBJECT-TYPE
			   SYNTAX       		INTEGER
								{
								hidden(1),
								readOnly(2),
								updateable(3)
								}
			   ACCESS           	read-only
			   STATUS           	mandatory
			   DESCRIPTION
			   "The value of this object provides the state
			    of the the parameter. (1-Hidden 2-Read-Only, 3-Updateable)."
			   ::= { gx2dualdrr2xDigitalEntry 33}
			   		   		   		   
   -- Testpoint Select

         dualdrr2xlabelTestpointSelect          OBJECT-TYPE
			   SYNTAX       		DisplayString (SIZE (0..80))         
			   ACCESS           	read-only
			   STATUS           	optional
			   DESCRIPTION
			   "The value of this object provides the label of the
			    Module's test point select Digital parameter. "
			   ::= { gx2dualdrr2xDigitalEntry 34}

		dualdrr2xenumTestpointSelect               	OBJECT-TYPE
			   SYNTAX       		DisplayString (SIZE (0..80))         
			   ACCESS           	read-only
			   STATUS           	optional
			   DESCRIPTION
			   "The value of this object represents the Enumeration values
			    possible for the Digital parameter. Each Enumerated values is
			    separated by a common. "
			   ::= { gx2dualdrr2xDigitalEntry 35}

		dualdrr2xvalueTestpointSelect         	OBJECT-TYPE
			   SYNTAX				INTEGER
								{
								one(1),
								two(2),
								three(3),
								four(4)
								}
			   ACCESS           	read-write
			   STATUS           	mandatory
			   DESCRIPTION
			   "The value of this object reflects the setting of the test point selector for
			    The Module. The user can enter a number from 1 to 4"
                
			   ::= { gx2dualdrr2xDigitalEntry 36}

		dualdrr2xstateflagTestpointSelect     	OBJECT-TYPE
			   SYNTAX       		INTEGER
								{
								hidden(1),
								readOnly(2),
								updateable(3)
								}
			   ACCESS           	read-only
			   STATUS           	mandatory
			   DESCRIPTION
			   "The value of this object provides the state
			    of the the parameter. (1-Hidden 2-Read-Only, 3-Updateable)."
			   ::= { gx2dualdrr2xDigitalEntry 37}
			   		   		   		   
   -- Active Channel Select

         dualdrr2xlabelOpFrequency          OBJECT-TYPE
			   SYNTAX       		DisplayString (SIZE (0..80))         
			   ACCESS           	read-only
			   STATUS           	optional
			   DESCRIPTION
			   "The value of this object provides the label of the
			    Module's active channels Digital parameter. "
			   ::= { gx2dualdrr2xDigitalEntry 38}

		dualdrr2xenumOpFrequency               	OBJECT-TYPE
			   SYNTAX       		DisplayString (SIZE (0..80))         
			   ACCESS           	read-only
			   STATUS           	optional
			   DESCRIPTION
			   "The value of this object represents the Enumeration values
			    possible for the Digital parameter. Each Enumerated values is
			    separated by a common. "
			   ::= { gx2dualdrr2xDigitalEntry 39}

		dualdrr2xvalueOpFrequency         	OBJECT-TYPE
			   SYNTAX				INTEGER
								{
								eightyfive(1),
								sixtyfive(2)
								}
			   ACCESS           	read-write
			   STATUS           	mandatory
			   DESCRIPTION
			   "The value of this object reflects which channels are active for
			    The Module. The user can enter a number from 1 to 4"
                
			   ::= { gx2dualdrr2xDigitalEntry 40}

		dualdrr2xstateflagOpFrequency     	OBJECT-TYPE
			   SYNTAX       		INTEGER
								{
								hidden(1),
								readOnly(2),
								updateable(3)
								}
			   ACCESS           	read-only
			   STATUS           	mandatory
			   DESCRIPTION
			   "The value of this object provides the state
			    of the the parameter. (1-Hidden 2-Read-Only, 3-Updateable)."
			   ::= { gx2dualdrr2xDigitalEntry 41}
			   		   		   		   
   -- Active Channel Select

         dualdrr2xlabelActChanSelect          OBJECT-TYPE
			   SYNTAX       		DisplayString (SIZE (0..80))         
			   ACCESS           	read-only
			   STATUS           	optional
			   DESCRIPTION
			   "The value of this object provides the label of the
			    Module's active channels Digital parameter. "
			   ::= { gx2dualdrr2xDigitalEntry 42}

		dualdrr2xenumActChanSelect               	OBJECT-TYPE
			   SYNTAX       		DisplayString (SIZE (0..80))         
			   ACCESS           	read-only
			   STATUS           	optional
			   DESCRIPTION
			   "The value of this object represents the Enumeration values
			    possible for the Digital parameter. Each Enumerated values is
			    separated by a common. "
			   ::= { gx2dualdrr2xDigitalEntry 43}

		dualdrr2xvalueActChanSelect         	OBJECT-TYPE
			   SYNTAX				INTEGER
								{
								none(1),
								channel1(2),
								channel2(3),
								both(4)
								}
			   ACCESS           	read-write
			   STATUS           	mandatory
			   DESCRIPTION
			   "The value of this object reflects which channels are active for
			    The Module. The user can enter a number from 1 to 4"
                
			   ::= { gx2dualdrr2xDigitalEntry 44}

		dualdrr2xstateflagActChanSelect     	OBJECT-TYPE
			   SYNTAX       		INTEGER
								{
								hidden(1),
								readOnly(2),
								updateable(3)
								}
			   ACCESS           	read-only
			   STATUS           	mandatory
			   DESCRIPTION
			   "The value of this object provides the state
			    of the the parameter. (1-Hidden 2-Read-Only, 3-Updateable)."
			   ::= { gx2dualdrr2xDigitalEntry 45}
			   		   		   		   
-- Factory default reset 

         dualdrr2xlabelFactoryDefaultReset           OBJECT-TYPE
			   SYNTAX       		DisplayString (SIZE (0..80))         
			   ACCESS           	read-only
			   STATUS           	optional
			   DESCRIPTION
			   "The value of this object provides the label of the
			    Factory Default Reset  Digital parameter."
			   ::= { gx2dualdrr2xDigitalEntry 46}

		dualdrr2xenumFactoryDefaultReset               	OBJECT-TYPE
			   SYNTAX       		DisplayString (SIZE (0..80))         
			   ACCESS           	read-only
			   STATUS           	optional
			   DESCRIPTION
			   "The value of this object represents the Enumeration values
			    possible for the Digital parameter. Each Enumerated values is
			    separated by a common. The first value has a enumerated value of 1."
			   ::= { gx2dualdrr2xDigitalEntry 47}


		dualdrr2xvalueFactoryDefaultReset         	OBJECT-TYPE
			   SYNTAX       		INTEGER
					    		{
							off(1),
							on(2)
					    		}
			   ACCESS           	read-write
			   STATUS           	mandatory
			   DESCRIPTION
			   "The read of this value will return a invalid value.
			    The read will not reflect the actual setting value for this parameter
			   "
			   ::= { gx2dualdrr2xDigitalEntry 48}

		dualdrr2xstateflagFactoryDefaultReset     	OBJECT-TYPE
			   SYNTAX       		INTEGER
								{
								hidden(1),
								read-only(2),
								updateable(3)
								}
			   ACCESS           	read-only
			   STATUS           	mandatory
			   DESCRIPTION
			   "The value of this object provides the state
			    of the the parameter. (1-Hidden 2-Read-Only, 3-Updateable)."
			   ::= { gx2dualdrr2xDigitalEntry 49} 
			   
   
 	--*********** STATUS *****************

		gx2dualdrr2xStatusTableIndex              OBJECT-TYPE
			   SYNTAX           INTEGER (1..2147483647)
			   ACCESS           read-only
			   STATUS           mandatory
			   DESCRIPTION
			   "The value of this object identifies the network
			    element. This index is equal to the
			    hfcCommonTableIndex for the same element."
			   ::= { gx2dualdrr2xStatusEntry 1}

--Boot status 
		dualdrr2xlabelBoot               	OBJECT-TYPE
			   SYNTAX       		DisplayString (SIZE (0..80))         
			   ACCESS           	read-only
			   STATUS           	optional
			   DESCRIPTION
			   "The value of this object provides the label of the
			    Boot Status  parameter."
			   ::= { gx2dualdrr2xStatusEntry 2}

		dualdrr2xvalueBoot              		OBJECT-TYPE
			   SYNTAX       		INTEGER
									{
									ok(1),
									undetermined(2),
									warning(3),
									minor(4),
									major(5),
									critical(6)
									}
			   ACCESS           	read-only
			   STATUS           	mandatory
			   DESCRIPTION
			   "The value of this object provides the current state of
			    the parameter (1-Ok, 2-Undetermined
			    3-Warning, 4-Minor, 5-Major, 6-Critical)."
			   ::= { gx2dualdrr2xStatusEntry 3}

		dualdrr2xstateflagBoot     	OBJECT-TYPE
			   SYNTAX       		INTEGER
								{
								hidden(1),
								read-only(2),
								updateable(3)
								}
			   ACCESS           	read-only
			   STATUS           	mandatory
			   DESCRIPTION
			   "The value of this object provides the state
			    of the the parameter. (1-Hidden 2-Read-Only, 3-Updateable)."
			   ::= { gx2dualdrr2xStatusEntry  4}

--Flash program status 
		dualdrr2xlabelFlash               	OBJECT-TYPE
			   SYNTAX       		DisplayString (SIZE (0..80))         
			   ACCESS           	read-only
			   STATUS           	optional
			   DESCRIPTION
			   "The value of this object provides the label of the
			    Flash Status  parameter."
			   ::= { gx2dualdrr2xStatusEntry 5}

		dualdrr2xvalueFlash              	OBJECT-TYPE
			   SYNTAX       		INTEGER
									{
									ok(1),
									undetermined(2),
									warning(3),
									minor(4),
									major(5),
									critical(6)
									}
			   ACCESS           	read-only
			   STATUS           	mandatory
			   DESCRIPTION
			   "The value of this object provides the current state of
			    the parameter (1-Ok, 2-Undetermined
			    3-Warning, 4-Minor, 5-Major, 6-Critical)."
			   ::= { gx2dualdrr2xStatusEntry 6}

		dualdrr2xstateflagFlash     	OBJECT-TYPE
			   SYNTAX       		INTEGER
								{
								hidden(1),
								read-only(2),
								updateable(3)
								}
			   ACCESS           	read-only
			   STATUS           	mandatory
			   DESCRIPTION
			   "The value of this object provides the state
			    of the the parameter. (1-Hidden 2-Read-Only, 3-Updateable)."
			   ::= { gx2dualdrr2xStatusEntry  7}

--Factory data crc 
		dualdrr2xlabelFactoryDataCRC           OBJECT-TYPE
			   SYNTAX       		DisplayString (SIZE (0..80))         
			   ACCESS           	read-only
			   STATUS           	optional
			   DESCRIPTION
			   "The value of this object provides the label of the
			    Factory Data CRC Status parameter."
			   ::= { gx2dualdrr2xStatusEntry 8}

		dualdrr2xvalueFactoryDataCRC          	OBJECT-TYPE
			   SYNTAX       		INTEGER
									{
									ok(1),
									undetermined(2),
									warning(3),
									minor(4),
									major(5),
									critical(6)
									}
			   ACCESS           	read-only
			   STATUS           	mandatory
			   DESCRIPTION
			   "The value of this object provides the current state of
			    the parameter (1-Ok, 2-Undetermined
			    3-Warning, 4-Minor, 5-Major, 6-Critical)."
			   ::= { gx2dualdrr2xStatusEntry 9}

		dualdrr2xstateflagFactoryDataCRC     	OBJECT-TYPE
			   SYNTAX       		INTEGER
								{
								hidden(1),
								read-only(2),
								updateable(3)
								}
			   ACCESS           	read-only
			   STATUS           	mandatory
			   DESCRIPTION
			   "The value of this object provides the state
			    of the the parameter. (1-Hidden 2-Read-Only, 3-Updateable)."
			   ::= { gx2dualdrr2xStatusEntry  10}

--Alarm data status CRC
		dualdrr2xlabelAlarmDataCrc               	      OBJECT-TYPE
			   SYNTAX       		DisplayString (SIZE (0..80))         
			   ACCESS           	read-only
			   STATUS           	optional
			   DESCRIPTION
			   "The value of this object provides the label of the
			    Alarm Data Crc parameter."
			   ::= { gx2dualdrr2xStatusEntry 11}

		dualdrr2xvalueAlarmDataCrc              		OBJECT-TYPE
			   SYNTAX       		INTEGER
									{
									ok(1),
									undetermined(2),
									warning(3),
									minor(4),
									major(5),
									critical(6)
									}
			   ACCESS           	read-only
			   STATUS           	mandatory
			   DESCRIPTION
			   "The value of this object provides the current state of
			    the parameter (1-Ok, 2-Undetermined
			    3-Warning, 4-Minor, 5-Major, 6-Critical)."
			   ::= { gx2dualdrr2xStatusEntry 12}

		dualdrr2xstateflagAlarmDataCrc     	OBJECT-TYPE
			   SYNTAX       		INTEGER
								{
								hidden(1),
								read-only(2),
								updateable(3)
								}
			   ACCESS           	read-only
			   STATUS           	mandatory
			   DESCRIPTION
			   "The value of this object provides the state
			    of the the parameter. (1-Hidden 2-Read-Only, 3-Updateable)."
			   ::= { gx2dualdrr2xStatusEntry  13}

--Calibration data status CRC
		dualdrr2xlabelCalibrationDataCrc               	      OBJECT-TYPE
			   SYNTAX       		DisplayString (SIZE (0..80))         
			   ACCESS           	read-only
			   STATUS           	optional
			   DESCRIPTION
			   "The value of this object provides the label of the
			    Calibration Data Crc parameter."
			   ::= { gx2dualdrr2xStatusEntry 14}

		dualdrr2xvalueCalibrationDataCrc              		OBJECT-TYPE
			   SYNTAX       		INTEGER
									{
									ok(1),
									undetermined(2),
									warning(3),
									minor(4),
									major(5),
									critical(6)
									}
			   ACCESS           	read-only
			   STATUS           	mandatory
			   DESCRIPTION
			   "The value of this object provides the current state of
			    the parameter (1-Ok, 2-Undetermined
			    3-Warning, 4-Minor, 5-Major, 6-Critical)."
			   ::= { gx2dualdrr2xStatusEntry 15}

		dualdrr2xstateflagCalibrationDataCrc     	OBJECT-TYPE
			   SYNTAX       		INTEGER
								{
								hidden(1),
								read-only(2),
								updateable(3)
								}
			   ACCESS           	read-only
			   STATUS           	mandatory
			   DESCRIPTION
			   "The value of this object provides the state
			    of the the parameter. (1-Hidden 2-Read-Only, 3-Updateable)."
			   ::= { gx2dualdrr2xStatusEntry  16}



--Module hardware status
		dualdrr2xlabelHardwareStatus              OBJECT-TYPE
			   SYNTAX       		DisplayString (SIZE (0..80))         
			   ACCESS           	read-only
			   STATUS           	optional
			   DESCRIPTION
			   "The value of this object provides the label of the
			   Module Hardware Status parameter."
			   ::= { gx2dualdrr2xStatusEntry 17}

		dualdrr2xvalueHardwareStatus              OBJECT-TYPE
			   SYNTAX       		INTEGER
									{
									ok(1),
									undetermined(2),
									warning(3),
									minor(4),
									major(5),
									critical(6)
									}
			   ACCESS           	read-only
			   STATUS           	mandatory
			   DESCRIPTION
			   "The value of this object provides the current state of
			    the parameter (1-Ok, 2-Undetermined
			    3-Warning, 4-Minor, 5-Major, 6-Critical)."
			   ::= { gx2dualdrr2xStatusEntry 18}

		dualdrr2xstateflagHardwareStatus     	OBJECT-TYPE
			   SYNTAX       		INTEGER
								{
								hidden(1),
								read-only(2),
								updateable(3)
								}
			   ACCESS           	read-only
			   STATUS           	mandatory
			   DESCRIPTION
			   "The value of this object provides the state
			    of the parameter. (1-Hidden 2-Read-Only, 3-Updateable)."
			   ::= { gx2dualdrr2xStatusEntry  19}
                            		
  --Channel 1 trip point status
   
		dualdrr2xlabelCh1TripPointStatus              OBJECT-TYPE
			   SYNTAX       		DisplayString (SIZE (0..80))         
			   ACCESS           	read-only
			   STATUS           	optional
			   DESCRIPTION
			   "The value of this object provides the label of the
			    Optical Trip Point Status parameter.It indicates whether 
			    the optical power is above(0) or below(1) trip point value"
			   ::= { gx2dualdrr2xStatusEntry 20}

		dualdrr2xvalueCh1TripPointStatus              OBJECT-TYPE
			   SYNTAX       		INTEGER
									{
									ok(1),
									undetermined(2),
									warning(3),
									minor(4),
									major(5),
									critical(6)
									}
			   ACCESS           	read-only
			   STATUS           	mandatory
			   DESCRIPTION
			   "The value of this object provides the current state of
			    the parameter (1-Ok, 2-Undetermined
			    3-Warning, 4-Minor, 5-Major, 6-Critical)."
			   ::= { gx2dualdrr2xStatusEntry 21}

		dualdrr2xstateflagCh1TripPointStatus     	OBJECT-TYPE
			   SYNTAX       		INTEGER
								{
								hidden(1),
								read-only(2),
								updateable(3)
								}
			   ACCESS           	read-only
			   STATUS           	mandatory
			   DESCRIPTION
			   "The value of this object provides the state
			    of the parameter. (1-Hidden 2-Read-Only, 3-Updateable)."
			   ::= { gx2dualdrr2xStatusEntry  22}
    
                                        
  --Link 1 Status 
		dualdrr2xlabelLink1Status              OBJECT-TYPE
			   SYNTAX       		DisplayString (SIZE (0..80))         
			   ACCESS           	read-only
			   STATUS           	optional
			   DESCRIPTION
			   "The value of this object provides the label of the
			    Link Activity Status parameter. It represents receiver
			    out of SYN with transmitter or Demux can not detect 
			    the optical signal."
			   ::= { gx2dualdrr2xStatusEntry 23}

		dualdrr2xvalueLink1Status              OBJECT-TYPE
			   SYNTAX       		INTEGER
									{
									ok(1),
									undetermined(2),
									warning(3),
									minor(4),
									major(5),
									critical(6)
									}
			   ACCESS           	read-only
			   STATUS           	mandatory
			   DESCRIPTION
			   "The value of this object provides the current state of
			    the parameter (1-Ok, 2-Undetermined
			    3-Warning, 4-Minor, 5-Major, 6-Critical)."
			   ::= { gx2dualdrr2xStatusEntry 24}

		dualdrr2xstateflagLink1Status     	OBJECT-TYPE
			   SYNTAX       		INTEGER
								{
								hidden(1),
								read-only(2),
								updateable(3)
								}
			   ACCESS           	read-only
			   STATUS           	mandatory
			   DESCRIPTION
			   "The value of this object provides the state
			    of the parameter. (1-Hidden 2-Read-Only, 3-Updateable)."
			   ::= { gx2dualdrr2xStatusEntry  25}
                          
  --Channel 2 trip point status
   
		dualdrr2xlabelCh2TripPointStatus              OBJECT-TYPE
			   SYNTAX       		DisplayString (SIZE (0..80))         
			   ACCESS           	read-only
			   STATUS           	optional
			   DESCRIPTION
			   "The value of this object provides the label of the
			    Optical Trip Point Status parameter.It indicates whether 
			    the optical power is above(0) or below(1) trip point value"
			   ::= { gx2dualdrr2xStatusEntry 26}

		dualdrr2xvalueCh2TripPointStatus              OBJECT-TYPE
			   SYNTAX       		INTEGER
									{
									ok(1),
									undetermined(2),
									warning(3),
									minor(4),
									major(5),
									critical(6)
									}
			   ACCESS           	read-only
			   STATUS           	mandatory
			   DESCRIPTION
			   "The value of this object provides the current state of
			    the parameter (1-Ok, 2-Undetermined
			    3-Warning, 4-Minor, 5-Major, 6-Critical)."
			   ::= { gx2dualdrr2xStatusEntry 27}

		dualdrr2xstateflagCh2TripPointStatus     	OBJECT-TYPE
			   SYNTAX       		INTEGER
								{
								hidden(1),
								read-only(2),
								updateable(3)
								}
			   ACCESS           	read-only
			   STATUS           	mandatory
			   DESCRIPTION
			   "The value of this object provides the state
			    of the parameter. (1-Hidden 2-Read-Only, 3-Updateable)."
			   ::= { gx2dualdrr2xStatusEntry  28}
                                            
  --Link 2 Status 

		dualdrr2xlabelLink2Status              OBJECT-TYPE
			   SYNTAX       		DisplayString (SIZE (0..80))         
			   ACCESS           	read-only
			   STATUS           	optional
			   DESCRIPTION
			   "The value of this object provides the label of the
			    Link Activity Status parameter. It represents receiver
			    out of SYN with transmitter or Demux can not detect 
			    the optical signal."
			   ::= { gx2dualdrr2xStatusEntry 29}

		dualdrr2xvalueLink2Status              OBJECT-TYPE
			   SYNTAX       		INTEGER
									{
									ok(1),
									undetermined(2),
									warning(3),
									minor(4),
									major(5),
									critical(6)
									}
			   ACCESS           	read-only
			   STATUS           	mandatory
			   DESCRIPTION
			   "The value of this object provides the current state of
			    the parameter (1-Ok, 2-Undetermined
			    3-Warning, 4-Minor, 5-Major, 6-Critical)."
			   ::= { gx2dualdrr2xStatusEntry 30}

		dualdrr2xstateflagLink2Status     	OBJECT-TYPE
			   SYNTAX       		INTEGER
								{
								hidden(1),
								read-only(2),
								updateable(3)
								}
			   ACCESS           	read-only
			   STATUS           	mandatory
			   DESCRIPTION
			   "The value of this object provides the state
			    of the parameter. (1-Hidden 2-Read-Only, 3-Updateable)."
			   ::= { gx2dualdrr2xStatusEntry  31}
                          
  --DRT 0 Status 

		dualdrr2xlabelDRT1Status              OBJECT-TYPE
			   SYNTAX       		DisplayString (SIZE (0..80))         
			   ACCESS           	read-only
			   STATUS           	optional
			   DESCRIPTION
			   "The value of this object provides the label of the
			    Link Activity Status parameter. It represents receiver
			    out of SYN with transmitter or Demux can not detect 
			    the optical signal."
			   ::= { gx2dualdrr2xStatusEntry 32}

		dualdrr2xvalueDRT1Status              OBJECT-TYPE
			   SYNTAX       		INTEGER
									{
									ok(1),
									undetermined(2),
									warning(3),
									minor(4),
									major(5),
									critical(6)
									}
			   ACCESS           	read-only
			   STATUS           	mandatory
			   DESCRIPTION
			   "The value of this object provides the current state of
			    the parameter (1-Ok, 2-Undetermined
			    3-Warning, 4-Minor, 5-Major, 6-Critical)."
			   ::= { gx2dualdrr2xStatusEntry 33}

		dualdrr2xstateflagDRT1Status     	OBJECT-TYPE
			   SYNTAX       		INTEGER
								{
								hidden(1),
								read-only(2),
								updateable(3)
								}
			   ACCESS           	read-only
			   STATUS           	mandatory
			   DESCRIPTION
			   "The value of this object provides the state
			    of the parameter. (1-Hidden 2-Read-Only, 3-Updateable)."
			   ::= { gx2dualdrr2xStatusEntry  34}
                          
                                       
  --SFP 0 Status 

		dualdrr2xlabelSFP0Status              OBJECT-TYPE
			   SYNTAX       		DisplayString (SIZE (0..80))         
			   ACCESS           	read-only
			   STATUS           	optional
			   DESCRIPTION
			   "The value of this object provides the label of the
			    Link Activity Status parameter. It represents receiver
			    out of SYN with transmitter or Demux can not detect 
			    the optical signal."
			   ::= { gx2dualdrr2xStatusEntry 35}

		dualdrr2xvalueSFP0Status              OBJECT-TYPE
			   SYNTAX       		INTEGER
									{
									ok(1),
									undetermined(2),
									warning(3),
									minor(4),
									major(5),
									critical(6)
									}
			   ACCESS           	read-only
			   STATUS           	mandatory
			   DESCRIPTION
			   "The value of this object provides the current state of
			    the parameter (1-Ok, 2-Undetermined
			    3-Warning, 4-Minor, 5-Major, 6-Critical)."
			   ::= { gx2dualdrr2xStatusEntry 36}

		dualdrr2xstateflagSFP0Status     	OBJECT-TYPE
			   SYNTAX       		INTEGER
								{
								hidden(1),
								read-only(2),
								updateable(3)
								}
			   ACCESS           	read-only
			   STATUS           	mandatory
			   DESCRIPTION
			   "The value of this object provides the state
			    of the parameter. (1-Hidden 2-Read-Only, 3-Updateable)."
			   ::= { gx2dualdrr2xStatusEntry  37}
                          
                                       
  --DRT 1 Status 

		dualdrr2xlabelDRT2Status              OBJECT-TYPE
			   SYNTAX       		DisplayString (SIZE (0..80))         
			   ACCESS           	read-only
			   STATUS           	optional
			   DESCRIPTION
			   "The value of this object provides the label of the
			    Link Activity Status parameter. It represents receiver
			    out of SYN with transmitter or Demux can not detect 
			    the optical signal."
			   ::= { gx2dualdrr2xStatusEntry 38}

		dualdrr2xvalueDRT2Status              OBJECT-TYPE
			   SYNTAX       		INTEGER
									{
									ok(1),
									undetermined(2),
									warning(3),
									minor(4),
									major(5),
									critical(6)
									}
			   ACCESS           	read-only
			   STATUS           	mandatory
			   DESCRIPTION
			   "The value of this object provides the current state of
			    the parameter (1-Ok, 2-Undetermined
			    3-Warning, 4-Minor, 5-Major, 6-Critical)."
			   ::= { gx2dualdrr2xStatusEntry 39}

		dualdrr2xstateflagDRT2Status     	OBJECT-TYPE
			   SYNTAX       		INTEGER
								{
								hidden(1),
								read-only(2),
								updateable(3)
								}
			   ACCESS           	read-only
			   STATUS           	mandatory
			   DESCRIPTION
			   "The value of this object provides the state
			    of the parameter. (1-Hidden 2-Read-Only, 3-Updateable)."
			   ::= { gx2dualdrr2xStatusEntry  40}
                          
                                       
  --SFP 1 Status 

		dualdrr2xlabelSFP1Status              OBJECT-TYPE
			   SYNTAX       		DisplayString (SIZE (0..80))         
			   ACCESS           	read-only
			   STATUS           	optional
			   DESCRIPTION
			   "The value of this object provides the label of the
			    Link Activity Status parameter. It represents receiver
			    out of SYN with transmitter or Demux can not detect 
			    the optical signal."
			   ::= { gx2dualdrr2xStatusEntry 41}

		dualdrr2xvalueSFP1Status              OBJECT-TYPE
			   SYNTAX       		INTEGER
									{
									ok(1),
									undetermined(2),
									warning(3),
									minor(4),
									major(5),
									critical(6)
									}
			   ACCESS           	read-only
			   STATUS           	mandatory
			   DESCRIPTION
			   "The value of this object provides the current state of
			    the parameter (1-Ok, 2-Undetermined
			    3-Warning, 4-Minor, 5-Major, 6-Critical)."
			   ::= { gx2dualdrr2xStatusEntry 42}

		dualdrr2xstateflagSFP1Status     	OBJECT-TYPE
			   SYNTAX       		INTEGER
								{
								hidden(1),
								read-only(2),
								updateable(3)
								}
			   ACCESS           	read-only
			   STATUS           	mandatory
			   DESCRIPTION
			   "The value of this object provides the state
			    of the parameter. (1-Hidden 2-Read-Only, 3-Updateable)."
			   ::= { gx2dualdrr2xStatusEntry  43}
                          
                                       
-- ************ FACTORY DATA ****************
		gx2dualdrr2xFactoryTableIndex              OBJECT-TYPE
			   SYNTAX           INTEGER (1..2147483647)
			   ACCESS           read-only
			   STATUS           mandatory
			   DESCRIPTION
			   "The value of this object identifies the network
			    element. This index is equal to the
			    hfcCommonTableIndex for the same element."
			   ::= { gx2dualdrr2xFactoryEntry 1}

		dualdrr2xbootControlByte          	OBJECT-TYPE
			   SYNTAX       		INTEGER
			   ACCESS           	read-only
			   STATUS           	mandatory
			   DESCRIPTION
			   "The value of this object indicates which bank the firmware
			    is currently being boot from."
			   ::= { gx2dualdrr2xFactoryEntry 2}

		dualdrr2xbootStatusByte          	OBJECT-TYPE
			   SYNTAX       		INTEGER
			   ACCESS           	read-only
			   STATUS           	mandatory
			   DESCRIPTION
			   "This object indicates the status of the last boot"
			   ::= { gx2dualdrr2xFactoryEntry 3}

		dualdrr2xbank1CRC          		OBJECT-TYPE
			   SYNTAX       		INTEGER
			   ACCESS           	read-only
			   STATUS           	mandatory
			   DESCRIPTION
			   "This object provides the CRC code of bank 0."
			   ::= { gx2dualdrr2xFactoryEntry 4}

		dualdrr2xbank2CRC          		OBJECT-TYPE
			   SYNTAX       		INTEGER
			   ACCESS           	read-only
			   STATUS           	mandatory
			   DESCRIPTION
			   "This object provides the CRC code of bank 1."
			   ::= { gx2dualdrr2xFactoryEntry 5}

		dualdrr2xprgEEPROMByte          		OBJECT-TYPE
			   SYNTAX       		INTEGER
			   ACCESS           	read-only
			   STATUS           	mandatory
			   DESCRIPTION
			   "This object indicates if the EEPROM has been programmed"
			   ::= { gx2dualdrr2xFactoryEntry 6}

		dualdrr2xfactoryCRC          		OBJECT-TYPE
			   SYNTAX       		INTEGER
			   ACCESS           	read-only
			   STATUS           	mandatory
			   DESCRIPTION
			   "This object provides the CRC code for the Factory data."
			   ::= { gx2dualdrr2xFactoryEntry 7}

		dualdrr2xcalculateCRC          		OBJECT-TYPE
			   SYNTAX       		INTEGER
					    		{
							factory(1),
							alarm(2),
							calibration(3)
					    		}
			   ACCESS           	read-only
			   STATUS           	mandatory
			   DESCRIPTION
			   "This object indicates which of the Emnums will have the
                      CRC calculated (1-factory, 2-alarm, 3-calibration)."
			   ::= { gx2dualdrr2xFactoryEntry 8}

		dualdrr2xhourMeter          		OBJECT-TYPE
			   SYNTAX       		INTEGER
			   ACCESS           	read-only
			   STATUS           	mandatory
			   DESCRIPTION
			   "This object provides the hour meter reading of the module."
			   ::= { gx2dualdrr2xFactoryEntry 9}

		dualdrr2xflashPrgCntA          		OBJECT-TYPE
			   SYNTAX       		INTEGER
			   ACCESS           	read-only
			   STATUS           	mandatory
			   DESCRIPTION
			   "This object provides the number of times Bank 0 flash has been 
                      programmed."
			   ::= { gx2dualdrr2xFactoryEntry 10}

		dualdrr2xflashPrgCntB          		OBJECT-TYPE
			   SYNTAX       		INTEGER
			   ACCESS           	read-only
			   STATUS           	mandatory
			   DESCRIPTION
			   "This object provides the number of times Bank 1 flash has been 
                      programmed."
			   ::= { gx2dualdrr2xFactoryEntry 11}

		dualdrr2xflashBankARev          		OBJECT-TYPE
			   SYNTAX       		DisplayString (SIZE (0..80))
			   ACCESS           	read-only
			   STATUS           	mandatory
			   DESCRIPTION
			   "This object provides the revision of flash bank 0."
			   ::= { gx2dualdrr2xFactoryEntry 12}

		dualdrr2xflashBankBRev          		OBJECT-TYPE
			   SYNTAX       		DisplayString (SIZE (0..80))
			   ACCESS           	read-only
			   STATUS           	mandatory
			   DESCRIPTION
			   "This object provides the revision of flash bank 1."
			   ::= { gx2dualdrr2xFactoryEntry 13}
                  
		dualdrr2xSubAgentRev          		OBJECT-TYPE
			   SYNTAX       		DisplayString (SIZE (0..80))
			   ACCESS           	read-only
			   STATUS           	mandatory
			   DESCRIPTION
			   "This object provides the subagent revision of receiver module."
			   ::= { gx2dualdrr2xFactoryEntry 14}

		dualdrr2xFPGA0FwRev			OBJECT-TYPE   
			   SYNTAX       		DisplayString (SIZE (0..80))
			   ACCESS           	read-only
			   STATUS           	mandatory
			   DESCRIPTION
			   "This object provides the Firmware revision of the first DRR FPGA."
			   ::= { gx2dualdrr2xFactoryEntry 15}

		dualdrr2xFPGA1FwRev			OBJECT-TYPE   
			   SYNTAX       		DisplayString (SIZE (0..80))
			   ACCESS           	read-only
			   STATUS           	mandatory
			   DESCRIPTION
			   "This object provides the Firmware revision of the second DRR FPGA."
			   ::= { gx2dualdrr2xFactoryEntry 16}


		dualdrr2xDRT1SerialNo		OBJECT-TYPE   
			   SYNTAX       		DisplayString (SIZE (0..80))
			   ACCESS           	read-only
			   STATUS           	mandatory
			   DESCRIPTION
			   "This object provides the Serial Number of the DRT attached to channel 1."
			   ::= { gx2dualdrr2xFactoryEntry 17}

		dualdrr2xDRT1SFPSerialNo	OBJECT-TYPE   
			   SYNTAX       		DisplayString (SIZE (0..80))
			   ACCESS           	read-only
			   STATUS           	mandatory
			   DESCRIPTION
			   "This object provides the Serial Number of the SFP in the DRT attached to channel 1."
			   ::= { gx2dualdrr2xFactoryEntry 18}

		dualdrr2xDRT1SFPPartNo		OBJECT-TYPE

			   SYNTAX       		DisplayString (SIZE (0..80))
			   ACCESS           	read-only
			   STATUS           	mandatory
			   DESCRIPTION
			   "This object provides the Part number of the SFP in the DRT attached to channel 1."
			   ::= { gx2dualdrr2xFactoryEntry 19}

		dualdrr2xDRT1FwRev			OBJECT-TYPE   
			   SYNTAX       		DisplayString (SIZE (0..80))
			   ACCESS           	read-only
			   STATUS           	mandatory
			   DESCRIPTION
			   "This object provides the Firmware revision of the DRT attached to channel 1."
			   ::= { gx2dualdrr2xFactoryEntry 20}

		dualdrr2xDRT1FpgaFwRev		OBJECT-TYPE   
			   SYNTAX       		DisplayString (SIZE (0..80))
			   ACCESS           	read-only
			   STATUS           	mandatory
			   DESCRIPTION
			   "This object provides the Firmware revision of the FPGA in the DRT attached to channel 1."
			   ::= { gx2dualdrr2xFactoryEntry 21}

		dualdrr2xDRT2SerialNo		OBJECT-TYPE   
			   SYNTAX       		DisplayString (SIZE (0..80))
			   ACCESS           	read-only
			   STATUS           	mandatory
			   DESCRIPTION
			   "This object provides the Serial Number of the DRT attached to channel 2"
			   ::= { gx2dualdrr2xFactoryEntry 22}

		dualdrr2xDRT2SFPSerialNo	OBJECT-TYPE   
			   SYNTAX       		DisplayString (SIZE (0..80))
			   ACCESS           	read-only
			   STATUS           	mandatory
			   DESCRIPTION
			   "This object provides the Serial Number of the SFP in the DRT attached to channel 2"
			   ::= { gx2dualdrr2xFactoryEntry 23}

		dualdrr2xDRT2SFPPartNo  	OBJECT-TYPE   
			   SYNTAX       		DisplayString (SIZE (0..80))
			   ACCESS           	read-only
			   STATUS           	mandatory
			   DESCRIPTION
			   "This object provides the Part number of the SFP in the DRT attached to channel 2."
			   ::= { gx2dualdrr2xFactoryEntry 24}

		dualdrr2xDRT2FwRev			OBJECT-TYPE   
			   SYNTAX       		DisplayString (SIZE (0..80))
			   ACCESS           	read-only
			   STATUS           	mandatory
			   DESCRIPTION
			   "This object provides the Firmware revision of the DRT attached to channel 2."
			   ::= { gx2dualdrr2xFactoryEntry 25}

		dualdrr2xDRT2FpgaFwRev		OBJECT-TYPE   
			   SYNTAX       		DisplayString (SIZE (0..80))
			   ACCESS           	read-only
			   STATUS           	mandatory
			   DESCRIPTION
			   "This object provides the Firmware revision of the FPGA in the DRT attached to channel 2."
			   ::= { gx2dualdrr2xFactoryEntry 26}

-- ****************************************************************
--
-- TRAP DEFINITIONS
--
--
-- Every trap generated by an HFC agents will include first 9 identical
-- fields. If particular variable is not supported in
-- particular TRAP-TYPE then default value will be returned.
--
-- DESCRIPTION will include explanation of use of generic
-- variables (trapAdditionalInfo******.)  If no
-- DESCRIPTION is given then generic variables will contain
-- default values.
--
-- *****************************************************************

-- **************************************************************************
--                              Digital Receiver Return Module traps
-- **************************************************************************
   trapdualdrrConfigChangeInteger TRAP-TYPE
       ENTERPRISE gx2DualDrr2x
       VARIABLES
	       {       
		trapIdentifier,
		trapNetworkElemModelNumber,
		trapNetworkElemSerialNum,
		trapPerceivedSeverity,
		trapNetworkElemOperState,
		trapNetworkElemAlarmStatus,  
		trapNetworkElemAdminState,
		trapNetworkElemAvailStatus,
		trapText,
		trapChangedObjectId,
		trapChangedValueInteger,
		trapNETrapLastTrapTimeStamp
	       }
       DESCRIPTION
	"This trap is issued if configuration of a single variable
	 with integer type was changed (via ANY interface).  
	 TrapChangedValueInteger variable may contain current reading
	 of that variable.
	 trapPerceivedSeverity - 'indeterminate'"
  ::= 1

   trapdualdrrConfigChangeDisplayString TRAP-TYPE
       ENTERPRISE gx2DualDrr2x
       VARIABLES
	       {       
		trapIdentifier,
		trapNetworkElemModelNumber,
		trapNetworkElemSerialNum,
		trapPerceivedSeverity,
		trapNetworkElemOperState,
		trapNetworkElemAlarmStatus,  
		trapNetworkElemAdminState,
		trapNetworkElemAvailStatus,
		trapText,
		trapChangedObjectId,
		trapChangedValueDisplayString,
		trapNETrapLastTrapTimeStamp
	       }
       DESCRIPTION
	"This trap is issued if configuration of a single variable
	 with DispalayString type was changed (via ANY interface).  
	 TrapChangedValueDisplayString variable may contain current reading
	 of that variable.
	 trapPerceivedSeverity - 'indeterminate'"
  ::= 2
        
   trapdualdrr12VCurrentAlarm TRAP-TYPE
	ENTERPRISE gx2DualDrr2x
	VARIABLES
		{       
		 trapIdentifier,
		 trapNetworkElemModelNumber,
		 trapNetworkElemSerialNum,
		 trapPerceivedSeverity,
		 trapNetworkElemOperState,
		 trapNetworkElemAlarmStatus,  
		 trapNetworkElemAdminState,
		 trapNetworkElemAvailStatus,
		 trapText,
		 trapChangedObjectId,
		 trapChangedValueInteger,
		 trapNETrapLastTrapTimeStamp
		}
	DESCRIPTION
	"This trap is issued when the 12V power supply Current
	 parameter goes out of range.
	 trapAdditionalInfoInteger variable contains current reading of 
	 the this parameter."
     ::= 3       
          
  trapdualdrrModuleTempAlarm TRAP-TYPE
	ENTERPRISE gx2DualDrr2x
	VARIABLES
		{       
		 trapIdentifier,
		 trapNetworkElemModelNumber,
		 trapNetworkElemSerialNum,
		 trapPerceivedSeverity,
		 trapNetworkElemOperState,
		 trapNetworkElemAlarmStatus,  
		 trapNetworkElemAdminState,
		 trapNetworkElemAvailStatus,
		 trapText,
		 trapChangedObjectId,
		 trapChangedValueInteger,
		 trapNETrapLastTrapTimeStamp
		}
	DESCRIPTION
	"This trap is issued when the Internal Module Temperature goes out of range.
	 trapAdditionalInfoInteger variable contains current reading of 
	 the this parameter."
    ::= 4
  
    trapdualdrrFanSpeedAlarm TRAP-TYPE
	ENTERPRISE gx2DualDrr2x
	VARIABLES
		{       
		 trapIdentifier,
		 trapNetworkElemModelNumber,
		 trapNetworkElemSerialNum,
		 trapPerceivedSeverity,
		 trapNetworkElemOperState,
		 trapNetworkElemAlarmStatus,  
		 trapNetworkElemAdminState,
		 trapNetworkElemAvailStatus,
		 trapText,
		 trapChangedObjectId,
		 trapChangedValueInteger,
		 trapNETrapLastTrapTimeStamp
		}
	DESCRIPTION
	"This trap is issued when the Fan Speed 
	 parameter goes out of range.
	 trapAdditionalInfoInteger variable contains current reading of 
	 the this parameter."
  ::= 5

  trapdualdrrFlashAlarm TRAP-TYPE
	ENTERPRISE gx2DualDrr2x
	VARIABLES
		{       
		 trapIdentifier,
		 trapNetworkElemModelNumber,
		 trapNetworkElemSerialNum,
		 trapPerceivedSeverity,
		 trapNetworkElemOperState,
		 trapNetworkElemAlarmStatus,  
		 trapNetworkElemAdminState,
		 trapNetworkElemAvailStatus,
		 trapText,
		 trapChangedObjectId,
		 trapChangedValueInteger,
		 trapNETrapLastTrapTimeStamp
		}
	DESCRIPTION
	"This trap is issued when the detects an error during
	Flash memory operations."
  ::= 6
  
  trapdualdrrBankBootAlarm TRAP-TYPE
	ENTERPRISE gx2DualDrr2x
	VARIABLES
		{       
		 trapIdentifier,
		 trapNetworkElemModelNumber,
		 trapNetworkElemSerialNum,
		 trapPerceivedSeverity,
		 trapNetworkElemOperState,
		 trapNetworkElemAlarmStatus,  
		 trapNetworkElemAdminState,
		 trapNetworkElemAvailStatus,
		 trapText,
		 trapChangedObjectId,
		 trapChangedValueInteger,
		 trapNETrapLastTrapTimeStamp
		}
	DESCRIPTION
	"This trap is issued when the module detects an error while booting
	from bank 0 or bank 1."
  ::= 7

	trapdualdrrAlarmDataCRCAlarm TRAP-TYPE
	ENTERPRISE gx2DualDrr2x
	VARIABLES
		{       
		 trapIdentifier,
		 trapNetworkElemModelNumber,
		 trapNetworkElemSerialNum,
		 trapPerceivedSeverity,
		 trapNetworkElemOperState,
		 trapNetworkElemAlarmStatus,  
		 trapNetworkElemAdminState,
		 trapNetworkElemAvailStatus,
		 trapText,
		 trapChangedObjectId,
		 trapChangedValueInteger,
		 trapNETrapLastTrapTimeStamp
		}
	DESCRIPTION
	"This trap is issued when the Alarm Data CRC is incorrect."
  ::= 8

	trapdualdrrHardwareErrAlarm TRAP-TYPE
	ENTERPRISE gx2DualDrr2x
	VARIABLES
		{       
		 trapIdentifier,
		 trapNetworkElemModelNumber,
		 trapNetworkElemSerialNum,
		 trapPerceivedSeverity,
		 trapNetworkElemOperState,
		 trapNetworkElemAlarmStatus,  
		 trapNetworkElemAdminState,
		 trapNetworkElemAvailStatus,
		 trapText,
		 trapChangedObjectId,
		 trapChangedValueInteger,
		 trapNETrapLastTrapTimeStamp
		}
	DESCRIPTION
	"This trap is issued when hardware is abnormal."
  ::= 9

 	trapdualdrrOpticalSignal1Alarm TRAP-TYPE
	ENTERPRISE gx2DualDrr2x
	VARIABLES
		{       
		 trapIdentifier,
		 trapNetworkElemModelNumber,
		 trapNetworkElemSerialNum,
		 trapPerceivedSeverity,
		 trapNetworkElemOperState,
		 trapNetworkElemAlarmStatus,  
		 trapNetworkElemAdminState,
		 trapNetworkElemAvailStatus,
		 trapText,
		 trapChangedObjectId,
		 trapChangedValueInteger,
		 trapNETrapLastTrapTimeStamp
		}
	DESCRIPTION
	"This trap is issued when the optical signal 1 is beyond the preset range."  
  ::= 10
 
 	trapdualdrrOpticalSignal2Alarm TRAP-TYPE
	ENTERPRISE gx2DualDrr2x
	VARIABLES
		{       
		 trapIdentifier,
		 trapNetworkElemModelNumber,
		 trapNetworkElemSerialNum,
		 trapPerceivedSeverity,
		 trapNetworkElemOperState,
		 trapNetworkElemAlarmStatus,  
		 trapNetworkElemAdminState,
		 trapNetworkElemAvailStatus,
		 trapText,
		 trapChangedObjectId,
		 trapChangedValueInteger,
		 trapNETrapLastTrapTimeStamp
		}
	DESCRIPTION
	"This trap is issued when the optical signal 2 is beyond the preset range."  
  ::= 11
 
	trapdualdrrFactoryDataCRCAlarm TRAP-TYPE
	ENTERPRISE gx2DualDrr2x
	VARIABLES
		{       
		 trapIdentifier,
		 trapNetworkElemModelNumber,
		 trapNetworkElemSerialNum,
		 trapPerceivedSeverity,
		 trapNetworkElemOperState,
		 trapNetworkElemAlarmStatus,  
		 trapNetworkElemAdminState,
		 trapNetworkElemAvailStatus,
		 trapText,
		 trapChangedObjectId,
		 trapChangedValueInteger,
		 trapNETrapLastTrapTimeStamp
		}
	DESCRIPTION
	"This trap is issued when the Factory Data CRC is incorrect."
  ::= 12

	trapdualdrrResetFactoryDefaultAlarm TRAP-TYPE
	ENTERPRISE gx2DualDrr2x
	VARIABLES
		{       
		 trapIdentifier,
		 trapNetworkElemModelNumber,
		 trapNetworkElemSerialNum,
		 trapPerceivedSeverity,
		 trapNetworkElemOperState,
		 trapNetworkElemAlarmStatus,  
		 trapNetworkElemAdminState,
		 trapNetworkElemAvailStatus,
		 trapText,
		 trapChangedObjectId,
		 trapChangedValueInteger,
		 trapNETrapLastTrapTimeStamp
		}
	DESCRIPTION
	"This trap is issued when the Factory Default Reset occurs."
  ::= 13

	trapdualdrrTripPoint1Alarm TRAP-TYPE
	ENTERPRISE gx2DualDrr2x
	VARIABLES
		{       
		 trapIdentifier,
		 trapNetworkElemModelNumber,
		 trapNetworkElemSerialNum,
		 trapPerceivedSeverity,
		 trapNetworkElemOperState,
		 trapNetworkElemAlarmStatus,  
		 trapNetworkElemAdminState,
		 trapNetworkElemAvailStatus,
		 trapText,
		 trapChangedObjectId,
		 trapChangedValueInteger,
		 trapNETrapLastTrapTimeStamp
		}
	DESCRIPTION
	"This trap is issued when the Input 1 optical power is lower than the custumer set 
	trip point and trippoint mode as ALARM_ONLY or SWITCH & ALARM."
  ::= 14      
  
	trapdualdrrTripPoint2Alarm TRAP-TYPE
	ENTERPRISE gx2DualDrr2x
	VARIABLES
		{       
		 trapIdentifier,
		 trapNetworkElemModelNumber,
		 trapNetworkElemSerialNum,
		 trapPerceivedSeverity,
		 trapNetworkElemOperState,
		 trapNetworkElemAlarmStatus,  
		 trapNetworkElemAdminState,
		 trapNetworkElemAvailStatus,
		 trapText,
		 trapChangedObjectId,
		 trapChangedValueInteger,
		 trapNETrapLastTrapTimeStamp
		}
	DESCRIPTION
	"This trap is issued when the Input 2 optical power is lower than the custumer set 
	trip point and trippoint mode as ALARM_ONLY or SWITCH & ALARM."
  ::= 15      
  
    trapdualdrrLink1Alarm TRAP-TYPE
	ENTERPRISE gx2DualDrr2x
	VARIABLES
		{       
		 trapIdentifier,
		 trapNetworkElemModelNumber,
		 trapNetworkElemSerialNum,
		 trapPerceivedSeverity,
		 trapNetworkElemOperState,
		 trapNetworkElemAlarmStatus,  
		 trapNetworkElemAdminState,
		 trapNetworkElemAvailStatus,
		 trapText,
		 trapChangedObjectId,
		 trapChangedValueInteger,
		 trapNETrapLastTrapTimeStamp
		}
	DESCRIPTION
	"This trap is issued when receiver 1 is out of SYN with transmitter"
  ::= 16

    trapdualdrrLink2Alarm TRAP-TYPE
	ENTERPRISE gx2DualDrr2x
	VARIABLES
		{       
		 trapIdentifier,
		 trapNetworkElemModelNumber,
		 trapNetworkElemSerialNum,
		 trapPerceivedSeverity,
		 trapNetworkElemOperState,
		 trapNetworkElemAlarmStatus,  
		 trapNetworkElemAdminState,
		 trapNetworkElemAvailStatus,
		 trapText,
		 trapChangedObjectId,
		 trapChangedValueInteger,
		 trapNETrapLastTrapTimeStamp
		}
	DESCRIPTION
	"This trap is issued when receiver 2 is out of SYN with transmitter"
  ::= 17

    trapdualdrrCalibrationDataCRCAlarm TRAP-TYPE
	ENTERPRISE gx2DualDrr2x
	VARIABLES
		{       
		 trapIdentifier,
		 trapNetworkElemModelNumber,
		 trapNetworkElemSerialNum,
		 trapPerceivedSeverity,
		 trapNetworkElemOperState,
		 trapNetworkElemAlarmStatus,  
		 trapNetworkElemAdminState,
		 trapNetworkElemAvailStatus,
		 trapText,
		 trapChangedObjectId,
		 trapChangedValueInteger,
		 trapNETrapLastTrapTimeStamp
		}
	DESCRIPTION
	"This trap is issued when the Calibration Data CRC is incorrect"
  ::= 18

    trapdualdrrSFP1OptPWRAlarm TRAP-TYPE
	ENTERPRISE gx2DualDrr2x
	VARIABLES
		{       
		 trapIdentifier,
		 trapNetworkElemModelNumber,
		 trapNetworkElemSerialNum,
		 trapPerceivedSeverity,
		 trapNetworkElemOperState,
		 trapNetworkElemAlarmStatus,  
		 trapNetworkElemAdminState,
		 trapNetworkElemAvailStatus,
		 trapText,
		 trapChangedObjectId,
		 trapChangedValueInteger,
		 trapNETrapLastTrapTimeStamp
		}
	DESCRIPTION
	"This trap is issued when SFP 1's optical power is incorrect"
  ::= 19

    trapdualdrrDRT1Cur24VAlarm TRAP-TYPE
	ENTERPRISE gx2DualDrr2x
	VARIABLES
		{       
		 trapIdentifier,
		 trapNetworkElemModelNumber,
		 trapNetworkElemSerialNum,
		 trapPerceivedSeverity,
		 trapNetworkElemOperState,
		 trapNetworkElemAlarmStatus,  
		 trapNetworkElemAdminState,
		 trapNetworkElemAvailStatus,
		 trapText,
		 trapChangedObjectId,
		 trapChangedValueInteger,
		 trapNETrapLastTrapTimeStamp
		}
	DESCRIPTION
	"This trap is issued when DRT 1's 24 volt current is incorrect"
  ::= 20

    trapdualdrrDRT1ModTempAarm TRAP-TYPE
	ENTERPRISE gx2DualDrr2x
	VARIABLES
		{       
		 trapIdentifier,
		 trapNetworkElemModelNumber,
		 trapNetworkElemSerialNum,
		 trapPerceivedSeverity,
		 trapNetworkElemOperState,
		 trapNetworkElemAlarmStatus,  
		 trapNetworkElemAdminState,
		 trapNetworkElemAvailStatus,
		 trapText,
		 trapChangedObjectId,
		 trapChangedValueInteger,
		 trapNETrapLastTrapTimeStamp
		}
	DESCRIPTION
	"This trap is issued when DRT 1's Module telperature is incorrect"
  ::= 21

    trapdualdrrSFP2OptPWRAlarm TRAP-TYPE
	ENTERPRISE gx2DualDrr2x
	VARIABLES
		{       
		 trapIdentifier,
		 trapNetworkElemModelNumber,
		 trapNetworkElemSerialNum,
		 trapPerceivedSeverity,
		 trapNetworkElemOperState,
		 trapNetworkElemAlarmStatus,  
		 trapNetworkElemAdminState,
		 trapNetworkElemAvailStatus,
		 trapText,
		 trapChangedObjectId,
		 trapChangedValueInteger,
		 trapNETrapLastTrapTimeStamp
		}
	DESCRIPTION
	"This trap is issued when SFP 2's optical power is incorrect"
  ::= 22

    trapdualdrrDRT2Cur24VAlarm TRAP-TYPE
	ENTERPRISE gx2DualDrr2x
	VARIABLES
		{       
		 trapIdentifier,
		 trapNetworkElemModelNumber,
		 trapNetworkElemSerialNum,
		 trapPerceivedSeverity,
		 trapNetworkElemOperState,
		 trapNetworkElemAlarmStatus,  
		 trapNetworkElemAdminState,
		 trapNetworkElemAvailStatus,
		 trapText,
		 trapChangedObjectId,
		 trapChangedValueInteger,
		 trapNETrapLastTrapTimeStamp
		}
	DESCRIPTION
	"This trap is issued when DRT 2's 24 volt current is incorrect"
  ::= 23

    trapdualdrrDRT2ModTempAarm TRAP-TYPE
	ENTERPRISE gx2DualDrr2x
	VARIABLES
		{       
		 trapIdentifier,
		 trapNetworkElemModelNumber,
		 trapNetworkElemSerialNum,
		 trapPerceivedSeverity,
		 trapNetworkElemOperState,
		 trapNetworkElemAlarmStatus,  
		 trapNetworkElemAdminState,
		 trapNetworkElemAvailStatus,
		 trapText,
		 trapChangedObjectId,
		 trapChangedValueInteger,
		 trapNETrapLastTrapTimeStamp
		}
	DESCRIPTION
	"This trap is issued when DRT 2's Module telperature is incorrect"
  ::= 24

  END
