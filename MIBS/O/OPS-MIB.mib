-- extracted from draft-anda-ops-mib-01.txt
-- at Thu Oct 12 07:11:15 2000

   OPS-MIB DEFINITIONS ::= BEGIN

   IMPORTS
       MODULE-IDENTITY, OBJECT-TYPE, NOTIFICATION-TYPE,
       IpAddress, experimental, Integer32, Unsigned32, Gauge32
           FROM SNMPv2-SMI
       DisplayString, RowStatus, DateAndTime, MacAddress,
       TEXTUAL-CONVENTION, TruthValue, TimeStamp
           FROM SNMPv2-TC
       MODULE-COMPLIANCE, OBJECT-GROUP
           FROM SNMPv2-CONF
       InterfaceIndex
           FROM IF-MIB;

   opsMIB MODULE-IDENTITY
       LAST-UPDATED "9910060000Z"
       ORGANIZATION "ANDA Networks, Inc."
       CONTACT-INFO
               "        Ray Jamp
                Postal: ANDA Networks, Inc.
                        2708 Orchard Parkway
                        San Jose, CA 95134

                Definitions of Managed Objects for OPS    October 2000

                   Tel: +1 408-519-4900
                   Fax: +1 408-519-4901
                E-mail: rjamp@andanetworks.com

                        Yu-Jen Hsiao
                 Postal: ANDA Networks, Inc.
                         2708 Orchard Parkway
                         San Jose, CA 95134
                    Tel: +1 408-519-4900
                    Fax: +1 408-519-4901
                 E-mail: yjhsiao@andanets.com"

       DESCRIPTION
           "This is the MIB module for OPS-compliant
           CPE for managing configurations of
           the CPE system and its voice services."

       REVISION      "9910060000Z"
       DESCRIPTION
           "Published as draft-anda-ops-mib-01"
       ::= { experimental 1 }

   -- *****************************************************************
   --
   -- The Open Provisioning Standard (OPS) MIB defines managed objects
   -- for flow-though provisioning and management functions. This
   -- document defines two groups of management objects for
   -- next-generation customer premise equipment (NG-CPE). The first
   -- group of objects are of a general configuration nature.
   -- The second group of objects are similar to the Analog Line
   -- Termination objects of a GR-303 Remote Terminal as defined in
   -- the GR-303-Core document. A NG-CPE that implements the
   -- OPS MIB is an OPS compliant NG-CPE (OPS-CPE).
   --
   -- The network management systems at the Network Operation Center
   -- (NOC) perform flow-through provisioning and management of
   -- OPS-IADs through an OPS-compliant Multi-Service Access
   -- Concentrator (MAS).
   --
   -- *****************************************************************

   opsMIBObjects        OBJECT IDENTIFIER ::= { opsMIB 1 }
   iadOPS               OBJECT IDENTIFIER ::= { opsMIBObjects 1 }
   iOpsIADConfig        OBJECT IDENTIFIER ::= { iadOPS 1 }
   iOpsIADVoiceService  OBJECT IDENTIFIER ::= { iadOPS 2 }
   dlcOPS               OBJECT IDENTIFIER ::= { opsMIBObjects 2 }
   dacOPS               OBJECT IDENTIFIER ::= { opsMIBObjects 3 }

   -- *****************************************************************
   --
   -- The OPS IAD Configuration Group
   --
   -- *****************************************************************

   iOpsIADIfIndex OBJECT-TYPE
       SYNTAX  InterfaceIndex
       MAX-ACCESS  read-only
       STATUS  current
       DESCRIPTION
           "Index of the interface that the IAD uses to
           communicate with the Multi-Service Access
           Concentrator (MAS)."
       ::= { iOpsIADConfig 1 }

   iOpsIADManufacturerName OBJECT-TYPE
       SYNTAX  DisplayString (SIZE(0..255))
       MAX-ACCESS  read-only
       STATUS  current
       DESCRIPTION
           "Name and contact information of the manufacturer
           of the IAD."
       ::= { iOpsIADConfig 2 }

   iOpsIADSerialNumber OBJECT-TYPE
       SYNTAX  DisplayString (SIZE(0..255))
       MAX-ACCESS  read-only
       STATUS  current
       DESCRIPTION
           "Serial number of the IAD."
       ::= { iOpsIADConfig 3 }

   iOpsIADCLEICode OBJECT-TYPE
       SYNTAX  DisplayString (SIZE(0..255))
       MAX-ACCESS  read-only
       STATUS  current
       DESCRIPTION
           "Common Language Equipment Identifier Code of the IAD."
       ::= { iOpsIADConfig 4 }

   iOpsIADAdminStatus OBJECT-TYPE
       SYNTAX  INTEGER {
                        up(1),
                        down(2),
                        test(3)
                       }
       MAX-ACCESS  read-write
       STATUS  current
       DESCRIPTION
           "Identifies the administrative status of the IAD."
       DEFVAL  { up }
       ::= { iOpsIADConfig 5 }

   iOpsIADOperStatus OBJECT-TYPE
       SYNTAX  INTEGER {
                        up(1),
                        down(2),
                        testing(3),
                        unknown(4)


                       }
       MAX-ACCESS  read-only
       STATUS  current
       DESCRIPTION
           "Identifies the operational status of the IAD."
       ::= { iOpsIADConfig 6 }

   iOpsIADAlarmStatus OBJECT-TYPE
       SYNTAX  INTEGER {
                        noAlarm(1),
                        minorAlarm(2),
                        majorAlarm(3),
                        criticalAlarm(4)
                       }
       MAX-ACCESS  read-only
       STATUS  current
       DESCRIPTION
           "Identifies the current alarm status of the IAD. If multiple
           alarms are present, this object displays the highest
           severity alarm value."
       ::= { iOpsIADConfig 7 }

   iOpsIADOperStatusLastChange OBJECT-TYPE
      SYNTAX  TimeStamp
       MAX-ACCESS  read-only
       STATUS  current
       DESCRIPTION
           "The value of the SNMPv2 MIBs 'sysUpTime' object-type at the
           time the IAD entered its current operating state.

           If the IADs current state was entered prior to the last
           re-initialization of the SNMP agent, then this object will
           contain a zero (0) value."
       ::= { iOpsIADConfig 8 }

   iOpsIADResetIAD OBJECT-TYPE
       SYNTAX  INTEGER {
                        none(1),
                        warmReboot(2),
                        coldReboot(3)
                       }
       MAX-ACCESS  read-write
       STATUS  current
       DESCRIPTION
           "Reboot the IAD. The IAD will boot up running the system
           image file specified in the 'iOpsIADSoftwareFileName'
           object-type.

           It is highly recommended that the IAD contain bootstrap
           code that the IAD can default to, in the unlikely scenario
           that the file specified in 'iOpsIADSoftwareFileName'
           does not exist on the IAD or is otherwise invalid.

           This is an action attribute and it is meaningless to attempt

           to read this value."
       ::= { iOpsIADConfig 9 }

   iOpsIADSoftwareFileName OBJECT-TYPE
       SYNTAX  DisplayString (SIZE(0..255))
       MAX-ACCESS  read-write
       STATUS  current
       DESCRIPTION
           "Contains the name of the system image file that the IAD
           will attempt to boot from.

           If IAD does not support multiple system image files, then
           this object becomes read-only and is only capable of
           containing the same file that is uploaded in the
           'iOpsIADSoftwareUpgradeFileName' object-type.

           This object only specifies the file name of the system image
           file residing on the IAD and not a full path name as is
           specified in the 'iOpsIADSoftwareUpgradeFileName'
           object-type.

           The SNMP Agent will reject an SNMP SET PDU message on this
           object if the file does not exist on the IAD or if the file
           is otherwise invalid (incorrect name, corrupt, etc.)."
       ::= { iOpsIADConfig 10 }

   iOpsIADSoftwareUpgradeFileName OBJECT-TYPE
       SYNTAX  DisplayString (SIZE(0..255))
       MAX-ACCESS  read-write
       STATUS  current
       DESCRIPTION
           "Contains the name of the system image file to be
           downloaded to the IAD. The full path name of the file must
           be specified.

           The IP address of the server used to download the file must
           first be specified in the 'iOpsIADServerIP' object-type.

           The server used to download the file defaults to the
           TFTP protocol. This default may be changed to 'FTP' or to
           'other'. It is specified in the 'iOpsIADServerType'
           object-type.

           If an alternate transfer protocol is to be used, it must
           be specified before attempting the file download."
       ::= { iOpsIADConfig 11 }

   iOpsIADDownloadSoftware OBJECT-TYPE
       SYNTAX  INTEGER {
                        downloadSoftwareFromServer(1),
                        downloadComplete(2),
                        downloadFailed(3),
                        downloadInProgress(4),
                        none(5)


                        }
   MAX-ACCESS  read-write
       STATUS    current
       DESCRIPTION
           "Is used to download the system image file to the IAD or to
           obtain status about the file download:

           1) The SNMP SET PDU message is used to initiate a download
           of the system image file to the IAD.
           2) The SNMP GET, GET-NEXT, OR GET-BULK PDU messages are used
           to obtain status of the previously initiated download.

           When initiating a download of the system image file, the
           attributes of this object and the attributes of the
           'iOpsIADSaveSoftware' object-type must be included in the
           same SNMP SET PDU message.

           'iOpsIADSaveSoftware' is used to specify either:
           1) A save of the file on the IAD.
           2) A save of the file on the IAD and then perform a reboot
           of the IAD.

           The IP address of the server used to transfer the file or
           the status information is specified in the 'iOpsIADServerIP'
           object-type.

           The server used to download the system image file defaults
           to the TFTP protocol. However, this default may be changed
           to 'FTP' or to 'other'. It is specified in the
           'iOpsIADServerType' object-type.

           If an alternate transfer protocol is used, it must first
           be specified before attempting the file download.

           If the IAD is unable to complete the file transfer for any
           reason, the values of the 'iOpsIADAdminStatus' and
           'iOpsIADOperStatus' object-types must remain in the 'up'
           status in order for the IAD to be available to accept
           subsequent system image file downloads.

           SET PDU message:
           1: Download the system image file from the server to the
           IAD. The system image file name is specified in the
           'iOpsIADSoftwareUpgradeFileName' object-type.

           GET, GET-NEXT, or GET-BULK PDU message:
           2: The download of the system image file is complete.
           3: The download of the system image file failed.
           4: The download of the system image file is in progress.
           5. No status can be returned because no prior SET operation
           was performed."
       ::= { iOpsIADConfig 12 }

   iOpsIADSaveSoftware OBJECT-TYPE

       SYNTAX  INTEGER {
                        save(1),
                        saveAndReboot(2)
                       }
       MAX-ACCESS  read-write
       STATUS  current
       DESCRIPTION
           "Save downloaded system image file with the option to
           reboot the IAD.

           For IADs that can contain multiple system image files,
           either option can be used.

           For IADs that can only contain one system image file,
           only the 'saveAndReboot' option can be used.

           1) When the 'save' option is specified, the IAD will not
           reboot after the file transfer is completed. the IAD will
           continue to use the currently running system image file.

           In order for the IAD to come up with the new system image
           the next time it is rebooted, the network manager must set
           the 'iOpsIADSoftwareFileName' object-type with the
           downloaded file name.

           2) If the 'saveAndReboot' option is specified, the IAD will
           reboot with the new system image if:

           - The file transfer successfully completed, AND
           - The file is not corrupt

           The SNMP Agent must update iOpsIADSoftwareFileName with
           the 'iOpsIADSoftwareUpgradeFileName' object-type before
           the reboot.

           When initiating a download, the attributes of this object
           and the attributes of the 'iOpsIADDownloadSoftware'
           object-type must be included in the same
           SNMP SET PDU message.

           This is an action attribute and it is meaningless to attempt
           to read this value."
       ::= { iOpsIADConfig 13 }

   iOpsIADSoftwareVersion OBJECT-TYPE
       SYNTAX  DisplayString (SIZE(0..255))
       MAX-ACCESS  read-only
       STATUS  current
       DESCRIPTION
           "Version number of the currently running system image."
       ::= { iOpsIADConfig 14 }

   iOpsIADReConfigIAD OBJECT-TYPE
       SYNTAX  INTEGER {

                        none(1),
                        reConfig(2)
                       }
       MAX-ACCESS  read-write
       STATUS  current
       DESCRIPTION
           "Change the current configuration file (persistent database)
           running on the IAD to a new configuration file specified in
           the 'iOpsIADConfigFileName' object-type."
       ::= { iOpsIADConfig 15 }

   iOpsIADConfigFileName OBJECT-TYPE
       SYNTAX  DisplayString (SIZE(0..255))
       MAX-ACCESS  read-write
       STATUS  current
       DESCRIPTION
           "Contains the configuration file name that the IAD will
           attempt to load.

           If the IAD does not support multiple configuration files,
           then this object becomes read-only and is only capable of
           containing the same file that is uploaded to the
           'iOpsIADConfigUpgradeFileName' object-type.

           This object only contains the file name of the
           configuration file residing on the IAD and not a full
           path name as is specified in the
           'iOpsIADConfigUpgradeFileName' object-type.

           The SNMP Agent will reject an SNMP SET PDU message on this
           object if the file does not exist on the IAD or if the file
           is otherwise invalid (incorrect name, corrupt, etc.)."
       ::= { iOpsIADConfig 16 }

   iOpsIADConfigUpgradeFileName OBJECT-TYPE
       SYNTAX  DisplayString (SIZE(0..255))
       MAX-ACCESS  read-write
       STATUS  current
       DESCRIPTION
           "Contains the name of the configuration file to be
           downloaded to the IAD. The full path name of the file must
           be specified.

           The IP address of the server used to download the file must
           first be specified in the 'iOpsIADServerIP' object-type.

           The server used to download the file defaults to the
           TFTP protocol. This default may be changed to 'FTP' or to
           'other'. It is specified in the 'iOpsIADServerType'
           object-type.

           If an alternate transfer protocol is to be used, it must
           be specified before attempting the file download."
       ::= { iOpsIADConfig 17 }


   iOpsIADUpDownloadConfiguration OBJECT-TYPE
       SYNTAX  INTEGER {
                        downloadConfigFileFromServer(1),
                        uploadConfigFileToServer(2),
                        uploadOrDownloadComplete(3),
                        uploadOrDownloadFailed(4),
                        downloadInProgress(5),
                        uploadInProgress(6),
                        none(7)
                       }
   MAX-ACCESS  read-write
       STATUS  current
       DESCRIPTION
           "Is used to download the configuration file to the IAD,
           or to upload the configuration from the IAD, or to obtain
           status about the file download or upload:

           1) The SNMP SET PDU message is used to initiate the download
           or upload of the configuration file.
           2) The SNMP GET, GET-NEXT, or GET-BULK messages are used to
           obtain status of the previously initiated download or
           upload.

           When initiating a download or upload, of the configuration
           file, the attributes of this object and the attributes of
           the 'iOpsIADSaveConfiguration' object-type must be included
           in the same SNMP SET PDU message.

           The IP address of the server used to transfer the file or
           the status information is specified in iOpsIADServerIP.

           The server used to download or upload the configuration
           file defaults to the TFTP protocol. However, this default
           may be changed to 'FTP' or to 'other'. It is specified in
           the 'iOpsIADServerType' object-type.

           If an alternate transfer protocol is used, it must first
           be specified before attempting the file download.

           If the IAD is unable to complete the file transfer for any
           reason, the values of the 'iOpsIADAdminStatus' and
           'iOpsIADOperStatus' object-types must remain in the 'up'
           status in order for the IAD to be available to accept
           subsequent requests for configuration file
           downloads or uploads.

           SET PDU message:
           1: Download the configuration file from the server to the
           IAD. The configuration file name is specified in the
           'iOpsIADConfigUpgradeFileName' object-type.
           2: Upload the configuration script from the IAD to the
           server. he configuration file name is specified in the
           'iOpsIADConfigUpgradeFileName' object-type.


           GET, GET-NEXT, or GET-BULK PDU message:
           3: The upload or download of the configuration file is
           complete.
           4: The upload or download of the configuration file failed.
           5: The download of the configuration file is in progress.
           6: The upload of the configuration file is in progress.
           7. No status can be returned because no prior SET operation
           was performed."
   ::= { iOpsIADConfig 18 }

   iOpsIADSaveConfiguration OBJECT-TYPE
       SYNTAX  INTEGER {
                        none(1),
                        save(2),
                        saveAndReconfigure(3)
                       }
       MAX-ACCESS  read-write
       STATUS  current
       DESCRIPTION
           "Save the downloaded configuration file, but continue to use
           the currently running configuration file or start using the
           newly downloaded configuration file.

           For IADs that can contain multiple configuration files,
           either option can be used.

           For IADs that can only contain one configuration file,
           only the 'saveAndReconfigure' option can be used.

           1) When the 'none' option is specified.

           2) When the 'save' option is specified, the IAD will
           continue to use the currently running configuration file.
           In order for the IAD to use the newly downloaded
           configuration file, the network manager should set
           the 'iOpsIADConfigFileName' object-type with the newly
           downloaded configuration file name, and then set the
           'iOpsIADReConfigIAD' object-type to the value
           'reConfig(2)'.

           3) When 'saveAndReconfigure' is specified, the IAD will
           immediately  start using the new configuration file if:

           - The file transfer successfully completed, AND
           - The file is not corrupt

           The SNMP Agent must update the 'iOpsIADConfigFileName'
           object-type with the 'iOpsIADConfigUpgradeFileName'
           object-type before using the newly downloaded
           configuration file.

           When initiating a download, the attributes of this object
           and the attributes of the 'iOpsIADUpDownloadConfiguration'

           object-type must be included in the same SNMP SET PDU
           message.

           This is an action attribute and it is meaningless to attempt
           to read this value."
       ::= { iOpsIADConfig 19 }

   iOpsIADVersionConfig OBJECT-TYPE
       SYNTAX  DisplayString (SIZE(0..255))
       MAX-ACCESS  read-only
       STATUS  current
       DESCRIPTION
           "Version of Configuration."
       ::= { iOpsIADConfig 20 }

   iOpsIADMgmtChType OBJECT-TYPE
       SYNTAX  INTEGER {
                         andaFDL(1),
                         ds0(2),
                         fr-dlci(3),
                         atmVPIVCI(4)
                        }
       MAX-ACCESS  read-only
       STATUS  current
       DESCRIPTION
           "Specifies the type of management channel to be used, where:
           1) 'andaFDL' is the ANDA facility data link channel
           2) 'dso' is a DS0 channel
           3) 'fr-dlci' is a Frame-Relay circuit
           4) 'atmVPIVCI' is an ATM virtual circuit"
       ::= { iOpsIADConfig 21 }

   iOpsIADMgmtChNumber OBJECT-TYPE
       SYNTAX  Unsigned32
       MAX-ACCESS  read-write
       STATUS  current
       DESCRIPTION
           "This field is set according the value specified in the
           'iOpsIADMgmtChType' object-type:

           If 'iOpsIADMgmtChType' is 'andaFDL(1)' -
                   this object is not applicable.
           If 'iOpsIADMgmtChType' is 'ds0(2)' -
                   is the DS0 channel number to use.
           If 'iOpsIADMgmtChType' is 'fr-dlci(3)' -
                   is the DLCI number to use.
           If 'iOpsIADMgmtChType' is 'atmVPIVCI(4)' -
                   is set as follows:
                   The most significant 16-bit word is the VPI.
                   The least significant 16-bit word is the VCI."
   ::= { iOpsIADConfig 22 }

   iOpsIADMgmtChBandwidth OBJECT-TYPE
       SYNTAX  Gauge32

       UNITS  "Kbps"
       MAX-ACCESS  read-write
       STATUS  current
       DESCRIPTION
           "This object is only valid when 'iOpsIADMgmtChType' is
           'fr-dlci(3)' or 'atmVPIVCI(4)'.
           This object indicates the amount of bandwidth that is
           allocated for the management channel."
       ::= { iOpsIADConfig 23 }

   iOpsIADMgmtChInactivityTimer OBJECT-TYPE
       SYNTAX  INTEGER (1..1000)
       UNITS   "Seconds"
       MAX-ACCESS  read-write
       STATUS  current
       DESCRIPTION
           "Amount of time of inactivity allowed on a management
           channel before the link is declared down. The MAS should
           poll IAD on a keep-alive timer."
   DEFVAL  { 60 }
       ::= { iOpsIADConfig 24 }

   iOpsIADDataService OBJECT-TYPE
       SYNTAX  INTEGER {
                        frameRelay(1),
                        atm(2),
                        ppp(3)
                       }
       MAX-ACCESS  read-only
       STATUS  current
       DESCRIPTION
           "Indicates the type of data service offered by the IAD:
           '1' is Frame Relay
           '2' is ATM
           '3' is PPP"
       ::= { iOpsIADConfig 25 }

   iOpsIADDateAndTime OBJECT-TYPE
       SYNTAX  DateAndTime
       MAX-ACCESS  read-write
       STATUS  current
       DESCRIPTION
           "Is the date and time on the IAD."
       ::= { iOpsIADConfig 26 }

   iOpsIADMacAddress OBJECT-TYPE
       SYNTAX  MacAddress
       MAX-ACCESS  read-only
       STATUS  current
       DESCRIPTION
           "Is the MAC address on the IAD."
       ::= { iOpsIADConfig 27 }

   iOpsIADPublicIPAddress OBJECT-TYPE

       SYNTAX  IpAddress
       MAX-ACCESS  read-write
       STATUS  current
       DESCRIPTION
           "Is the IP address on the IAD."
       ::= { iOpsIADConfig 28 }

   iOpsIADSubnetMask OBJECT-TYPE
       SYNTAX  IpAddress
       MAX-ACCESS  read-write
       STATUS  current
       DESCRIPTION
           "Is the subnet mask on the IAD."
       ::= { iOpsIADConfig 29 }

   iOpsIADGateway OBJECT-TYPE
       SYNTAX  IpAddress
       MAX-ACCESS  read-write
       STATUS  current
       DESCRIPTION
           "Is the Gateway IP address."
       ::= { iOpsIADConfig 30 }

   iOpsIADDHCPIP OBJECT-TYPE
       SYNTAX  IpAddress
       MAX-ACCESS  read-write
       STATUS  current
       DESCRIPTION
           "If used, is the IP address of the DHCP server."
       ::= { iOpsIADConfig 31 }

   iOpsIADServerIP OBJECT-TYPE
       SYNTAX  IpAddress
       MAX-ACCESS  read-write
       STATUS  current
       DESCRIPTION
           "Is the IP address of the server used for the system image
           file downloads, for the downloads and uploads of the
           configuration file (persistent database) and for obtaining
           status information about the file transfer. "
       ::= { iOpsIADConfig 32 }

   iOpsIADServerType OBJECT-TYPE
       SYNTAX  INTEGER {
                        tftpServer(1),
                        ftpServer(2),
                        otherServer(3)
                       }
       MAX-ACCESS  read-write
       STATUS  current
       DESCRIPTION
           "Indicates the type of file transfer to be used.
           TFTP is the default and will be used unless another
           selection is specified."

       DEFVAL  { tftpServer }
       ::= { iOpsIADConfig 33 }

   iOpsIADServerLoginName OBJECT-TYPE
       SYNTAX  DisplayString (SIZE(0..255))
       MAX-ACCESS  read-write
       STATUS  current
       DESCRIPTION
           "Is the Login Name of the Server."
       ::= { iOpsIADConfig 34 }

   iOpsIADServerPasswd OBJECT-TYPE
       SYNTAX  OCTET STRING (SIZE (0..1024))
       MAX-ACCESS accessible-for-notify
       STATUS  current
       DESCRIPTION
           "Is the password used to login to the Server. It may be
           encrypted.
           This value is write only."
        ::= { iOpsIADConfig 35 }

   iOpsIADMasPublicKey OBJECT-TYPE
       SYNTAX  OCTET STRING (SIZE (0..1024))
       MAX-ACCESS  read-write
       STATUS  current
       DESCRIPTION
           "Is the public key of the MAS which, when combined with the
           private key stored on the IAD, can be used to encrypt and
           decrypt the community name in an SNMP PDU."
       ::= { iOpsIADConfig 36 }

   iOpsIADManagementPasswd OBJECT-TYPE
       SYNTAX  DisplayString (SIZE(0..255))
       MAX-ACCESS accessible-for-notify
       STATUS  current
       DESCRIPTION
           "Is the password assigned to an IAD to be used by a directly
           connected management station to login to the IAD.
           This value is write only."
       ::= { iOpsIADConfig 37 }

   -- *****************************************************************
   --
   -- The OPS Voice Service Table
   --
   -- *****************************************************************

   iOpsIADVlNumber OBJECT-TYPE
       SYNTAX  Gauge32
       MAX-ACCESS  read-only
       STATUS  current
       DESCRIPTION
           "Indicates the number of voice lines on the IAD."
       ::= { iOpsIADVoiceService 1 }


   iOpsIADVlTable OBJECT-TYPE
       SYNTAX  SEQUENCE OF IOpsIADVlEntry
       MAX-ACCESS  not-accessible
       STATUS  current
       DESCRIPTION
           "Is a list of the voice line entries. The number of entries
           is indicated by the value of the 'iOpsIADVlNumber'
           object-type."
       ::= { iOpsIADVoiceService 2 }

   iOpsIADVlEntry OBJECT-TYPE
       SYNTAX  IOpsIADVlEntry
       MAX-ACCESS  not-accessible
       STATUS  current
       DESCRIPTION
           "Is an entry that contains the objects pertaining to a
           voice line uniquely identified by the 'iOpsIADVlIndex'
           object-type."
       INDEX   { iOpsIADVlIndex }
       ::= { iOpsIADVlTable 1 }

   IOpsIADVlEntry ::=
       SEQUENCE {
                  iOpsIADVlIndex
                      INTEGER,
                  iOpsIADVlDS1IfIndex
                      InterfaceIndex,
                  iOpsIADVlDS0Index
                      INTEGER,
                  iOpsIADVlOperStatus
                      INTEGER,
                  iOpsIADVlSecondaryServiceState
                      INTEGER,
                  iOpsIADVlAdminStatus
                      INTEGER,
                  iOpsIADVlOperStatusLastChange
                      TimeStamp,
                  iOpsIADVlLoopbackTestResult
                      INTEGER,
                  iOpsIADVlNumberOfWires
                      INTEGER,
                  iOpsIADVlSignalFunctionCode
                      INTEGER,
                  iOpsIADVlRobbedBitMode
                      INTEGER,
                  iOpsIADVlCallReferenceValue
                      INTEGER,
                  iOpsIADVlRingingCadence
                      INTEGER,
                  iOpsIADVlVoiceProtocolType
                      INTEGER,
                  iOpsIADVlPhoneNumber
                      DisplayString,


                  iOpsIADVlTransmitImpedance
                      INTEGER,
                  iOpsIADVlReceiveImpedance
                      INTEGER,
                  iOpsIADVlTransmitLoss
                      INTEGER,
                  iOpsIADVlReceiveLoss
                      INTEGER,
                  iOpsIADVlPayloadType
                      INTEGER,
                  iOpsIADVlEchoCancellation
                      TruthValue,
                  iOpsIADVlEchoDelay
                      INTEGER,
                  iOpsIADVlSilenceSuppression
                      TruthValue,
                  iOpsIADVlGenerateTestTone
                      TruthValue,
                  iOpsIADVlRowStatus
                      RowStatus
                }

   iOpsIADVlIndex OBJECT-TYPE
       SYNTAX  INTEGER
       MAX-ACCESS  not-accessible
       STATUS  current
       DESCRIPTION
           "Is the index of the voice line."
       ::= { iOpsIADVlEntry 1 }

   iOpsIADVlDS1IfIndex OBJECT-TYPE
       SYNTAX  InterfaceIndex
       MAX-ACCESS  read-create
       STATUS  current
       DESCRIPTION
           "Is the associated DS1 interface index, if the IAD has
           one or more DS1s. The value of this object is zero (0),
           if there are no DS1s local to the IAD."
       ::= { iOpsIADVlEntry 2 }

   iOpsIADVlDS0Index OBJECT-TYPE
       SYNTAX  INTEGER
       MAX-ACCESS  read-create
       STATUS  current
       DESCRIPTION
           "Is the DS0 index within the DS1, or, the index of the
           individual POTS line"
       ::= { iOpsIADVlEntry 3 }

   iOpsIADVlOperStatus OBJECT-TYPE
       SYNTAX  INTEGER {
                        up-InService(1),
                        down-OutOfService(2),
                        testing(3),


                        unknown(4)
                       }
       MAX-ACCESS  read-only
       STATUS  current
       DESCRIPTION
           "Indicates the operating status of the voice line.
           Is one of the following:

           'up-InService' - The line is in service
           'down-OutOfService' - The line is out of service
           'testing' - The line is currently undergoing a test
           'unknown' - The status of the line cannot be determined"
           ::= { iOpsIADVlEntry 4 }

   iOpsIADVlSecondaryServiceState OBJECT-TYPE
       SYNTAX  INTEGER {
                        none(1),
                        manual-OOS(2),
                        switch-OOS(3),
                        los-OOS(4),
                        oof-OOS(5),
                        maintenance-OOS(6)
                       }
       MAX-ACCESS  read-only
       STATUS  current
       DESCRIPTION
           "This indicates any current alarm on the voice line."
       ::= { iOpsIADVlEntry 5 }

   iOpsIADVlAdminStatus OBJECT-TYPE
       SYNTAX  INTEGER {
                        up-restore(1),
                        down-remove(2),
                        test-loopback(3)
                       }
       MAX-ACCESS  read-create
       STATUS  current
       DESCRIPTION
           "This identifies the desired administrative status of the
            voice line. It is one of the following values:

            'up-restore' - activate or restore the voice service
            'down-remove' - deactivate or remove the voice service
            'test-loopback' - initiate loopback test on the voice line
                 The test result can be monitored by polling
                 the 'iOpsIADVlLoopbackTestResult' object-type.

           If this object is set to 'test-loopback(3)' on a voice line
           that is still running a previously initiated
           'test-loopback(3)', a second (simultaneous) loopback test
           will not be invoked. In this case, the status of the
           line in test will be indicated by the
           'iOpsIADVlLoopbackTestResult' object-type as
           'test-inProgress(2)'."

       DEFVAL  { up-restore }
       ::= { iOpsIADVlEntry 6 }

   iOpsIADVlOperStatusLastChange OBJECT-TYPE
       SYNTAX  TimeStamp
       MAX-ACCESS  read-only
       STATUS  current
       DESCRIPTION
           "The value of the SNMPv2 MIBs 'sysUpTime' object-type at
           the time this voice line entered its current operating
           status state.

           If the current state of the voice line was entered prior
           to the last re-initialization of the SNMP agent, then
           this object will contain a zero (0) value."
       ::= { iOpsIADVlEntry 7 }

   iOpsIADVlLoopbackTestResult  OBJECT-TYPE
        SYNTAX  INTEGER {
                         no-Test(1),
                         test-inProgress(2),
                         test-Pass(3),
                         test-Fail-OffHook(4),
                         test-Fail-Bell(5),
                         test-Fail-Others(6)
                        }
       MAX-ACCESS  read-only
       STATUS  current
       DESCRIPTION
           "Indicates the results of the loopback test that was
           initiated by the 'iOpsIADVlAdminStatus'
           object-type."
           ::= { iOpsIADVlEntry 8 }

   iOpsIADVlNumberOfWires OBJECT-TYPE
       SYNTAX  INTEGER {
                        wires2(1),
                        wires4(2),
                        wires6(3),
                        wires8(4)
                       }
       MAX-ACCESS  read-only
       STATUS  current
       DESCRIPTION
           "Indicates the number of wires on the line."
       ::= { iOpsIADVlEntry 9 }

   iOpsIADVlSignalFunctionCode OBJECT-TYPE
       SYNTAX  INTEGER {
                        fxsLoopStart(1),
                        fxsGroundStart(2),
                        fxsWinkStart(3),
                        fxoLoopStart(4),
                        fxoGroundStart(5),


                        fxoWinkStart(6),
                        eAndM2-2(7),
                        eAndM2-4(8),
                        eAndM4-2(9),
                        eAndM4-4(10)
                       }
       MAX-ACCESS  read-create
       STATUS  current
       DESCRIPTION
           "Is the Generic Signal Function code for the voice line.
           The default value is 'fxsLoopStart'."
       DEFVAL  { fxsLoopStart }
       ::= { iOpsIADVlEntry 10 }

   iOpsIADVlRobbedBitMode OBJECT-TYPE
       SYNTAX  INTEGER {
                        inactive(1),
                        clearChannel(2),
                        abcd(3),
                        ab(4),
                        a(5)
                       }
       MAX-ACCESS  read-create
       STATUS  current
       DESCRIPTION
           "Is the Robbed Bit Signal mode for the voice line.
           The default value is 'abcd'."
       DEFVAL  { abcd }
       ::= { iOpsIADVlEntry 11 }

   iOpsIADVlCallReferenceValue OBJECT-TYPE
       SYNTAX  INTEGER (1..2048)
       MAX-ACCESS  read-create
       STATUS  current
       DESCRIPTION
           "Indicates the Call Reference Value (CRV)."
       ::= { iOpsIADVlEntry 12 }

   iOpsIADVlRingingCadence OBJECT-TYPE
       SYNTAX  INTEGER
       MAX-ACCESS  read-create
       STATUS  current
       DESCRIPTION
           "Indicates the ring cadence. "
       ::= { iOpsIADVlEntry 13 }

   iOpsIADVlVoiceProtocolType OBJECT-TYPE
       SYNTAX  INTEGER {
                        ds0(1),
                        voATM-AAL1(2),
                        voATM-AAL2(3),
                        voIP(4)
                       }
       MAX-ACCESS  read-create

       STATUS  current
       DESCRIPTION
           "Indicates the type of voice protocol that will be used."
       ::= { iOpsIADVlEntry 14 }

   iOpsIADVlPhoneNumber OBJECT-TYPE
       SYNTAX  DisplayString (SIZE(0..255))
       MAX-ACCESS  read-create
       STATUS  current
       DESCRIPTION
           "Indicates the telephone number of the voice line."
       ::= { iOpsIADVlEntry 15 }

   iOpsIADVlTransmitImpedance OBJECT-TYPE
       SYNTAX  INTEGER {
                        none(1),
                        ohm-50(2),
                        ohm-600(3),
                        ohm-900(4),
                        ohm-1200(5)
                       }
       MAX-ACCESS  read-create
       STATUS  current
       DESCRIPTION
           "Indicates the Transmit Impedance."
       DEFVAL  { none }
       ::= { iOpsIADVlEntry 16 }

   iOpsIADVlReceiveImpedance OBJECT-TYPE
       SYNTAX  INTEGER {
                        none(1),
                        ohm-50(2),
                        ohm-600(3),
                        ohm-900(4),
                        ohm-1200(5)
                       }
       MAX-ACCESS  read-create
       STATUS  current
       DESCRIPTION
           "Indicates the Receive Impedance."
       DEFVAL  { none }
       ::= { iOpsIADVlEntry 17 }

   iOpsIADVlTransmitLoss OBJECT-TYPE
       SYNTAX  INTEGER (0..20)
       UNITS  "db"
       MAX-ACCESS  read-create
       STATUS  current
       DESCRIPTION
           "Indicates the Transmit Loss."
       DEFVAL  { 0 }
       ::= { iOpsIADVlEntry 18 }

   iOpsIADVlReceiveLoss OBJECT-TYPE

       SYNTAX  INTEGER (0..20)
       UNITS  "db"
       MAX-ACCESS  read-create
       STATUS  current
       DESCRIPTION
           " Indicates the Receive Loss"
       DEFVAL  { 0 }
       ::= { iOpsIADVlEntry 19 }

   iOpsIADVlPayloadType OBJECT-TYPE
       SYNTAX  INTEGER {
                        pcm-u-law(1),
                        pcm-a-law(2),
                        g711(3),
                        g726(4),
                        g728(5),
                        g723-1-5-6K(6),
                        g723-1-6-4K(7),
                        g729(8),
                        g729-A(9)
                       }
       MAX-ACCESS  read-create
       STATUS  current
       DESCRIPTION
           " Indicates the Payload type."
       DEFVAL  { pcm-u-law }
       ::= { iOpsIADVlEntry 20 }

   iOpsIADVlEchoCancellation OBJECT-TYPE
       SYNTAX  TruthValue
       MAX-ACCESS  read-create
       STATUS  current
       DESCRIPTION
           "Indicates if Echo Cancellation is ON or OFF."
       DEFVAL  { false }
       ::= { iOpsIADVlEntry 21 }

   iOpsIADVlEchoDelay OBJECT-TYPE
       SYNTAX  INTEGER (0..120)
       UNITS  "ms"
       MAX-ACCESS  read-create
       STATUS  current
       DESCRIPTION
           "Indicates the length of the Echo Delay in milliseconds."
       DEFVAL  { 0 }
       ::= { iOpsIADVlEntry 22 }

   iOpsIADVlSilenceSuppression OBJECT-TYPE
       SYNTAX  TruthValue
       MAX-ACCESS  read-create
       STATUS  current
       DESCRIPTION
           "Indicates if Silence Suppression is ON or OFF."
       DEFVAL  { false }

       ::= { iOpsIADVlEntry 23 }

   iOpsIADVlGenerateTestTone OBJECT-TYPE
       SYNTAX  TruthValue
       MAX-ACCESS  read-create
       STATUS  current
       DESCRIPTION
           "Indicates if Test Tone Generation is ON or OFF."
       DEFVAL  { false }
       ::= { iOpsIADVlEntry 24 }

   iOpsIADVlRowStatus OBJECT-TYPE
       SYNTAX  RowStatus
       MAX-ACCESS  read-create
       STATUS  current
       DESCRIPTION
           "Status of this entry in the iOpsIADVlTable. This variable
           is used to create a new voice line for the IAD.

           To create and activate the voice line, this object should
           be set to 'createAndGo'.

           To create the voice line in an inactive administrative
           state, this object should be set to 'createAndWait'.

           The voice line can then be activated later, when desired,
           by setting this object to 'active'."
       ::= { iOpsIADVlEntry 25 }

   -- *****************************************************************
   --
   -- IAD notification
   --
   -- *****************************************************************

   iadNotificationPrefix OBJECT IDENTIFIER ::= { opsMIB 2 }
   iadNotifications OBJECT IDENTIFIER ::= { iadNotificationPrefix 1 }

   iadOperStatusChange NOTIFICATION-TYPE
       OBJECTS {
                iOpsIADOperStatus,
                iOpsIADOperStatusLastChange
               }
       STATUS  current
       DESCRIPTION
           "This notification is sent when the IAD status changes.
           The following information is returned:

           iOpsIADOperStatus - The new operational status of the IAD
           iOpsIADOperStatusLastChange - The last time the IAD
           operational status changed state"
       ::= { iadNotifications 1 }

   softwareDownloadComplete  NOTIFICATION-TYPE

       OBJECTS {
                iOpsIADDownloadSoftware
               }
       STATUS  current
       DESCRIPTION
           "This notification is sent after an attempt to download the
           system image file to the IAD. The status of the download is
           returned in the 'iOpsIADDownloadSoftware' object-type.
           The value is either:
           'download complete(1)' or
           'download failed(2)'"
       ::= { iadNotifications 2 }

   configUpDownloadComplete  NOTIFICATION-TYPE
       OBJECTS {
                iOpsIADUpDownloadConfiguration
               }
       STATUS  current
       DESCRIPTION
           "This notification is sent after an attempt to download
           or upload the configuration file to or from the IAD.
           The status of the file transfer is returned in the
           'iOpsIADUpDownloadConfiguration' object-type.
           The value is either:
           'up/download complete(1)' or
           'up/download failed(2)'"
       ::= { iadNotifications 3 }

   iadVoiceLineOperStatusChange NOTIFICATION-TYPE
       OBJECTS {
                iOpsIADVlOperStatus,
                iOpsIADVlOperStatusLastChange
               }
       STATUS  current
       DESCRIPTION
           "This notification is sent when the IAD voice line status
           changes. The following information is returned:
           iOpsIADVlOperStatus - The new operational status of IAD
                   voice line
           iOpsIADVlOperStatusLastChange - The last time the line
                   status changed state"
       ::= { iadNotifications 4 }

   voiceLineLoopbackTestComplete  NOTIFICATION-TYPE
       OBJECTS {
                iOpsIADVlLoopbackTestResult
               }
   STATUS  current
       DESCRIPTION
           "This notification is sent after attempting a loopback test
           on a voice line. The 'iOpsIADVlLoopbackTestResult'
           object-type returns the result of the loopback test."
       ::= { iadNotifications 5 }

   -- *****************************************************************
   --
   -- Conformance Information
   --
   -- *****************************************************************

   opsMIBConformance   OBJECT IDENTIFIER ::= { opsMIB 3 }
   opsMIBGroups        OBJECT IDENTIFIER ::= { opsMIBConformance 1 }
   opsMIBCompliances   OBJECT IDENTIFIER ::= { opsMIBConformance 2 }

   -- *****************************************************************
   --
   -- Compliance Statements
   --
   -- *****************************************************************

   opsMIBCompliance  MODULE-COMPLIANCE
       STATUS  current
       DESCRIPTION
           "The compliance statement for SNMP entities which implement
           OPS MIB."
       MODULE  -- this module
        MANDATORY-GROUPS {
                          iOpsIADConfigGroup,
                          iOpsIADVoiceServiceGroup
                         }

       GROUP  iOpsIADSecurityConfigGroup
       DESCRIPTION
           "Support for public key encryption or IAD login from
           external sites is optional."

       OBJECT  iOpsIADSoftwareFileName
       SYNTAX  DisplayString (SIZE(0..255))
       MIN-ACCESS  read-only
       DESCRIPTION
           "Write access is not required if the IAD does not support
           multiple system image files."

       OBJECT  iOpsIADSaveSoftware
       SYNTAX  INTEGER {
                        saveAndReboot(2)
                       }
       DESCRIPTION
           "'saveAndReboot' is the only value supported for IADs that
           cannot contain multiple system image files."

       OBJECT  iOpsIADConfigFileName
       SYNTAX  DisplayString (SIZE(0..255))
       MIN-ACCESS  read-only
       DESCRIPTION
           "Write access is not required if the IAD does not support
           multiple configuration files."

       OBJECT  iOpsIADSaveConfiguration
       SYNTAX  INTEGER {
                        saveAndReconfigure(3)
                       }
       DESCRIPTION
           "'saveAndReconfigure' is the only value supported for IADs
           that cannot support multiple configuration files."

       OBJECT  iOpsIADMgmtChBandwidth
       SYNTAX  INTEGER
       MIN-ACCESS  read-only
       DESCRIPTION
           "Write access is not required."

       OBJECT  iOpsIADMgmtChInactivityTimer
       SYNTAX  INTEGER (1..1000)
       MIN-ACCESS  read-only
       DESCRIPTION
           "Write access is not required."

       OBJECT  iOpsIADDateAndTime
       SYNTAX  DateAndTime
       MIN-ACCESS  read-only
       DESCRIPTION
           "Write access is not required."

       OBJECT  iOpsIADPublicIPAddress
       SYNTAX  IpAddress
       MIN-ACCESS  read-only
       DESCRIPTION
           "Write access is not required."

       OBJECT  iOpsIADSubnetMask
       SYNTAX  IpAddress
       MIN-ACCESS  read-only
       DESCRIPTION
           "Write access is not required."

       OBJECT  iOpsIADGateway
       SYNTAX  IpAddress
       MIN-ACCESS   read-only
       DESCRIPTION
           "Write access is not required."

       OBJECT  iOpsIADDHCPIP
       SYNTAX  IpAddress
       MIN-ACCESS  read-only
       DESCRIPTION
           "Write access is not required."

       OBJECT  iOpsIADServerType
       SYNTAX  INTEGER {
                        tftpServer(1)
                       }


       DESCRIPTION
           "TFTP service from the Server is required. Other kinds
           of file transfer protocols are optional."

       OBJECT  iOpsIADVlRowStatus
       SYNTAX  INTEGER {
                        active(1),
                        createAndGo(4),
                        destroy(6)
                       }
       MIN-ACCESS  read-only
       DESCRIPTION
           "Write access is not required, and only three of the six
           enumerated values for the RowStatus textual convention
           are supported."
       ::= { opsMIBCompliances 1 }

   -- *****************************************************************
   --
   -- Units of Conformance
   --
   -- *****************************************************************

   iOpsIADConfigGroup  OBJECT-GROUP
       OBJECTS {
                iOpsIADIfIndex,
                iOpsIADSerialNumber,
                iOpsIADCLEICode,
                iOpsIADAdminStatus,
                iOpsIADOperStatus,
                iOpsIADAlarmStatus,
                iOpsIADOperStatusLastChange,
                iOpsIADResetIAD,
                iOpsIADSoftwareFileName,
                iOpsIADSoftwareUpgradeFileName,
                iOpsIADDownloadSoftware,
                iOpsIADSaveSoftware,
                iOpsIADSoftwareVersion,
                iOpsIADReConfigIAD,
                iOpsIADConfigFileName,
                iOpsIADConfigUpgradeFileName,
                iOpsIADUpDownloadConfiguration,
                iOpsIADSaveConfiguration,
                iOpsIADVersionConfig,
                iOpsIADMgmtChType,
                iOpsIADMgmtChNumber,
                iOpsIADMgmtChBandwidth,
                iOpsIADMgmtChInactivityTimer,
                iOpsIADDataService,
                iOpsIADMacAddress,
                iOpsIADPublicIPAddress,
                iOpsIADSubnetMask,
                iOpsIADGateway,
                iOpsIADDHCPIP,

                iOpsIADServerIP,
                iOpsIADServerType,
                iOpsIADServerLoginName,
                iOpsIADServerPasswd
               }
       STATUS  current
       DESCRIPTION
           "A collection of objects that support the configuration
           of the IAD."
       ::= { opsMIBGroups 1 }

   iOpsIADSecurityConfigGroup  OBJECT-GROUP
       OBJECTS {
                iOpsIADMasPublicKey,
                iOpsIADManagementPasswd
               }
       STATUS  current
       DESCRIPTION
           "A collection of objects pertaining to security."
       ::= { opsMIBGroups 2 }

   iOpsIADVoiceServiceGroup  OBJECT-GROUP
       OBJECTS {
                iOpsIADVlNumber,
                iOpsIADVlDS1IfIndex,
                iOpsIADVlDS0Index,
                iOpsIADVlOperStatus,
                iOpsIADVlSecondaryServiceState,
                iOpsIADVlAdminStatus,
                iOpsIADVlLoopbackTestResult ,
                iOpsIADVlNumberOfWires,
                iOpsIADVlSignalFunctionCode,
                iOpsIADVlRobbedBitMode,
                iOpsIADVlCallReferenceValue,
                iOpsIADVlRingingCadence,
                iOpsIADVlVoiceProtocolType,
                iOpsIADVlPhoneNumber,
                iOpsIADVlTransmitImpedance,
                iOpsIADVlReceiveImpedance,
                iOpsIADVlTransmitLoss,
                iOpsIADVlReceiveLoss,
                iOpsIADVlPayloadType,
                iOpsIADVlEchoCancellation,
                iOpsIADVlEchoDelay,
                iOpsIADVlSilenceSuppression,
                iOpsIADVlGenerateTestTone,
                iOpsIADVlRowStatus
               }
       STATUS  current
       DESCRIPTION
           "A collection of objects that support the phone services
           at the IAD."
       ::= { opsMIBGroups 3 }

   END

-- 
--    Copyright (C) The Internet Society (2000). All Rights Reserved.
-- 
--    This document and translations of it may be copied and furnished to
--    others, and derivative works that comment on or otherwise explain it
--    or assist in its implementation may be prepared, copied, published
--    and distributed, in whole or in part, without restriction of any
--    kind, provided that the above copyright notice and this paragraph
--    are included on all such copies and derivative works. However, this
--    document itself may not be modified in any way, such as by removing
--    the copyright notice or references to the Internet Society or other
--    Internet organizations, except as needed for the purpose of
--    developing Internet standards in which case the procedures for
--    copyrights defined in the Internet Standards process must be
--    followed, or as required to translate it into languages other than
--    English.
-- 
--    The limited permissions granted above are perpetual and will not be
--    revoked by the Internet Society or its successors or assigns.
-- 
--    This document and the information contained herein is provided on an
--    "AS IS" basis and THE INTERNET SOCIETY AND THE INTERNET ENGINEERING
--    TASK FORCE DISCLAIMS ALL WARRANTIES, EXPRESS OR IMPLIED, INCLUDING
--    BUT NOT LIMITED TO ANY WARRANTY THAT THE USE OF THE INFORMATION
--    HEREIN WILL NOT INFRINGE ANY RIGHTS OR ANY IMPLIED WARRANTIES OF
--    MERCHANTABILITY OR FITNESS FOR A PARTICULAR PURPOSE."
