-- ODS TokenRing Enterprise Specific MIB (March 09, 1992)

ODS-TRMIB DEFINITIONS ::= BEGIN

IMPORTS
        enterprises, NetworkAddress, IpAddress, Counter, Gauge,
                TimeTicks, OBJECT-TYPE FROM RFC1155-SMI
					 DisplayString FROM SNMPv2-TC
        snmp FROM RFC1158-MIB;


ods                     OBJECT IDENTIFIER ::= { enterprises 50 }

enc                     OBJECT IDENTIFIER ::= { ods 1 }
enBridge                OBJECT IDENTIFIER ::= { ods 2 }
tokenRing               OBJECT IDENTIFIER ::= { ods 3 }
trBridge                OBJECT IDENTIFIER ::= { ods 4 }

trMib1                  OBJECT IDENTIFIER ::= { tokenRing 1 }

trSystem                OBJECT IDENTIFIER ::= { trMib1 1 }
trAdmin                 OBJECT IDENTIFIER ::= { trMib1 2 }
trBox                   OBJECT IDENTIFIER ::= { trSystem 1 }
trCards                 OBJECT IDENTIFIER ::= { trSystem 2 }
trPorts                 OBJECT IDENTIFIER ::= { trSystem 3 }
trRing                  OBJECT IDENTIFIER ::= { trSystem 4 }
trTrapEnable            OBJECT IDENTIFIER ::= { trSystem 5 }

-- --------------------------------------------------------

-- The box group contains objects pertaining to the
-- concentrator as a whole.

boxChassisId OBJECT-TYPE
        SYNTAX  INTEGER {
                        ods290(32),         -- Multi-slot modular system
                        ods861-rj45(112),   -- 16 port token ring box(tw)
                        ods861-uc(96),      -- 16 port token ring box(tw)
                        ods841(80),         -- 16 port token ring box(fo)
                        ods840(64)          -- 16 port token ring box(fo)
               }
        ACCESS  read-only
        STATUS  mandatory
        DESCRIPTION
                        "The type of chassis used for the concentrator.
                        For modular concentrators, the hardware is
                        further qualifed by the value of cardId for each
                        card installed in the concentrator."
        ::= { trBox 1 }

boxMaxDeinCount OBJECT-TYPE
        SYNTAX  INTEGER
        ACCESS  read-write
        STATUS  mandatory
        DESCRIPTION
                        "Contains the maximum number of successive
                        de-inserts that can occur before a given
                        port is shut off automatically."
        ::= { trBox 4 }

boxMaxDeinDelta OBJECT-TYPE
        SYNTAX  INTEGER
        ACCESS  read-write
        STATUS  mandatory
        DESCRIPTION
                        "The maximum time in seconds between successive
                         de-inserts for a given port for which the
                         portDeinCount will be incremeneted."
        ::= { trBox 5 }

boxReset OBJECT-TYPE
        SYNTAX  INTEGER
        ACCESS  read-write
        STATUS  mandatory
        DESCRIPTION
                        "Setting to 1 will reboot the agent."
        ::= { trBox 7 }

boxFWVersion OBJECT-TYPE
        SYNTAX  DisplayString (SIZE (0..255))
        ACCESS  read-only
        STATUS  mandatory
        DESCRIPTION
                        "The version of the firmware that is currently
                         resident."
        ::= { trBox 8 }

trapId  OBJECT-TYPE
        SYNTAX  INTEGER
        ACCESS  not-accessible
        STATUS  mandatory
        DESCRIPTION
                        "The trap Id for this particular trap.  It is a
                         one-up counter that identifies this trap."
        ::= { trBox 9 }

changedOid OBJECT-TYPE
        SYNTAX  OBJECT IDENTIFIER
        ACCESS  not-accessible
        STATUS  mandatory
        DESCRIPTION
                        "The Object Id of the variable that is the
                         reason for sending the trap."
        ::= { trBox 10 }

changedValue OBJECT-TYPE
        SYNTAX  INTEGER
        ACCESS  not-accessible
        STATUS  mandatory
        DESCRIPTION
                        "The value of the variable that is being
                         trapped."
        ::= { trBox 11 }

changedDescr OBJECT-TYPE
        SYNTAX  DisplayString (SIZE (0..255))
        ACCESS  not-accessible
        STATUS  mandatory
        DESCRIPTION
                        "A textual description of the variable, the slot,
                         the port, and the new value that is being trapped."
        ::= { trBox 12 }

tftpAddress OBJECT-TYPE
        SYNTAX  IpAddress
        ACCESS  read-write
        STATUS  mandatory
        DESCRIPTION
                        "The IP address from which TFTP packets will be
                         accepted by the agent."
        ::= { trBox 13 }

dosCommand OBJECT-TYPE
        SYNTAX  DisplayString (SIZE (0..40))
        ACCESS  read-write
        STATUS  mandatory
        DESCRIPTION
                        "A Dos command that will be executed."
        ::= { trBox 14 }

dosExitCode OBJECT-TYPE
        SYNTAX  INTEGER
        ACCESS  read-only
        STATUS  mandatory
        DESCRIPTION
                        "The status of the last executed DOS command."
        ::= { trBox 15 }

enbBcnIsoAlg OBJECT-TYPE
        SYNTAX  INTEGER {
                        enable(1),
                        disable(2)
                }
        ACCESS  read-write
        STATUS  mandatory
        DESCRIPTION
                        "Enable for the Beacon Isolation Algorithm.
                         When this variable is set to enable, then
                         if the ring beacons and is unable to recover
                         itself, the MAU will execute the Beacon
                         Isolation Algorithm.  This algorithm will
                         attempt to isolate the problem in the ring to
                         a single port.  This algorithm should
                         ONLY be enabled if all MAU's in the ring are
                         ODS MAU's with in-band agents that also have
                         enbBcnIsoAlg set to enable.  NOTE: this should
                         be set to disable for all MAU's in the ring
                         if any of the in-band agents has control of
                         an MAU that has multiple rings."
        ::= { trBox 16 }

-- --------------------------------------------------------

cardNumSlots OBJECT-TYPE
        SYNTAX  INTEGER
        ACCESS  read-only
        STATUS  mandatory
        DESCRIPTION
                        "The number of slots in the concentrator.  For
                        modular concentrators, this value is the maximum
                        number of cards that can be installed.  For
                        non-modular concentrators, the value is always
                        one."
        ::= { trCards 1 }

cardNumCards OBJECT-TYPE
        SYNTAX  INTEGER
        ACCESS  read-only
        STATUS  mandatory
        DESCRIPTION
                        "The number of cards actually installed in the
                        concentrator.  For non-modular concentrators, the
                        value is always one."
        ::= { trCards 2 }

-- --------------------------------------------------------

-- The card table contains information pertaining to each
-- card installed in the concentrator.  The size of the
-- table may change dynamically as old cards are removed
-- or new ones are installed.

cardTable OBJECT-TYPE
        SYNTAX  SEQUENCE OF CardEntry
        ACCESS  not-accessible
        STATUS  mandatory
        DESCRIPTION
                        "A list of card entries for each card installed in
                        the concentrator.  The number of entries is given
                        by the value of CardNumCards."
        ::= { trCards 3 }

cardEntry OBJECT-TYPE
        SYNTAX  CardEntry
        ACCESS  not-accessible
        STATUS  mandatory
        DESCRIPTION
                        "A card entry containing objects pertaining to a
                        card installed in the concentrator."
        INDEX   { cardIndex }
        ::= { cardTable 1 }

CardEntry ::= SEQUENCE {
        cardBypass              INTEGER,
        cardRingStar            INTEGER,
        cardRingSpeed           INTEGER,
        cardCableType           INTEGER,
        cardReset               INTEGER,
        cardSwitch              INTEGER,
        cardControl             INTEGER,
        cardID                  INTEGER,
        cardIndex               INTEGER,
        cardDescrip             DisplayString,
        cardNumPorts            INTEGER,
        cardHasPorts            INTEGER,
        cardHasRingInt          INTEGER,
        cardHasTW               INTEGER
}

cardBypass OBJECT-TYPE
        SYNTAX  INTEGER {
                        bypassOn(1),
                        bypassOff(2),
                        unavailable(3)
                }
        ACCESS  read-write
        STATUS  mandatory
        DESCRIPTION
                        "The current bypass state of the card."
        ::= { cardEntry 1 }

cardRingStar OBJECT-TYPE
        SYNTAX  INTEGER {
                        starMode(1),
                        ringMode(2),
                        unavailable(3)
                }
        ACCESS  read-write
        STATUS  mandatory
        DESCRIPTION
                        "The Ring/Star mode of the card."
        ::= { cardEntry 2 }

cardRingSpeed OBJECT-TYPE
        SYNTAX  INTEGER {
                        speed16MHz(1),
                        speed4MHz(2),
                        unavailable(3)
                }
        ACCESS  read-only
        STATUS  mandatory
        DESCRIPTION
                        "The Ring Speed of the card."
        ::= { cardEntry 3 }

cardCableType OBJECT-TYPE
        SYNTAX  INTEGER {
                        type3(1),
                        type1(2),
                        unavailable(3)
                }
        ACCESS  read-write
        STATUS  mandatory
        DESCRIPTION
                        "The card's Cable Type."
        ::= { cardEntry 4 }

cardReset OBJECT-TYPE
        SYNTAX  INTEGER {
                        on(1),
                        off(2),
                        unavailable(3)
                }
        ACCESS  read-only
        STATUS  mandatory
        DESCRIPTION
                        "The card's Reset Switch state."
        ::= { cardEntry 6 }

cardSwitch OBJECT-TYPE
        SYNTAX  INTEGER {
                        sw(1),
                        hw(2),
                        unavailable(3)
                }
        ACCESS  read-only
        STATUS  mandatory
        DESCRIPTION
                        "The state of the HW/SW switch on the card."
        ::= { cardEntry 7 }

cardControl OBJECT-TYPE
        SYNTAX  INTEGER {
                        sw(1),
                        hw(2),
                        unavailable(3)
                }
        ACCESS  read-only
        STATUS  mandatory
        DESCRIPTION
                        "Who currently controls the card, HW or SW."
        ::= { cardEntry 8 }

cardId OBJECT-TYPE
        SYNTAX  INTEGER {
                        revA(1),                -- Revision A of 841/861 type
                        revB(2),                -- Revision B of 841/861 type
                        revC(3),                -- Revision C of 841/861 type
                        ods290-FO10port(31),    -- 10-port fiber optic card
                        ods290-DB910port(237),  -- 10-port DB9 card
                        ods290-12port(239),     -- 12-port card
                        ods290-ringint(251),    -- ring interface card
                        ods290-ATRJ16port(126), -- 16 port active RJ45 card
                        ods290-ATR50(125),      -- 16 port active TELCO card
                        ods290-RMringmgr(45),   -- Ring Manager card
                        ods290-386-20RM(42),    -- 386/20 In-band mgr card
                        ods290-386-20Bridge(41) -- 386/20 Bridge card
                }
        ACCESS  read-only
        STATUS  mandatory
        DESCRIPTION
                        "The type of card installed in the concentrator.
                         If the chassis is a modular chassis, then cardId
                         defines the type of card.  However, if the chassis
                         is an 841 or 861 type chassis, then boxChassisId
                         fully defines the type of card installed, so for
                         a non-modular chassis the cardId specifies the
                         Revision level."
        ::= { cardEntry 9 }

cardIndex OBJECT-TYPE
        SYNTAX  INTEGER
        ACCESS  read-only
        STATUS  mandatory
        DESCRIPTION
                        "The slot in which the card is installed.  This
                        value uniquely identifies the card.  Its value
                        ranges between 1 and the value of CardNumSlots."
        ::= { cardEntry 10 }

cardDescrip OBJECT-TYPE
        SYNTAX  DisplayString (SIZE (0..255))
        ACCESS  read-only
        STATUS  mandatory
        DESCRIPTION
                        "A textual description of the card including
                        the ODS model number, media type and number of
                        ports."
        ::= { cardEntry 11 }

cardNumPorts OBJECT-TYPE
        SYNTAX  INTEGER
        ACCESS  read-only
        STATUS  mandatory
        DESCRIPTION
                        "The number of configurable ports on the card.
                        For some cards, the value may be zero."
        ::= { cardEntry 12 }

cardHasPorts OBJECT-TYPE
        SYNTAX  INTEGER  { hasUserPorts(1),
                           noUserPorts(2)
                }
        ACCESS  read-only
        STATUS  mandatory
        DESCRIPTION
                        "This value describes if there are configurable
                         user ports on the card."
        ::= { cardEntry 13 }

cardHasRingInt OBJECT-TYPE
        SYNTAX  INTEGER  { hasRingPorts(1),
                           noRingPorts(2)
                }
        ACCESS  read-only
        STATUS  mandatory
        DESCRIPTION
                        "This value describes if the card has ring in and
                         ring out ports."
        ::= { cardEntry 14 }

cardHasTW OBJECT-TYPE
        SYNTAX  INTEGER  { hasTW(1),
                           noTW(2)
                }
        ACCESS  read-only
        STATUS  mandatory
        DESCRIPTION
                        "This value describes if the card's user ports are
                         twisted wire or not."
        ::= { cardEntry 15 }

cardHasCtrl OBJECT-TYPE
        SYNTAX  INTEGER  { hasCtrl(1),
                           noCtrl(2)
                }
        ACCESS  read-only
        STATUS  mandatory
        DESCRIPTION
                        "This value describes if the card has a HW/SW Control
                         switch or not."
        ::= { cardEntry 16 }

cardHasBypass OBJECT-TYPE
        SYNTAX  INTEGER  { hasBypass(1),
                           noBypass(2)
                }
        ACCESS  read-only
        STATUS  mandatory
        DESCRIPTION
                        "This value describes if the card has a Bypass
                         switch or not."
        ::= { cardEntry 17 }

-- --------------------------------------------------------

-- The port table contains information pertaining to each
-- configurable port in the concentrator.  The size of the
-- table may change dynamically as old cards are removed
-- or new ones are installed.

portTable OBJECT-TYPE
        SYNTAX  SEQUENCE OF PortEntry
        ACCESS  not-accessible
        STATUS  mandatory
        DESCRIPTION
                        "A list of port entries for each interface port in
                         the concentrator.  The number of entries is given
                         by the sum of CardNumPorts for each card in the
                         CardTable."
        ::= { trPorts 1 }

portEntry OBJECT-TYPE
        SYNTAX  PortEntry
        ACCESS  not-accessible
        STATUS  mandatory
        DESCRIPTION
                        "A port entry containing objects pertaining to an
                         interface port in the concentrator."
        INDEX   { portCard, portIndex }
        ::= { portTable 1 }

PortEntry ::= SEQUENCE {
        portEnable              INTEGER,
        portActStatus           INTEGER,
        portRingInsert          INTEGER,
        portDeinCount           Counter,
        portCard                INTEGER,
        portIndex               INTEGER
        }

portEnable OBJECT-TYPE
        SYNTAX  INTEGER {
                        on(1),
                        off(2)
                }
        ACCESS  read-write
        STATUS  mandatory
        DESCRIPTION
                        "The current enable status of the port.  If
                         the value is off(2), no data is passed through
                         the port."
        ::= { portEntry 1 }

portActStatus OBJECT-TYPE
        SYNTAX  INTEGER {
                        true(1),
                        false(2)
                }
        ACCESS  read-only
        STATUS  mandatory
        DESCRIPTION
                        "Whether we currently see activity on the port.
                         If we have activity, then the value is true(1)."
        ::= { portEntry 2 }

portRingInsert OBJECT-TYPE
        SYNTAX  INTEGER {
                        true(1),
                        false(2)
                }
        ACCESS  read-only
        STATUS  mandatory
        DESCRIPTION
                        "Whether someone is currently inserted onto the
                         ring through this port.  If true(1), then someone
                         is inserted onto this port."
        ::= { portEntry 3 }

portDeinCount OBJECT-TYPE
        SYNTAX  Counter
        ACCESS  read-write
        STATUS  mandatory
        DESCRIPTION
                        "Current count of successive deinserts that occurred
                         on this port, each within MaxDeinDelta of the previous
                         deinsert."
        ::= { portEntry 4 }

portCard OBJECT-TYPE
        SYNTAX  INTEGER
        ACCESS  read-only
        STATUS  mandatory
        DESCRIPTION
                        "The card on which the port exists.  The card
                         identified by this value is the same card as
                         identified by the same value of CardIndex."
        ::= { portEntry 5 }

portIndex OBJECT-TYPE
        SYNTAX  INTEGER
        ACCESS  read-only
        STATUS  mandatory
        DESCRIPTION
                        "An integer which uniquely identifes this port on
                         the card.  Its value ranges between 1 and the
                         value of CardNumPorts for the card."
        ::= { portEntry 6 }

-- --------------------------------------------------------

-- The ring port table contains information pertaining to the
-- Ring In and Ring Out ports of the concentrator.

ringportTable OBJECT-TYPE
        SYNTAX  SEQUENCE OF RingEntry
        ACCESS  not-accessible
        STATUS  mandatory
        DESCRIPTION
                        "A list of entries for Ring In and Ring Out
                         ports of the concentrator."
        ::= { trRing 1 }

ringEntry OBJECT-TYPE
        SYNTAX  RingEntry
        ACCESS  not-accessible
        STATUS  mandatory
        DESCRIPTION
                        "A ring port entry containing objects pertaining
                         the concentrator's Ring In and Ring Out ports."
        INDEX   { rpCard, rpIndex }
        ::= { ringportTable 1 }

RingEntry ::= SEQUENCE {
        rpMode                INTEGER,
        rpFOTW                INTEGER,
        rpLoopBack            INTEGER,
        rpVoltSense           INTEGER,
        rpActStatus           INTEGER,
        rpCarrSense           INTEGER,
        rpCard                INTEGER,
        rpIndex               INTEGER,
        rpHasTW               INTEGER
}

rpMode OBJECT-TYPE
        SYNTAX  INTEGER {
                        autoLoop(1),
                        internalLoop(2),
                        normal(3)
                }
        ACCESS  read-write
        STATUS  mandatory
        DESCRIPTION
                        "The current status of the ring port."
        ::= { ringEntry 1 }

rpFOTW OBJECT-TYPE
        SYNTAX  INTEGER {
                        fiberOptic(1),
                        twistedWire(2)
                }
        ACCESS  read-write
        STATUS  mandatory
        DESCRIPTION
                        "Whether fiber optic or twisted wire are
                         currently being used by the ring port."
        ::= { ringEntry 2 }

rpLoopBack OBJECT-TYPE
        SYNTAX  INTEGER {
                        loopBackOn(1),
                        noLoopBack(2)
                }
        ACCESS  read-only
        STATUS  mandatory
        DESCRIPTION
                        "Whether the concentrator's ring port is in
                         loopback mode."
        ::= { ringEntry 3 }

rpVoltSense OBJECT-TYPE
        SYNTAX  INTEGER {
                        voltSenseOn(1),
                        noVoltSense(2)
                }
        ACCESS  read-only
        STATUS  mandatory
        DESCRIPTION
                        "Whether voltage is being sensed across the
                         ring port."
        ::= { ringEntry 4 }

rpActStatus OBJECT-TYPE
        SYNTAX  INTEGER {
                        true(1),
                        false(2)
                }
        ACCESS  read-only
        STATUS  mandatory
        DESCRIPTION
                        "Whether we currently see activity on the port.
                         if we have activity, then the value is true(1)."
        ::= { ringEntry 5 }

rpCarrSense OBJECT-TYPE
        SYNTAX  INTEGER {
                        carrSenseOn(1),
                        noCarrSense(2)
                }
        ACCESS  read-only
        STATUS  mandatory
        DESCRIPTION
                        "Whether a carrier is sensed on the ring port."
        ::= { ringEntry 6 }

rpCard OBJECT-TYPE
        SYNTAX  INTEGER
        ACCESS  read-only
        STATUS  mandatory
        DESCRIPTION
                        "The card on which the ring ports exist.  The
                         card identified by this value is the same card as
                         identified by the same value of CardIndex."
        ::= { ringEntry 7 }

rpIndex OBJECT-TYPE
        SYNTAX  INTEGER {
                        ringInPort(1),
                        ringOutPort(2)
                }
        ACCESS  read-only
        STATUS  mandatory
        DESCRIPTION
                        "An integer which uniquely identifies this ring
                         port on the card.  Its value ranges between
                         1 (Ring In) and 2 (Ring Out)."
        ::= { ringEntry 8 }

rpHasTW OBJECT-TYPE
        SYNTAX  INTEGER {
                        true(1),
                        false(2)
                }
        ACCESS  read-only
        STATUS  mandatory
        DESCRIPTION
                        "Whether or not the ring port has Twisted Wire."
        ::= { ringEntry 9 }

-- --------------------------------------------------------

-- The Trap Enable group contains objects that the agent uses
-- to determine which traps are to be sent to the defined network
-- manager(s).  Each variable can be individually enabled or disabled.

teLoopBack OBJECT-TYPE
        SYNTAX  INTEGER {
                        enabled(1),
                        disabled(2)
                }
        ACCESS  read-write
        STATUS  mandatory
        DESCRIPTION
                        "The Loopback state for a ring port has changed.
                         This trap will be sent to the defined management
                         station(s) if the value of teLoopBack enabled(1)."
        ::= { trTrapEnable 1 }

teMode OBJECT-TYPE
        SYNTAX  INTEGER {
                        enabled(1),
                        disabled(2)
                }
        ACCESS  read-write
        STATUS  mandatory
        DESCRIPTION
                        "The state of the Ring Port mode switch has
                         changed (Normal, Internal Loop, Auto Loop).
                         This trap will be sent to the defined management
                         station(s) if the value of teMode is enabled(1)."
        ::= { trTrapEnable 2 }

teFOTW OBJECT-TYPE
        SYNTAX  INTEGER {
                        enabled(1),
                        disabled(2)
                }
        ACCESS  read-write
        STATUS  mandatory
        DESCRIPTION
                        "The state of the Fiber Optic/Twisted Wire
                         switch has changed.  This trap will be sent to
                         the defined management station(s) if the value
                         of teFOTW is enabled(1)."
        ::= { trTrapEnable 3 }

teRingInsert OBJECT-TYPE
        SYNTAX  INTEGER {
                        enabled(1),
                        disabled(2)
                }
        ACCESS  read-write
        STATUS  mandatory
        DESCRIPTION
                        "A user was inserted onto the ring or de-inserted
                         from the ring.  This trap will be sent to
                         the defined management station(s) if the value
                         of teRingInsert is enabled(1)."
        ::= { trTrapEnable 4 }

teDeinCount OBJECT-TYPE
        SYNTAX  INTEGER {
                        enabled(1),
                        disabled(2)
                }
        ACCESS  read-write
        STATUS  mandatory
        DESCRIPTION
                        "The De-insert count for one of the user ports
                         is now greater than 1.  This trap will be sent to
                         the defined management station(s) if the value
                         of teDeinCount is enabled(1)."
        ::= { trTrapEnable 5 }

teEnable OBJECT-TYPE
        SYNTAX  INTEGER {
                        enabled(1),
                        disabled(2)
                }
        ACCESS  read-write
        STATUS  mandatory
        DESCRIPTION
                        "The state of one of the user port switches has
                         changed.  This trap will be sent to the defined
                         management station(s) if the value of
                         teEnable is enabled(1)."
        ::= { trTrapEnable 6 }

teBypass OBJECT-TYPE
        SYNTAX  INTEGER {
                        enabled(1),
                        disabled(2)
                }
        ACCESS  read-write
        STATUS  mandatory
        DESCRIPTION
                        "The state of the Bypass control switch has
                         changed.  This trap will be sent to the defined
                         management station(s) if the value of teBypass
                         is enabled(1)."
        ::= { trTrapEnable 7 }

teRingStar OBJECT-TYPE
        SYNTAX  INTEGER {
                        enabled(1),
                        disabled(2)
                }
        ACCESS  read-write
        STATUS  mandatory
        DESCRIPTION
                        "The state of the Ring/Star control switch has
                         changed.  This trap will be sent to the defined
                         management station(s) if the value of teRingStar
                         is enabled(1)."
        ::= { trTrapEnable 8 }

teRingSpeed OBJECT-TYPE
        SYNTAX  INTEGER {
                        enabled(1),
                        disabled(2)
                }
        ACCESS  read-write
        STATUS  mandatory
        DESCRIPTION
                        "The state of the Ring Speed (Clock) control switch
                         has changed.  This trap will be sent to the defined
                         management station(s) if the value of te_4_16 is
                         enabled(1)."
        ::= { trTrapEnable 9 }

teCableType OBJECT-TYPE
        SYNTAX  INTEGER {
                        enabled(1),
                        disabled(2)
                }
        ACCESS  read-write
        STATUS  mandatory
        DESCRIPTION
                        "The state of the Cable Type control switch has
                         changed.  This trap will be sent to the defined
                         management station(s) if the value of teCableType
                         is enabled(1)."
        ::= { trTrapEnable 10 }

teSwitch OBJECT-TYPE
        SYNTAX  INTEGER {
                        enabled(1),
                        disabled(2)
                }
        ACCESS  read-write
        STATUS  mandatory
        DESCRIPTION
                        "The state of the HW/SW control switch has
                         changed.  This trap will be sent to the defined
                         management station(s) if the value of teSwitch
                         is enabled(1)."
        ::= { trTrapEnable 12 }

teLanManager OBJECT-TYPE
        SYNTAX  INTEGER {
                        enabled(1),
                        disabled(2)
                }
        ACCESS  read-write
        STATUS  mandatory
        DESCRIPTION
                        "The Ringin or Ringout has gone into Loopback.
                         This alert will be sent to IBM's Lan Manager
                         management station(s) if the value of teLanManager
                         is enabled(1)."
        ::= { trTrapEnable 15 }

END
