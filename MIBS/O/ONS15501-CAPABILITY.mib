ONS15501-CAPABILITY   DEFINITIONS ::= BEGIN


IMPORTS
    MODULE-IDENTITY
        FROM SNMPv2-SMI
    AGENT-CAPABILITIES
        FROM SNMPv2-CONF
    synchronous
        FROM ONS15501-MIB;


ons15501MIBCapabilities MODULE-IDENTITY
    LAST-UPDATED "200210151800Z"
    ORGANIZATION "Cisco Systems, Inc."
    CONTACT-INFO
            "   Cisco Systems
                Customer Service

             Postal: 170 W Tasman Drive
                     San Jose, CA 95134
                     USA

                Tel: +1 800 553-NETS

             E-mail: cs-dwdm@cisco.com"
    DESCRIPTION
        "The MIB capability definition for ONS-15501 Optical 
         Amplifier."
    REVISION     "200210151800Z"
    DESCRIPTION
        "Initial version of this MIB module"
    ::= {  synEmbLxCapability 11 }


synEmbLxCapability  OBJECT IDENTIFIER ::= { synchronous 15 }


ons15501CapOld AGENT-CAPABILITIES
    PRODUCT-RELEASE        "Release 3.0 of ONS15501 software."
    STATUS  current
    DESCRIPTION
        "The agent capability for ONS15501 release 3.0.
         The entity MIB is modeled as a single chassis
         containing 2 ports (input /output) and a power
         supply units. None of the parts are Field Replaceable
         Units (FRU). 
         Main purpose of supporting the Entity MIB is for
         proper notification correlation."
    SUPPORTS SNMPv2-MIB
        INCLUDES {
                  systemGroup,
                  snmpGroup, 
                  snmpBasicNotificationsGroup
                 }
        VARIATION
          sysORLastChange
            ACCESS          not-implemented
            DESCRIPTION     "Not implemented."
        VARIATION
          sysORID
            ACCESS          not-implemented
            DESCRIPTION     "Not implemented."
        VARIATION
          sysORUpTime
            ACCESS          not-implemented
            DESCRIPTION     "Not implemented."
        VARIATION
          sysORDescr
            ACCESS          not-implemented
            DESCRIPTION     "Not implemented."
    SUPPORTS ENTITY-MIB
        INCLUDES {
                  entityPhysicalGroup,
                  entityPhysical2Group,
                  entityGeneralGroup, 
                  entityNotificationsGroup 
                 }
        VARIATION
          entPhysicalSerialNum
            ACCESS          read-only
            DESCRIPTION     "The serial numbers are not writeable."
        VARIATION
          entPhysicalAlias
            ACCESS          read-write
            DESCRIPTION     "Writeable only for chassis."
        VARIATION
          entPhysicalAssetID
            ACCESS          read-write
            DESCRIPTION     "Writeable only for chassis."
    SUPPORTS ONS15501-MIB
        INCLUDES {
                  ons15501SysInfoGroup,
                  ons15501FinalAttrGroup,
                  ons15501TrapLogGroup,
                  ons15501ActiveAlarmGroup,
                  ons15501TrapDescriptionGroup,
                  ons15501FinalNotificationsGroup
                 }
    ::= { ons15501MIBCapabilities 1 }



ons15501CapDC AGENT-CAPABILITIES
    PRODUCT-RELEASE        "DC series of ONS15501, Release 4.0"
    STATUS  current
    DESCRIPTION
        "The agent capability for ONS15501 release 4.0
         for DC series.
         The entity MIB is modeled as a single chassis
         containing 2 ports (input /output) and two power
         supply units. None of the parts are FRU. 
         Main purpose of supporting the Entity MIB is for
         proper notification correlation."
    SUPPORTS SNMPv2-MIB
        INCLUDES {
                  systemGroup,
                  snmpSetGroup, 
                  snmpGroup, 
                  snmpCommunityGroup,
                  snmpBasicNotificationsGroup
                 }
    SUPPORTS ENTITY-MIB
        INCLUDES {
                  entityPhysicalGroup,
                  entityPhysical2Group,
                  entityGeneralGroup, 
                  entityNotificationsGroup 
                 }
        VARIATION
          entPhysicalSerialNum
            ACCESS          read-only
            DESCRIPTION     "The serial numbers are not writeable."
        VARIATION
          entPhysicalAlias
            ACCESS          read-write
            DESCRIPTION     "Writeable only for chassis."
        VARIATION
          entPhysicalAssetID
            ACCESS          read-write
            DESCRIPTION     "Writeable only for chassis."
    SUPPORTS ONS15501-MIB
        INCLUDES {
                  ons15501SysInfoGroup2,
                  ons15501CoreAttrGroup,
                  ons15501TrapLogGroup,
                  ons15501ActiveAlarmGroup,
                  ons15501TrapDescriptionGroup,
                  ons15501FinalNotificationsGroup,
                  ons15501PowerSupplyStatusGroup,
                  ons15501PowerSupplyLevelGroup
                 }
    ::= { ons15501MIBCapabilities 2 }



ons15501CapAC AGENT-CAPABILITIES
    PRODUCT-RELEASE        "AC series of ONS15501, Release 4.0"
    STATUS  current
    DESCRIPTION
        "The agent capability for ONS15501 release 4.0
         for AC series.
         The entity MIB is modeled as a single chassis
         containing 2 ports (input /output) and two power
         supply units. None of the parts are FRU. 
         Main purpose of supporting the Entity MIB is for
         proper notification correlation."
    SUPPORTS SNMPv2-MIB
        INCLUDES {
                  systemGroup,
                  snmpSetGroup, 
                  snmpGroup, 
                  snmpCommunityGroup,
                  snmpBasicNotificationsGroup
                 }
    SUPPORTS ENTITY-MIB
        INCLUDES {
                  entityPhysicalGroup,
                  entityPhysical2Group,
                  entityGeneralGroup, 
                  entityNotificationsGroup 
                 }
        VARIATION
          entPhysicalSerialNum
            ACCESS          read-only
            DESCRIPTION     "The serial numbers are not writeable."
        VARIATION
          entPhysicalAlias
            ACCESS          read-write
            DESCRIPTION     "Writeable only for chassis."
        VARIATION
          entPhysicalAssetID
            ACCESS          read-write
            DESCRIPTION     "Writeable only for chassis."
    SUPPORTS ONS15501-MIB
        INCLUDES {
                  ons15501SysInfoGroup2,
                  ons15501CoreAttrGroup,
                  ons15501TrapLogGroup,
                  ons15501ActiveAlarmGroup,
                  ons15501TrapDescriptionGroup,
                  ons15501FinalNotificationsGroup,
                  ons15501PowerSupplyStatusGroup
                 }
    ::= { ons15501MIBCapabilities 3 }


END
