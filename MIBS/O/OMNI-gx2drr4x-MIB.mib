OMNI-gx2drr4x-MIB DEFINITIONS ::= BEGIN

    IMPORTS
	IpAddress, TimeTicks, Counter            
					      FROM RFC1155-SMI
	
	OBJECT-TYPE                     
					      FROM RFC-1212
	DisplayString        
					      FROM RFC1213-MIB
	TRAP-TYPE                       
					      FROM RFC-1215
	gx2Drr4x
					      FROM GX2HFC-MIB

	trapIdentifier,trapNetworkElemModelNumber,
	trapNetworkElemSerialNum, trapPerceivedSeverity,
	trapNetworkElemOperState, trapNetworkElemAlarmStatus,
	trapNetworkElemAdminState, trapNetworkElemAvailStatus,
	trapText, trapNETrapLastTrapTimeStamp, trapChangedObjectId,
	trapChangedValueInteger, trapChangedValueDisplayString
					      FROM NLSBBN-TRAPS-MIB;



	       -- This MIB module uses the extended OBJECT-TYPE macro as
	       -- defined in RFC1212 and the TRAP-TYPE macro as defined
	       -- in RFC 1215.

      -- *********************************************************************
      -- *                                                                   *  
      -- * REVISION history:                                                 *
      -- *	      MIB at Rev 0 to support Firmware at Rev A, Feb 08, 2005    * 
      -- *                                                                   *
      -- *********************************************************************

	-- OMNISTAR Digital Receiver Return 4X Module MIB MODULE

	-- This MIB module defines information for management of HFC networks
		-- 
		-- The MIB module assumes that all generic (static) network element
		-- information is defined in a different module such as the HFC module
		-- The MIB consists of two groups:
		-- the device type descriptor subgroup and 
		-- gx2drr4x Network Elements subgroup.
		-- The device type descriptor subgroup is used to define 
		-- parameters specific to gx2drr4x device type.
		-- These parameters are common across all network elements
		-- from gx2drr4x device type.
		--
		-- The gx2drr4x Network Elements subgroup is
		-- a list of gx2drr4x type elements in the
		-- current network topology with nominal
		-- and current parameter values for the
		-- individual network elements; the individual
		-- network elements are identified by  
		-- index from hfcCommonTable.
		-- That implies the hfcCommonTableIndex and
		-- gx2drr4xTableIndex are equal for each individual
		-- network element.
		-- This table is an extension of the hfcCommonTable
		-- for all elements of gx2drr4x type.
		--
		-- Both groups are mandatory for management of gx2drr4x devices.

-- ****************************************************************************
		--
		-- All floating point numbers will be represented by an IEEE 32 Bit number.
		-- Conversion of this number must be done on the user interface to view the 
		-- actual floating point number. 
		--

		Float ::= Counter  -- UNSIGNED (32 BITS) 

-- ****************************************************************************

		-- gx2drr4x Device Descriptor subgroup.

		-- The device type descriptor subgroup is used to define 
		-- parameters specific to gx2drr4x device type.
		-- These parameters are common across all network elements
		-- from gx2drr4x device type.


		 gx2drr4xDescriptor OBJECT IDENTIFIER ::= {gx2Drr4x 1}



--*****************************************************************************
		--              gx2drr4x Table
		
		--
		-- The individual network elements indentified by  
		-- index from hfcCommonTable.
		-- That implies what hfcCommonTableIndex and
		-- gx2drr4xTableIndex are equal for each individual
		-- nettwork element.
		-- This table should be used as an extension of the hfcCommonTable
		-- for all elements of gx2drr4x type.

	-- ANALOG TABLE:
	-- Analog table hold analog parameters. 
	--    For each analog parameter, there are following alarm limits:
      --       major high, major low, minor high and minor low.
      --    Firmware use these limits to determine alarm related to this parameter. Based on 
	--    individual parameter, certain alarm limit may not be populated.   
      --    For the unused entry, this MIB provides the following comment:
 	--    "This object is not used by this module and always returns invalid float value 
	--	of 0xFFFFFFFF . This object is kept here for persistence." 

	       gx2drr4xAnalogTable                    OBJECT-TYPE
			 SYNTAX             SEQUENCE OF Gx2drr4xAnalogEntry
			 ACCESS             not-accessible
			 STATUS             mandatory
			 DESCRIPTION
			 "This table contains gx2drr4x specific analog parameters with
			  nominal,limits and current values."
			 ::= { gx2Drr4x 2 }


	       gx2drr4xAnalogEntry               OBJECT-TYPE
			 SYNTAX             Gx2drr4xAnalogEntry
			 ACCESS             not-accessible
			 STATUS             mandatory
			 DESCRIPTION
			 "This list contains the analog parameters and descriptions."
			 INDEX { gx2drr4xAnalogTableIndex }
			 ::= { gx2drr4xAnalogTable  1}

--*****************************************************************************
	       gx2drr4xDigitalTable                    OBJECT-TYPE
			 SYNTAX             SEQUENCE OF Gx2drr4xDigitalEntry
			 ACCESS             not-accessible
			 STATUS             mandatory
			 DESCRIPTION
			 "This table contains gx2drr4x specific digital parameters with
			  nominal and current values."
			 ::= { gx2Drr4x 3 }

	       gx2drr4xDigitalEntry               OBJECT-TYPE
			 SYNTAX             Gx2drr4xDigitalEntry
			 ACCESS             not-accessible
			 STATUS             mandatory
			 DESCRIPTION
			 "This list contains individual digital parameters and descriptions."
			 INDEX { gx2drr4xDigitalTableIndex }
			 ::= { gx2drr4xDigitalTable  2}

--*****************************************************************************
	       gx2drr4xStatusTable                    OBJECT-TYPE
			 SYNTAX             SEQUENCE OF Gx2drr4xStatusEntry
			 ACCESS             not-accessible
			 STATUS             mandatory
			 DESCRIPTION
			 "This table contains gx2drr4x specific status parameters with
			  nominal and current values."
			 ::= { gx2Drr4x 4 }

	       gx2drr4xStatusEntry               OBJECT-TYPE
			 SYNTAX             Gx2drr4xStatusEntry
			 ACCESS             not-accessible
			 STATUS             mandatory
			 DESCRIPTION
			 "This list contains Status parameters and descriptions."
			 INDEX { gx2drr4xStatusTableIndex }
			 ::= { gx2drr4xStatusTable  3}

--*****************************************************************************
	       gx2drr4xFactoryTable                    OBJECT-TYPE
			 SYNTAX             SEQUENCE OF Gx2drr4xFactoryEntry
			 ACCESS             not-accessible
			 STATUS             mandatory
			 DESCRIPTION
			 "This table contains gx2drr4x specific factory setting parameters with
			  nominal and current values."
			 ::= { gx2Drr4x 5 }

	       gx2drr4xFactoryEntry               OBJECT-TYPE
			 SYNTAX             Gx2drr4xFactoryEntry
			 ACCESS             not-accessible
			 STATUS             mandatory
			 DESCRIPTION
			 "This list contains Factory setting parameters and descriptions."
			 INDEX { gx2drr4xFactoryTableIndex }
			 ::= { gx2drr4xFactoryTable  4}

--*****************************************************************************


	      Gx2drr4xAnalogEntry    ::= SEQUENCE  
	       {
		gx2drr4xAnalogTableIndex      INTEGER,
 		
		drr4xlabelRFAAttenuation			DisplayString (SIZE (0..80)),
		drr4xuomRFAAttenuation			DisplayString (SIZE (0..80)),
		drr4xmajorHighRFAAttenuation		Float,
		drr4xmajorLowRFAAttenuation		Float, 
		drr4xminorHighRFAAttenuation		Float,
		drr4xminorLowRFAAttenuation		Float, 
		drr4xcurrentValueRFAAttenuation	Float, 
		drr4xstateFlagRFAAttenuation		INTEGER,
		drr4xminValueRFAAttenuation		Float,
		drr4xmaxValueRFAAttenuation 		Float,
		drr4xalarmStateRFAAttenuation		INTEGER,
		
		drr4xlabelRFBAttenuation			DisplayString (SIZE (0..80)),
		drr4xuomRFBAttenuation			DisplayString (SIZE (0..80)),
		drr4xmajorHighRFBAttenuation		Float, 
		drr4xmajorLowRFBAttenuation		Float, 
		drr4xminorHighRFBAttenuation		Float,
		drr4xminorLowRFBAttenuation		Float, 
		drr4xcurrentValueRFBAttenuation	Float, 
		drr4xstateFlagRFBAttenuation		INTEGER,
		drr4xminValueRFBAttenuation		Float,
		drr4xmaxValueRFBAttenuation 		Float,
		drr4xalarmStateRFBAttenuation		INTEGER,
  
      	drr4xlabelRFCAttenuation			DisplayString (SIZE (0..80)),
		drr4xuomRFCAttenuation			DisplayString (SIZE (0..80)),
		drr4xmajorHighRFCAttenuation		Float, 
		drr4xmajorLowRFCAttenuation		Float, 
		drr4xminorHighRFCAttenuation		Float,
		drr4xminorLowRFCAttenuation		Float, 
		drr4xcurrentValueRFCAttenuation	Float, 
		drr4xstateFlagRFCAttenuation		INTEGER,
		drr4xminValueRFCAttenuation		Float,
		drr4xmaxValueRFCAttenuation 		Float,
		drr4xalarmStateRFCAttenuation		INTEGER,
  
	   	drr4xlabelRFDAttenuation			DisplayString (SIZE (0..80)),
		drr4xuomRFDAttenuation			DisplayString (SIZE (0..80)),
		drr4xmajorHighRFDAttenuation		Float, 
		drr4xmajorLowRFDAttenuation		Float, 
		drr4xminorHighRFDAttenuation		Float,
		drr4xminorLowRFDAttenuation		Float, 
		drr4xcurrentValueRFDAttenuation	Float, 
		drr4xstateFlagRFDAttenuation		INTEGER,
		drr4xminValueRFDAttenuation		Float,
		drr4xmaxValueRFDAttenuation 		Float,
		drr4xalarmStateRFDAttenuation		INTEGER,
  
		drr4xlabelTrippointLevel			DisplayString (SIZE (0..80)),
		drr4xuomTrippointLevel			DisplayString (SIZE (0..80)),
		drr4xmajorHighTrippointLevel		Float, 
		drr4xmajorLowTrippointLevel		Float, 
		drr4xminorHighTrippointLevel		Float,
		drr4xminorLowTrippointLevel		Float, 
		drr4xcurrentValueTrippointLevel	Float, 
		drr4xstateFlagTrippointLevel		INTEGER,
		drr4xminValueTrippointLevel		Float,
		drr4xmaxValueTrippointLevel 		Float,
		drr4xalarmStateTrippointLevel  	INTEGER,	
		                   
            drr4xlabelOptCurrent				DisplayString (SIZE (0..80)),
		drr4xuomOptCurrent				DisplayString (SIZE (0..80)),
		drr4xmajorHighOptCurrent			Float, 
		drr4xmajorLowOptCurrent			Float, 
		drr4xminorHighOptCurrent			Float,
		drr4xminorLowOptCurrent			Float, 
		drr4xcurrentValueOptCurrent		Float, 
		drr4xstateFlagOptCurrent			INTEGER,
		drr4xminValueOptCurrent			Float,
		drr4xmaxValueOptCurrent 			Float,
		drr4xalarmStateOptCurrent			INTEGER,
                 
		drr4xlabel12VCurrent				DisplayString (SIZE (0..80)),
		drr4xuom12VCurrent				DisplayString (SIZE (0..80)),
		drr4xmajorHigh12VCurrent			Float, 
		drr4xmajorLow12VCurrent			Float, 
		drr4xminorHigh12VCurrent			Float,
		drr4xminorLow12VCurrent			Float, 
		drr4xcurrentValue12VCurrent		Float, 
		drr4xstateFlag12VCurrent			INTEGER,
		drr4xminValue12VCurrent			Float,
		drr4xmaxValue12VCurrent 			Float,
		drr4xalarmState12VCurrent			INTEGER, 
		
		drr4xlabelModTemp			    	DisplayString (SIZE (0..80)),
		drr4xuomModTemp					DisplayString (SIZE (0..80)),
		drr4xmajorHighModTemp				Float, 
		drr4xmajorLowModTemp				Float, 
		drr4xminorHighModTemp				Float,
		drr4xminorLowModTemp				Float, 
		drr4xcurrentValueModTemp			Float, 
		drr4xstateFlagModTemp				INTEGER,
		drr4xminValueModTemp				Float,
		drr4xmaxValueModTemp				Float,
		drr4xalarmStateModTemp			INTEGER,    
			
		drr4xlabelFanCurrent			DisplayString (SIZE (0..80)),
		drr4xuomFanCurrent			DisplayString (SIZE (0..80)),
		drr4xmajorHighFanCurrent		Float, 
		drr4xmajorLowFanCurrent		Float, 
		drr4xminorHighFanCurrent		Float,
		drr4xminorLowFanCurrent		Float, 
		drr4xcurrentValueFanCurrent	Float, 
		drr4xstateFlagFanCurrent		INTEGER,
		drr4xminValueFanCurrent		Float,
		drr4xmaxValueFanCurrent 		Float,
		drr4xalarmStateFanCurrent		INTEGER
				
		}

		-- ****************  Digital Parameters ***********************
	     Gx2drr4xDigitalEntry    ::= SEQUENCE  
	     {
		gx2drr4xDigitalTableIndex         INTEGER,    
		               
            drr4xlabelTrippointMode   	    DisplayString (SIZE (0..80)),
		drr4xenumTrippointMode		    DisplayString (SIZE (0..80)),
		drr4xvalueTrippointMode		    INTEGER,
		drr4xstateflagTrippointMode       INTEGER,
		    							         
		drr4xlabelFactoryDefaultReset	    DisplayString (SIZE (0..80)),
		drr4xenumFactoryDefaultReset		DisplayString (SIZE (0..80)),
		drr4xvalueFactoryDefaultReset		INTEGER,
		drr4xstateflagFactoryDefaultReset INTEGER                             
	    }

		-- ****************  Status Parameters ************************************
	     Gx2drr4xStatusEntry    ::= SEQUENCE  
	     {
		gx2drr4xStatusTableIndex      INTEGER,

		drr4xlabelBoot				DisplayString (SIZE (0..80)),
		drr4xvalueBoot				INTEGER,
		drr4xstateflagBoot			INTEGER,
		
		drr4xlabelFlash				DisplayString (SIZE (0..80)),
		drr4xvalueFlash				INTEGER,
		drr4xstateflagFlash			INTEGER,

		drr4xlabelFactoryDataCRC 		DisplayString (SIZE (0..80)),
		drr4xvalueFactoryDataCRC		INTEGER,
		drr4xstateflagFactoryDataCRC	INTEGER,

		drr4xlabelAlarmDataCrc		DisplayString (SIZE (0..80)),
		drr4xvalueAlarmDataCrc		INTEGER,
		drr4xstateflagAlarmDataCrc	INTEGER,

		drr4xlabelCalibrationDataCrc		DisplayString (SIZE (0..80)),
		drr4xvalueCalibrationDataCrc		INTEGER,
		drr4xstateflagCalibrationDataCrc	INTEGER,

		drr4xlabelHardwareStatus		DisplayString (SIZE (0..80)),
		drr4xvalueHardwareStatus		INTEGER,
		drr4xstateflagHardwareStatus	INTEGER, 
	
		drr4xlabelOpticTripPointStatus		 DisplayString (SIZE (0..80)),
		drr4xvalueOpticTripPointStatus		 INTEGER,
		drr4xstateflagOpticTripPointStatus	 INTEGER,
			
		drr4xlabelLinkStatus	                 DisplayString (SIZE (0..80)),
		drr4xvalueLinkStatus		             INTEGER,
		drr4xstateflagLinkStatus	             INTEGER     
		}


		-- ****************  Factory Parameters *************************************
       Gx2drr4xFactoryEntry    ::= SEQUENCE  
       {
		gx2drr4xFactoryTableIndex       INTEGER,
		drr4xbootControlByte  			INTEGER,
		drr4xbootStatusByte   			INTEGER,
		drr4xbank1CRC    			        INTEGER,
		drr4xbank2CRC    			        INTEGER,
		drr4xprgEEPROMByte    			INTEGER,
		drr4xfactoryCRC    			    INTEGER,
		drr4xcalculateCRC    				INTEGER,
		drr4xhourMeter    				INTEGER,
		drr4xflashPrgCntA    				INTEGER,
		drr4xflashPrgCntB    				INTEGER,
		drr4xflashBankARev    			DisplayString (SIZE (0..80)),
		drr4xflashBankBRev    			DisplayString (SIZE (0..80)),
		drr4xSubAgentRev					DisplayString (SIZE (0..80))
		}
            -- ************** Analog Parameters ****************************
		gx2drr4xAnalogTableIndex              OBJECT-TYPE
			   SYNTAX           INTEGER (1..2147483647)
			   ACCESS           read-only
			   STATUS           mandatory
			   DESCRIPTION
			   "The value of this object identifies the network
			    element. This index is equal to the
			    hfcCommonTableIndex for the same element."
			   ::= { gx2drr4xAnalogEntry 1}
			   
 -- RFAAttenuation         
        drr4xlabelRFAAttenuation           OBJECT-TYPE
			   SYNTAX           DisplayString (SIZE (0..80))
			   ACCESS           read-only
			   STATUS           optional
			   DESCRIPTION
			   "The value of this object provides the label of the
			    RF Channel A Attenuation Analog parameter."
			   ::= { gx2drr4xAnalogEntry 2}

		drr4xuomRFAAttenuation             OBJECT-TYPE
			   SYNTAX           DisplayString (SIZE (0..80))
			   ACCESS           read-only
			   STATUS           optional
			   DESCRIPTION
			   "The value of this object provides the Unit of Measure of the
			     RF Channel A Attenuation Analog parameter. The unit is in dB"
			   ::= { gx2drr4xAnalogEntry 3}

		drr4xmajorHighRFAAttenuation       OBJECT-TYPE
			   SYNTAX           Float 
			   ACCESS           read-only
			   STATUS           obsolete
			   DESCRIPTION
			   "This object is not used by this module and always returns invalid float value
			    of 0xFFFFFFFF . It is kept here for persistence."
			   ::= { gx2drr4xAnalogEntry 4}

		drr4xmajorLowRFAAttenuation        OBJECT-TYPE
			   SYNTAX           Float 
			   ACCESS           read-only
			   STATUS           obsolete
			   DESCRIPTION
			    "This object is not used by this module and always returns invalid float value
			    of 0xFFFFFFFF . It is kept here for persistence."
			   ::= { gx2drr4xAnalogEntry 5}

		drr4xminorHighRFAAttenuation       OBJECT-TYPE
			   SYNTAX           Float
			   ACCESS           read-only
			   STATUS           obsolete
			   DESCRIPTION
			    "This object is not used by this module and always returns invalid float value
			    of 0xFFFFFFFF . It is kept here for persistence."
			   ::= { gx2drr4xAnalogEntry 6}

		drr4xminorLowRFAAttenuation        OBJECT-TYPE
			   SYNTAX           Float 
			   ACCESS           read-only
			   STATUS           obsolete
			   DESCRIPTION
			    "This object is not used by this module and always returns invalid float value
			    of 0xFFFFFFFF . It is kept here for persistence."
			   ::= { gx2drr4xAnalogEntry 7}

		drr4xcurrentValueRFAAttenuation    OBJECT-TYPE
			   SYNTAX           Float 
			   ACCESS           read-write
			   STATUS           mandatory
			   DESCRIPTION
			   "The value of this object provides the Current value
			    of the RF Channel A Attenuation Analog parameter." 
			   ::= { gx2drr4xAnalogEntry 8}

		drr4xstateFlagRFAAttenuation       OBJECT-TYPE
			   SYNTAX           INTEGER
								{
								hidden(1),
								read-only(2),
								updateable(3)
								}
			   ACCESS           read-only
			   STATUS           mandatory
			   DESCRIPTION
			   "The value of this object provides the state
			    of the RF Channel A Attenuation Analog parameter. (1-hidden	
			          2-read-only, 3-updateable)."
			   ::= { gx2drr4xAnalogEntry 9}

		drr4xminValueRFAAttenuation        OBJECT-TYPE
			   SYNTAX           Float
			   ACCESS           read-only
			   STATUS           mandatory
			   DESCRIPTION
			   "The value of this object provides the minimum value
			    the RF Channel A Attenuation Analog parameter can achive."
			    ::= { gx2drr4xAnalogEntry 10}

		drr4xmaxValueRFAAttenuation        OBJECT-TYPE
			   SYNTAX           Float
			   ACCESS           read-only
			   STATUS           mandatory
			   DESCRIPTION
			   "The value of this object provides the maximum value
			    the RF Channel A Attenuation Analog parameter can achive."
			   ::= { gx2drr4xAnalogEntry 11}

        drr4xalarmStateRFAAttenuation      OBJECT-TYPE
			   SYNTAX           INTEGER
									{
									noAlarm(1),
									majorLowAlarm(2),
									minorLowAlarm(3),
									minorHighAlarm(4),
									majorHighAlarm(5),
									informational(6)
									}
			   ACCESS           read-only
			   STATUS           mandatory
			   DESCRIPTION
			   "The value of this object provides the curent alarm state of
			    the RF Channel A Attenuation Analog parameter."
			   ::= { gx2drr4xAnalogEntry 12}
			   
			   
-- 	RFBAttenuation		         
       
          		drr4xlabelRFBAttenuation           OBJECT-TYPE
			   SYNTAX           DisplayString (SIZE (0..80))
			   ACCESS           read-only
			   STATUS           optional
			   DESCRIPTION
			   "The value of this object provides the label of the
			    RF Channel B Attenuation Analog parameter."
			   ::= { gx2drr4xAnalogEntry 13}

		drr4xuomRFBAttenuation             OBJECT-TYPE
			   SYNTAX           DisplayString (SIZE (0..80))
			   ACCESS           read-only
			   STATUS           optional
			   DESCRIPTION
			   "The value of this object provides the Unit of Measure of the
			     RF Channel B Attenuation Analog parameter."
			   ::= { gx2drr4xAnalogEntry 14}

		drr4xmajorHighRFBAttenuation       OBJECT-TYPE
			   SYNTAX           Float 
			   ACCESS           read-only
			   STATUS           obsolete
			   DESCRIPTION
			 "This object is not used by this module and always returns invalid float value
			    of 0xFFFFFFFF . It is kept here for persistence."
			   ::= { gx2drr4xAnalogEntry 15}

		drr4xmajorLowRFBAttenuation        OBJECT-TYPE
			   SYNTAX           Float 
			   ACCESS           read-only
			   STATUS           obsolete
			   DESCRIPTION
			   "This object is not used by this module and always returns invalid float value
			    of 0xFFFFFFFF . It is kept here for persistence."

			   ::= { gx2drr4xAnalogEntry 16}

		drr4xminorHighRFBAttenuation       OBJECT-TYPE
			   SYNTAX           Float
			   ACCESS           read-only
			   STATUS           obsolete
			   DESCRIPTION
			   "This object is not used by this module and always returns invalid float value
			    of 0xFFFFFFFF . It is kept here for persistence."
			   ::= { gx2drr4xAnalogEntry 17}

		drr4xminorLowRFBAttenuation        OBJECT-TYPE
			   SYNTAX           Float 
			   ACCESS           read-only
			   STATUS           obsolete
			   DESCRIPTION
			    "This object is not used by this module and always returns invalid float value
			    of 0xFFFFFFFF. It is kept here for persistence."
			   ::= { gx2drr4xAnalogEntry 18}

		drr4xcurrentValueRFBAttenuation    OBJECT-TYPE
			   SYNTAX           Float 
			   ACCESS           read-write
			   STATUS           mandatory
			   DESCRIPTION
			   "The value of this object provides the Current value
			    of the RF Channel B Attenuation Analog parameter. The unit is dB "              
			   ::= { gx2drr4xAnalogEntry 19}

		drr4xstateFlagRFBAttenuation       OBJECT-TYPE
			   SYNTAX           INTEGER
								{
								hidden(1),
								read-only(2),
								updateable(3)
								}
			   ACCESS           read-only
			   STATUS           mandatory
			   DESCRIPTION
			   "The value of this object provides the state
			    of the RF Channel B Attenuation Analog parameter. (1-hidden	
			          2-read-only, 3-updateable)."
			   ::= { gx2drr4xAnalogEntry 20}

		drr4xminValueRFBAttenuation        OBJECT-TYPE
			   SYNTAX           Float
			   ACCESS           read-only
			   STATUS           mandatory
			   DESCRIPTION
			   "The value of this object provides the minimum value
			    the RF Channel B Attenuation Analog parameter can achive."
			   ::= { gx2drr4xAnalogEntry 21}

		drr4xmaxValueRFBAttenuation        OBJECT-TYPE
			   SYNTAX           Float
			   ACCESS           read-only
			   STATUS           mandatory
			   DESCRIPTION
			   "The value of this object provides the maximum value
			    the RF Channel B Attenuation Analog parameter can achive."
			   ::= { gx2drr4xAnalogEntry 22}

        drr4xalarmStateRFBAttenuation      OBJECT-TYPE
			   SYNTAX           INTEGER
									{
									noAlarm(1),
									majorLowAlarm(2),
									minorLowAlarm(3),
									minorHighAlarm(4),
									majorHighAlarm(5),
									informational(6)
									}
			   ACCESS           read-only
			   STATUS           mandatory
			   DESCRIPTION
			   "The value of this object provides the curent alarm state of
			    the RF Channel B Attenuation Analog parameter."
			   ::= { gx2drr4xAnalogEntry 23}

-- 	RFCAttenuation		         
       
          		drr4xlabelRFCAttenuation           OBJECT-TYPE
			   SYNTAX           DisplayString (SIZE (0..80))
			   ACCESS           read-only
			   STATUS           optional
			   DESCRIPTION
			   "The value of this object provides the label of the
			    RF Channel C Attenuation Analog parameter."
			   ::= { gx2drr4xAnalogEntry 24}

		drr4xuomRFCAttenuation             OBJECT-TYPE
			   SYNTAX           DisplayString (SIZE (0..80))
			   ACCESS           read-only
			   STATUS           optional
			   DESCRIPTION
			   "The value of this object provides the Unit of Measure of the
			     RF Channel C Attenuation Analog parameter."
			   ::= { gx2drr4xAnalogEntry 25}

		drr4xmajorHighRFCAttenuation       OBJECT-TYPE
			   SYNTAX           Float 
			   ACCESS           read-only
			   STATUS           obsolete
			   DESCRIPTION
			 "This object is not used by this module and always returns invalid float value
			    of 0xFFFFFFFF . It is kept here for persistence."
			   ::= { gx2drr4xAnalogEntry 26}

		drr4xmajorLowRFCAttenuation        OBJECT-TYPE
			   SYNTAX           Float 
			   ACCESS           read-only
			   STATUS           obsolete
			   DESCRIPTION
			   "This object is not used by this module and always returns invalid float value
			    of 0xFFFFFFFF . It is kept here for persistence."

			   ::= { gx2drr4xAnalogEntry 27}

		drr4xminorHighRFCAttenuation       OBJECT-TYPE
			   SYNTAX           Float
			   ACCESS           read-only
			   STATUS           obsolete
			   DESCRIPTION
			   "This object is not used by this module and always returns invalid float value
			    of 0xFFFFFFFF . It is kept here for persistence."
			   ::= { gx2drr4xAnalogEntry 28}

		drr4xminorLowRFCAttenuation        OBJECT-TYPE
			   SYNTAX           Float 
			   ACCESS           read-only
			   STATUS           obsolete
			   DESCRIPTION
			    "This object is not used by this module and always returns invalid float value
			    of 0xFFFFFFFF. It is kept here for persistence."
			   ::= { gx2drr4xAnalogEntry 29}

		drr4xcurrentValueRFCAttenuation    OBJECT-TYPE
			   SYNTAX           Float 
			   ACCESS           read-write
			   STATUS           mandatory
			   DESCRIPTION
			   "The value of this object provides the Current value
			    of the RF Channel C Attenuation Analog parameter. The unit is dB "              
			   ::= { gx2drr4xAnalogEntry 30}

		drr4xstateFlagRFCAttenuation       OBJECT-TYPE
			   SYNTAX           INTEGER
								{
								hidden(1),
								read-only(2),
								updateable(3)
								}
			   ACCESS           read-only
			   STATUS           mandatory
			   DESCRIPTION
			   "The value of this object provides the state
			    of the RF Channel C Attenuation Analog parameter. (1-hidden	
			          2-read-only, 3-updateable)."
			   ::= { gx2drr4xAnalogEntry 31}

		drr4xminValueRFCAttenuation        OBJECT-TYPE
			   SYNTAX           Float
			   ACCESS           read-only
			   STATUS           mandatory
			   DESCRIPTION
			   "The value of this object provides the minimum value
			    the RF Channel C Attenuation Analog parameter can achive."
			   ::= { gx2drr4xAnalogEntry 32}

		drr4xmaxValueRFCAttenuation        OBJECT-TYPE
			   SYNTAX           Float
			   ACCESS           read-only
			   STATUS           mandatory
			   DESCRIPTION
			   "The value of this object provides the maximum value
			    the RF Channel C Attenuation Analog parameter can achive."
			   ::= { gx2drr4xAnalogEntry 33}

        drr4xalarmStateRFCAttenuation      OBJECT-TYPE
			   SYNTAX           INTEGER
									{
									noAlarm(1),
									majorLowAlarm(2),
									minorLowAlarm(3),
									minorHighAlarm(4),
									majorHighAlarm(5),
									informational(6)
									}
			   ACCESS           read-only
			   STATUS           mandatory
			   DESCRIPTION
			   "The value of this object provides the curent alarm state of
			    the RF Channel C Attenuation Analog parameter."
			   ::= { gx2drr4xAnalogEntry 34}
                            	
-- 	RFDAttenuation		         
       
          		drr4xlabelRFDAttenuation           OBJECT-TYPE
			   SYNTAX           DisplayString (SIZE (0..80))
			   ACCESS           read-only
			   STATUS           optional
			   DESCRIPTION
			   "The value of this object provides the label of the
			    RF Channel D Attenuation Analog parameter."
			   ::= { gx2drr4xAnalogEntry 35}

		drr4xuomRFDAttenuation             OBJECT-TYPE
			   SYNTAX           DisplayString (SIZE (0..80))
			   ACCESS           read-only
			   STATUS           optional
			   DESCRIPTION
			   "The value of this object provides the Unit of Measure of the
			     RF Channel D Attenuation Analog parameter."
			   ::= { gx2drr4xAnalogEntry 36}

		drr4xmajorHighRFDAttenuation       OBJECT-TYPE
			   SYNTAX           Float 
			   ACCESS           read-only
			   STATUS           obsolete
			   DESCRIPTION
			 "This object is not used by this module and always returns invalid float value
			    of 0xFFFFFFFF . It is kept here for persistence."
			   ::= { gx2drr4xAnalogEntry 37}

		drr4xmajorLowRFDAttenuation        OBJECT-TYPE
			   SYNTAX           Float 
			   ACCESS           read-only
			   STATUS           obsolete
			   DESCRIPTION
			   "This object is not used by this module and always returns invalid float value
			    of 0xFFFFFFFF . It is kept here for persistence."

			   ::= { gx2drr4xAnalogEntry 38}

		drr4xminorHighRFDAttenuation       OBJECT-TYPE
			   SYNTAX           Float
			   ACCESS           read-only
			   STATUS           obsolete
			   DESCRIPTION
			   "This object is not used by this module and always returns invalid float value
			    of 0xFFFFFFFF . It is kept here for persistence."
			   ::= { gx2drr4xAnalogEntry 39}

		drr4xminorLowRFDAttenuation        OBJECT-TYPE
			   SYNTAX           Float 
			   ACCESS           read-only
			   STATUS           obsolete
			   DESCRIPTION
			    "This object is not used by this module and always returns invalid float value
			    of 0xFFFFFFFF. It is kept here for persistence."
			   ::= { gx2drr4xAnalogEntry 40}

		drr4xcurrentValueRFDAttenuation    OBJECT-TYPE
			   SYNTAX           Float 
			   ACCESS           read-write
			   STATUS           mandatory
			   DESCRIPTION
			   "The value of this object provides the Current value
			    of the RF Channel D Attenuation Analog parameter. The unit is dB "              
			   ::= { gx2drr4xAnalogEntry 41}

		drr4xstateFlagRFDAttenuation       OBJECT-TYPE
			   SYNTAX           INTEGER
								{
								hidden(1),
								read-only(2),
								updateable(3)
								}
			   ACCESS           read-only
			   STATUS           mandatory
			   DESCRIPTION
			   "The value of this object provides the state
			    of the RF Channel D Attenuation Analog parameter. (1-hidden	
			          2-read-only, 3-updateable)."
			   ::= { gx2drr4xAnalogEntry 42}

		drr4xminValueRFDAttenuation        OBJECT-TYPE
			   SYNTAX           Float
			   ACCESS           read-only
			   STATUS           mandatory
			   DESCRIPTION
			   "The value of this object provides the minimum value
			    the RF Channel B Attenuation Analog parameter can achive."
			   ::= { gx2drr4xAnalogEntry 43}

		drr4xmaxValueRFDAttenuation        OBJECT-TYPE
			   SYNTAX           Float
			   ACCESS           read-only
			   STATUS           mandatory
			   DESCRIPTION
			   "The value of this object provides the maximum value
			    the RF Channel D Attenuation Analog parameter can achive."
			   ::= { gx2drr4xAnalogEntry 44}

        drr4xalarmStateRFDAttenuation      OBJECT-TYPE
			   SYNTAX           INTEGER
									{
									noAlarm(1),
									majorLowAlarm(2),
									minorLowAlarm(3),
									minorHighAlarm(4),
									majorHighAlarm(5),
									informational(6)
									}
			   ACCESS           read-only
			   STATUS           mandatory
			   DESCRIPTION
			   "The value of this object provides the curent alarm state of
			    the RF Channel D Attenuation Analog parameter."
			   ::= { gx2drr4xAnalogEntry 45}
                            	                            			   
-- 	TrippointLevel	          
        drr4xlabelTrippointLevel           OBJECT-TYPE
			   SYNTAX           DisplayString (SIZE (0..80))
			   ACCESS           read-only
			   STATUS           optional
			   DESCRIPTION
			   "The value of this object provides the label of the
			    trip point level Analog parameter."
			   ::= { gx2drr4xAnalogEntry 46}

		drr4xuomTrippointLevel             OBJECT-TYPE
			   SYNTAX           DisplayString (SIZE (0..80))
			   ACCESS           read-only
			   STATUS           optional
			   DESCRIPTION
			   "The value of this object provides the Unit of Measure of the
			     trip point level Analog parameter."
			   ::= { gx2drr4xAnalogEntry 47}

		drr4xmajorHighTrippointLevel       OBJECT-TYPE
			   SYNTAX           Float 
			   ACCESS           read-only
			   STATUS           obsolete
			   DESCRIPTION
			      "This object is not used by this module and always returns invalid float value
			    of 0xFFFFFFFF . It is kept here for persistence."
			   ::= { gx2drr4xAnalogEntry 48}

		drr4xmajorLowTrippointLevel        OBJECT-TYPE
			   SYNTAX           Float 
			   ACCESS           read-only
			   STATUS           obsolete
			   DESCRIPTION
			      "This object is not used by this module and always returns invalid float value
			    of 0xFFFFFFFF . It is kept here for persistence."
			   ::= { gx2drr4xAnalogEntry 49}

		drr4xminorHighTrippointLevel       OBJECT-TYPE
			   SYNTAX           Float
			   ACCESS           read-only
			   STATUS           obsolete
			   DESCRIPTION
			      "This object is not used by this module and always returns invalid float value
			    of 0xFFFFFFFF . It is kept here for persistence."
			   ::= { gx2drr4xAnalogEntry 50}

		drr4xminorLowTrippointLevel        OBJECT-TYPE
			   SYNTAX           Float 
			   ACCESS           read-only
			   STATUS           obsolete
			   DESCRIPTION
			      "This object is not used by this module and always returns invalid float value
			    of 0xFFFFFFFF . It is kept here for persistence."
			   ::= { gx2drr4xAnalogEntry 51}

		drr4xcurrentValueTrippointLevel    OBJECT-TYPE
			   SYNTAX           Float 
			   ACCESS           read-write
			   STATUS           mandatory
			   DESCRIPTION
			   "The value of this object provides the Current value of the trip point level Analog parameter. The trip point level set the custumer preferred 
                      optical input level.
                This parameter combined with trippoint mode decides the trippoint alarm and RF channel output impedance.
                      
                when optical power level is lower than trip point level(Set by this parameter)
                    1) When trip point mode is ALARM_SWITCH,  trip point alarm will be generated and RF output 
                      impedance will be changed to high impedance.
                    2) When trippoint mode is ALARM_ONLY, trippoint alarm will be generated but RF output inpedance 
                      remains to be low impedance.    
			   This trip point level value is a floating point number that is represented as an IEEE 32 bit number."
			   ::= { gx2drr4xAnalogEntry 52}

		drr4xstateFlagTrippointLevel       OBJECT-TYPE
			   SYNTAX           INTEGER
								{
								hidden(1),
								read-only(2),
								updateable(3)
								}
			   ACCESS           read-only
			   STATUS           mandatory
			   DESCRIPTION
			   "The value of this object provides the state
			    of the trip point level Analog parameter. (1-hidden
			          2-read-only, 3-updateable)."
			   ::= { gx2drr4xAnalogEntry 53}

		drr4xminValueTrippointLevel        OBJECT-TYPE
			   SYNTAX           Float
			   ACCESS           read-only
			   STATUS           mandatory
			   DESCRIPTION
			   "The value of this object provides the minimum value
			    the trip point level Analog parameter can achive." 
			   ::= { gx2drr4xAnalogEntry 54}

		drr4xmaxValueTrippointLevel        OBJECT-TYPE
			   SYNTAX           Float
			   ACCESS           read-only
			   STATUS           mandatory
			   DESCRIPTION
			   "The value of this object provides the maximum value
			    the trip point level Analog parameter can achive."
			   ::= { gx2drr4xAnalogEntry 55}

        drr4xalarmStateTrippointLevel      OBJECT-TYPE
			   SYNTAX           INTEGER
									{
									noAlarm(1),
									majorLowAlarm(2),
									minorLowAlarm(3),
									minorHighAlarm(4),
									majorHighAlarm(5),
									informational(6)
									}
			   ACCESS           read-only
			   STATUS           mandatory
			   DESCRIPTION
			   "The value of this object provides the curent alarm state of
			    the trip point level Analog parameter."
			   ::= { gx2drr4xAnalogEntry 56}
			               
-- Optical power 
	    drr4xlabelOptCurrent           OBJECT-TYPE
			   SYNTAX           DisplayString (SIZE (0..80))
			   ACCESS           read-only
			   STATUS           optional
			   DESCRIPTION
			   "The value of this object provides the label of the
			    Optical Power Current Analog parameter."
			   ::= { gx2drr4xAnalogEntry 57}

		drr4xuomOptCurrent             OBJECT-TYPE
			   SYNTAX           DisplayString (SIZE (0..80))
			   ACCESS           read-only
			   STATUS           optional
			   DESCRIPTION
			   "The value of this object provides the Unit of Measure of the
			    Optical Power Current Analog parameter."
			   ::= { gx2drr4xAnalogEntry 58}

		drr4xmajorHighOptCurrent       OBJECT-TYPE
			   SYNTAX           Float 
			   ACCESS           read-only
			   STATUS           mandatory
			   DESCRIPTION
			   "The value of this object provides the Major High alarm value
			    of the Optical Power Current Analog parameter."
			   ::= { gx2drr4xAnalogEntry 59}


		drr4xmajorLowOptCurrent        OBJECT-TYPE
			   SYNTAX           Float 
			   ACCESS           read-only
			   STATUS           mandatory
			   DESCRIPTION
			   "The value of this object provides the Major Low alarm value
			    of the Optical Power Current Analog parameter."
			   ::= { gx2drr4xAnalogEntry 60}

		drr4xminorHighOptCurrent       OBJECT-TYPE
			   SYNTAX           Float
			   ACCESS           read-only
			   STATUS           obsolete
			   DESCRIPTION
			    "This object is not used by this module and always returns invalid float value
			    of 0xFFFFFFFF . It is kept here for persistence."
			   ::= { gx2drr4xAnalogEntry 61}

		drr4xminorLowOptCurrent        OBJECT-TYPE
			   SYNTAX           Float 
			   ACCESS           read-only
			   STATUS           obsolete
			   DESCRIPTION
			   "This object is not used by this module and always returns invalid float value
			    of 0xFFFFFFFF . It is kept here for persistence."
			   ::= { gx2drr4xAnalogEntry 62}

		drr4xcurrentValueOptCurrent    OBJECT-TYPE
			   SYNTAX           Float 
			   ACCESS           read-only
			   STATUS           mandatory
			   DESCRIPTION
			   "The value of this object provides the Current value
			    of the Optical Power Current Analog parameter.

			   The input optical power in lower than min value, 
			   drr4xcurrentValueOptCurrent will report -99dBm

 			   The input optical power in higher than this value, 
			   drr4xcurrentValueOptCurrent will report 99dBm"
			   ::= { gx2drr4xAnalogEntry 63}

		drr4xstateFlagOptCurrent       OBJECT-TYPE
			   SYNTAX           INTEGER
								{
								hidden(1),
								read-only(2),
								updateable(3)
								}
			   ACCESS           read-only
			   STATUS           mandatory
			   DESCRIPTION
			   "The value of this object provides the state
			    of the Optical Power Current Analog parameter. (1-hidden	
			          2-read-only, 3-updateable)."
			   ::= { gx2drr4xAnalogEntry 64}

		drr4xminValueOptCurrent        OBJECT-TYPE
			   SYNTAX           Float
			   ACCESS           read-only
			   STATUS           mandatory
			   DESCRIPTION
			   "This is recommended min range for display gauge"			 
			   ::= { gx2drr4xAnalogEntry 65}

		drr4xmaxValueOptCurrent        OBJECT-TYPE
			   SYNTAX           Float
			   ACCESS           read-only
			   STATUS           mandatory
			   DESCRIPTION
			   "This is recommended max range for display gauge"			  
			   ::= { gx2drr4xAnalogEntry 66}

        drr4xalarmStateOptCurrent      OBJECT-TYPE
			   SYNTAX           INTEGER
									{
									noAlarm(1),
									majorLowAlarm(2),
									minorLowAlarm(3),
									minorHighAlarm(4),
									majorHighAlarm(5),
									informational(6)
									}
			   ACCESS           read-only
			   STATUS           mandatory
			   DESCRIPTION
			   "The value of this object provides the curent alarm state of
			    the Optical Power Current Analog parameter."
			   ::= { gx2drr4xAnalogEntry 67}
			   
-- 12V current 
    	drr4xlabel12VCurrent           OBJECT-TYPE
			   SYNTAX           DisplayString (SIZE (0..80))
			   ACCESS           read-only
			   STATUS           optional
			   DESCRIPTION
			   "The value of this object provides the label of the
			    12v power supply Current Analog parameter."
			   ::= { gx2drr4xAnalogEntry 68}

		drr4xuom12VCurrent             OBJECT-TYPE
			   SYNTAX           DisplayString (SIZE (0..80))
			   ACCESS           read-only
			   STATUS           optional
			   DESCRIPTION
			   "The value of this object provides the Unit of Measure of the
			    12v power supply Current Analog parameter."
			   ::= { gx2drr4xAnalogEntry 69}

		drr4xmajorHigh12VCurrent       OBJECT-TYPE
			   SYNTAX           Float 
			   ACCESS           read-only
			   STATUS           mandatory
			   DESCRIPTION
			   "The value of this object provides the Major High alarm value
			    of the 12v power supply Current Analog parameter."
			   ::= { gx2drr4xAnalogEntry 70}


		drr4xmajorLow12VCurrent        OBJECT-TYPE
			   SYNTAX           Float 
			   ACCESS           read-only
			   STATUS           mandatory
			   DESCRIPTION
			   "The value of this object provides the Major Low alarm value
			    of the 12v power supply Current Analog parameter."
			   ::= { gx2drr4xAnalogEntry 71}

		drr4xminorHigh12VCurrent       OBJECT-TYPE
			   SYNTAX           Float
			   ACCESS           read-only
			   STATUS           mandatory
			   DESCRIPTION
			   "The value of this object provides the Minor High alarm value
			    of the 12v power supply Current Analog parameter."
			   ::= { gx2drr4xAnalogEntry 72}

		drr4xminorLow12VCurrent        OBJECT-TYPE
			   SYNTAX           Float 
			   ACCESS           read-only
			   STATUS           mandatory
			   DESCRIPTION
			   "The value of this object provides the Minor Low alarm value
			    of the 12v power supply Current Analog parameter."
			   ::= { gx2drr4xAnalogEntry 73}

		drr4xcurrentValue12VCurrent    OBJECT-TYPE
			   SYNTAX           Float 
			   ACCESS           read-only
			   STATUS           mandatory
			   DESCRIPTION
			   "The value of this object provides the Current value
			    of the 12v power supply Current parameter."
			   ::= { gx2drr4xAnalogEntry 74}

		drr4xstateFlag12VCurrent       OBJECT-TYPE
			   SYNTAX           INTEGER
								{
								hidden(1),
								read-only(2),
								updateable(3)
								}
			   ACCESS           read-only
			   STATUS           mandatory
			   DESCRIPTION
			   "The value of this object provides the state
			    of the 12v power supply Current Analog parameter. (1-hidden	
			          2-read-only, 3-updateable)."
			   ::= { gx2drr4xAnalogEntry 75}

		drr4xminValue12VCurrent        OBJECT-TYPE
			   SYNTAX           Float
			   ACCESS           read-only
			   STATUS           mandatory
			   DESCRIPTION
			   "The value of this object provides the minimum value
			    the 12v power supply Current Analog parameter can achive."
			   ::= { gx2drr4xAnalogEntry 76}

		drr4xmaxValue12VCurrent        OBJECT-TYPE
			   SYNTAX           Float
			   ACCESS           read-only
			   STATUS           mandatory
			   DESCRIPTION
			   "The value of this object provides the maximum value
			    the 12v power supply Current Analog parameter can achive."
			   ::= { gx2drr4xAnalogEntry 77}

        drr4xalarmState12VCurrent      OBJECT-TYPE
			   SYNTAX           INTEGER
									{
									noAlarm(1),
									majorLowAlarm(2),
									minorLowAlarm(3),
									minorHighAlarm(4),
									majorHighAlarm(5),
									informational(6)
									}
			   ACCESS           read-only
			   STATUS           mandatory
			   DESCRIPTION
			   "The value of this object provides the curent alarm state of
			    the 12v power supply Current Analog parameter."
			   ::= { gx2drr4xAnalogEntry 78}
			   
-- Module Temperature 

		drr4xlabelModTemp              OBJECT-TYPE
			   SYNTAX           DisplayString (SIZE (0..80))
			   ACCESS           read-only
			   STATUS           optional
			   DESCRIPTION
			   "The value of this object provides the label of the
			    Module Temperature Analog parameter."
			   ::= { gx2drr4xAnalogEntry 79}

		drr4xuomModTemp                OBJECT-TYPE
			   SYNTAX           DisplayString (SIZE (0..80))
			   ACCESS           read-only
			   STATUS           optional
			   DESCRIPTION
			   "The value of this object provides the Unit of Measure of the
			    Module Temperature Analog parameter."
			   ::= { gx2drr4xAnalogEntry 80}

		drr4xmajorHighModTemp          OBJECT-TYPE
			   SYNTAX           Float 
			   ACCESS           read-only
			   STATUS           mandatory
			   DESCRIPTION
			   "The value of this object provides the Major High alarm value
			    of the Module Temperature Analog parameter."
			   ::= { gx2drr4xAnalogEntry 81}


		drr4xmajorLowModTemp           OBJECT-TYPE
			   SYNTAX           Float 
			   ACCESS           read-only
			   STATUS           mandatory
			   DESCRIPTION
			   "The value of this object provides the Major Low alarm value
			    of the Module Temperature Analog parameter."
			     ::= { gx2drr4xAnalogEntry 82}

		drr4xminorHighModTemp          OBJECT-TYPE
			   SYNTAX           Float
			   ACCESS           read-only
			   STATUS           mandatory
			   DESCRIPTION
			   "The value of this object provides the Minor High alarm value
			    of the Module Temperature Analog parameter."
			    ::= { gx2drr4xAnalogEntry 83}

		drr4xminorLowModTemp           OBJECT-TYPE
			   SYNTAX           Float 
			   ACCESS           read-only
			   STATUS           mandatory
			   DESCRIPTION
			   "The value of this object provides the Minor Low alarm value
			    of the Module Temperature Analog parameter."
			    ::= { gx2drr4xAnalogEntry 84}

		drr4xcurrentValueModTemp       OBJECT-TYPE
			   SYNTAX           Float 
			   ACCESS           read-only
			   STATUS           mandatory
			   DESCRIPTION
			   "The value of this object provides the Current value
			    of the Module Temperature Analog parameter."
			   ::= { gx2drr4xAnalogEntry 85}

		drr4xstateFlagModTemp          OBJECT-TYPE
			   SYNTAX           INTEGER
								{
								hidden(1),
								read-only(2),
								updateable(3)
								}
			   ACCESS           read-only
			   STATUS           mandatory
			   DESCRIPTION
			   "The value of this object provides the state
			    of the Module Temperature Analog parameter. (1-hidden	
			          2-read-only, 3-updateable)."
			   ::= { gx2drr4xAnalogEntry 86}

		drr4xminValueModTemp           OBJECT-TYPE
			   SYNTAX           Float
			   ACCESS           read-only
			   STATUS           mandatory
			   DESCRIPTION
			   "The value of this object provides the minimum value
			    the Module Temperature Analog parameter can achive."
			    ::= { gx2drr4xAnalogEntry 87}

		drr4xmaxValueModTemp           OBJECT-TYPE
			   SYNTAX           Float
			   ACCESS           read-only
			   STATUS           mandatory
			   DESCRIPTION
			   "The value of this object provides the maximum value
			    the Module Temperature Analog parameter can achive."
			   ::= { gx2drr4xAnalogEntry 88}

		drr4xalarmStateModTemp         OBJECT-TYPE
			   SYNTAX           INTEGER
									{
									noAlarm(1),
									majorLowAlarm(2),
									minorLowAlarm(3),
									minorHighAlarm(4),
									majorHighAlarm(5),
									informational(6)
									}
			   ACCESS           read-only
			   STATUS           mandatory
			   DESCRIPTION
			   "The value of this object provides the curent alarm state of
			    the Module Temperature Analog parameter."
			   ::= { gx2drr4xAnalogEntry 89}
			     
			   
-- Fan current 
		drr4xlabelFanCurrent           OBJECT-TYPE
			   SYNTAX           DisplayString (SIZE (0..80))
			   ACCESS           read-only
			   STATUS           optional
			   DESCRIPTION
			   "The value of this object provides the label of the
			    Fan Current Analog parameter."
			   ::= { gx2drr4xAnalogEntry 90}

		drr4xuomFanCurrent             OBJECT-TYPE
			   SYNTAX           DisplayString (SIZE (0..80))
			   ACCESS           read-only
			   STATUS           optional
			   DESCRIPTION
			   "The value of this object provides the Unit of Measure of the
			    Fan Current Analog parameter."
			   ::= { gx2drr4xAnalogEntry 91}

		drr4xmajorHighFanCurrent       OBJECT-TYPE
			   SYNTAX           Float 
			   ACCESS           read-only
			   STATUS           mandatory
			   DESCRIPTION
			   "The value of this object provides the Major High alarm value
			    of the Fan Current Analog parameter."
			   ::= { gx2drr4xAnalogEntry 92}


		drr4xmajorLowFanCurrent        OBJECT-TYPE
			   SYNTAX           Float 
			   ACCESS           read-only
			   STATUS           mandatory
			   DESCRIPTION
			   "The value of this object provides the Major Low alarm value
			    of the Fan Current Analog parameter."
			   ::= { gx2drr4xAnalogEntry 93}

		drr4xminorHighFanCurrent       OBJECT-TYPE
			   SYNTAX           Float
			   ACCESS           read-only
			   STATUS           obsolete
			   DESCRIPTION
			   "This object is not used by this module and always returns invalid float value
			    of 0xFFFFFFFF . It is kept here for persistence."
			   ::= { gx2drr4xAnalogEntry 94}

		drr4xminorLowFanCurrent        OBJECT-TYPE
			   SYNTAX           Float 
			   ACCESS           read-only
			   STATUS           obsolete
			   DESCRIPTION
			   "This object is not used by this module and always returns invalid float value
			    of 0xFFFFFFFF . It is kept here for persistence."
			   ::= { gx2drr4xAnalogEntry 95}

		drr4xcurrentValueFanCurrent    OBJECT-TYPE
			   SYNTAX           Float 
			   ACCESS           read-only
			   STATUS           mandatory
			   DESCRIPTION
			   "The value of this object provides the Current value
			    of the Fan Current Analog parameter."
			   ::= { gx2drr4xAnalogEntry 96}

		drr4xstateFlagFanCurrent       OBJECT-TYPE
			   SYNTAX           INTEGER
								{
								hidden(1),
								read-only(2),
								updateable(3)
								}
			   ACCESS           read-only
			   STATUS           mandatory
			   DESCRIPTION
			   "The value of this object provides the state
			    of the Module Temperature Analog parameter. (1-hidden	
			          2-read-only, 3-updateable)."
			   ::= { gx2drr4xAnalogEntry 97}

		drr4xminValueFanCurrent        OBJECT-TYPE
			   SYNTAX           Float
			   ACCESS           read-only
			   STATUS           mandatory
			   DESCRIPTION
			   "The value of this object provides the minimum value
			    the Fan Current Analog parameter can achive."
			   ::= { gx2drr4xAnalogEntry 98}

		drr4xmaxValueFanCurrent        OBJECT-TYPE
			   SYNTAX           Float
			   ACCESS           read-only
			   STATUS           mandatory
			   DESCRIPTION
			   "The value of this object provides the maximum value
			    the Fan Current Analog parameter can achive."
			   ::= { gx2drr4xAnalogEntry 99}

        drr4xalarmStateFanCurrent      OBJECT-TYPE
			   SYNTAX           INTEGER
									{
									noAlarm(1),
									majorLowAlarm(2),
									minorLowAlarm(3),
									minorHighAlarm(4),
									majorHighAlarm(5),
									informational(6)
									}
			   ACCESS           read-only
			   STATUS           mandatory
			   DESCRIPTION
			   "The value of this object provides the curent alarm state of
			    the Fan Current Analog parameter."
			   ::= { gx2drr4xAnalogEntry 100}  
			   
    			   
-- ************************ Digital parameters **********************************
		gx2drr4xDigitalTableIndex              OBJECT-TYPE
			   SYNTAX           INTEGER (1..2147483647)
			   ACCESS           read-only
			   STATUS           mandatory
			   DESCRIPTION
			   "The value of this object identifies the network
			    element. This index is equal to the
			    hfcCommonTableIndex for the same element."
               ::= { gx2drr4xDigitalEntry 1}
               
   -- Trip point mode   
         drr4xlabelTrippointMode          OBJECT-TYPE
			   SYNTAX       		DisplayString (SIZE (0..80))         
			   ACCESS           	read-only
			   STATUS           	optional
			   DESCRIPTION
			   "The value of this object provides the label of the
			    Trip point mode Digital parameter. The trip point mode defines the RF switch 
                      action based on the optical power input to the DRR"
			   ::= { gx2drr4xDigitalEntry 2}

		drr4xenumTrippointMode               	OBJECT-TYPE
			   SYNTAX       		DisplayString (SIZE (0..80))         
			   ACCESS           	read-only
			   STATUS           	optional
			   DESCRIPTION
			   "The value of this object represents the Enumeration values
			    possible for the Digital parameter. Each Enumerated values is
			    separated by a common. "
			   ::= { gx2drr4xDigitalEntry 3}


		drr4xvalueTrippointMode         	OBJECT-TYPE
			   SYNTAX					INTEGER{
			   							off(1),
			   							alarmOnly(2),
			   							alarm-and-Switch(3)
			   							}			   					    	
			   ACCESS           	read-write
			   STATUS           	mandatory
			   DESCRIPTION
			   "The value of this object is the current value of trip point mode.
			   There are three possible value: 1-off, 2-alarm_only, 3-alarm&switch.
			   			   
			   If module input optical power is higher than the preset trippoint value,
			        no operational difference for these three modes. 
			   
			   If module input optical power is less than the preset trippoint value, 
                     1) When trippoint mode is OFF, no trippoint alarm will be generated and RF output impedance 
                     will stay normal as low.
                     2) When tripoint mode is ALARM_ONLY, trip_point alarm will be generated when the input optical power 
                     lower than the preset trippoint level but RF output impedance will stay normal as low. 
                     3) When trippoint mode is ALARM_SWITCH, trip point alarm will be generated and RF output impedance 
                     will switch to abnorml"
			   ::= { gx2drr4xDigitalEntry 4}

		drr4xstateflagTrippointMode     	OBJECT-TYPE
			   SYNTAX       		INTEGER
								{
								hidden(1),
								readOnly(2),
								updateable(3)
								}
			   ACCESS           	read-only
			   STATUS           	mandatory
			   DESCRIPTION
			   "The value of this object provides the state
			    of the the parameter. (1-Hidden 2-Read-Only, 3-Updateable)."
			   ::= { gx2drr4xDigitalEntry 5}
			   		   		   		   
-- Factory default reset 
         drr4xlabelFactoryDefaultReset           OBJECT-TYPE
			   SYNTAX       		DisplayString (SIZE (0..80))         
			   ACCESS           	read-only
			   STATUS           	optional
			   DESCRIPTION
			   "The value of this object provides the label of the
			    Factory Default Reset  Digital parameter."
			   ::= { gx2drr4xDigitalEntry 6}

		drr4xenumFactoryDefaultReset               	OBJECT-TYPE
			   SYNTAX       		DisplayString (SIZE (0..80))         
			   ACCESS           	read-only
			   STATUS           	optional
			   DESCRIPTION
			   "The value of this object represents the Enumeration values
			    possible for the Digital parameter. Each Enumerated values is
			    separated by a common. The first value has a enumerated value of 1."
			   ::= { gx2drr4xDigitalEntry 7}


		drr4xvalueFactoryDefaultReset         	OBJECT-TYPE
			   SYNTAX       		INTEGER
					    		{
							off(1),
							on(2)
					    		}
			   ACCESS           	read-write
			   STATUS           	mandatory
			   DESCRIPTION
			   "The read of this value will return a invalid value.
			    The read will not reflect the actual setting value for this parameter
			   "
			   ::= { gx2drr4xDigitalEntry 8}

		drr4xstateflagFactoryDefaultReset     	OBJECT-TYPE
			   SYNTAX       		INTEGER
								{
								hidden(1),
								read-only(2),
								updateable(3)
								}
			   ACCESS           	read-only
			   STATUS           	mandatory
			   DESCRIPTION
			   "The value of this object provides the state
			    of the the parameter. (1-Hidden 2-Read-Only, 3-Updateable)."
			   ::= { gx2drr4xDigitalEntry 9} 
			   
   
 	--*********** STATUS *****************
		gx2drr4xStatusTableIndex              OBJECT-TYPE
			   SYNTAX           INTEGER (1..2147483647)
			   ACCESS           read-only
			   STATUS           mandatory
			   DESCRIPTION
			   "The value of this object identifies the network
			    element. This index is equal to the
			    hfcCommonTableIndex for the same element."
			   ::= { gx2drr4xStatusEntry 1}

--Boot status 
		drr4xlabelBoot               	OBJECT-TYPE
			   SYNTAX       		DisplayString (SIZE (0..80))         
			   ACCESS           	read-only
			   STATUS           	optional
			   DESCRIPTION
			   "The value of this object provides the label of the
			    Boot Status  parameter."
			   ::= { gx2drr4xStatusEntry 2}

		drr4xvalueBoot              		OBJECT-TYPE
			   SYNTAX       		INTEGER
									{
									ok(1),
									undetermined(2),
									warning(3),
									minor(4),
									major(5),
									critical(6)
									}
			   ACCESS           	read-only
			   STATUS           	mandatory
			   DESCRIPTION
			   "The value of this object provides the current state of
			    the parameter (1-Ok, 2-Undetermined
			    3-Warning, 4-Minor, 5-Major, 6-Critical)."
			   ::= { gx2drr4xStatusEntry 3}

		drr4xstateflagBoot     	OBJECT-TYPE
			   SYNTAX       		INTEGER
								{
								hidden(1),
								read-only(2),
								updateable(3)
								}
			   ACCESS           	read-only
			   STATUS           	mandatory
			   DESCRIPTION
			   "The value of this object provides the state
			    of the the parameter. (1-Hidden 2-Read-Only, 3-Updateable)."
			   ::= { gx2drr4xStatusEntry  4}

--Flash program status 
		drr4xlabelFlash               	OBJECT-TYPE
			   SYNTAX       		DisplayString (SIZE (0..80))         
			   ACCESS           	read-only
			   STATUS           	optional
			   DESCRIPTION
			   "The value of this object provides the label of the
			    Flash Status  parameter."
			   ::= { gx2drr4xStatusEntry 5}

		drr4xvalueFlash              	OBJECT-TYPE
			   SYNTAX       		INTEGER
									{
									ok(1),
									undetermined(2),
									warning(3),
									minor(4),
									major(5),
									critical(6)
									}
			   ACCESS           	read-only
			   STATUS           	mandatory
			   DESCRIPTION
			   "The value of this object provides the current state of
			    the parameter (1-Ok, 2-Undetermined
			    3-Warning, 4-Minor, 5-Major, 6-Critical)."
			   ::= { gx2drr4xStatusEntry 6}

		drr4xstateflagFlash     	OBJECT-TYPE
			   SYNTAX       		INTEGER
								{
								hidden(1),
								read-only(2),
								updateable(3)
								}
			   ACCESS           	read-only
			   STATUS           	mandatory
			   DESCRIPTION
			   "The value of this object provides the state
			    of the the parameter. (1-Hidden 2-Read-Only, 3-Updateable)."
			   ::= { gx2drr4xStatusEntry  7}

--Factory data crc 
		drr4xlabelFactoryDataCRC           OBJECT-TYPE
			   SYNTAX       		DisplayString (SIZE (0..80))         
			   ACCESS           	read-only
			   STATUS           	optional
			   DESCRIPTION
			   "The value of this object provides the label of the
			    Factory Data CRC Status parameter."
			   ::= { gx2drr4xStatusEntry 8}

		drr4xvalueFactoryDataCRC          	OBJECT-TYPE
			   SYNTAX       		INTEGER
									{
									ok(1),
									undetermined(2),
									warning(3),
									minor(4),
									major(5),
									critical(6)
									}
			   ACCESS           	read-only
			   STATUS           	mandatory
			   DESCRIPTION
			   "The value of this object provides the current state of
			    the parameter (1-Ok, 2-Undetermined
			    3-Warning, 4-Minor, 5-Major, 6-Critical)."
			   ::= { gx2drr4xStatusEntry 9}

		drr4xstateflagFactoryDataCRC     	OBJECT-TYPE
			   SYNTAX       		INTEGER
								{
								hidden(1),
								read-only(2),
								updateable(3)
								}
			   ACCESS           	read-only
			   STATUS           	mandatory
			   DESCRIPTION
			   "The value of this object provides the state
			    of the the parameter. (1-Hidden 2-Read-Only, 3-Updateable)."
			   ::= { gx2drr4xStatusEntry  10}

--Alarm data status CRC
		drr4xlabelAlarmDataCrc               	      OBJECT-TYPE
			   SYNTAX       		DisplayString (SIZE (0..80))         
			   ACCESS           	read-only
			   STATUS           	optional
			   DESCRIPTION
			   "The value of this object provides the label of the
			    Alarm Data Crc parameter."
			   ::= { gx2drr4xStatusEntry 11}

		drr4xvalueAlarmDataCrc              		OBJECT-TYPE
			   SYNTAX       		INTEGER
									{
									ok(1),
									undetermined(2),
									warning(3),
									minor(4),
									major(5),
									critical(6)
									}
			   ACCESS           	read-only
			   STATUS           	mandatory
			   DESCRIPTION
			   "The value of this object provides the current state of
			    the parameter (1-Ok, 2-Undetermined
			    3-Warning, 4-Minor, 5-Major, 6-Critical)."
			   ::= { gx2drr4xStatusEntry 12}

		drr4xstateflagAlarmDataCrc     	OBJECT-TYPE
			   SYNTAX       		INTEGER
								{
								hidden(1),
								read-only(2),
								updateable(3)
								}
			   ACCESS           	read-only
			   STATUS           	mandatory
			   DESCRIPTION
			   "The value of this object provides the state
			    of the the parameter. (1-Hidden 2-Read-Only, 3-Updateable)."
			   ::= { gx2drr4xStatusEntry  13}

--Calibration data status CRC
		drr4xlabelCalibrationDataCrc               	      OBJECT-TYPE
			   SYNTAX       		DisplayString (SIZE (0..80))         
			   ACCESS           	read-only
			   STATUS           	optional
			   DESCRIPTION
			   "The value of this object provides the label of the
			    Calibration Data Crc parameter."
			   ::= { gx2drr4xStatusEntry 14}

		drr4xvalueCalibrationDataCrc              		OBJECT-TYPE
			   SYNTAX       		INTEGER
									{
									ok(1),
									undetermined(2),
									warning(3),
									minor(4),
									major(5),
									critical(6)
									}
			   ACCESS           	read-only
			   STATUS           	mandatory
			   DESCRIPTION
			   "The value of this object provides the current state of
			    the parameter (1-Ok, 2-Undetermined
			    3-Warning, 4-Minor, 5-Major, 6-Critical)."
			   ::= { gx2drr4xStatusEntry 15}

		drr4xstateflagCalibrationDataCrc     	OBJECT-TYPE
			   SYNTAX       		INTEGER
								{
								hidden(1),
								read-only(2),
								updateable(3)
								}
			   ACCESS           	read-only
			   STATUS           	mandatory
			   DESCRIPTION
			   "The value of this object provides the state
			    of the the parameter. (1-Hidden 2-Read-Only, 3-Updateable)."
			   ::= { gx2drr4xStatusEntry  16}



--Module hardware status
		drr4xlabelHardwareStatus              OBJECT-TYPE
			   SYNTAX       		DisplayString (SIZE (0..80))         
			   ACCESS           	read-only
			   STATUS           	optional
			   DESCRIPTION
			   "The value of this object provides the label of the
			   Module Hardware Status parameter."
			   ::= { gx2drr4xStatusEntry 17}

		drr4xvalueHardwareStatus              OBJECT-TYPE
			   SYNTAX       		INTEGER
									{
									ok(1),
									undetermined(2),
									warning(3),
									minor(4),
									major(5),
									critical(6)
									}
			   ACCESS           	read-only
			   STATUS           	mandatory
			   DESCRIPTION
			   "The value of this object provides the current state of
			    the parameter (1-Ok, 2-Undetermined
			    3-Warning, 4-Minor, 5-Major, 6-Critical)."
			   ::= { gx2drr4xStatusEntry 18}

		drr4xstateflagHardwareStatus     	OBJECT-TYPE
			   SYNTAX       		INTEGER
								{
								hidden(1),
								read-only(2),
								updateable(3)
								}
			   ACCESS           	read-only
			   STATUS           	mandatory
			   DESCRIPTION
			   "The value of this object provides the state
			    of the parameter. (1-Hidden 2-Read-Only, 3-Updateable)."
			   ::= { gx2drr4xStatusEntry  19}
                            
  --Optical signal trip point status 
		drr4xlabelOpticTripPointStatus              OBJECT-TYPE
			   SYNTAX       		DisplayString (SIZE (0..80))         
			   ACCESS           	read-only
			   STATUS           	optional
			   DESCRIPTION
			   "The value of this object provides the label of the
			    Optical Trip Point Status parameter.It indicates whether 
			    the optical power is above(0) or below(1) trip point value"
			   ::= { gx2drr4xStatusEntry 20}

		drr4xvalueOpticTripPointStatus              OBJECT-TYPE
			   SYNTAX       		INTEGER
									{
									ok(1),
									undetermined(2),
									warning(3),
									minor(4),
									major(5),
									critical(6)
									}
			   ACCESS           	read-only
			   STATUS           	mandatory
			   DESCRIPTION
			   "The value of this object provides the current state of
			    the parameter (1-Ok, 2-Undetermined
			    3-Warning, 4-Minor, 5-Major, 6-Critical)."
			   ::= { gx2drr4xStatusEntry 21}

		drr4xstateflagOpticTripPointStatus     	OBJECT-TYPE
			   SYNTAX       		INTEGER
								{
								hidden(1),
								read-only(2),
								updateable(3)
								}
			   ACCESS           	read-only
			   STATUS           	mandatory
			   DESCRIPTION
			   "The value of this object provides the state
			    of the parameter. (1-Hidden 2-Read-Only, 3-Updateable)."
			   ::= { gx2drr4xStatusEntry  22}
    
                                        
         --Link Status 
		drr4xlabelLinkStatus              OBJECT-TYPE
			   SYNTAX       		DisplayString (SIZE (0..80))         
			   ACCESS           	read-only
			   STATUS           	optional
			   DESCRIPTION
			   "The value of this object provides the label of the
			    Link Activity Status parameter. It represents receiver
			    out of SYN with transmitter or Demux can not detect 
			    the optical signal."
			   ::= { gx2drr4xStatusEntry 23}

		drr4xvalueLinkStatus              OBJECT-TYPE
			   SYNTAX       		INTEGER
									{
									ok(1),
									undetermined(2),
									warning(3),
									minor(4),
									major(5),
									critical(6)
									}
			   ACCESS           	read-only
			   STATUS           	mandatory
			   DESCRIPTION
			   "The value of this object provides the current state of
			    the parameter (1-Ok, 2-Undetermined
			    3-Warning, 4-Minor, 5-Major, 6-Critical)."
			   ::= { gx2drr4xStatusEntry 24}

		drr4xstateflagLinkStatus     	OBJECT-TYPE
			   SYNTAX       		INTEGER
								{
								hidden(1),
								read-only(2),
								updateable(3)
								}
			   ACCESS           	read-only
			   STATUS           	mandatory
			   DESCRIPTION
			   "The value of this object provides the state
			    of the parameter. (1-Hidden 2-Read-Only, 3-Updateable)."
			   ::= { gx2drr4xStatusEntry  25}
                          
                                       
-- ************ FACTORY DATA ****************
		gx2drr4xFactoryTableIndex              OBJECT-TYPE
			   SYNTAX           INTEGER (1..2147483647)
			   ACCESS           read-only
			   STATUS           mandatory
			   DESCRIPTION
			   "The value of this object identifies the network
			    element. This index is equal to the
			    hfcCommonTableIndex for the same element."
			   ::= { gx2drr4xFactoryEntry 1}

		drr4xbootControlByte          	OBJECT-TYPE
			   SYNTAX       		INTEGER
			   ACCESS           	read-only
			   STATUS           	mandatory
			   DESCRIPTION
			   "The value of this object indicates which bank the firmware
			    is currently being boot from."
			   ::= { gx2drr4xFactoryEntry 2}

		drr4xbootStatusByte          	OBJECT-TYPE
			   SYNTAX       		INTEGER
			   ACCESS           	read-only
			   STATUS           	mandatory
			   DESCRIPTION
			   "This object indicates the status of the last boot"
			   ::= { gx2drr4xFactoryEntry 3}

		drr4xbank1CRC          		OBJECT-TYPE
			   SYNTAX       		INTEGER
			   ACCESS           	read-only
			   STATUS           	mandatory
			   DESCRIPTION
			   "This object provides the CRC code of bank 0."
			   ::= { gx2drr4xFactoryEntry 4}

		drr4xbank2CRC          		OBJECT-TYPE
			   SYNTAX       		INTEGER
			   ACCESS           	read-only
			   STATUS           	mandatory
			   DESCRIPTION
			   "This object provides the CRC code of bank 1."
			   ::= { gx2drr4xFactoryEntry 5}

		drr4xprgEEPROMByte          		OBJECT-TYPE
			   SYNTAX       		INTEGER
			   ACCESS           	read-only
			   STATUS           	mandatory
			   DESCRIPTION
			   "This object indicates if the EEPROM has been programmed"
			   ::= { gx2drr4xFactoryEntry 6}

		drr4xfactoryCRC          		OBJECT-TYPE
			   SYNTAX       		INTEGER
			   ACCESS           	read-only
			   STATUS           	mandatory
			   DESCRIPTION
			   "This object provides the CRC code for the Factory data."
			   ::= { gx2drr4xFactoryEntry 7}

		drr4xcalculateCRC          		OBJECT-TYPE
			   SYNTAX       		INTEGER
					    		{
							factory(1),
							alarm(2),
							calibration(3)
					    		}
			   ACCESS           	read-only
			   STATUS           	mandatory
			   DESCRIPTION
			   "This object indicates which of the Emnums will have the
                      CRC calculated (1-factory, 2-alarm, 3-calibration)."
			   ::= { gx2drr4xFactoryEntry 8}

		drr4xhourMeter          		OBJECT-TYPE
			   SYNTAX       		INTEGER
			   ACCESS           	read-only
			   STATUS           	mandatory
			   DESCRIPTION
			   "This object provides the hour meter reading of the module."
			   ::= { gx2drr4xFactoryEntry 9}

		drr4xflashPrgCntA          		OBJECT-TYPE
			   SYNTAX       		INTEGER
			   ACCESS           	read-only
			   STATUS           	mandatory
			   DESCRIPTION
			   "This object provides the number of times Bank 0 flash has been 
                      programmed."
			   ::= { gx2drr4xFactoryEntry 10}

		drr4xflashPrgCntB          		OBJECT-TYPE
			   SYNTAX       		INTEGER
			   ACCESS           	read-only
			   STATUS           	mandatory
			   DESCRIPTION
			   "This object provides the number of times Bank 1 flash has been 
                      programmed."
			   ::= { gx2drr4xFactoryEntry 11}

		drr4xflashBankARev          		OBJECT-TYPE
			   SYNTAX       		DisplayString (SIZE (0..80))
			   ACCESS           	read-only
			   STATUS           	mandatory
			   DESCRIPTION
			   "This object provides the revision of flash bank 0."
			   ::= { gx2drr4xFactoryEntry 12}

		drr4xflashBankBRev          		OBJECT-TYPE
			   SYNTAX       		DisplayString (SIZE (0..80))
			   ACCESS           	read-only
			   STATUS           	mandatory
			   DESCRIPTION
			   "This object provides the revision of flash bank 1."
			   ::= { gx2drr4xFactoryEntry 13}
                  
		drr4xSubAgentRev          		OBJECT-TYPE
			   SYNTAX       		DisplayString (SIZE (0..80))
			   ACCESS           	read-only
			   STATUS           	mandatory
			   DESCRIPTION
			   "This object provides the subagent revision of receiver module."
			   ::= { gx2drr4xFactoryEntry 14}

-- ****************************************************************
--
-- TRAP DEFINITIONS
--
--
-- Every trap generated by an HFC agents will include first 9 identical
-- fields. If particular variable is not supported in
-- particular TRAP-TYPE then default value will be returned.
--
-- DESCRIPTION will include explanation of use of generic
-- variables (trapAdditionalInfo******.)  If no
-- DESCRIPTION is given then generic variables will contain
-- default values.
--
-- *****************************************************************

-- **************************************************************************
--                              Digital Receiver Return Module traps
-- **************************************************************************
   trapdrrConfigChangeInteger TRAP-TYPE
       ENTERPRISE gx2Drr4x
       VARIABLES
	       {       
		trapIdentifier,
		trapNetworkElemModelNumber,
		trapNetworkElemSerialNum,
		trapPerceivedSeverity,
		trapNetworkElemOperState,
		trapNetworkElemAlarmStatus,  
		trapNetworkElemAdminState,
		trapNetworkElemAvailStatus,
		trapText,
		trapChangedObjectId,
		trapChangedValueInteger,
		trapNETrapLastTrapTimeStamp
	       }
       DESCRIPTION
	"This trap is issued if configuration of a single variable
	 with integer type was changed (via ANY interface).  
	 TrapChangedValueInteger variable may contain current reading
	 of that variable.
	 trapPerceivedSeverity - 'indeterminate'"
  ::= 1

   trapdrrConfigChangeDisplayString TRAP-TYPE
       ENTERPRISE gx2Drr4x
       VARIABLES
	       {       
		trapIdentifier,
		trapNetworkElemModelNumber,
		trapNetworkElemSerialNum,
		trapPerceivedSeverity,
		trapNetworkElemOperState,
		trapNetworkElemAlarmStatus,  
		trapNetworkElemAdminState,
		trapNetworkElemAvailStatus,
		trapText,
		trapChangedObjectId,
		trapChangedValueDisplayString,
		trapNETrapLastTrapTimeStamp
	       }
       DESCRIPTION
	"This trap is issued if configuration of a single variable
	 with DispalayString type was changed (via ANY interface).  
	 TrapChangedValueDisplayString variable may contain current reading
	 of that variable.
	 trapPerceivedSeverity - 'indeterminate'"
  ::= 2
        
   trapdrr12VCurrentAlarm TRAP-TYPE
	ENTERPRISE gx2Drr4x
	VARIABLES
		{       
		 trapIdentifier,
		 trapNetworkElemModelNumber,
		 trapNetworkElemSerialNum,
		 trapPerceivedSeverity,
		 trapNetworkElemOperState,
		 trapNetworkElemAlarmStatus,  
		 trapNetworkElemAdminState,
		 trapNetworkElemAvailStatus,
		 trapText,
		 trapChangedObjectId,
		 trapChangedValueInteger,
		 trapNETrapLastTrapTimeStamp
		}
	DESCRIPTION
	"This trap is issued when the 12V power supply Current 
	 parameter goes out of range.
	 trapAdditionalInfoInteger variable contains current reading of 
	 the this parameter."
     ::= 3       
          
  trapdrrModuleTempAlarm TRAP-TYPE
	ENTERPRISE gx2Drr4x
	VARIABLES
		{       
		 trapIdentifier,
		 trapNetworkElemModelNumber,
		 trapNetworkElemSerialNum,
		 trapPerceivedSeverity,
		 trapNetworkElemOperState,
		 trapNetworkElemAlarmStatus,  
		 trapNetworkElemAdminState,
		 trapNetworkElemAvailStatus,
		 trapText,
		 trapChangedObjectId,
		 trapChangedValueInteger,
		 trapNETrapLastTrapTimeStamp
		}
	DESCRIPTION
	"This trap is issued when the Internal Module Temperature goes out of range.
	 trapAdditionalInfoInteger variable contains current reading of 
	 the this parameter."
    ::= 4
  
    trapdrrFanCurrentAlarm TRAP-TYPE
	ENTERPRISE gx2Drr4x
	VARIABLES
		{       
		 trapIdentifier,
		 trapNetworkElemModelNumber,
		 trapNetworkElemSerialNum,
		 trapPerceivedSeverity,
		 trapNetworkElemOperState,
		 trapNetworkElemAlarmStatus,  
		 trapNetworkElemAdminState,
		 trapNetworkElemAvailStatus,
		 trapText,
		 trapChangedObjectId,
		 trapChangedValueInteger,
		 trapNETrapLastTrapTimeStamp
		}
	DESCRIPTION
	"This trap is issued when the Fan Current 
	 parameter goes out of range.
	 trapAdditionalInfoInteger variable contains current reading of 
	 the this parameter."
  ::= 5

  trapdrrFlashAlarm TRAP-TYPE
	ENTERPRISE gx2Drr4x
	VARIABLES
		{       
		 trapIdentifier,
		 trapNetworkElemModelNumber,
		 trapNetworkElemSerialNum,
		 trapPerceivedSeverity,
		 trapNetworkElemOperState,
		 trapNetworkElemAlarmStatus,  
		 trapNetworkElemAdminState,
		 trapNetworkElemAvailStatus,
		 trapText,
		 trapChangedObjectId,
		 trapChangedValueInteger,
		 trapNETrapLastTrapTimeStamp
		}
	DESCRIPTION
	"This trap is issued when the detects an error during
	Flash memory operations."
  ::= 6
  
  trapdrrBankBootAlarm TRAP-TYPE
	ENTERPRISE gx2Drr4x
	VARIABLES
		{       
		 trapIdentifier,
		 trapNetworkElemModelNumber,
		 trapNetworkElemSerialNum,
		 trapPerceivedSeverity,
		 trapNetworkElemOperState,
		 trapNetworkElemAlarmStatus,  
		 trapNetworkElemAdminState,
		 trapNetworkElemAvailStatus,
		 trapText,
		 trapChangedObjectId,
		 trapChangedValueInteger,
		 trapNETrapLastTrapTimeStamp
		}
	DESCRIPTION
	"This trap is issued when the module detects an error while booting
	from bank 0 or bank 1."
  ::= 7

	trapdrrAlarmDataCRCAlarm TRAP-TYPE
	ENTERPRISE gx2Drr4x
	VARIABLES
		{       
		 trapIdentifier,
		 trapNetworkElemModelNumber,
		 trapNetworkElemSerialNum,
		 trapPerceivedSeverity,
		 trapNetworkElemOperState,
		 trapNetworkElemAlarmStatus,  
		 trapNetworkElemAdminState,
		 trapNetworkElemAvailStatus,
		 trapText,
		 trapChangedObjectId,
		 trapChangedValueInteger,
		 trapNETrapLastTrapTimeStamp
		}
	DESCRIPTION
	"This trap is issued when the Alarm Data CRC is incorrect."
  ::= 8

	trapdrrHardwareErrAlarm TRAP-TYPE
	ENTERPRISE gx2Drr4x
	VARIABLES
		{       
		 trapIdentifier,
		 trapNetworkElemModelNumber,
		 trapNetworkElemSerialNum,
		 trapPerceivedSeverity,
		 trapNetworkElemOperState,
		 trapNetworkElemAlarmStatus,  
		 trapNetworkElemAdminState,
		 trapNetworkElemAvailStatus,
		 trapText,
		 trapChangedObjectId,
		 trapChangedValueInteger,
		 trapNETrapLastTrapTimeStamp
		}
	DESCRIPTION
	"This trap is issued when hardware is abnormal."
  ::= 9

 	trapdrrOpticalSignalAlarm TRAP-TYPE
	ENTERPRISE gx2Drr4x
	VARIABLES
		{       
		 trapIdentifier,
		 trapNetworkElemModelNumber,
		 trapNetworkElemSerialNum,
		 trapPerceivedSeverity,
		 trapNetworkElemOperState,
		 trapNetworkElemAlarmStatus,  
		 trapNetworkElemAdminState,
		 trapNetworkElemAvailStatus,
		 trapText,
		 trapChangedObjectId,
		 trapChangedValueInteger,
		 trapNETrapLastTrapTimeStamp
		}
	DESCRIPTION
	"This trap is issued when the optical signal is beyond the preset range."  
  ::= 10
 
	trapdrrFactoryDataCRCAlarm TRAP-TYPE
	ENTERPRISE gx2Drr4x
	VARIABLES
		{       
		 trapIdentifier,
		 trapNetworkElemModelNumber,
		 trapNetworkElemSerialNum,
		 trapPerceivedSeverity,
		 trapNetworkElemOperState,
		 trapNetworkElemAlarmStatus,  
		 trapNetworkElemAdminState,
		 trapNetworkElemAvailStatus,
		 trapText,
		 trapChangedObjectId,
		 trapChangedValueInteger,
		 trapNETrapLastTrapTimeStamp
		}
	DESCRIPTION
	"This trap is issued when the Factory Data CRC is incorrect."
  ::= 11

	trapdrrResetFactoryDefaultAlarm TRAP-TYPE
	ENTERPRISE gx2Drr4x
	VARIABLES
		{       
		 trapIdentifier,
		 trapNetworkElemModelNumber,
		 trapNetworkElemSerialNum,
		 trapPerceivedSeverity,
		 trapNetworkElemOperState,
		 trapNetworkElemAlarmStatus,  
		 trapNetworkElemAdminState,
		 trapNetworkElemAvailStatus,
		 trapText,
		 trapChangedObjectId,
		 trapChangedValueInteger,
		 trapNETrapLastTrapTimeStamp
		}
	DESCRIPTION
	"This trap is issued when the Factory Default Reset occurs."
  ::= 12

	trapdrrTripPointAlarm TRAP-TYPE
	ENTERPRISE gx2Drr4x
	VARIABLES
		{       
		 trapIdentifier,
		 trapNetworkElemModelNumber,
		 trapNetworkElemSerialNum,
		 trapPerceivedSeverity,
		 trapNetworkElemOperState,
		 trapNetworkElemAlarmStatus,  
		 trapNetworkElemAdminState,
		 trapNetworkElemAvailStatus,
		 trapText,
		 trapChangedObjectId,
		 trapChangedValueInteger,
		 trapNETrapLastTrapTimeStamp
		}
	DESCRIPTION
	"This trap is issued when the Input optical power is lower than the custumer set 
	trip point and trippoint mode as ALARM_ONLY or SWITCH & ALARM."
  ::= 13       
  
    trapdrrLinkAlarm TRAP-TYPE
	ENTERPRISE gx2Drr4x
	VARIABLES
		{       
		 trapIdentifier,
		 trapNetworkElemModelNumber,
		 trapNetworkElemSerialNum,
		 trapPerceivedSeverity,
		 trapNetworkElemOperState,
		 trapNetworkElemAlarmStatus,  
		 trapNetworkElemAdminState,
		 trapNetworkElemAvailStatus,
		 trapText,
		 trapChangedObjectId,
		 trapChangedValueInteger,
		 trapNETrapLastTrapTimeStamp
		}
	DESCRIPTION
	"This trap is issued when receiver is out of SYN with transmitter"
  ::= 14 
    trapdrrCalibrationDataCRCAlarm TRAP-TYPE
	ENTERPRISE gx2Drr4x
	VARIABLES
		{       
		 trapIdentifier,
		 trapNetworkElemModelNumber,
		 trapNetworkElemSerialNum,
		 trapPerceivedSeverity,
		 trapNetworkElemOperState,
		 trapNetworkElemAlarmStatus,  
		 trapNetworkElemAdminState,
		 trapNetworkElemAvailStatus,
		 trapText,
		 trapChangedObjectId,
		 trapChangedValueInteger,
		 trapNETrapLastTrapTimeStamp
		}
	DESCRIPTION
	"This trap is issued when the Calibration Data CRC is incorrect"
  ::= 15 

  END
