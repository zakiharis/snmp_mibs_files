OMNI-gx2OSW10B-MIB DEFINITIONS ::= BEGIN

    IMPORTS
	IpAddress, TimeTicks, Counter, DisplayString            
					      FROM RFC1155-SMI
--	IpAddress, TimeTicks            
--					      FROM RFC1155-SMI
--	OBJECT-TYPE                     
--					      FROM RFC-1212
--	sysUpTime, DisplayString        
--					      FROM RFC1213-MIB
--	TRAP-TYPE                       
--					      FROM RFC-1215
--	gi, motproxies                   
--					      FROM NLS-BBNIDENT-MIB
	gx2Osw10b
					      FROM GX2HFC-MIB

	trapIdentifier,trapNetworkElemModelNumber,
	trapNetworkElemSerialNum, trapPerceivedSeverity,
	trapNetworkElemOperState, trapNetworkElemAlarmStatus,
	trapNetworkElemAdminState, trapNetworkElemAvailStatus,
	trapText, trapNETrapLastTrapTimeStamp, trapChangedObjectId,
	trapChangedValueInteger, trapChangedValueDisplayString
					      FROM NLSBBN-TRAPS-MIB;



	       -- This MIB module uses the extended OBJECT-TYPE macro as
	       -- defined in RFC1212 and the TRAP-TYPE macro as defined
	       -- in RFC 1215.

		   --REVISION	"4" Jan 20, 2003
		   --DESCRIPTION
		   --			Added revision and description comment section


		--    OMNISTAR Optical Switch Module MIB MODULE

	-- This MIB module defines information for management of HFC networks
		-- 
		-- The MIB module assumes that all generic (static) network element
		-- information is defined in a different module such as the HFC module
		-- The MIB consists of two groups:
		-- the device type descriptor subgroup and 
		-- gx2Osw10b Network Elements subgroup.
		-- The device type descriptor subgroup is used to define 
		-- parameters specific to gx2Osw10b device type.
		-- These parameters are common across all network elements
		-- from gx2Osw10b device type.
		--
		-- The gx2Osw10b Network Elements subgroup is
		-- a list of gx2Osw10b type elements in the
		-- current network topology with nominal
		-- and current parameter values for the
		-- individual network elements; the individual
		-- network elements are identified by  
		-- index from hfcCommonTable.
		-- That implies what hfcCommonTableIndex and
		-- gx2Osw10bTableIndex are equal for each individual
		-- network element.
		-- This table is an extension of the hfcCommonTable
		-- for all elements of gx2Lmc type.
		--
		-- Both groups are mandatory for management of gx2Lmc devices.

-- ****************************************************************************
		--
		-- All floating point numbers will be represented by an IEEE 32 Bit number.
		-- Conversion of this number must be done on the user interface to view the 
		-- actual floating point number. 
		--

		Float ::= Counter  -- UNSIGNED (32 BITS) 

-- ****************************************************************************

		-- gx2Osw10b Device Descriptor subgroup.

		-- The device type descriptor subgroup is used to define 
		-- parameters specific to gx2Osw10b device type.
		-- These parameters are common across all network elements
		-- from gx2Osw10b device type.


		gx2Osw10bDescriptor OBJECT IDENTIFIER ::= {gx2Osw10b 1}



--*****************************************************************************
		--              gx2Osw10b Table
		
		-- Contains a list of all gx2Osw10b type devices in
		-- the network. Each device is characterized with
		-- current network topology information, with nominal
		-- and current parameter values for the
		-- individual network elements;
		--
		-- The individual network elements identified by  
		-- index from hfcCommonTable.
		-- That implies what hfcCommonTableIndex and
		-- gx2Osw10bTableIndex are equal for each individual
		-- network element.
		-- This table should be used as an extension of the hfcCommonTable
		-- for all elements of gx2Osw10b type.


	       gx2Osw10bAnalogTable                    OBJECT-TYPE
			 SYNTAX             SEQUENCE OF Gx2Osw10bAnalogEntry
			 ACCESS             not-accessible
			 STATUS             mandatory
			 DESCRIPTION
			 "This table contains gx2Osw10b specific parameters with
			  nominal and current values."
			 ::= { gx2Osw10b 2 }


	       gx2Osw10bAnalogEntry               OBJECT-TYPE
			 SYNTAX             Gx2Osw10bAnalogEntry
			 ACCESS             not-accessible
			 STATUS             mandatory
			 DESCRIPTION
			 "This list contains the analog parameters and descriptions."
			 INDEX { gx2Osw10bAnalogTableIndex }
			 ::= { gx2Osw10bAnalogTable  1}

--*****************************************************************************
	       gx2Osw10bDigitalTable                    OBJECT-TYPE
			 SYNTAX             SEQUENCE OF Gx2Osw10bDigitalEntry
			 ACCESS             not-accessible
			 STATUS             mandatory
			 DESCRIPTION
			 "This table contains gx2Osw10b specific parameters with
			  nominal and current values."
			 ::= { gx2Osw10b 3 }

	       gx2Osw10bDigitalEntry               OBJECT-TYPE
			 SYNTAX             Gx2Osw10bDigitalEntry
			 ACCESS             not-accessible
			 STATUS             mandatory
			 DESCRIPTION
			 "This list contains digital parameters and descriptions."
			 INDEX { gx2Osw10bDigitalTableIndex }
			 ::= { gx2Osw10bDigitalTable  2}

--*****************************************************************************
	       gx2Osw10bStatusTable                    OBJECT-TYPE
			 SYNTAX             SEQUENCE OF Gx2Osw10bStatusEntry
			 ACCESS             not-accessible
			 STATUS             mandatory
			 DESCRIPTION
			 "This table contains gx2Osw10b specific parameters with
			  nominal and current values."
			 ::= { gx2Osw10b 4 }

	       gx2Osw10bStatusEntry               OBJECT-TYPE
			 SYNTAX             Gx2Osw10bStatusEntry
			 ACCESS             not-accessible
			 STATUS             mandatory
			 DESCRIPTION
			 "This list contains Status parameters and descriptions."
			 INDEX { gx2Osw10bStatusTableIndex }
			 ::= { gx2Osw10bStatusTable  3}

--*****************************************************************************
	       gx2Osw10bFactoryTable                    OBJECT-TYPE
			 SYNTAX             SEQUENCE OF Gx2Osw10bFactoryEntry
			 ACCESS             not-accessible
			 STATUS             mandatory
			 DESCRIPTION
			 "This table contains gx2Osw10b specific parameters with
			  nominal and current values."
			 ::= { gx2Osw10b 5 }

	       gx2Osw10bFactoryEntry               OBJECT-TYPE
			 SYNTAX             Gx2Osw10bFactoryEntry
			 ACCESS             not-accessible
			 STATUS             mandatory
			 DESCRIPTION
			 "This list contains Factory parameters and descriptions."
			 INDEX { gx2Osw10bFactoryTableIndex }
			 ::= { gx2Osw10bFactoryTable  4}

--*****************************************************************************

	       gx2Osw10bHoldTimeTable                    OBJECT-TYPE
			 SYNTAX             SEQUENCE OF Gx2Osw10bHoldTimeEntry
			 ACCESS             not-accessible
			 STATUS             mandatory
			 DESCRIPTION
			 "This table contains gx2Osw10b specific parameters with
			  nominal and current values."
			 ::= { gx2Osw10b 6 }

	       gx2Osw10bHoldTimeEntry               OBJECT-TYPE
			 SYNTAX             Gx2Osw10bHoldTimeEntry
			 ACCESS             not-accessible
			 STATUS             mandatory
			 DESCRIPTION
			 "This list contains digital product class and the
			  associated RF channel parameters and descriptions."
			 INDEX { rxgx2Osw10bHoldTimeTableIndex, rxgx2Osw10bHoldTimeSpecIndex }
			 ::= { gx2Osw10bHoldTimeTable  5}

--***********************************************************************



	      Gx2Osw10bAnalogEntry    ::= SEQUENCE  
	       {
		gx2Osw10bAnalogTableIndex         INTEGER,
		
		--           Analog Parameters

		osw10blabelPriOpticalInputLevel			DisplayString (SIZE (0..80)),
		osw10buomPriOpticalInputLevel			DisplayString (SIZE (0..80)),
		osw10bmajorHighPriOpticalInputLevel		Float, 
		osw10bmajorLowPriOpticalInputLevel		Float, 
		osw10bminorHighPriOpticalInputLevel		Float,
		osw10bminorLowPriOpticalInputLevel		Float, 
		osw10bcurrentValuePriOpticalInputLevel		Float, 
		osw10bstateFlagPriOpticalInputLevel		INTEGER,
		osw10bminValuePriOpticalInputLevel		Float,
		osw10bmaxValuePriOpticalInputLevel		Float,
		osw10balarmStatePriOpticalInputLevel		INTEGER,

		osw10blabelSecOpticalInputLevel			DisplayString (SIZE (0..80)),
		osw10buomSecOpticalInputLevel			DisplayString (SIZE (0..80)),
		osw10bmajorHighSecOpticalInputLevel		Float, 
		osw10bmajorLowSecOpticalInputLevel		Float, 
		osw10bminorHighSecOpticalInputLevel		Float,
		osw10bminorLowSecOpticalInputLevel		Float, 
		osw10bcurrentValueSecOpticalInputLevel		Float, 
		osw10bstateFlagSecOpticalInputLevel		INTEGER,
		osw10bminValueSecOpticalInputLevel		Float,
		osw10bmaxValueSecOpticalInputLevel 		Float,
		osw10balarmStateSecOpticalInputLevel	INTEGER,

		osw10blabelPriOpticalThreshold			DisplayString (SIZE (0..80)),
		osw10buomPriOpticalThreshold			DisplayString (SIZE (0..80)),
		osw10bmajorHighPriOpticalThreshold		Float, 
		osw10bmajorLowPriOpticalThreshold		Float, 
		osw10bminorHighPriOpticalThreshold		Float,
		osw10bminorLowPriOpticalThreshold		Float, 
		osw10bcurrentValuePriOpticalThreshold		Float, 
		osw10bstateFlagPriOpticalThreshold		INTEGER,
		osw10bminValuePriOpticalThreshold		Float,
		osw10bmaxValuePriOpticalThreshold		Float,
		osw10balarmStatePriOpticalThreshold		INTEGER,

		osw10blabelSecOpticalThreshold			DisplayString (SIZE (0..80)),
		osw10buomSecOpticalThreshold			DisplayString (SIZE (0..80)),
		osw10bmajorHighSecOpticalThreshold		Float, 
		osw10bmajorLowSecOpticalThreshold		Float, 
		osw10bminorHighSecOpticalThreshold		Float,
		osw10bminorLowSecOpticalThreshold		Float, 
		osw10bcurrentValueSecOpticalThreshold		Float, 
		osw10bstateFlagSecOpticalThreshold		INTEGER,
		osw10bminValueSecOpticalThreshold		Float,
		osw10bmaxValueSecOpticalThreshold 		Float,
		osw10balarmStateSecOpticalThreshold		INTEGER,

		osw10blabelModTemp			DisplayString (SIZE (0..80)),
		osw10buomModTemp				DisplayString (SIZE (0..80)),
		osw10bmajorHighModTemp			Float, 
		osw10bmajorLowModTemp			Float, 
		osw10bminorHighModTemp			Float,
		osw10bminorLowModTemp			Float, 
		osw10bcurrentValueModTemp		Float, 
		osw10bstateFlagModTemp			INTEGER,
		osw10bminValueModTemp			Float,
		osw10bmaxValueModTemp			Float,
		osw10balarmStateModTemp			INTEGER,

		osw10blabelFanCurrent			DisplayString (SIZE (0..80)),
		osw10buomFanCurrent			DisplayString (SIZE (0..80)),
		osw10bmajorHighFanCurrent		Float, 
		osw10bmajorLowFanCurrent		Float, 
		osw10bminorHighFanCurrent		Float,
		osw10bminorLowFanCurrent		Float, 
		osw10bcurrentValueFanCurrent		Float, 
		osw10bstateFlagFanCurrent		INTEGER,
		osw10bminValueFanCurrent		Float,
		osw10bmaxValueFanCurrent 		Float,
		osw10balarmStateFanCurrent		INTEGER
		}

		-- ****************  Digital Parameters ***********************
	     Gx2Osw10bDigitalEntry    ::= SEQUENCE  
	     {
		gx2Osw10bDigitalTableIndex         INTEGER,

		osw10blabelSwitchControl		DisplayString (SIZE (0..80)),
		osw10benumSwitchControl			DisplayString (SIZE (0..80)),
		osw10bvalueSwitchControl		INTEGER,
		osw10bstateflagSwitchControl   	INTEGER,

		osw10blabelSwitchMode	    	        DisplayString (SIZE (0..80)),
		osw10benumSwitchMode			DisplayString (SIZE (0..80)),
		osw10bvalueSwitchMode		        INTEGER,
		osw10bstateflagSwitchMode   	        INTEGER,

		osw10blabelRevertMode			DisplayString (SIZE (0..80)),
		osw10benumRevertMode			DisplayString (SIZE (0..80)),
		osw10bvalueRevertMode			INTEGER,
		osw10bstateflagRevertMode   		INTEGER,

		osw10blabelRevertTime			DisplayString (SIZE (0..80)),
		osw10benumRevertTime			DisplayString (SIZE (0..80)),
		osw10bvalueRevertTime			INTEGER,
		osw10bstateflagRevertTime  	 	INTEGER,

		osw10blabelWavelength			DisplayString (SIZE (0..80)),
		osw10benumWavelength			DisplayString (SIZE (0..80)),
		osw10bvalueWavelength			INTEGER,
		osw10bstateflagWavelength  	 	INTEGER,

		osw10blabelSwitchMonitor		DisplayString (SIZE (0..80)),
		osw10benumSwitchMonitor			DisplayString (SIZE (0..80)),
		osw10bvalueSwitchMonitor		INTEGER,
		osw10bstateflagSwitchMonitor  	INTEGER,

	    osw10blabelOperationMode		DisplayString (SIZE (0..80)),
		osw10benumOperationMode			DisplayString (SIZE (0..80)),
		osw10bvalueOperationMode		INTEGER,
		osw10bstateflagOperationMode  	INTEGER,

		osw10blabelFactoryDefault		DisplayString (SIZE (0..80)),
		osw10benumFactoryDefault		DisplayString (SIZE (0..80)),
		osw10bvalueFactoryDefault		INTEGER,
		osw10bstateflagFactoryDefault   	INTEGER
		}

		-- ****************  Status Parameters ************************************
	     Gx2Osw10bStatusEntry    ::= SEQUENCE  
	     {
		gx2Osw10bStatusTableIndex         INTEGER,

		osw10blabelBoot				DisplayString (SIZE (0..80)),
		osw10bvalueBoot				INTEGER,
		osw10bstateflagBoot			INTEGER,
		
		osw10blabelFlash				DisplayString (SIZE (0..80)),
		osw10bvalueFlash				INTEGER,
		osw10bstateflagFlash			INTEGER,

		osw10blabelFactoryDataCRC 		DisplayString (SIZE (0..80)),
		osw10bvalueFactoryDataCRC		INTEGER,
		osw10bstateflagFactoryDataCRC		INTEGER,

            osw10blabelCalibrateTableStatus	DisplayString (SIZE (0..80)),
		osw10bvalueCalibrateTableStatus	INTEGER,
		osw10bstateflagCalibrateTableStatus	INTEGER,

		osw10blabelAlarmDataCrc			DisplayString (SIZE (0..80)),
		osw10bvalueAlarmDataCrc			INTEGER,
		osw10bstateflagAlarmDataCrc		INTEGER,

		osw10blabelInputStatus		      DisplayString (SIZE (0..80)),
		osw10bvalueInputStatus		      INTEGER,
		osw10bstateflagInputStatus		INTEGER,

		osw10blabelPriActiveStatus		DisplayString (SIZE (0..80)),
		osw10bvaluePriActiveStatus		INTEGER,
		osw10bstateflagPriActiveStatus	INTEGER,

            osw10blabelHardwareErr		      DisplayString (SIZE (0..80)),
		osw10bvalueHardwareErr		      INTEGER,
		osw10bstateflagHardwareErr		INTEGER,

		osw10blabelPriThresholdStatus	      DisplayString (SIZE (0..80)),
		osw10bvaluePriThresholdStatus		INTEGER,
		osw10bstateflagPriThresholdStatus	INTEGER,

		osw10blabelSecThresholdStatus		DisplayString (SIZE (0..80)),
		osw10bvalueSecThresholdStatus		INTEGER,
		osw10bstateflagSecThresholdStatus	INTEGER

		}


		-- ****************  Factory Parameters *************************************
       Gx2Osw10bFactoryEntry    ::= SEQUENCE  
       {
		gx2Osw10bFactoryTableIndex         INTEGER,
		osw10bbootControlByte  			INTEGER,
		osw10bbootStatusByte   			INTEGER,
		osw10bbank1CRC    			INTEGER,
		osw10bbank2CRC    			INTEGER,
		osw10bprgEEPROMByte    			INTEGER,
		osw10bfactoryCRC    			INTEGER,
		osw10bcalculateCRC    			INTEGER,
		osw10bhourMeter    			INTEGER,
		osw10bflashPrgCntA    			INTEGER,
		osw10bflashPrgCntB    			INTEGER,
		osw10bflashBankARev    			DisplayString (SIZE (0..80)),
		osw10bflashBankBRev    			DisplayString (SIZE (0..80))

		}



		-- ****************  Hold Time Parameters *************************************
	    Gx2Osw10bHoldTimeEntry    ::= SEQUENCE  
	    {
		rxgx2Osw10bHoldTimeTableIndex        INTEGER,
		rxgx2Osw10bHoldTimeSpecIndex         INTEGER,   
		rxgx2Osw10bHoldTimeData  			 INTEGER
		}


            -- ************** Analog Parameters ****************************
		gx2Osw10bAnalogTableIndex              OBJECT-TYPE
			   SYNTAX           INTEGER (1..4294967295)
			   ACCESS           read-only
			   STATUS           mandatory
			   DESCRIPTION
			   "The value of this object identifies the network
			    element. This index is equal to the
			    hfcCommonTableIndex for the same element."
			   ::= { gx2Osw10bAnalogEntry 1}

-- New Parameter

		osw10blabelPriOpticalInputLevel              OBJECT-TYPE
			   SYNTAX           DisplayString (SIZE (0..80))
			   ACCESS           read-only
			   STATUS           optional
			   DESCRIPTION
			   "The value of this object provides the label of the
			    Primary Optical Input Level Analog parameter."
			   ::= { gx2Osw10bAnalogEntry 2}

		osw10buomPriOpticalInputLevel                OBJECT-TYPE
			   SYNTAX           DisplayString (SIZE (0..80))
			   ACCESS           read-only
			   STATUS           optional
			   DESCRIPTION
			   "The value of this object provides the Unit of Measure of the
			    Primary Optical Input Level Analog parameter."
			   ::= { gx2Osw10bAnalogEntry 3}

		osw10bmajorHighPriOpticalInputLevel          OBJECT-TYPE
			   SYNTAX           Float 
			   ACCESS           read-only
			   STATUS           mandatory
			   DESCRIPTION
			   "The value of this object provides the Major High alarm value
			    of the Primary Optical Input Level Analog parameter.
			   This value is a floating point number that is represented as an IEEE 32 bit number."
			   ::= { gx2Osw10bAnalogEntry 4}


		osw10bmajorLowPriOpticalInputLevel           OBJECT-TYPE
			   SYNTAX           Float 
			   ACCESS           read-only
			   STATUS           mandatory
			   DESCRIPTION
			   "The value of this object provides the Major Low alarm value
			    of the Primary Optical Input Level Analog parameter.
			   This value is a floating point number that is represented as an IEEE 32 bit number."
			   ::= { gx2Osw10bAnalogEntry 5}

		osw10bminorHighPriOpticalInputLevel          OBJECT-TYPE
			   SYNTAX           Float
			   ACCESS           read-only
			   STATUS           mandatory
			   DESCRIPTION
			   "The value of this object provides the Minor High alarm value
			    of the Primary Optical Input Level Analog parameter.
			   This value is a floating point number that is represented as an IEEE 32 bit number."
			   ::= { gx2Osw10bAnalogEntry 6}

		osw10bminorLowPriOpticalInputLevel           OBJECT-TYPE
			   SYNTAX           Float 
			   ACCESS           read-only
			   STATUS           mandatory
			   DESCRIPTION
			   "The value of this object provides the Minor Low alarm value
			    of the Primary Optical Input Level Analog parameter.
			   This value is a floating point number that is represented as an IEEE 32 bit number."
			   ::= { gx2Osw10bAnalogEntry 7}

		osw10bcurrentValuePriOpticalInputLevel       OBJECT-TYPE
			   SYNTAX           Float 
			   ACCESS           read-only
			   STATUS           mandatory
			   DESCRIPTION
			   "The value of this object provides the Current value
			    of the Primary Optical Input Level Analog parameter.
			   This value is a floating point number that is represented as an IEEE 32 bit number."
			   ::= { gx2Osw10bAnalogEntry 8}

		osw10bstateFlagPriOpticalInputLevel          OBJECT-TYPE
			   SYNTAX           INTEGER
								{
								hidden(1),
								read-only(2),
								updateable(3)
								}
			   ACCESS           read-only
			   STATUS           mandatory
			   DESCRIPTION
			   "The value of this object provides the state
			    of the Primary Optical Input Level Analog parameter. (0-Hidden	
			          1-Read-Only, 2-Updateable)."
			   ::= { gx2Osw10bAnalogEntry 9}

		osw10bminValuePriOpticalInputLevel           OBJECT-TYPE
			   SYNTAX           Float
			   ACCESS           read-only
			   STATUS           mandatory
			   DESCRIPTION
			   "The value of this object provides the minimum value
			    the Primary Optical Input Level Analog parameter can achive.
			   This value is a floating point number that is represented as an IEEE 32 bit number."
			   ::= { gx2Osw10bAnalogEntry 10}

		osw10bmaxValuePriOpticalInputLevel           OBJECT-TYPE
			   SYNTAX           Float
			   ACCESS           read-only
			   STATUS           mandatory
			   DESCRIPTION
			   "The value of this object provides the maximum value
			    the Primary Optical Input Level Analog parameter can achieve.
			   This value is a floating point number that is represented as an IEEE 32 bit number."
			   ::= { gx2Osw10bAnalogEntry 11}

		osw10balarmStatePriOpticalInputLevel         OBJECT-TYPE
			   SYNTAX           INTEGER
									{
									noAlarm(1),
									majorLowAlarm(2),
									minorLowAlarm(3),
									minorHighAlarm(4),
									majorHighAlarm(5),
									informational(6)
									}
			   ACCESS           read-only
			   STATUS           mandatory
			   DESCRIPTION
			   "The value of this object provides the current alarm state of
			    the Primary Optical Input Level Analog parameter."
			   ::= { gx2Osw10bAnalogEntry 12}

-- New Parameter

		osw10blabelSecOpticalInputLevel              OBJECT-TYPE
			   SYNTAX           DisplayString (SIZE (0..80))
			   ACCESS           read-only
			   STATUS           optional
			   DESCRIPTION
			   "The value of this object provides the label of the
			    Secondary Optical Input Level Analog parameter."
			   ::= { gx2Osw10bAnalogEntry 13}

		osw10buomSecOpticalInputLevel                OBJECT-TYPE
			   SYNTAX           DisplayString (SIZE (0..80))
			   ACCESS           read-only
			   STATUS           optional
			   DESCRIPTION
			   "The value of this object provides the Unit of Measure of the
			    Secondary Optical Input Level Analog parameter."
			   ::= { gx2Osw10bAnalogEntry 14}

		osw10bmajorHighSecOpticalInputLevel          OBJECT-TYPE
			   SYNTAX           Float 
			   ACCESS           read-only
			   STATUS           mandatory
			   DESCRIPTION
			   "The value of this object provides the Major High alarm value
			    of the Secondary Optical Input Level Analog parameter.
			   This value is a floating point number that is represented as an IEEE 32 bit number."
			   ::= { gx2Osw10bAnalogEntry 15}


		osw10bmajorLowSecOpticalInputLevel           OBJECT-TYPE
			   SYNTAX           Float 
			   ACCESS           read-only
			   STATUS           mandatory
			   DESCRIPTION
			   "The value of this object provides the Major Low alarm value
			    of the Secondary Optical Input Level Analog parameter.
			   This value is a floating point number that is represented as an IEEE 32 bit number."
			   ::= { gx2Osw10bAnalogEntry 16}

		osw10bminorHighSecOpticalInputLevel          OBJECT-TYPE
			   SYNTAX           Float
			   ACCESS           read-only
			   STATUS           mandatory
			   DESCRIPTION
			   "The value of this object provides the Minor High alarm value
			    of the Secondary Optical Input Level Analog parameter.
			   This value is a floating point number that is represented as an IEEE 32 bit number."
			   ::= { gx2Osw10bAnalogEntry 17}

		osw10bminorLowSecOpticalInputLevel           OBJECT-TYPE
			   SYNTAX           Float 
			   ACCESS           read-only
			   STATUS           mandatory
			   DESCRIPTION
			   "The value of this object provides the Minor Low alarm value
			    of the Secondary Optical Input Level Analog parameter.
			   This value is a floating point number that is represented as an IEEE 32 bit number."
			   ::= { gx2Osw10bAnalogEntry 18}

		osw10bcurrentValueSecOpticalInputLevel       OBJECT-TYPE
			   SYNTAX           Float 
			   ACCESS           read-only
			   STATUS           mandatory
			   DESCRIPTION
			   "The value of this object provides the Current value
			    of the Secondary Optical Input Level Analog parameter.
			   This value is a floating point number that is represented as an IEEE 32 bit number."
			   ::= { gx2Osw10bAnalogEntry 19}

		osw10bstateFlagSecOpticalInputLevel          OBJECT-TYPE
			   SYNTAX           INTEGER
								{
								hidden(1),
								read-only(2),
								updateable(3)
								}
			   ACCESS           read-only
			   STATUS           mandatory
			   DESCRIPTION
			   "The value of this object provides the state
			    of the Secondary Optical Input Level Analog parameter. (0-Hidden	
			          1-Read-Only, 2-Updateable)."
			   ::= { gx2Osw10bAnalogEntry 20}

		osw10bminValueSecOpticalInputLevel           OBJECT-TYPE
			   SYNTAX           Float
			   ACCESS           read-only
			   STATUS           mandatory
			   DESCRIPTION
			   "The value of this object provides the minimum value
			    the Secondary Optical Input Level Analog parameter can achive.
			   This value is a floating point number that is represented as an IEEE 32 bit number."
			   ::= { gx2Osw10bAnalogEntry 21}

		osw10bmaxValueSecOpticalInputLevel           OBJECT-TYPE
			   SYNTAX           Float
			   ACCESS           read-only
			   STATUS           mandatory
			   DESCRIPTION
			   "The value of this object provides the maximum value
			    the Secondary Optical Input Level Analog parameter can achive.
			   This value is a floating point number that is represented as an IEEE 32 bit number."
			   ::= { gx2Osw10bAnalogEntry 22}

		osw10balarmStateSecOpticalInputLevel         OBJECT-TYPE
			   SYNTAX           INTEGER
									{
									noAlarm(1),
									majorLowAlarm(2),
									minorLowAlarm(3),
									minorHighAlarm(4),
									majorHighAlarm(5),
									informational(6)
									}
			   ACCESS           read-only
			   STATUS           mandatory
			   DESCRIPTION
			   "The value of this object provides the curent alarm state of
			    the Secondary Optical Input Level Analog parameter."
			   ::= { gx2Osw10bAnalogEntry 23}


-- New Parameter

		osw10blabelPriOpticalThreshold              OBJECT-TYPE
			   SYNTAX           DisplayString (SIZE (0..80))
			   ACCESS           read-only
			   STATUS           optional
			   DESCRIPTION
			   "The value of this object provides the label of the
			    Primary Optical Input Threshold Analog parameter."
			   ::= { gx2Osw10bAnalogEntry 24}

		osw10buomPriOpticalThreshold                OBJECT-TYPE
			   SYNTAX           DisplayString (SIZE (0..80))
			   ACCESS           read-only
			   STATUS           optional
			   DESCRIPTION
			   "The value of this object provides the Unit of Measure of the
			    Primary Optical Input Threshold Analog parameter."
			   ::= { gx2Osw10bAnalogEntry 25}

		osw10bmajorHighPriOpticalThreshold          OBJECT-TYPE
			   SYNTAX           Float 
			   ACCESS           read-only
			   STATUS           mandatory
			   DESCRIPTION
			   "The value of this object provides the Major High alarm value
			    of the Primary Optical Input Threshold Analog parameter.
			   This value is a floating point number that is represented as an IEEE 32 bit number."
			   ::= { gx2Osw10bAnalogEntry 26}


		osw10bmajorLowPriOpticalThreshold           OBJECT-TYPE
			   SYNTAX           Float 
			   ACCESS           read-only
			   STATUS           mandatory
			   DESCRIPTION
			   "The value of this object provides the Major Low alarm value
			    of the Primary Optical Input Threshold Analog parameter.
			   This value is a floating point number that is represented as an IEEE 32 bit number."
			   ::= { gx2Osw10bAnalogEntry 27}

		osw10bminorHighPriOpticalThreshold          OBJECT-TYPE
			   SYNTAX           Float
			   ACCESS           read-only
			   STATUS           mandatory
			   DESCRIPTION
			   "The value of this object provides the Minor High alarm value
			    of the Primary Optical Input Threshold Analog parameter.
			   This value is a floating point number that is represented as an IEEE 32 bit number."
			   ::= { gx2Osw10bAnalogEntry 28}

		osw10bminorLowPriOpticalThreshold           OBJECT-TYPE
			   SYNTAX           Float 
			   ACCESS           read-only
			   STATUS           mandatory
			   DESCRIPTION
			   "The value of this object provides the Minor Low alarm value
			    of the Primary Optical Input Threshold Analog parameter.
			   This value is a floating point number that is represented as an IEEE 32 bit number."
			   ::= { gx2Osw10bAnalogEntry 29}

		osw10bcurrentValuePriOpticalThreshold       OBJECT-TYPE
			   SYNTAX           Float 
			   ACCESS           read-write
			   STATUS           mandatory
			   DESCRIPTION
			   "The value of this object provides the Current value
			    of the Primary Optical Input Threshold Analog parameter.
			   This value is a floating point number that is represented as an IEEE 32 bit number."
			   ::= { gx2Osw10bAnalogEntry 30}

		osw10bstateFlagPriOpticalThreshold          OBJECT-TYPE
			   SYNTAX           INTEGER
								{
								hidden(1),
								read-only(2),
								updateable(3)
								}
			   ACCESS           read-only
			   STATUS           mandatory
			   DESCRIPTION
			   "The value of this object provides the state
			    of the Primary Optical Input Threshold Analog parameter. (0-Hidden	
			          1-Read-Only, 2-Updateable)."
			   ::= { gx2Osw10bAnalogEntry 31}

		osw10bminValuePriOpticalThreshold           OBJECT-TYPE
			   SYNTAX           Float
			   ACCESS           read-write
			   STATUS           mandatory
			   DESCRIPTION
			   "The value of this object provides the minimum value
			    the Primary Optical Input Threshold Analog parameter can achive.
			   This value is a floating point number that is represented as an IEEE 32 bit number."
			   ::= { gx2Osw10bAnalogEntry 32}

		osw10bmaxValuePriOpticalThreshold           OBJECT-TYPE
			   SYNTAX           Float
			   ACCESS           read-only
			   STATUS           mandatory
			   DESCRIPTION
			   "The value of this object provides the maximum value
			    the Primary Optical Input Threshold Analog parameter can achive.
			   This value is a floating point number that is represented as an IEEE 32 bit number."
			   ::= { gx2Osw10bAnalogEntry 33}

		osw10balarmStatePriOpticalThreshold         OBJECT-TYPE
			   SYNTAX           INTEGER
									{
									noAlarm(1),
									majorLowAlarm(2),
									minorLowAlarm(3),
									minorHighAlarm(4),
									majorHighAlarm(5),
									informational(6)
									}
			   ACCESS           read-only
			   STATUS           mandatory
			   DESCRIPTION
			   "The value of this object provides the curent alarm state of
			    the Primary Optical Threshold Analog parameter."
			   ::= { gx2Osw10bAnalogEntry 34}

-- New Parameter

		osw10blabelSecOpticalThreshold              OBJECT-TYPE
			   SYNTAX           DisplayString (SIZE (0..80))
			   ACCESS           read-only
			   STATUS           optional
			   DESCRIPTION
			   "The value of this object provides the label of the
			    Secondary Optical Input Threshold Analog parameter."
			   ::= { gx2Osw10bAnalogEntry 35}

		osw10buomSecOpticalThreshold                OBJECT-TYPE
			   SYNTAX           DisplayString (SIZE (0..80))
			   ACCESS           read-only
			   STATUS           optional
			   DESCRIPTION
			   "The value of this object provides the Unit of Measure of the
			    Secondary Optical Input Threshold Analog parameter."
			   ::= { gx2Osw10bAnalogEntry 36}

		osw10bmajorHighSecOpticalThreshold          OBJECT-TYPE
			   SYNTAX           Float 
			   ACCESS           read-only
			   STATUS           mandatory
			   DESCRIPTION
			   "The value of this object provides the Major High alarm value
			    of the Secondary Optical Input Threshold Analog parameter.
			   This value is a floating point number that is represented as an IEEE 32 bit number."
			   ::= { gx2Osw10bAnalogEntry 37}


		osw10bmajorLowSecOpticalThreshold           OBJECT-TYPE
			   SYNTAX           Float 
			   ACCESS           read-only
			   STATUS           mandatory
			   DESCRIPTION
			   "The value of this object provides the Major Low alarm value
			    of the Secondary Optical Input Threshold Analog parameter.
			   This value is a floating point number that is represented as an IEEE 32 bit number."
			   ::= { gx2Osw10bAnalogEntry 38}

		osw10bminorHighSecOpticalThreshold          OBJECT-TYPE
			   SYNTAX           Float
			   ACCESS           read-only
			   STATUS           mandatory
			   DESCRIPTION
			   "The value of this object provides the Minor High alarm value
			    of the Secondary Optical Input Threshold Analog parameter.
			   This value is a floating point number that is represented as an IEEE 32 bit number."
			   ::= { gx2Osw10bAnalogEntry 39}

		osw10bminorLowSecOpticalThreshold           OBJECT-TYPE
			   SYNTAX           Float 
			   ACCESS           read-only
			   STATUS           mandatory
			   DESCRIPTION
			   "The value of this object provides the Minor Low alarm value
			    of the Secondary Optical Input Threshold Analog parameter.
			   This value is a floating point number that is represented as an IEEE 32 bit number."
			   ::= { gx2Osw10bAnalogEntry 40}

		osw10bcurrentValueSecOpticalThreshold       OBJECT-TYPE
			   SYNTAX           Float 
			   ACCESS           read-write
			   STATUS           mandatory
			   DESCRIPTION
			   "The value of this object provides the Current value
			    of the Secondary Optical Input Threshold Analog parameter.
			   This value is a floating point number that is represented as an IEEE 32 bit number."
			   ::= { gx2Osw10bAnalogEntry 41}

		osw10bstateFlagSecOpticalThreshold          OBJECT-TYPE
			   SYNTAX           INTEGER
								{
								hidden(1),
								read-only(2),
								updateable(3)
								}
			   ACCESS           read-only
			   STATUS           mandatory
			   DESCRIPTION
			   "The value of this object provides the state
			    of the Secondary Optical Input Threshold Analog parameter. (0-Hidden	
			          1-Read-Only, 2-Updateable)."
			   ::= { gx2Osw10bAnalogEntry 42}

		osw10bminValueSecOpticalThreshold           OBJECT-TYPE
			   SYNTAX           Float
			   ACCESS           read-only
			   STATUS           mandatory
			   DESCRIPTION
			   "The value of this object provides the minimum value
			    the Secondary Optical Input Threshold Analog parameter can achive.
			   This value is a floating point number that is represented as an IEEE 32 bit number."
			   ::= { gx2Osw10bAnalogEntry 43}

		osw10bmaxValueSecOpticalThreshold           OBJECT-TYPE
			   SYNTAX           Float
			   ACCESS           read-only
			   STATUS           mandatory
			   DESCRIPTION
			   "The value of this object provides the maximum value
			    the Secondary Optical Input Threshold Analog parameter can achive.
			   This value is a floating point number that is represented as an IEEE 32 bit number."
			   ::= { gx2Osw10bAnalogEntry 44}

		osw10balarmStateSecOpticalThreshold         OBJECT-TYPE
			   SYNTAX           INTEGER
									{
									noAlarm(1),
									majorLowAlarm(2),
									minorLowAlarm(3),
									minorHighAlarm(4),
									majorHighAlarm(5),
									informational(6)
									}
			   ACCESS           read-only
			   STATUS           mandatory
			   DESCRIPTION
			   "The value of this object provides the curent alarm state of
			    the Secondary Optical Threshold Analog parameter."
			   ::= { gx2Osw10bAnalogEntry 45}

-- New Parameter

		osw10blabelModTemp              OBJECT-TYPE
			   SYNTAX           DisplayString (SIZE (0..80))
			   ACCESS           read-only
			   STATUS           optional
			   DESCRIPTION
			   "The value of this object provides the label of the
			    Module Temperature Analog parameter."
			   ::= { gx2Osw10bAnalogEntry 46}

		osw10buomModTemp                OBJECT-TYPE
			   SYNTAX           DisplayString (SIZE (0..80))
			   ACCESS           read-only
			   STATUS           optional
			   DESCRIPTION
			   "The value of this object provides the Unit of Measure of the
			    Module Temperature Analog parameter."
			   ::= { gx2Osw10bAnalogEntry 47}

		osw10bmajorHighModTemp          OBJECT-TYPE
			   SYNTAX           Float 
			   ACCESS           read-only
			   STATUS           mandatory
			   DESCRIPTION
			   "The value of this object provides the Major High alarm value
			    of the Module Temperature Analog parameter.
			   This value is a floating point number that is represented as an IEEE 32 bit number."
			   ::= { gx2Osw10bAnalogEntry 48}


		osw10bmajorLowModTemp           OBJECT-TYPE
			   SYNTAX           Float 
			   ACCESS           read-only
			   STATUS           mandatory
			   DESCRIPTION
			   "The value of this object provides the Major Low alarm value
			    of the Module Temperature Analog parameter.
			   This value is a floating point number that is represented as an IEEE 32 bit number."
			   ::= { gx2Osw10bAnalogEntry 49}

		osw10bminorHighModTemp          OBJECT-TYPE
			   SYNTAX           Float
			   ACCESS           read-only
			   STATUS           mandatory
			   DESCRIPTION
			   "The value of this object provides the Minor High alarm value
			    of the Module Temperature Analog parameter.
			   This value is a floating point number that is represented as an IEEE 32 bit number."
			   ::= { gx2Osw10bAnalogEntry 50}

		osw10bminorLowModTemp           OBJECT-TYPE
			   SYNTAX           Float 
			   ACCESS           read-only
			   STATUS           mandatory
			   DESCRIPTION
			   "The value of this object provides the Minor Low alarm value
			    of the Module Temperature Analog parameter.
			   This value is a floating point number that is represented as an IEEE 32 bit number."
			   ::= { gx2Osw10bAnalogEntry 51}

		osw10bcurrentValueModTemp       OBJECT-TYPE
			   SYNTAX           Float 
			   ACCESS           read-only
			   STATUS           mandatory
			   DESCRIPTION
			   "The value of this object provides the Current value
			    of the Module Temperature Analog parameter.
			   This value is a floating point number that is represented as an IEEE 32 bit number."
			   ::= { gx2Osw10bAnalogEntry 52}

		osw10bstateFlagModTemp          OBJECT-TYPE
			   SYNTAX           INTEGER
								{
								hidden(1),
								read-only(2),
								updateable(3)
								}
			   ACCESS           read-only
			   STATUS           mandatory
			   DESCRIPTION
			   "The value of this object provides the state
			    of the Module Temperature Analog parameter. (0-Hidden	
			          1-Read-Only, 2-Updateable)."
			   ::= { gx2Osw10bAnalogEntry 53}

		osw10bminValueModTemp           OBJECT-TYPE
			   SYNTAX           Float
			   ACCESS           read-only
			   STATUS           mandatory
			   DESCRIPTION
			   "The value of this object provides the minimum value
			    the Module Temperature Analog parameter can achive.
			   This value is a floating point number that is represented as an IEEE 32 bit number."
			   ::= { gx2Osw10bAnalogEntry 54}

		osw10bmaxValueModTemp           OBJECT-TYPE
			   SYNTAX           Float
			   ACCESS           read-only
			   STATUS           mandatory
			   DESCRIPTION
			   "The value of this object provides the maximum value
			    the Module Temperature Analog parameter can achive.
			   This value is a floating point number that is represented as an IEEE 32 bit number."
			   ::= { gx2Osw10bAnalogEntry 55}

		osw10balarmStateModTemp         OBJECT-TYPE
			   SYNTAX           INTEGER
									{
									noAlarm(1),
									majorLowAlarm(2),
									minorLowAlarm(3),
									minorHighAlarm(4),
									majorHighAlarm(5),
									informational(6)
									}
			   ACCESS           read-only
			   STATUS           mandatory
			   DESCRIPTION
			   "The value of this object provides the curent alarm state of
			    the Module Temperature Analog parameter."
			   ::= { gx2Osw10bAnalogEntry 56}
-- New Parameter

		osw10blabelFanCurrent           OBJECT-TYPE
			   SYNTAX           DisplayString (SIZE (0..80))
			   ACCESS           read-only
			   STATUS           optional
			   DESCRIPTION
			   "The value of this object provides the label of the
			    Fan Current Analog parameter."
			   ::= { gx2Osw10bAnalogEntry 57}

		osw10buomFanCurrent             OBJECT-TYPE
			   SYNTAX           DisplayString (SIZE (0..80))
			   ACCESS           read-only
			   STATUS           optional
			   DESCRIPTION
			   "The value of this object provides the Unit of Measure of the
			    Fan Current Analog parameter."
			   ::= { gx2Osw10bAnalogEntry 58}

		osw10bmajorHighFanCurrent       OBJECT-TYPE
			   SYNTAX           Float 
			   ACCESS           read-only
			   STATUS           mandatory
			   DESCRIPTION
			   "The value of this object provides the Major High alarm value
			    of the Fan Current Analog parameter.
			   This value is a floating point number that is represented as an IEEE 32 bit number."
			   ::= { gx2Osw10bAnalogEntry 59}


		osw10bmajorLowFanCurrent        OBJECT-TYPE
			   SYNTAX           Float 
			   ACCESS           read-only
			   STATUS           mandatory
			   DESCRIPTION
			   "The value of this object provides the Major Low alarm value
			    of the Fan Current Analog parameter.
			   This value is a floating point number that is represented as an IEEE 32 bit number."
			   ::= { gx2Osw10bAnalogEntry 60}

		osw10bminorHighFanCurrent       OBJECT-TYPE
			   SYNTAX           Float
			   ACCESS           read-only
			   STATUS           mandatory
			   DESCRIPTION
			   "The value of this object provides the Minor High alarm value
			    of the Fan Current Analog parameter.
			   This value is a floating point number that is represented as an IEEE 32 bit number."
			   ::= { gx2Osw10bAnalogEntry 61}

		osw10bminorLowFanCurrent        OBJECT-TYPE
			   SYNTAX           Float 
			   ACCESS           read-only
			   STATUS           mandatory
			   DESCRIPTION
			   "The value of this object provides the Minor Low alarm value
			    of the Fan Current Analog parameter.
			   This value is a floating point number that is represented as an IEEE 32 bit number."
			   ::= { gx2Osw10bAnalogEntry 62}

		osw10bcurrentValueFanCurrent    OBJECT-TYPE
			   SYNTAX           Float 
			   ACCESS           read-only
			   STATUS           mandatory
			   DESCRIPTION
			   "The value of this object provides the Current value
			    of the Fan Current Analog parameter.
			   This value is a floating point number that is represented as an IEEE 32 bit number."
			   ::= { gx2Osw10bAnalogEntry 63}

		osw10bstateFlagFanCurrent       OBJECT-TYPE
			   SYNTAX           INTEGER
								{
								hidden(1),
								read-only(2),
								updateable(3)
								}
			   ACCESS           read-only
			   STATUS           mandatory
			   DESCRIPTION
			   "The value of this object provides the state
			    of the Fan Current Analog parameter. (0-Hidden	
			          1-Read-Only, 2-Updateable)."
			   ::= { gx2Osw10bAnalogEntry 64}

		osw10bminValueFanCurrent        OBJECT-TYPE
			   SYNTAX           Float
			   ACCESS           read-only
			   STATUS           mandatory
			   DESCRIPTION
			   "The value of this object provides the minimum value
			    the Fan Current Analog parameter can achieve.
			   This value is a floating point number that is represented as an IEEE 32 bit number."
			   ::= { gx2Osw10bAnalogEntry 65}

		osw10bmaxValueFanCurrent        OBJECT-TYPE
			   SYNTAX           Float
			   ACCESS           read-only
			   STATUS           mandatory
			   DESCRIPTION
			   "The value of this object provides the maximum value
			    the Fan Current Analog parameter can achieve.
			   This value is a floating point number that is represented as an IEEE 32 bit number."
			   ::= { gx2Osw10bAnalogEntry 66}

        osw10balarmStateFanCurrent      OBJECT-TYPE
			   SYNTAX           INTEGER
									{
									noAlarm(1),
									majorLowAlarm(2),
									minorLowAlarm(3),
									minorHighAlarm(4),
									majorHighAlarm(5),
									informational(6)
									}
			   ACCESS           read-only
			   STATUS           mandatory
			   DESCRIPTION
			   "The value of this object provides the current alarm state of
			    the Fan Current Analog parameter."
			   ::= { gx2Osw10bAnalogEntry 67}

-- ************************ Digital parameters **********************************
		gx2Osw10bDigitalTableIndex              OBJECT-TYPE
			   SYNTAX           INTEGER (1..4294967295)
			   ACCESS           read-only
			   STATUS           mandatory
			   DESCRIPTION
			   "The value of this object identifies the network
			    element. This index is equal to the
			    hfcCommonTableIndex for the same element."
			   ::= { gx2Osw10bDigitalEntry 1}

-- New parameter

		osw10blabelSwitchControl           OBJECT-TYPE
			   SYNTAX       		DisplayString (SIZE (0..80))         
			   ACCESS           	read-only
			   STATUS           	optional
			   DESCRIPTION
			   "The value of this object provides the label of the
			    Switch Control Digital parameter."
			   ::= { gx2Osw10bDigitalEntry 2}

		osw10benumSwitchControl              	OBJECT-TYPE
			   SYNTAX       		DisplayString (SIZE (0..80))         
			   ACCESS           	read-only
			   STATUS           	optional
			   DESCRIPTION
			   "The value of this object represents the Enumeration values
			    possible for the Digital parameter. Each Enumerated values is
			    separated by a common. The first value has a enumerated value of 1."
			   ::= { gx2Osw10bDigitalEntry 3}


		osw10bvalueSwitchControl         	OBJECT-TYPE
			   SYNTAX       		INTEGER
					    		{
							through(1),
							crossover(2)
					    		}
			   ACCESS           	read-write
			   STATUS           	mandatory
			   DESCRIPTION
			   "The value of this object is the current value of the parameter."
			   ::= { gx2Osw10bDigitalEntry 4}

		osw10bstateflagSwitchControl     	OBJECT-TYPE
			   SYNTAX       		INTEGER
								{
								hidden(1),
								read-only(2),
								updateable(3)
								}
			   ACCESS           	read-only
			   STATUS           	mandatory
			   DESCRIPTION
			   "The value of this object provides the state
			    of the the parameter. (0-Hidden 1-Read-Only, 2-Updateable)."
			   ::= { gx2Osw10bDigitalEntry 5}

		osw10blabelSwitchMode           OBJECT-TYPE
			   SYNTAX       		DisplayString (SIZE (0..80))         
			   ACCESS           	read-only
			   STATUS           	optional
			   DESCRIPTION
			   "The value of this object provides the label of the
			    Switch Control Digital parameter."
			   ::= { gx2Osw10bDigitalEntry 6}

		osw10benumSwitchMode              	OBJECT-TYPE
			   SYNTAX       		DisplayString (SIZE (0..80))         
			   ACCESS           	read-only
			   STATUS           	optional
			   DESCRIPTION
			   "The value of this object represents the Enumeration values
			    possible for the Digital parameter. Each Enumerated values is
			    separated by a common. The first value has a enumerated value of 1."
			   ::= { gx2Osw10bDigitalEntry 7}


		osw10bvalueSwitchMode         	OBJECT-TYPE
			   SYNTAX       		INTEGER
					    		{
							automatic(1),
							manual(2)
					    		}
			   ACCESS           	read-write
			   STATUS           	mandatory
			   DESCRIPTION
			   "The value of this object is the current value of the parameter."
			   ::= { gx2Osw10bDigitalEntry 8}

		osw10bstateflagSwitchMode     	OBJECT-TYPE
			   SYNTAX       		INTEGER
								{
								hidden(1),
								read-only(2),
								updateable(3)
								}
			   ACCESS           	read-only
			   STATUS           	mandatory
			   DESCRIPTION
			   "The value of this object provides the state
			    of the parameter. (0-Hidden 1-Read-Only, 2-Updateable)."
			   ::= { gx2Osw10bDigitalEntry 9}


		osw10blabelRevertMode	           OBJECT-TYPE
			   SYNTAX       		DisplayString (SIZE (0..80))         
			   ACCESS           	read-only
			   STATUS           	optional
			   DESCRIPTION
			   "The value of this object provides the label of the
			    Revert Mode Digital parameter."
			   ::= { gx2Osw10bDigitalEntry 10}

		osw10benumRevertMode               	OBJECT-TYPE
			   SYNTAX       		DisplayString (SIZE (0..80))         
			   ACCESS           	read-only
			   STATUS           	optional
			   DESCRIPTION
			   "The value of this object represents the Enumeration values
			    possible for the Digital parameter. Each Enumerated values is
			    separated by a common. The first value has a enumerated value of 1."
			   ::= { gx2Osw10bDigitalEntry 11}


		osw10bvalueRevertMode         	OBJECT-TYPE
			   SYNTAX       		INTEGER
					    		{
							off(1),
							on(2)
					    		}
			   ACCESS           	read-write
			   STATUS           	mandatory
			   DESCRIPTION
			   "The value of this object is the current value of the parameter."
			   ::= { gx2Osw10bDigitalEntry 12}

		osw10bstateflagRevertMode     	OBJECT-TYPE
			   SYNTAX       		INTEGER
								{
								hidden(1),
								read-only(2),
								updateable(3)
								}
			   ACCESS           	read-only
			   STATUS           	mandatory
			   DESCRIPTION
			   "The value of this object provides the state
			    of the the parameter. (0-Hidden 1-Read-Only, 2-Updateable)."
			   ::= { gx2Osw10bDigitalEntry 13}

		osw10blabelRevertTime	     		OBJECT-TYPE
			   SYNTAX       		DisplayString (SIZE (0..80))         
			   ACCESS           	read-only
			   STATUS           	optional
			   DESCRIPTION
			   "The value of this object provides the label of the
			    Revert Time Digital parameter."
			   ::= { gx2Osw10bDigitalEntry 14}

		osw10benumRevertTime               	OBJECT-TYPE
			   SYNTAX       		DisplayString (SIZE (0..80))         
			   ACCESS           	read-only
			   STATUS           	optional
			   DESCRIPTION
			   "The value of this object represents the Enumeration values
			    possible for the Digital parameter. Each Enumerated values is
			    separated by a common. The first value has a enumerated value of 1."
			   ::= { gx2Osw10bDigitalEntry 15}


		osw10bvalueRevertTime         	OBJECT-TYPE
			   SYNTAX       		INTEGER
					    		{
							tensec(1),
							sixtysec(2),
							sixhundredsec(3)
					    		}
			   ACCESS           	read-write
			   STATUS           	mandatory
			   DESCRIPTION
			   "The value of this object is the current value of the parameter."
			   ::= { gx2Osw10bDigitalEntry 16}

		osw10bstateflagRevertTime     	OBJECT-TYPE
			   SYNTAX       		INTEGER
								{
								hidden(1),
								read-only(2),
								updateable(3)
								}
			   ACCESS           	read-only
			   STATUS           	mandatory
			   DESCRIPTION
			   "The value of this object provides the state
			    of the the parameter. (0-Hidden 1-Read-Only, 2-Updateable)."
			   ::= { gx2Osw10bDigitalEntry 17}

		osw10blabelWavelength	     		OBJECT-TYPE
			   SYNTAX       		DisplayString (SIZE (0..80))         
			   ACCESS           	read-only
			   STATUS           	optional
			   DESCRIPTION
			   "The value of this object provides the label of the
			    Wavelength Digital parameter."
			   ::= { gx2Osw10bDigitalEntry 18}

		osw10benumWavelength               	OBJECT-TYPE
			   SYNTAX       		DisplayString (SIZE (0..80))         
			   ACCESS           	read-only
			   STATUS           	optional
			   DESCRIPTION
			   "The value of this object represents the Enumeration values
			    possible for the Digital parameter. Each Enumerated values is
			    separated by a common. The first value has a enumerated value of 1."
			   ::= { gx2Osw10bDigitalEntry 19}


		osw10bvalueWavelength         	OBJECT-TYPE
			   SYNTAX       		INTEGER
					    		{
							    thirteentennm(1),
							    fifteenfiftynnm(2)
					    		}
			   ACCESS           	read-write
			   STATUS           	mandatory
			   DESCRIPTION
			   "The value of this object is the current value of the parameter."
			   ::= { gx2Osw10bDigitalEntry 20}

		osw10bstateflagWavelength     	OBJECT-TYPE
			   SYNTAX       		INTEGER
								{
								hidden(1),
								read-only(2),
								updateable(3)
								}
			   ACCESS           	read-only
			   STATUS           	mandatory
			   DESCRIPTION
			   "The value of this object provides the state
			    of the the parameter. (0-Hiden 1-Read-Only, 2-Updateable)."
			   ::= { gx2Osw10bDigitalEntry 21}

		osw10blabelSwitchMonitor	           OBJECT-TYPE
			   SYNTAX       		DisplayString (SIZE (0..80))         
			   ACCESS           	read-only
			   STATUS           	optional
			   DESCRIPTION
			   "The value of this object provides the label of the
			    Switch State Digital parameter."
			   ::= { gx2Osw10bDigitalEntry 22}

		osw10benumSwitchMonitor               	OBJECT-TYPE
			   SYNTAX       		DisplayString (SIZE (0..80))         
			   ACCESS           	read-only
			   STATUS           	optional
			   DESCRIPTION
			   "The value of this object represents the Enumeration values
			    possible for the Digital parameter. Each Enumerated values is
			    separated by a common. The first value has a enumerated value of 1."
			   ::= { gx2Osw10bDigitalEntry 23}


		osw10bvalueSwitchMonitor         	OBJECT-TYPE
			   SYNTAX       		INTEGER
					    		{
							through(1),
							crossover(2)
					    		}
			   ACCESS           	read-only
			   STATUS           	mandatory
			   DESCRIPTION
			   "The value of this object is the current value of the parameter."
			   ::= { gx2Osw10bDigitalEntry 24}

		osw10bstateflagSwitchMonitor     	OBJECT-TYPE
			   SYNTAX       		INTEGER
								{
								hidden(1),
								read-only(2),
								updateable(3)
								}
			   ACCESS           	read-only
			   STATUS           	mandatory
			   DESCRIPTION
			   "The value of this object provides the state
			    of the parameter. (0-Hidden 1-Read-Only, 2-Updateable)."
			   ::= { gx2Osw10bDigitalEntry 25}

		osw10blabelOperationMode	           OBJECT-TYPE
			   SYNTAX       		DisplayString (SIZE (0..80))         
			   ACCESS           	read-only
			   STATUS           	optional
			   DESCRIPTION
			   "The value of this object provides the label of the
			    Switch State Digital parameter."
			   ::= { gx2Osw10bDigitalEntry 26}

		osw10benumOperationMode               	OBJECT-TYPE
			   SYNTAX       		DisplayString (SIZE (0..80))         
			   ACCESS           	read-only
			   STATUS           	optional
			   DESCRIPTION
			   "The value of this object represents the Enumeration values
			    possible for the Digital parameter. Each Enumerated values is
			    separated by a common. The first value has a enumerated value of 1."
			   ::= { gx2Osw10bDigitalEntry 27}


		osw10bvalueOperationMode         	OBJECT-TYPE
			   SYNTAX       		INTEGER
					    		{
							mode2x1(1),
							mode1x2(2),
							mode2x2(3)
					    		}
			   ACCESS           	read-write
			   STATUS           	mandatory
			   DESCRIPTION
			   "The value of this object is the current value of the parameter."
			   ::= { gx2Osw10bDigitalEntry 28}

		osw10bstateflagOperationMode     	OBJECT-TYPE
			   SYNTAX       		INTEGER
								{
								hidden(1),
								read-only(2),
								updateable(3)
								}
			   ACCESS           	read-only
			   STATUS           	mandatory
			   DESCRIPTION
			   "The value of this object provides the state
			    of the parameter. (0-Hidden 1-Read-Only, 2-Updateable)."
			   ::= { gx2Osw10bDigitalEntry 29}


		osw10blabelFactoryDefault           OBJECT-TYPE
			   SYNTAX       		DisplayString (SIZE (0..80))         
			   ACCESS           	read-only
			   STATUS           	optional
			   DESCRIPTION
			   "The value of this object provides the label of the
			    Factory Default Reset  Digital parameter."
			   ::= { gx2Osw10bDigitalEntry 30}

		osw10benumFactoryDefault               	OBJECT-TYPE
			   SYNTAX       		DisplayString (SIZE (0..80))         
			   ACCESS           	read-only
			   STATUS           	optional
			   DESCRIPTION
			   "The value of this object represents the Enumeration values
			    possible for the Digital parameter. Each Enumerated values is
			    separated by a common. The first value has a enumerated value of 1."
			   ::= { gx2Osw10bDigitalEntry 31}


		osw10bvalueFactoryDefault         	OBJECT-TYPE
			   SYNTAX       		INTEGER
					    		{
							off(1),
							on(2)
					    		}
			   ACCESS           	read-write
			   STATUS           	mandatory
			   DESCRIPTION
			   "The value of this object is the current value of the parameter."
			   ::= { gx2Osw10bDigitalEntry 32}

		osw10bstateflagFactoryDefault     	OBJECT-TYPE
			   SYNTAX       		INTEGER
								{
								hidden(1),
								read-only(2),
								updateable(3)
								}
			   ACCESS           	read-only
			   STATUS           	mandatory
			   DESCRIPTION
			   "The value of this object provides the state
			    of the the parameter. (0-Hidden 1-Read-Only, 2-Updateable)."
			   ::= { gx2Osw10bDigitalEntry 33}


		--*********** STATUS *****************
		gx2Osw10bStatusTableIndex              OBJECT-TYPE
			   SYNTAX           INTEGER (1..4294967295)
			   ACCESS           read-only
			   STATUS           mandatory
			   DESCRIPTION
			   "The value of this object identifies the network
			    element. This index is equal to the
			    hfcCommonTableIndex for the same element."
			   ::= { gx2Osw10bStatusEntry 1}

--New Parameter
		osw10blabelBoot               	OBJECT-TYPE
			   SYNTAX       		DisplayString (SIZE (0..80))         
			   ACCESS           	read-only
			   STATUS           	optional
			   DESCRIPTION
			   "The value of this object provides the label of the
			    Boot Status parameter."
			   ::= { gx2Osw10bStatusEntry 2}

		osw10bvalueBoot              		OBJECT-TYPE
			   SYNTAX       		INTEGER
									{
									ok(1),
									undetermined(2),
									warning(3),
									minor(4),
									major(5),
									critical(6)
									}
			   ACCESS           	read-only
			   STATUS           	mandatory
			   DESCRIPTION
			   "The value of this object provides the current state of
			    the parameter (0-Ok, 1-Undetermined
			    2-Warning, 3-Minor, 4-Major, 5-Critical)."
			   ::= { gx2Osw10bStatusEntry 3}

		osw10bstateflagBoot     	OBJECT-TYPE
			   SYNTAX       		INTEGER
								{
								hidden(1),
								read-only(2),
								updateable(3)
								}
			   ACCESS           	read-only
			   STATUS           	mandatory
			   DESCRIPTION
			   "The value of this object provides the state
			    of the the parameter. (0-Hidden 1-Read-Only, 2-Updateable)."
			   ::= { gx2Osw10bStatusEntry  4}



--New Parameter
		osw10blabelFlash               	OBJECT-TYPE
			   SYNTAX       		DisplayString (SIZE (0..80))         
			   ACCESS           	read-only
			   STATUS           	optional
			   DESCRIPTION
			   "The value of this object provides the label of the
			    Flash Status parameter."
			   ::= { gx2Osw10bStatusEntry 5}

		osw10bvalueFlash              	OBJECT-TYPE
			   SYNTAX       		INTEGER
									{
									ok(1),
									undetermined(2),
									warning(3),
									minor(4),
									major(5),
									critical(6)
									}
			   ACCESS           	read-only
			   STATUS           	mandatory
			   DESCRIPTION
			   "The value of this object provides the current state of
			    the parameter (0-Ok, 1-Undetermined
			    2-Warning, 3-Minor, 4-Major, 5-Critical)."
			   ::= { gx2Osw10bStatusEntry 6}

		osw10bstateflagFlash     	OBJECT-TYPE
			   SYNTAX       		INTEGER
								{
								hidden(1),
								read-only(2),
								updateable(3)
								}
			   ACCESS           	read-only
			   STATUS           	mandatory
			   DESCRIPTION
			   "The value of this object provides the state
			    of the parameter. (0-Hidden 1-Read-Only, 2-Updateable)."
			   ::= { gx2Osw10bStatusEntry  7}

--New Parameter
		osw10blabelFactoryDataCRC           OBJECT-TYPE
			   SYNTAX       		DisplayString (SIZE (0..80))         
			   ACCESS           	read-only
			   STATUS           	optional
			   DESCRIPTION
			   "The value of this object provides the label of the
			    Factory Data CRC Status parameter."
			   ::= { gx2Osw10bStatusEntry 8}

		osw10bvalueFactoryDataCRC          	OBJECT-TYPE
			   SYNTAX       		INTEGER
									{
									ok(1),
									undetermined(2),
									warning(3),
									minor(4),
									major(5),
									critical(6)
									}
			   ACCESS           	read-only
			   STATUS           	mandatory
			   DESCRIPTION
			   "The value of this object provides the current state of
			    the parameter (0-Ok, 1-Undetermined
			    2-Warning, 3-Minor, 4-Major, 5-Critical)."
			   ::= { gx2Osw10bStatusEntry 9}

		osw10bstateflagFactoryDataCRC     	OBJECT-TYPE
			   SYNTAX       		INTEGER
								{
								hidden(1),
								read-only(2),
								updateable(3)
								}
			   ACCESS           	read-only
			   STATUS           	mandatory
			   DESCRIPTION
			   "The value of this object provides the state
			    of the parameter. (0-Hidden 1-Read-Only, 2-Updateable)."
			   ::= { gx2Osw10bStatusEntry  10}

--Calibration table invalid 
		osw10blabelCalibrateTableStatus           OBJECT-TYPE
			   SYNTAX       		DisplayString (SIZE (0..80))         
			   ACCESS           	read-only
			   STATUS           	optional
			   DESCRIPTION
			   "The value of this object provides the label of optical input calibration table status description"
			   ::= { gx2Osw10bStatusEntry 11}

		osw10bvalueCalibrateTableStatus         	OBJECT-TYPE
			   SYNTAX       		INTEGER
									{
									ok(1),
									undetermined(2),
									warning(3),
									minor(4),
									major(5),
									critical(6)
									}
			   ACCESS           	read-only
			   STATUS           	mandatory
			   DESCRIPTION
			   "The value of this object provides the current state of
			    the parameter (0-Ok, 1-Undetermined
			    2-Warning, 3-Minor, 4-Major, 5-Critical)."
			   ::= { gx2Osw10bStatusEntry 12}

		osw10bstateflagCalibrateTableStatus     	OBJECT-TYPE
			   SYNTAX       		INTEGER
								{
								hidden(1),
								read-only(2),
								updateable(3)
								}
			   ACCESS           	read-only
			   STATUS           	mandatory
			   DESCRIPTION
			   "The value of this object provides the state
			    of the parameter. (0-Hidden 1-Read-Only, 2-Updateable)."
			   ::= { gx2Osw10bStatusEntry  13}

--Alarm data CRC
		osw10blabelAlarmDataCrc               	      OBJECT-TYPE
			   SYNTAX       		DisplayString (SIZE (0..80))         
			   ACCESS           	read-only
			   STATUS           	optional
			   DESCRIPTION
			   "The value of this object provides the label of the
			    Alarm Data Crc parameter."
			   ::= { gx2Osw10bStatusEntry 14}

		osw10bvalueAlarmDataCrc              		OBJECT-TYPE
			   SYNTAX       		INTEGER
									{
									ok(1),
									undetermined(2),
									warning(3),
									minor(4),
									major(5),
									critical(6)
									}
			   ACCESS           	read-only
			   STATUS           	mandatory
			   DESCRIPTION
			   "The value of this object provides the current state of
			    the parameter (0-Ok, 1-Undetermined
			    2-Warning, 3-Minor, 4-Major, 5-Critical)."
			   ::= { gx2Osw10bStatusEntry 15}

		osw10bstateflagAlarmDataCrc     	OBJECT-TYPE
			   SYNTAX       		INTEGER
								{
								hidden(1),
								read-only(2),
								updateable(3)
								}
			   ACCESS           	read-only
			   STATUS           	mandatory
			   DESCRIPTION
			   "The value of this object provides the state
			    of the parameter. (0-Hidden 1-Read-Only, 2-Updateable)."
			   ::= { gx2Osw10bStatusEntry  16}

--New Parameter // this status has been replaced by sec input threshold status and pri input threshold status
-- So Mibs Rev. B after, shall be obsolete. 
		osw10blabelInputStatus              OBJECT-TYPE
			   SYNTAX       		DisplayString (SIZE (0..80))         
			   ACCESS           	read-only
			   STATUS           	obsolete
			   DESCRIPTION
			   "The value of this object provides the label of the
			    Input Status parameter."
			   ::= { gx2Osw10bStatusEntry 17}

		osw10bvalueInputStatus              OBJECT-TYPE
			   SYNTAX       		INTEGER
									{
									ok(1),
									undetermined(2),
									warning(3),
									minor(4),
									major(5),
									critical(6)
									}
			   ACCESS           	read-only
			   STATUS           	obsolete
			   DESCRIPTION
			   "The value of this object provides the current state of
			    the parameter (0-Ok, 1-Undetermined
			    2-Warning, 3-Minor, 4-Major, 5-Critical)."
			   ::= { gx2Osw10bStatusEntry 18}

		osw10bstateflagInputStatus     	OBJECT-TYPE
			   SYNTAX       		INTEGER
								{
								hidden(1),
								read-only(2),
								updateable(3)
								}
			   ACCESS           	read-only
			   STATUS           	obsolete
			   DESCRIPTION
			   "The value of this object provides the state
			    of the parameter. (0-Hidden 1-Read-Only, 2-Updateable)."
			   ::= { gx2Osw10bStatusEntry  19}

--New Parameter
		osw10blabelPriActiveStatus              OBJECT-TYPE
			   SYNTAX       		DisplayString (SIZE (0..80))         
			   ACCESS           	read-only
			   STATUS           	optional
			   DESCRIPTION
			   "The value of this object provides the label of the
			    Primary Active Status parameter."
			   ::= { gx2Osw10bStatusEntry 20}

		osw10bvaluePriActiveStatus              OBJECT-TYPE
			   SYNTAX       		INTEGER
									{
									ok(1),
									undetermined(2),
									warning(3),
									minor(4),
									major(5),
									critical(6)
									}
			   ACCESS           	read-only
			   STATUS           	mandatory
			   DESCRIPTION
			   "The value of this object provides the current state of
			    the parameter (0-Ok, 1-Undetermined
			    2-Warning, 3-Minor, 4-Major, 5-Critical)."
			   ::= { gx2Osw10bStatusEntry 21}

		osw10bstateflagPriActiveStatus     	OBJECT-TYPE
			   SYNTAX       		INTEGER
								{
								hidden(1),
								read-only(2),
								updateable(3)
								}
			   ACCESS           	read-only
			   STATUS           	mandatory
			   DESCRIPTION
			   "The value of this object provides the state
			    of the parameter. (0-Hidden 1-Read-Only, 2-Updateable)."
			   ::= { gx2Osw10bStatusEntry  22}

--Hardware error 

		osw10blabelHardwareErr                   OBJECT-TYPE
			   SYNTAX       		DisplayString (SIZE (0..80))         
			   ACCESS           	read-only
			   STATUS           	optional
			   DESCRIPTION
			   "The value of this object provides the label of the
			    Primary Active Status parameter."
			   ::= { gx2Osw10bStatusEntry 23}

		osw10bvalueHardwareErr                   OBJECT-TYPE
			   SYNTAX       		INTEGER
									{
									ok(1),
									undetermined(2),
									warning(3),
									minor(4),
									major(5),
									critical(6)
									}
			   ACCESS           	read-only
			   STATUS           	mandatory
			   DESCRIPTION
			   "The value of this object provides the current state of
			    the parameter (0-Ok, 1-Undetermined
			    2-Warning, 3-Minor, 4-Major, 5-Critical)."
			   ::= { gx2Osw10bStatusEntry 24}

		osw10bstateflagHardwareErr     	OBJECT-TYPE
			   SYNTAX       		INTEGER
								{
								hidden(1),
								read-only(2),
								updateable(3)
								}
			   ACCESS           	read-only
			   STATUS           	mandatory
			   DESCRIPTION
			   "The value of this object provides the state
			    of the parameter. (0-Hidden 1-Read-Only, 2-Updateable)."
			   ::= { gx2Osw10bStatusEntry  25}


--New Parameter
		osw10blabelPriThresholdStatus              OBJECT-TYPE
			   SYNTAX       		DisplayString (SIZE (0..80))         
			   ACCESS           	read-only
			   STATUS           	optional
			   DESCRIPTION
			   "The value of this object provides the label of the
			    Primary Input Below The Threshold Status parameter."
			   ::= { gx2Osw10bStatusEntry 26}

		osw10bvaluePriThresholdStatus              OBJECT-TYPE
			   SYNTAX       		INTEGER
									{
									ok(1),
									undetermined(2),
									warning(3),
									minor(4),
									major(5),
									critical(6)
									}
			   ACCESS           	read-only
			   STATUS           	mandatory
			   DESCRIPTION
			   "The value of this object provides the current state of
			    the parameter (0-Ok, 1-Undetermined
			    2-Warning, 3-Minor, 4-Major, 5-Critical)."
			   ::= { gx2Osw10bStatusEntry 27}

		osw10bstateflagPriThresholdStatus     	OBJECT-TYPE
			   SYNTAX       		INTEGER
								{
								hidden(1),
								read-only(2),
								updateable(3)
								}
			   ACCESS           	read-only
			   STATUS           	mandatory
			   DESCRIPTION
			   "The value of this object provides the state
			    of the parameter. (0-Hidden 1-Read-Only, 2-Updateable)."
			   ::= { gx2Osw10bStatusEntry  28}

--New Parameter
		osw10blabelSecThresholdStatus              OBJECT-TYPE
			   SYNTAX       		DisplayString (SIZE (0..80))         
			   ACCESS           	read-only
			   STATUS           	optional
			   DESCRIPTION
			   "The value of this object provides the label of the
			    Primary Input Below The Threshold Status parameter."
			   ::= { gx2Osw10bStatusEntry 29}

		osw10bvalueSecThresholdStatus              OBJECT-TYPE
			   SYNTAX       		INTEGER
									{
									ok(1),
									undetermined(2),
									warning(3),
									minor(4),
									major(5),
									critical(6)
									}
			   ACCESS           	read-only
			   STATUS           	mandatory
			   DESCRIPTION
			   "The value of this object provides the current state of
			    the parameter (0-Ok, 1-Undetermined
			    2-Warning, 3-Minor, 4-Major, 5-Critical)."
			   ::= { gx2Osw10bStatusEntry 30}

		osw10bstateflagSecThresholdStatus     	OBJECT-TYPE
			   SYNTAX       		INTEGER
								{
								hidden(1),
								read-only(2),
								updateable(3)
								}
			   ACCESS           	read-only
			   STATUS           	mandatory
			   DESCRIPTION
			   "The value of this object provides the state
			    of the parameter. (0-Hidden 1-Read-Only, 2-Updateable)."
			   ::= { gx2Osw10bStatusEntry  31}



            -- ************ FACTORY DATA ****************
		gx2Osw10bFactoryTableIndex              OBJECT-TYPE
			   SYNTAX           INTEGER (1..4294967295)
			   ACCESS           read-only
			   STATUS           mandatory
			   DESCRIPTION
			   "The value of this object identifies the network
			    element. This index is equal to the
			    hfcCommonTableIndex for the same element."
			   ::= { gx2Osw10bFactoryEntry 1}

		osw10bbootControlByte          	OBJECT-TYPE
			   SYNTAX       		INTEGER
			   ACCESS           	read-only
			   STATUS           	mandatory
			   DESCRIPTION
			   "The value of this object indicates which bank the firmware
			    is currently being boot from."
			   ::= { gx2Osw10bFactoryEntry 2}

		osw10bbootStatusByte          	OBJECT-TYPE
			   SYNTAX       		INTEGER
			   ACCESS           	read-only
			   STATUS           	mandatory
			   DESCRIPTION
			   "This object indicates the status of the last boot"
			   ::= { gx2Osw10bFactoryEntry 3}

		osw10bbank1CRC          		OBJECT-TYPE
			   SYNTAX       		INTEGER
			   ACCESS           	read-only
			   STATUS           	mandatory
			   DESCRIPTION
			   "This object provides the CRC code of bank 0."
			   ::= { gx2Osw10bFactoryEntry 4}

		osw10bbank2CRC          		OBJECT-TYPE
			   SYNTAX       		INTEGER
			   ACCESS           	read-only
			   STATUS           	mandatory
			   DESCRIPTION
			   "This object provides the CRC code of bank 1."
			   ::= { gx2Osw10bFactoryEntry 5}

		osw10bprgEEPROMByte          		OBJECT-TYPE
			   SYNTAX       		INTEGER
			   ACCESS           	read-only
			   STATUS           	mandatory
			   DESCRIPTION
			   "This object indicates if the EEPROM has been programmed"
			   ::= { gx2Osw10bFactoryEntry 6}

		osw10bfactoryCRC          		OBJECT-TYPE
			   SYNTAX       		INTEGER
			   ACCESS           	read-only
			   STATUS           	mandatory
			   DESCRIPTION
			   "This object provides the CRC code for the Factory data."
			   ::= { gx2Osw10bFactoryEntry 7}

		osw10bcalculateCRC          		OBJECT-TYPE
			   SYNTAX       		INTEGER
					    		{
							factory(1),
                                          calTable(2),
							alarm(3),
							na(4)
					    		}
			   ACCESS           	read-only
			   STATUS           	mandatory
			   DESCRIPTION
			   "This object indicates which of the Enums will have the CRC calculated."
			   ::= { gx2Osw10bFactoryEntry 8}

		osw10bhourMeter          		OBJECT-TYPE
			   SYNTAX       		INTEGER
			   ACCESS           	read-only
			   STATUS           	mandatory
			   DESCRIPTION
			   "This object provides the hour meter reading of the module."
			   ::= { gx2Osw10bFactoryEntry 9}

		osw10bflashPrgCntA          		OBJECT-TYPE
			   SYNTAX       		INTEGER
			   ACCESS           	read-only
			   STATUS           	mandatory
			   DESCRIPTION
			   "This object provides the number of times Bank 1 flash has been 
                      programmed."
			   ::= { gx2Osw10bFactoryEntry 10}

		osw10bflashPrgCntB          		OBJECT-TYPE
			   SYNTAX       		INTEGER
			   ACCESS           	read-only
			   STATUS           	mandatory
			   DESCRIPTION
			   "This object provides the number of times Bank 1 flash has been 
                      programmed."
			   ::= { gx2Osw10bFactoryEntry 11}

		osw10bflashBankARev          		OBJECT-TYPE
			   SYNTAX       		DisplayString (SIZE (0..80))
			   ACCESS           	read-only
			   STATUS           	mandatory
			   DESCRIPTION
			   "This object provides the revision of flash bank 0."
			   ::= { gx2Osw10bFactoryEntry 12}

		osw10bflashBankBRev          		OBJECT-TYPE
			   SYNTAX       		DisplayString (SIZE (0..80))
			   ACCESS           	read-only
			   STATUS           	mandatory
			   DESCRIPTION
			   "This object provides the revision of flash bank 1."
			   ::= { gx2Osw10bFactoryEntry 13}



            -- ************ Hold Time DATA ****************
		rxgx2Osw10bHoldTimeTableIndex              OBJECT-TYPE
			   SYNTAX           INTEGER (1..4294967295)
			   ACCESS           read-only
			   STATUS           mandatory
			   DESCRIPTION
			   "The value of this object is the index of the data object."
			   ::= { gx2Osw10bHoldTimeEntry 1}

		rxgx2Osw10bHoldTimeSpecIndex              OBJECT-TYPE
			   SYNTAX           INTEGER (1..4294967295)
			   ACCESS           read-only
			   STATUS           mandatory
			   DESCRIPTION
			   "The value of this object identifies the index of the alarm object to be modified."
			   ::= { gx2Osw10bHoldTimeEntry 2}

		rxgx2Osw10bHoldTimeData          	OBJECT-TYPE
			   SYNTAX       		INTEGER
			   ACCESS           	read-write
			   STATUS           	mandatory
			   DESCRIPTION
			   "The value of this object provides access to the hold timers used 
			   to suppress nose on analog objects. This object is a 32 bit object. 
			   Validation data is entered into bytes zero and one of the object. 
			   Bytes three and four are used to entering the hold time for the 
			   specified alarm object. The Hold timer data ranges from 0 to 1300 seconds.
			   The index of this object corresponds to the alarm object to be modified. 
			   Alarm Hold timers correspond to the index of this object as follows:  
			   Index 1 = xxx, index 2 = xxxx, Index 3 = xxxx, 
			   The hold time is represented in seconds."
			   ::= { gx2Osw10bHoldTimeEntry 3}

-- ****************************************************************
--
-- TRAP DEFINITIONS
--
--
-- Every trap generated by an HFC agents will include first 9 identical
-- fields. If particular variable is not supported in
-- particular TRAP-TYPE then default value will be returned.
--
-- DESCRIPTION will include explanation of use of generic
-- variables (trapAdditionalInfo******.)  If no
-- DESCRIPTION is given then generic variables will contain
-- default values.
--
-- *****************************************************************

--***************************************************************************
-- ***********!!! THE TRAP SECTION HAS NOT BEEN COMPLETED YET !!! ***********
--***************************************************************************

-- **************************************************************************
--                              Optical Switch Module traps
-- **************************************************************************
   trapOSW10BConfigChangeInteger TRAP-TYPE
       ENTERPRISE gx2Osw10b
       VARIABLES
	       {       
		trapIdentifier,
		trapNetworkElemModelNumber,
		trapNetworkElemSerialNum,
		trapPerceivedSeverity,
		trapNetworkElemOperState,
		trapNetworkElemAlarmStatus,  
		trapNetworkElemAdminState,
		trapNetworkElemAvailStatus,
		trapText,
		trapChangedObjectId,
		trapChangedValueInteger,
		trapNETrapLastTrapTimeStamp
	       }
       DESCRIPTION
	"This trap is issued if configuration of a single variable
	 with integer type was changed (via ANY interface).  
	 TrapChangedValueInteger variable may contain current reading
	 of that variable.
	 trapPerceivedSeverity - 'indeterminate'"
  ::= 1

   trapOSW10BConfigChangeDisplayString TRAP-TYPE
       ENTERPRISE gx2Osw10b
       VARIABLES
	       {       
		trapIdentifier,
		trapNetworkElemModelNumber,
		trapNetworkElemSerialNum,
		trapPerceivedSeverity,
		trapNetworkElemOperState,
		trapNetworkElemAlarmStatus,  
		trapNetworkElemAdminState,
		trapNetworkElemAvailStatus,
		trapText,
		trapChangedObjectId,
		trapChangedValueDisplayString,
		trapNETrapLastTrapTimeStamp
	       }
       DESCRIPTION
	"This trap is issued if configuration of a single variable
	 with DispalayString type was changed (via ANY interface).  
	 TrapChangedValueDisplayString variable may contain current reading
	 of that variable.
	 trapPerceivedSeverity - 'indeterminate'"
  ::= 2

  trapOSW10BOpticalInputAlarm TRAP-TYPE
	ENTERPRISE gx2Osw10b
	VARIABLES
		{       
		 trapIdentifier,
		 trapNetworkElemModelNumber,
		 trapNetworkElemSerialNum,
		 trapPerceivedSeverity,
		 trapNetworkElemOperState,
		 trapNetworkElemAlarmStatus,  
		 trapNetworkElemAdminState,
		 trapNetworkElemAvailStatus,
		 trapText,
		 trapChangedObjectId,
		 trapChangedValueInteger,
		 trapNETrapLastTrapTimeStamp
		}
	DESCRIPTION
	"This trap is issued when the Switch Control signals 
	 go out of range.
	 trapAdditionalInfoInteger variable contains current reading of 
	 this parameter."
  ::= 3
  
  trapOSW10BFanCurrentAlarm TRAP-TYPE
	ENTERPRISE gx2Osw10b
	VARIABLES
		{       
		 trapIdentifier,
		 trapNetworkElemModelNumber,
		 trapNetworkElemSerialNum,
		 trapPerceivedSeverity,
		 trapNetworkElemOperState,
		 trapNetworkElemAlarmStatus,  
		 trapNetworkElemAdminState,
		 trapNetworkElemAvailStatus,
		 trapText,
		 trapChangedObjectId,
		 trapChangedValueInteger,
		 trapNETrapLastTrapTimeStamp
		}
	DESCRIPTION
	"This trap is issued when the Fan Current 
	 parameter goes out of range.
	 trapAdditionalInfoInteger variable contains current reading of 
	 the this parameter."
  ::= 4

  trapOSW10BModuleTempAlarm TRAP-TYPE
	ENTERPRISE gx2Osw10b
	VARIABLES
		{       
		 trapIdentifier,
		 trapNetworkElemModelNumber,
		 trapNetworkElemSerialNum,
		 trapPerceivedSeverity,
		 trapNetworkElemOperState,
		 trapNetworkElemAlarmStatus,  
		 trapNetworkElemAdminState,
		 trapNetworkElemAvailStatus,
		 trapText,
		 trapChangedObjectId,
		 trapChangedValueInteger,
		 trapNETrapLastTrapTimeStamp
		}
	DESCRIPTION
	"This trap is issued when the Temperature goes out of range.
	 trapAdditionalInfoInteger variable contains current reading of 
	 the this parameter."
  ::= 5

  trapOSW10BFlashAlarm TRAP-TYPE
	ENTERPRISE gx2Osw10b
	VARIABLES
		{       
		 trapIdentifier,
		 trapNetworkElemModelNumber,
		 trapNetworkElemSerialNum,
		 trapPerceivedSeverity,
		 trapNetworkElemOperState,
		 trapNetworkElemAlarmStatus,  
		 trapNetworkElemAdminState,
		 trapNetworkElemAvailStatus,
		 trapText,
		 trapChangedObjectId,
		 trapChangedValueInteger,
		 trapNETrapLastTrapTimeStamp
		}
	DESCRIPTION
	"This trap is issued when the detects an error during
	Flash memory operations."
  ::= 6

  trapOSW10BBankBootAlarm TRAP-TYPE
	ENTERPRISE gx2Osw10b
	VARIABLES
		{       
		 trapIdentifier,
		 trapNetworkElemModelNumber,
		 trapNetworkElemSerialNum,
		 trapPerceivedSeverity,
		 trapNetworkElemOperState,
		 trapNetworkElemAlarmStatus,  
		 trapNetworkElemAdminState,
		 trapNetworkElemAvailStatus,
		 trapText,
		 trapChangedObjectId,
		 trapChangedValueInteger,
		 trapNETrapLastTrapTimeStamp
		}
	DESCRIPTION
	"This trap is issued when the detects an error while booting
	from bank 0 or bank 1."
  ::= 7

	trapOSW10BCaliDataCRCAlarm TRAP-TYPE
	ENTERPRISE gx2Osw10b
	VARIABLES
		{       
		 trapIdentifier,
		 trapNetworkElemModelNumber,
		 trapNetworkElemSerialNum,
		 trapPerceivedSeverity,
		 trapNetworkElemOperState,
		 trapNetworkElemAlarmStatus,  
		 trapNetworkElemAdminState,
		 trapNetworkElemAvailStatus,
		 trapText,
		 trapChangedObjectId,
		 trapChangedValueInteger,
		 trapNETrapLastTrapTimeStamp
		}
	DESCRIPTION
	"This trap is issued when the optical calibration table corrupted."
  ::= 8

	trapOSW10BFactoryDataCRCAlarm TRAP-TYPE
	ENTERPRISE gx2Osw10b
	VARIABLES
		{       
		 trapIdentifier,
		 trapNetworkElemModelNumber,
		 trapNetworkElemSerialNum,
		 trapPerceivedSeverity,
		 trapNetworkElemOperState,
		 trapNetworkElemAlarmStatus,  
		 trapNetworkElemAdminState,
		 trapNetworkElemAvailStatus,
		 trapText,
		 trapChangedObjectId,
		 trapChangedValueInteger,
		 trapNETrapLastTrapTimeStamp
		}
	DESCRIPTION
	"This trap is issued when the Factory Data CRC is incorrect."
  ::= 9

	trapOSW10BAlarmDataCRCAlarm TRAP-TYPE
	ENTERPRISE gx2Osw10b
	VARIABLES
		{       
		 trapIdentifier,
		 trapNetworkElemModelNumber,
		 trapNetworkElemSerialNum,
		 trapPerceivedSeverity,
		 trapNetworkElemOperState,
		 trapNetworkElemAlarmStatus,  
		 trapNetworkElemAdminState,
		 trapNetworkElemAvailStatus,
		 trapText,
		 trapChangedObjectId,
		 trapChangedValueInteger,
		 trapNETrapLastTrapTimeStamp
		}
	DESCRIPTION
	"This trap is issued when the Alarm Data CRC is incorrect."
  ::= 10

	trapOSW10BInputSwitchedAlarm TRAP-TYPE
	ENTERPRISE gx2Osw10b
	VARIABLES
		{       
		 trapIdentifier,
		 trapNetworkElemModelNumber,
		 trapNetworkElemSerialNum,
		 trapPerceivedSeverity,
		 trapNetworkElemOperState,
		 trapNetworkElemAlarmStatus,  
		 trapNetworkElemAdminState,
		 trapNetworkElemAvailStatus,
		 trapText,
		 trapChangedObjectId,
		 trapChangedValueInteger,
		 trapNETrapLastTrapTimeStamp
		}
	DESCRIPTION
	"This trap is issued when the Optical input switched. This is info only alarm, unit nothing wrong"
  ::= 11

	trapOSW10BResetFactoryDefaultAlarm TRAP-TYPE
	ENTERPRISE gx2Osw10b
	VARIABLES
		{       
		 trapIdentifier,
		 trapNetworkElemModelNumber,
		 trapNetworkElemSerialNum,
		 trapPerceivedSeverity,
		 trapNetworkElemOperState,
		 trapNetworkElemAlarmStatus,  
		 trapNetworkElemAdminState,
		 trapNetworkElemAvailStatus,
		 trapText,
		 trapChangedObjectId,
		 trapChangedValueInteger,
		 trapNETrapLastTrapTimeStamp
		}
	DESCRIPTION
	"This trap is issued when the Factory Default Reset occurs. This is info only"
  ::= 12

	trapOSW10BSecondaryInputActiveAlarm TRAP-TYPE
	ENTERPRISE gx2Osw10b
	VARIABLES
		{       
		 trapIdentifier,
		 trapNetworkElemModelNumber,
		 trapNetworkElemSerialNum,
		 trapPerceivedSeverity,
		 trapNetworkElemOperState,
		 trapNetworkElemAlarmStatus,  
		 trapNetworkElemAdminState,
		 trapNetworkElemAvailStatus,
		 trapText,
		 trapChangedObjectId,
		 trapChangedValueInteger,
		 trapNETrapLastTrapTimeStamp
		}
	DESCRIPTION
	"This trap is issued when the secondary input becomes active."
  ::= 13

	trapOSW10BPriOpticInputAlarm TRAP-TYPE
	ENTERPRISE gx2Osw10b
	VARIABLES
		{       
		 trapIdentifier,
		 trapNetworkElemModelNumber,
		 trapNetworkElemSerialNum,
		 trapPerceivedSeverity,
		 trapNetworkElemOperState,
		 trapNetworkElemAlarmStatus,  
		 trapNetworkElemAdminState,
		 trapNetworkElemAvailStatus,
		 trapText,
		 trapChangedObjectId,
		 trapChangedValueInteger,
		 trapNETrapLastTrapTimeStamp
		}
	DESCRIPTION
	"This trap is issued when primary optical input out of range."
  ::= 14

	trapOSW10BSecOpticInputAlarm TRAP-TYPE
	ENTERPRISE gx2Osw10b
	VARIABLES
		{       
		 trapIdentifier,
		 trapNetworkElemModelNumber,
		 trapNetworkElemSerialNum,
		 trapPerceivedSeverity,
		 trapNetworkElemOperState,
		 trapNetworkElemAlarmStatus,  
		 trapNetworkElemAdminState,
		 trapNetworkElemAvailStatus,
		 trapText,
		 trapChangedObjectId,
		 trapChangedValueInteger,
		 trapNETrapLastTrapTimeStamp
		}
	DESCRIPTION
	"This trap is issued when Sec optical input out of range."
  ::= 15

	trapOSW10BHardwareErrorAlarm TRAP-TYPE
	ENTERPRISE gx2Osw10b
	VARIABLES
		{       
		 trapIdentifier,
		 trapNetworkElemModelNumber,
		 trapNetworkElemSerialNum,
		 trapPerceivedSeverity,
		 trapNetworkElemOperState,
		 trapNetworkElemAlarmStatus,  
		 trapNetworkElemAdminState,
		 trapNetworkElemAvailStatus,
		 trapText,
		 trapChangedObjectId,
		 trapChangedValueInteger,
		 trapNETrapLastTrapTimeStamp
		}
	DESCRIPTION
	"This trap is issued when hardware error happens."
  ::= 16


  END
