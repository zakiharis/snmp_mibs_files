-- =====================================================================
-- == OPENGEAR-HOST-MIB :                                             ==
-- == Opengear user connect notification Management Information Base  ==
-- ==                                                                 ==
-- == (c) Copyright 2005-2010 Opengear Inc.                           ==
-- =====================================================================

OPENGEAR-HOST-MIB DEFINITIONS ::= BEGIN

IMPORTS
	ogMgmt
		FROM OG-SMI-MIB
	MODULE-IDENTITY, NOTIFICATION-TYPE, OBJECT-TYPE, Integer32
		FROM SNMPv2-SMI
	MODULE-COMPLIANCE, NOTIFICATION-GROUP, OBJECT-GROUP
		FROM SNMPv2-CONF
	DisplayString
		FROM SNMPv2-TC;

ogHostMib MODULE-IDENTITY
        LAST-UPDATED "201003221127Z"
        ORGANIZATION "Opengear Inc."
        CONTACT-INFO
                "Opengear Inc.
                 630 West 9560 South,
                 Sandy, UT 84070
                 support@opengear.com"
        DESCRIPTION
                "Opengear host connection MIB"
        REVISION "201003221127Z"
	DESCRIPTION
		"Syntax corrections by Opengear Inc."
        REVISION "200811271140Z"
	DESCRIPTION
		"Initial version."
        ::= { ogMgmt 14 }

ogHostMibObjects OBJECT IDENTIFIER ::= { ogHostMib 10 }

-- Subgroups

oghostEvent OBJECT IDENTIFIER ::= { ogHostMibObjects 1 }

oghostEventTable OBJECT-TYPE
        SYNTAX     SEQUENCE OF OgHostEventEntry
        MAX-ACCESS not-accessible
        STATUS     current
        DESCRIPTION
                "A table of sensor status events generated by this device."
        ::= { oghostEvent 1 }

oghostEventEntry OBJECT-TYPE
        SYNTAX     OgHostEventEntry
        MAX-ACCESS not-accessible
        STATUS     current
        DESCRIPTION
                "A console connection event occuring at this
                 device. Each entry is indexed by a message index."
        INDEX   { oghostEventIndex }
        ::= { oghostEventTable 1 }

OgHostEventEntry ::=
    SEQUENCE {
        oghostEventIndex       Integer32,
	oghostEventUsername    DisplayString,
	oghostEventType        DisplayString,
	oghostEventAddress     DisplayString,
	oghostEventDescription DisplayString,
	oghostEventProtocol    DisplayString,
	oghostEventPort        Integer32
    }

oghostEventIndex OBJECT-TYPE
        SYNTAX     Integer32 (1..2147483647)
        MAX-ACCESS not-accessible
        STATUS     current
        DESCRIPTION
                "A monotonically increasing integer for the sole
                 purpose of indexing messages.  When it reaches the
                 maximum value the agent flushes the table and wraps
                 the value back to 1."
        ::= { oghostEventEntry 1 }

oghostEventUsername OBJECT-TYPE
	SYNTAX DisplayString
	MAX-ACCESS read-only
	STATUS current
	DESCRIPTION
	        "The user pertaining to the connection event"
	::= { oghostEventEntry 10 }

oghostEventType OBJECT-TYPE
	SYNTAX DisplayString
	MAX-ACCESS read-only
	STATUS current
	DESCRIPTION
	        "The type of connection event"
	::= { oghostEventEntry 11 }

oghostEventAddress OBJECT-TYPE
	SYNTAX DisplayString
	MAX-ACCESS read-only
	STATUS current
	DESCRIPTION
		"The address of the host to which this connection applies."
	::= { oghostEventEntry 12 }

oghostEventDescription OBJECT-TYPE
	SYNTAX DisplayString
	MAX-ACCESS read-only
	STATUS current
	DESCRIPTION
		"The description of the host to which this connection applies."
	::= { oghostEventEntry 13 }

oghostEventProtocol OBJECT-TYPE
	SYNTAX DisplayString
	MAX-ACCESS read-only
	STATUS current
	DESCRIPTION
		"The internet protocl to which this connection applies."
	::= { oghostEventEntry 14 }

oghostEventPort OBJECT-TYPE
	SYNTAX Integer32
	MAX-ACCESS read-only
	STATUS current
	DESCRIPTION
		"The applicable port number of the host."
	::= { oghostEventEntry 15 }

ogHostMibNotificationPrefix    OBJECT IDENTIFIER ::= {
	ogHostMib 2
}

oghostMibNotifications         OBJECT IDENTIFIER ::= {
	ogHostMibNotificationPrefix 0
}

oghostEventOccurred NOTIFICATION-TYPE
	OBJECTS {
		oghostEventUsername,
		oghostEventType,
		oghostEventAddress,
		oghostEventDescription,
		oghostEventProtocol,
		oghostEventPort }
	STATUS current
	DESCRIPTION
		"The notification sent when a user connection event occurs"
	::= { oghostMibNotifications 200 }

-- conformance information

ogHostMibConformance OBJECT IDENTIFIER ::= { ogHostMib 3 }
ogHostMibCompliances OBJECT IDENTIFIER ::= { ogHostMibConformance 1 }
ogHostMibGroups      OBJECT IDENTIFIER ::= { ogHostMibConformance 2 }

-- compliance statements

ogHostMibCompliance MODULE-COMPLIANCE
       STATUS  current
       DESCRIPTION
               "The compliance statement for entities which implement
                the Opengear sensor MIB."
       MODULE  -- this module
               MANDATORY-GROUPS { ogHostMibGroup }

       GROUP oghostNotificationsGroup
       DESCRIPTION
           "The implementation of this group is
           mandatory for those systems where
           sensor notification is supported."

       ::= { ogHostMibCompliances 1 }

-- Units of conformance

ogHostMibGroup OBJECT-GROUP
       OBJECTS { oghostEventUsername,
	         oghostEventType,
		 oghostEventAddress,
		 oghostEventDescription,
		 oghostEventProtocol,
		 oghostEventPort }
       STATUS  current
       DESCRIPTION
               "A collection of objects providing the sensor MIB capability."
      ::= { ogHostMibGroups 1 }

oghostNotificationsGroup NOTIFICATION-GROUP
       NOTIFICATIONS {
               oghostEventOccurred
       }
       STATUS  current
       DESCRIPTION
               "A collection of notification(s) for sensor system."
       ::= { ogHostMibGroups 2 }

END
