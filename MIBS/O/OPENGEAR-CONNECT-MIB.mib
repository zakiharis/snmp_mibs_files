-- =====================================================================
-- == OPENGEAR-CONNECT-MIB :                                          ==
-- == Opengear connection notification Management Information Base    ==
-- ==                                                                 ==
-- == (c) Copyright 2005-2010 Opengear Inc.                           ==
-- =====================================================================

OPENGEAR-CONNECT-MIB DEFINITIONS ::= BEGIN

IMPORTS
	ogMgmt
		FROM OPENGEAR-SMI-MIB
	OBJECT-TYPE
		FROM RFC-1212
	MODULE-IDENTITY, NOTIFICATION-TYPE, Integer32
		FROM SNMPv2-SMI
	MODULE-COMPLIANCE, NOTIFICATION-GROUP, OBJECT-GROUP
		FROM SNMPv2-CONF
	DisplayString
		FROM SNMPv2-TC;

ogConnectMib MODULE-IDENTITY
	LAST-UPDATED "201003221127Z"
	ORGANIZATION "Opengear Inc."
	CONTACT-INFO
               "Opengear Inc.
                630 West 9560 South,
                Sandy, UT 84070
                support@opengear.com"
	DESCRIPTION
               "Opengear console connection MIB"
	REVISION "201003221127Z"
	DESCRIPTION
		"Syntax corrections by Opengear Inc."
        REVISION "200811271140Z"
	DESCRIPTION
               "Initial version."
       ::= { ogMgmt 10 }

ogConnectMibObjects OBJECT IDENTIFIER ::= { ogConnectMib 10 }

-- Subgroups

ogconnEvent OBJECT IDENTIFIER ::= { ogConnectMibObjects 1 }

ogconnEventTable OBJECT-TYPE
        SYNTAX     SEQUENCE OF OgConnEventEntry
        MAX-ACCESS not-accessible
        STATUS     current
        DESCRIPTION
                "A table of sensor status events generated by this device."
        ::= { ogconnEvent 1 }

ogconnEventEntry OBJECT-TYPE
        SYNTAX     OgConnEventEntry
        MAX-ACCESS not-accessible
        STATUS     current
        DESCRIPTION
                "A console connection event occuring at this
                 device. Each entry is indexed by a message index."
        INDEX   { ogconnEventIndex }
        ::= { ogconnEventTable 1 }

OgConnEventEntry ::=
    SEQUENCE {
        ogconnEventIndex      Integer32,
        ogconnEventUsername   DisplayString,
        ogconnEventType       DisplayString,
	ogconnEventPortNumber Integer32,
	ogconnEventPortLabel  DisplayString
    }

ogconnEventIndex OBJECT-TYPE
        SYNTAX     Integer32 (1..2147483647)
        MAX-ACCESS not-accessible
        STATUS     current
        DESCRIPTION
                "A monotonically increasing integer for the sole
                 purpose of indexing messages.  When it reaches the
                 maximum value the agent flushes the table and wraps
                 the value back to 1."
        ::= { ogconnEventEntry 1 }

ogconnEventUsername OBJECT-TYPE
	SYNTAX DisplayString
	MAX-ACCESS read-only
	STATUS current
	DESCRIPTION
	        "The user pertaining to the connection event"
	::= { ogconnEventEntry 10 }

ogconnEventType OBJECT-TYPE
	SYNTAX DisplayString
	MAX-ACCESS read-only
	STATUS current
	DESCRIPTION
	        "The type of connection event"
	::= { ogconnEventEntry 11 }

ogconnEventPortNumber OBJECT-TYPE
	SYNTAX Integer32
	MAX-ACCESS read-only
	STATUS current
	DESCRIPTION
		"Serial port number on which this connection applies"
	::= { ogconnEventEntry 12 }

ogconnEventPortLabel OBJECT-TYPE
	SYNTAX DisplayString
	MAX-ACCESS read-only
	STATUS current
	DESCRIPTION
		"The label for the serial port where the connection applies."
	::= { ogconnEventEntry 13 }

-- notifications

ogConnectMibNotificationPrefix    OBJECT IDENTIFIER ::= {
	ogConnectMib 2
}

ogconnMibNotifications         OBJECT IDENTIFIER ::= {
	ogConnectMibNotificationPrefix 0
}

ogconnEventOccurred NOTIFICATION-TYPE
	OBJECTS {
		ogconnEventUsername,
		ogconnEventType,
		ogconnEventPortNumber,
		ogconnEventPortLabel }
	STATUS current
	DESCRIPTION
		"The notification sent when a user connection event occurs"
	::= { ogconnMibNotifications 200 }

-- conformance information

ogConnectMibConformance OBJECT IDENTIFIER ::= { ogConnectMib 3 }
ogConnectMibCompliances OBJECT IDENTIFIER ::= { ogConnectMibConformance 1 }
ogConnectMibGroups      OBJECT IDENTIFIER ::= { ogConnectMibConformance 2 }

-- compliance statements

ogConnectMibCompliance MODULE-COMPLIANCE
       STATUS  current
       DESCRIPTION
               "The compliance statement for entities which implement
                the Opengear sensor MIB."
       MODULE  -- this module
               MANDATORY-GROUPS { ogConnectMibGroup }

       GROUP ogconnNotificationsGroup
       DESCRIPTION
           "The implementation of this group is
           mandatory for those systems where
           sensor notification is supported."

       ::= { ogConnectMibCompliances 1 }

-- Units of conformance

ogConnectMibGroup OBJECT-GROUP
       OBJECTS { ogconnEventUsername,
                 ogconnEventType,
                 ogconnEventPortNumber,
                 ogconnEventPortLabel
       }
       STATUS  current
       DESCRIPTION
               "A collection of objects providing the sensor MIB capability."
      ::= { ogConnectMibGroups 1 }

ogconnNotificationsGroup NOTIFICATION-GROUP
       NOTIFICATIONS {
               ogconnEventOccurred
       }
       STATUS  current
       DESCRIPTION
               "A collection of notification(s) for sensor system."
       ::= { ogConnectMibGroups 2 }

END
