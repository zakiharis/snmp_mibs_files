-- $OpenBSD: OPENBSD-SNMPD-CONF.txt,v 1.5 2012/02/09 16:50:18 sthen Exp $
--
-- Copyright (c) 2008 Reyk Floeter <reyk@openbsd.org>
--
-- Permission to use, copy, modify, and distribute this document for any
-- purpose with or without fee is hereby granted, provided that the above
-- copyright notice and this permission notice appear in all copies.
--
-- THE DOCUMENT IS PROVIDED "AS IS" AND THE AUTHOR DISCLAIMS ALL WARRANTIES
-- WITH REGARD TO THIS DOCUMENT INCLUDING ALL IMPLIED WARRANTIES OF
-- MERCHANTABILITY AND FITNESS. IN NO EVENT SHALL THE AUTHOR BE LIABLE FOR
-- ANY SPECIAL, DIRECT, INDIRECT, OR CONSEQUENTIAL DAMAGES OR ANY DAMAGES
-- WHATSOEVER RESULTING FROM LOSS OF USE, DATA OR PROFITS, WHETHER IN AN
-- ACTION OF CONTRACT, NEGLIGENCE OR OTHER TORTIOUS ACTION, ARISING OUT OF
-- OR IN CONNECTION WITH THE USE OR PERFORMANCE OF THIS DOCUMENT.

OPENBSD-SNMPD-CONF DEFINITIONS ::= BEGIN

--
-- This file lists all the MIBs that OpenBSD snmpd(8) implements at
-- present.  Non-OpenBSD MIB files are not included in this distribution.
--

IMPORTS
	-- Management Information Base (MIB) for the Simple Network
	-- Management Protocol (SNMPv2), RFC 3418, December 2002
	snmpMIB
	    FROM SNMPv2-MIB

	-- IANA ifTypes MIB, http://www.iana.org/assignments/ianaiftype-mib
	ianaifType
	    FROM IANAifType-MIB

	-- The Interface Group MIB, RFC 2863, June 2000
	ifMIB
	    FROM IF-MIB

	-- Definitions of Managed Objects for Bridges, RFC 4188,
	-- September 2005
	dot1dBridge
	    FROM BRIDGE-MIB

	-- Textual Conventions for Internet Network Addresses,
	-- RFC 4001, February 2005
	inetAddressMIB
	    FROM INET-ADDRESS-MIB

	-- Management Information Base for the Internet Protocol
	-- (IP), RFC 4293, April 2006
	ipMIB
	    FROM IP-MIB

	-- IP Forwarding MIB, RFC 4292, April 2006
	ipForward
	    FROM IP-FORWARD-MIB

	-- Host Resources MIB, RFC 2790, March 2000
	hostResourcesMibModule
	    FROM HOST-RESOURCES-MIB

	--
	-- OpenBSD-specific MIBs
	--

	-- Base MIB, OPENBSD-BASE-MIB.txt, OpenBSD 4.3
	openBSD
	    FROM OPENBSD-BASE-MIB

	-- pf(4) statistics MIB, OPENBSD-PF-MIB.txt
	pfMIBObjects
	    FROM OPENBSD-PF-MIB

	-- Kernel sensors MIB, OPENBSD-SENSORS-MIB.txt, OpenBSD 4.3
	sensorsMIBObjects
	    FROM OPENBSD-SENSORS-MIB

	-- Memory statistics MIB, OPENBSD-MEM-MIB.txt, OpenBSD 4.5
	memMIBObjects
	    FROM OPENBSD-MEM-MIB

	-- CARP interface & statistics MIB, OPENBSD-CARP-MIB.txt
	carpMIBObjects
	    FROM OPENBSD-CARP-MIB;

END
