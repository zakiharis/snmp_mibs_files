-- =====================================================================
-- == OG-SIGNAL-MIB:                                           ==
-- == Opengear port signal notification Management Information Base   ==
-- ==                                                                 ==
-- == (c) Copyright 2005-2014 Opengear Inc.                           ==
-- =====================================================================

OG-SIGNAL-MIB DEFINITIONS ::= BEGIN

IMPORTS
	ogMgmt
		FROM OG-SMI-MIB
	MODULE-IDENTITY, NOTIFICATION-TYPE, OBJECT-TYPE, Integer32
		FROM SNMPv2-SMI
	MODULE-COMPLIANCE, NOTIFICATION-GROUP, OBJECT-GROUP
		FROM SNMPv2-CONF
	DisplayString
		FROM SNMPv2-TC;

ogSignalMib MODULE-IDENTITY
	LAST-UPDATED "201308110000Z"
	ORGANIZATION "Opengear Inc."
	CONTACT-INFO
		"Opengear Inc.
		 630 West 9560 South,
		 Sandy, UT 84070
		 support@opengear.com"
	DESCRIPTION
		"Opengear serial console signal MIB"
	REVISION "201308110000Z"
	DESCRIPTION
		"Renamed from OPENGEAR-SIGNAL-MIB to OG-SIGNAL-MIB to
		fix naming discrepancy."
	REVISION "201003221127Z"
	DESCRIPTION
	"Syntax corrections by Opengear Inc."
	REVISION "200811271140Z"
	DESCRIPTION
		"Initial version."
        ::= { ogMgmt 11 }

ogSignalMibObjects OBJECT IDENTIFIER ::= { ogSignalMib 10 }

-- Subgroups

ogsgnlEvent OBJECT IDENTIFIER ::= { ogSignalMibObjects 1 }

ogsgnlEventTable OBJECT-TYPE
        SYNTAX     SEQUENCE OF OgSgnlEventEntry
        MAX-ACCESS not-accessible
        STATUS     current
        DESCRIPTION
                "A table of serial signal events generated by this device."
        ::= { ogsgnlEvent 1 }

ogsgnlEventEntry OBJECT-TYPE
        SYNTAX     OgSgnlEventEntry
        MAX-ACCESS not-accessible
        STATUS     current
        DESCRIPTION
                "A console connection event occuring at this
                 device. Each entry is indexed by a message index."
        INDEX   { ogsgnlEventIndex }
        ::= { ogsgnlEventTable 1 }

OgSgnlEventEntry ::=
    SEQUENCE {
        ogsgnlEventIndex        Integer32,
	ogsgnlEventType         DisplayString,
	ogsgnlEventState        DisplayString,
	ogsgnlEventPortNumber   Integer32,
	ogsgnlEventPortLabel    DisplayString
    }

ogsgnlEventIndex OBJECT-TYPE
        SYNTAX     Integer32 (1..2147483647)
        MAX-ACCESS not-accessible
        STATUS     current
        DESCRIPTION
                "A monotonically increasing integer for the sole
                 purpose of indexing messages.  When it reaches the
                 maximum value the agent flushes the table and wraps
                 the value back to 1."
        ::= { ogsgnlEventEntry 1 }

ogsgnlEventType OBJECT-TYPE
	SYNTAX DisplayString
	MAX-ACCESS read-only
	STATUS current
	DESCRIPTION
	        "The particular signal which changed"
	::= { ogsgnlEventEntry 10 }

ogsgnlEventState OBJECT-TYPE
	SYNTAX DisplayString
	MAX-ACCESS read-only
	STATUS current
	DESCRIPTION
	        "The current signal state"
	::= { ogsgnlEventEntry 11 }

ogsgnlEventPortNumber OBJECT-TYPE
	SYNTAX Integer32
	MAX-ACCESS read-only
	STATUS current
	DESCRIPTION
		"Serial port number on which this signal applies"
	::= { ogsgnlEventEntry 12 }

ogsgnlEventPortLabel OBJECT-TYPE
	SYNTAX DisplayString
	MAX-ACCESS read-only
	STATUS current
	DESCRIPTION
		"The label for the serial port where the signal applies."
	::= { ogsgnlEventEntry 13 }

-- notifications

ogSignalMibNotificationPrefix    OBJECT IDENTIFIER ::= {
	ogSignalMib 2
}

ogsgnlMibNotifications         OBJECT IDENTIFIER ::= {
	ogSignalMibNotificationPrefix 0
}

ogsgnlEventOccurred NOTIFICATION-TYPE
	OBJECTS {
		ogsgnlEventType,
		ogsgnlEventState,
		ogsgnlEventPortNumber,
		ogsgnlEventPortLabel
	}
	STATUS current
	DESCRIPTION
		"The notification sent when a signal change occurs"
	::= { ogsgnlMibNotifications 200 }

-- conformance information

ogSignalMibConformance OBJECT IDENTIFIER ::= { ogSignalMib 3 }
ogSignalMibCompliances OBJECT IDENTIFIER ::= { ogSignalMibConformance 1 }
ogSignalMibGroups      OBJECT IDENTIFIER ::= { ogSignalMibConformance 2 }

-- compliance statements

ogSignalMibCompliance MODULE-COMPLIANCE
       STATUS  current
       DESCRIPTION
               "The compliance statement for entities which implement
                the Opengear Signal MIB."
       MODULE  -- this module
               MANDATORY-GROUPS { ogSignalMibGroup }

       GROUP ogsgnlNotificationsGroup
       DESCRIPTION
           "The implementation of this group is
           mandatory for those systems where
           signal notification is supported."

       ::= { ogSignalMibCompliances 1 }

-- Units of conformance

ogSignalMibGroup OBJECT-GROUP
       OBJECTS {
		ogsgnlEventType,
		ogsgnlEventState,
		ogsgnlEventPortNumber,
		ogsgnlEventPortLabel
       }
       STATUS  current
       DESCRIPTION
               "A collection of objects providing the signal MIB capability."
      ::= { ogSignalMibGroups 1 }

ogsgnlNotificationsGroup NOTIFICATION-GROUP
       NOTIFICATIONS {
               ogsgnlEventOccurred
       }
       STATUS  current
       DESCRIPTION
               "A collection of notification(s) for signal system."
       ::= { ogSignalMibGroups 2 }

END
