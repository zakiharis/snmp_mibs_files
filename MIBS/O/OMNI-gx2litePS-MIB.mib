OMNI-gx2litePS-MIB DEFINITIONS ::= BEGIN

    IMPORTS
	IpAddress, TimeTicks, Counter            
					      FROM RFC1155-SMI
	OBJECT-TYPE
					      FROM RFC-1212
	sysUpTime, DisplayString
					      FROM RFC1213-MIB
	TRAP-TYPE
					      FROM RFC-1215
	gi, motproxies
					      FROM NLS-BBNIDENT-MIB
	gx2Liteps
					      FROM GX2HFC-MIB

	trapIdentifier,trapNetworkElemModelNumber,
	trapNetworkElemSerialNum, trapPerceivedSeverity,
	trapNetworkElemOperState, trapNetworkElemAlarmStatus,
	trapNetworkElemAdminState, trapNetworkElemAvailStatus,
	trapText, trapNETrapLastTrapTimeStamp, trapChangedObjectId,
	trapChangedValueInteger, trapChangedValueDisplayString
					      FROM NLSBBN-TRAPS-MIB;



	       -- This MIB module uses the extended OBJECT-TYPE macro as
	       -- defined in RFC1212 and the TRAP-TYPE macro as defined
	       -- in RFC 1215.

		   --REVISION	"4" Jan 20, 2003
		   --DESCRIPTION
		   --			Added revision and description comment section


		--    OMNISTAR GX2 Lite PS (Power Supply)  MIB MODULE

	-- This MIB module defines information for management of HFC networks
		--
		-- The MIB consists of gx2Liteps Network Elements subgroup.
		-- The device type descriptor subgroup is used to define
		-- parameters specific to gx2Liteps device type.
		--
		-- The gx2Liteps Network Elements subgroup is
		-- a list of gx2Liteps type elements in the
		-- current network topology with nominal
		-- and current parameter values for the
		-- individual network elements; 
		
-- ****************************************************************************
		--
		-- All floating point numbers will be represented by an IEEE 32 Bit
		-- number. Conversion of this number must be done on the user
        -- interface to view the actual floating point number.
		--

		Float ::= Counter  -- UNSIGNED (32 BITS)

-- ****************************************************************************

		-- gx2Liteps Device Descriptor subgroup.

		-- The device type descriptor subgroup is used to define
		-- parameters specific to gx2Psdc device type.


		gx2LitepsDescriptor OBJECT IDENTIFIER ::= {gx2Liteps 1}



--*****************************************************************************
-- // Section: Table definitions

		--              gx2Liteps Table

		-- Contains a list of all gx2Liteps type devices in
		-- the network. Each device is characterized with
		-- current network topology information, with nominal
		-- and current parameter values for the
		-- individual network elements;
		--

-- // Section: Table definitions - Analog

	       gx2LitepsAnalogTable                    OBJECT-TYPE
			 SYNTAX             SEQUENCE OF Gx2LitepsAnalogEntry
			 ACCESS             not-accessible
			 STATUS             mandatory
			 DESCRIPTION
			 "This table contains gx2Liteps specific parameters with
			  nominal and current values."
			 ::= { gx2Liteps 2 }


	       gx2LitepsAnalogEntry               OBJECT-TYPE
			 SYNTAX             Gx2LitepsAnalogEntry
			 ACCESS             not-accessible
			 STATUS             mandatory
			 DESCRIPTION
			 "This list contains digital product class and the
			  associated RF channel parameters and descriptions."
			 INDEX { gx2LitepsAnalogTableIndex }
			 ::= { gx2LitepsAnalogTable  1}

-- // Section: Table definitions - Digital
--*****************************************************************************
--  NO DIGITAL TABLE
--*****************************************************************************
-- // Section: Table definitions - Status

	       gx2LitepsStatusTable                    OBJECT-TYPE
			 SYNTAX             SEQUENCE OF Gx2LitepsStatusEntry
			 ACCESS             not-accessible
			 STATUS             mandatory
			 DESCRIPTION
			 "This table contains gx2Liteps specific parameters with
			  nominal and current values."
			 ::= { gx2Liteps 3 }

	       gx2LitepsStatusEntry               OBJECT-TYPE
			 SYNTAX             Gx2LitepsStatusEntry
			 ACCESS             not-accessible
			 STATUS             mandatory
			 DESCRIPTION
			 "This list contains digital product class and the
			  associated RF channel parameters and descriptions."
			 INDEX { gx2LitepsStatusTableIndex }
			 ::= { gx2LitepsStatusTable  2}

--*****************************************************************************
-- // Section: Table definitions - Factory

--  NO FACTORY TABLE
  
--*****************************************************************************
-- // Section: Analog parameters

	      Gx2LitepsAnalogEntry    ::= SEQUENCE
	       {
		gx2LitepsAnalogTableIndex         INTEGER,

		--           Analog Parameters
-- // Analog parameter : +12 Volts
		litepslabel12Volt 		DisplayString (SIZE (0..80)),
		litepsuom12Volt			DisplayString (SIZE (0..80)),
		litepsmajorHigh12Volt		Float,
		litepsmajorLow12Volt		Float,
		litepsminorHigh12Volt		Float,
		litepsminorLow12Volt		Float,
		litepscurrentValue12Volt	Float,
		litepsstateFlag12Volt		INTEGER,
		litepsminValue12Volt		Float,
		litepsmaxValue12Volt 		Float,
		litepsalarmState12Volt	INTEGER,

-- // Analog parameter : +5 Volts
		litepslabel5Volt 		DisplayString (SIZE (0..80)),
		litepsuom5Volt			DisplayString (SIZE (0..80)),
		litepsmajorHigh5Volt		Float,
		litepsmajorLow5Volt		Float,
		litepsminorHigh5Volt		Float,
		litepsminorLow5Volt		Float,
		litepscurrentValue5Volt	Float,
		litepsstateFlag5Volt		INTEGER,
		litepsminValue5Volt		Float,
		litepsmaxValue5Volt 		Float,
		litepsalarmState5Volt		INTEGER,

-- // Analog parameter : +3.7 Volts
		litepslabel3Volt		DisplayString (SIZE (0..80)),
		litepsuom3Volt			DisplayString (SIZE (0..80)),
		litepsmajorHigh3Volt		Float,
		litepsmajorLow3Volt		Float,
		litepsminorHigh3Volt		Float,
		litepsminorLow3Volt		Float,
		litepscurrentValue3Volt	Float,
		litepsstateFlag3Volt		INTEGER,
		litepsminValue3Volt		Float,
		litepsmaxValue3Volt 		Float,
		litepsalarmState3Volt		INTEGER
		}

		-- ****************  Digital Parameters ***********************
 -- // None for this module


		-- ****************  Status Parameters ************************************
-- // Section: Status parameters

	    Gx2LitepsStatusEntry    ::= SEQUENCE
	    {

		gx2LitepsStatusTableIndex         INTEGER,


-- // Status parameter : Hardware status
		litepslabelFan1Status 		DisplayString (SIZE (0..80)),
		litepsvalueFan1Status 		INTEGER,
		litepsstateflagFan1Status		INTEGER,

		litepslabelFan2Status 		DisplayString (SIZE (0..80)),
		litepsvalueFan2Status 		INTEGER,
		litepsstateflagFan2Status		INTEGER
		}


		-- ****************  Factory Parameters *************************************
-- // Section: Factory parameters        

 -- // None for this module


-- // Section: Analog parameter detail
        -- ************** Analog Parameters ****************************
		gx2LitepsAnalogTableIndex              OBJECT-TYPE
			   SYNTAX           INTEGER (1..4294967295)
			   ACCESS           read-only
			   STATUS           mandatory
			   DESCRIPTION
			   "The value of this object identifies the network
			    element. This index is equal to the
			    hfcCommonTableIndex for the same element."
			   ::= { gx2LitepsAnalogEntry 1}

-- // New Parameter : 12 Volt

		litepslabel12Volt         OBJECT-TYPE
			   SYNTAX           DisplayString (SIZE (0..80))
			   ACCESS           read-only
			   STATUS           optional
			   DESCRIPTION
			   "The value of this object provides the label of the 12 Volt Analog parameter."
			   ::= { gx2LitepsAnalogEntry 2}

		litepsuom12Volt           OBJECT-TYPE
			   SYNTAX           DisplayString (SIZE (0..80))
			   ACCESS           read-only
			   STATUS           optional
			   DESCRIPTION
			   "The value of this object provides the unit of measure of the 12 Volt
		            Analog parameter."
			   ::= { gx2LitepsAnalogEntry 3}

		litepsmajorHigh12Volt     OBJECT-TYPE
			   SYNTAX           Float
			   ACCESS           read-only
			   STATUS           mandatory
			   DESCRIPTION
			   "The value of this object provides the Major High alarm value of the 12 Volt
			    Analog parameter. This value is a floating point number that is represented
		  	    as an IEEE 32 Bit number."
			   ::= { gx2LitepsAnalogEntry 4}


		litepsmajorLow12Volt      OBJECT-TYPE
			   SYNTAX           Float
			   ACCESS           read-only
			   STATUS           mandatory
			   DESCRIPTION
			   "The value of this object provides the Major Low alarm value of the 12 Volt
			    Analog parameter. This value is a floating point number that is represented
			    as an IEEE 32 Bit number."
			   ::= { gx2LitepsAnalogEntry 5}

		litepsminorHigh12Volt     OBJECT-TYPE
			   SYNTAX           Float
			   ACCESS           read-only
			   STATUS           mandatory
			   DESCRIPTION
			   "The value of this object provides the Minor High alarm value of the 12 Volt
			    Analog parameter. This value is a floating point number that is represented
			    as an IEEE 32 Bit number."
			   ::= { gx2LitepsAnalogEntry 6}

		litepsminorLow12Volt      OBJECT-TYPE
			   SYNTAX           Float
			   ACCESS           read-only
			   STATUS           mandatory
			   DESCRIPTION
			   "The value of this object provides the Minor Low alarm value of the 12 Volt
			    Analog parameter. This value is a floating point number that is represented
			    as an IEEE 32 Bit number."
			   ::= { gx2LitepsAnalogEntry 7}

		litepscurrentValue12Volt  OBJECT-TYPE
			   SYNTAX           Float
			   ACCESS           read-only
			   STATUS           mandatory
			   DESCRIPTION
			   "The value of this object provides the Current value of the 12 Volt Analog
			    parameter. This value is a floating point number that is represented as an
			    IEEE 32 Bit number."
			   ::= { gx2LitepsAnalogEntry 8}

		litepsstateFlag12Volt     OBJECT-TYPE
			   SYNTAX           INTEGER
								{
								hidden(1),
								read-only(2),
								updateable(3)
								}
			   ACCESS           read-only
			   STATUS           mandatory
			   DESCRIPTION
			   "The value of this object provides the state of the 12 Volt Analog parameter.
			   (0-Hidden 1-Read-Only, 2-Updateable)"
			   ::= { gx2LitepsAnalogEntry 9}

		litepsminValue12Volt      OBJECT-TYPE
			   SYNTAX           Float
			   ACCESS           read-only
			   STATUS           mandatory
			   DESCRIPTION
			   "The value of this object provides the minimum value the 12 Volt Analog
			    parameter can achieve. This value is a floating point number that is
			    represented as an IEEE 32 Bit number."
			   ::= { gx2LitepsAnalogEntry 10}

		litepsmaxValue12Volt      OBJECT-TYPE
			   SYNTAX           Float
			   ACCESS           read-only
			   STATUS           mandatory
			   DESCRIPTION
			   "The value of this object provides the maximum value the 12 Volt Analog
  			    parameter can achieve. This value is a floating point number that is
			    represented as an IEEE 32 Bit number."
			   ::= { gx2LitepsAnalogEntry 11}

		litepsalarmState12Volt    OBJECT-TYPE
			   SYNTAX           INTEGER
									{
									noAlarm(1),
									majorLowAlarm(2),
									minorLowAlarm(3),
									minorHighAlarm(4),
									majorHighAlarm(5),
									informational(6)
									}
			   ACCESS           read-only
			   STATUS           mandatory
			   DESCRIPTION
			   "The value of this object provides the curent alarm state of the 12 Volt Analog
			    parameter."
			   ::= { gx2LitepsAnalogEntry 12}
-- // New Parameter : 5 Volt

		litepslabel5Volt      OBJECT-TYPE
			   SYNTAX           DisplayString (SIZE (0..80))
			   ACCESS           read-only
			   STATUS           optional
			   DESCRIPTION
			   "The value of this object provides the label of the Attenuator Setting Analog
			    parameter."
			   ::= { gx2LitepsAnalogEntry 13}

		litepsuom5Volt        OBJECT-TYPE
			   SYNTAX           DisplayString (SIZE (0..80))
			   ACCESS           read-only
			   STATUS           optional
			   DESCRIPTION
			   "The value of this object provides the Unit of Measure of the 5 Volt Analog
			    parameter."
			   ::= { gx2LitepsAnalogEntry 14}

		litepsmajorHigh5Volt  OBJECT-TYPE
			   SYNTAX           Float
			   ACCESS           read-only
			   STATUS           mandatory
			   DESCRIPTION
			   "The value of this object provides the Major High alarm value of the 5 Volt
			    Analog parameter. This value is a floating point number that is represented
			    as an IEEE 32 Bit number."
			   ::= { gx2LitepsAnalogEntry 15}


		litepsmajorLow5Volt   OBJECT-TYPE
			   SYNTAX           Float
			   ACCESS           read-only
			   STATUS           mandatory
			   DESCRIPTION
			   "The value of this object provides the Major Low alarm value of the 5 Volt
			    Analog parameter. This value is a floating point number that is represented
			    as an IEEE 32 Bit number."
			   ::= { gx2LitepsAnalogEntry 16}

		litepsminorHigh5Volt  OBJECT-TYPE
			   SYNTAX           Float
			   ACCESS           read-only
			   STATUS           mandatory
			   DESCRIPTION
            "The value of this object provides the Minor High alarm value of the 5 Volt
			    Analog parameter. This value is a floating point number that is represented
			    as an IEEE 32 Bit number."
			   ::= { gx2LitepsAnalogEntry 17}

		litepsminorLow5Volt   OBJECT-TYPE
			   SYNTAX           Float
			   ACCESS           read-only
			   STATUS           mandatory
			   DESCRIPTION
			   "The value of this object provides the Minor Low alarm value of the 5 Volt
			    Analog parameter. This value is a floating point number that is represented
			    as an IEEE 32 Bit number."
			   ::= { gx2LitepsAnalogEntry 18}

		litepscurrentValue5Volt   OBJECT-TYPE
			   SYNTAX           Float
			   ACCESS           read-only
			   STATUS           mandatory
			   DESCRIPTION
			   "The value of this object provides the Current value of the 5 Volt Analog
			    parameter. This value is a floating point number that is represented as
			    an IEEE 32 Bit number."
			   ::= { gx2LitepsAnalogEntry 19}

		litepsstateFlag5Volt  OBJECT-TYPE
			   SYNTAX           INTEGER
								{
								hidden(1),
								read-only(2),
								updateable(3)
								}
			   ACCESS           read-only
			   STATUS           mandatory
			   DESCRIPTION
			   "The value of this object provides the state of the 5 Volt Analog parameter.
			   (0-Hidden 1-Read-Only, 2-Updateable)."
			   ::= { gx2LitepsAnalogEntry 20}

		litepsminValue5Volt   OBJECT-TYPE
			   SYNTAX           Float
			   ACCESS           read-only
			   STATUS           mandatory
			   DESCRIPTION
			   "The value of this object provides the minimum value the 5 Volt Analog
			    parameter can achieve. This value is a floating point number that is
			    represented as an IEEE 32 Bit number."
			   ::= { gx2LitepsAnalogEntry 21}

		litepsmaxValue5Volt   OBJECT-TYPE
			   SYNTAX           Float
			   ACCESS           read-only
			   STATUS           mandatory
			   DESCRIPTION
			   "The value of this object provides the maximum value the 5 Volt Analog parameter
			    can achieve. This value is a floating point number that is represented as an
			    IEEE 32 Bit number."
			   ::= { gx2LitepsAnalogEntry 22}

		litepsalarmState5Volt OBJECT-TYPE
			   SYNTAX           INTEGER
									{
									noAlarm(1),
									majorLowAlarm(2),
									minorLowAlarm(3),
									minorHighAlarm(4),
									majorHighAlarm(5),
									informational(6)
									}
			   ACCESS           read-only
			   STATUS           mandatory
			   DESCRIPTION
			   "The value of this object provides the curent alarm state of the 5 Volt
			    Analog parameter. "
			   ::= { gx2LitepsAnalogEntry 23}
-- // New Parameter : 3.7 Volt

		litepslabel3Volt             OBJECT-TYPE
			   SYNTAX           DisplayString (SIZE (0..80))
			   ACCESS           read-only
			   STATUS           optional
			   DESCRIPTION
			   "The value of this object provides the label of the
			    3 Anode Volt Analog parameter."
			   ::= { gx2LitepsAnalogEntry 24}

		litepsuom3Volt               OBJECT-TYPE
			   SYNTAX           DisplayString (SIZE (0..80))
			   ACCESS           read-only
			   STATUS           optional
			   DESCRIPTION
            "The value of this object provides the Unit of Measure of the 3.7V anode voltage
             analog parameter."
			   ::= { gx2LitepsAnalogEntry 25}

		litepsmajorHigh3Volt         OBJECT-TYPE
			   SYNTAX           Float
			   ACCESS           read-only
			   STATUS           mandatory
			   DESCRIPTION
            "The value of this object provides the Major High alarm value of the 3.7V anode
             voltage analog parameter. This value is a floating point number that is
			    represented as an IEEE 32 Bit number."
			   ::= { gx2LitepsAnalogEntry 26}


		litepsmajorLow3Volt          OBJECT-TYPE
			   SYNTAX           Float
			   ACCESS           read-only
			   STATUS           mandatory
			   DESCRIPTION
            "The value of this object provides the Major Low alarm value of the 3.7V anode
             voltage analog parameter. This value is a floating point number that is
             represented as an IEEE 32 Bit number."
			   ::= { gx2LitepsAnalogEntry 27}

		litepsminorHigh3Volt         OBJECT-TYPE
			   SYNTAX           Float
			   ACCESS           read-only
			   STATUS           mandatory
			   DESCRIPTION
            "The value of this object provides the Minor High alarm value of the 3.7V anode
             voltage analog parameter. This value is a floating point number that is
             represented as an IEEE 32 Bit number."
			   ::= { gx2LitepsAnalogEntry 28}

		litepsminorLow3Volt          OBJECT-TYPE
			   SYNTAX           Float
			   ACCESS           read-only
			   STATUS           mandatory
			   DESCRIPTION
            "The value of this object provides the Minor Low alarm value of the 3.7V anode
             voltage analog parameter. This value is a floating point number that is
             represented as an IEEE 32 Bit number."
			   ::= { gx2LitepsAnalogEntry 29}

		litepscurrentValue3Volt      OBJECT-TYPE
			   SYNTAX           Float
			   ACCESS           read-only
			   STATUS           mandatory
			   DESCRIPTION
            "The value of this object provides the Current value of the 3.7V anode voltage
             analog parameter. This value is a floating point number that is represented
             as an IEEE 32 Bit number."
			   ::= { gx2LitepsAnalogEntry 30}

		litepsstateFlag3Volt         OBJECT-TYPE
			   SYNTAX           INTEGER
								{
								hidden(1),
								read-only(2),
								updateable(3)
								}
			   ACCESS           read-only
			   STATUS           mandatory
			   DESCRIPTION
            "The value of this object provides the state of the 3 Volt Analog parameter.
             (0-Hidden 1-Read-Only, 2-Updateable). "
			   ::= { gx2LitepsAnalogEntry 31}

		litepsminValue3Volt          OBJECT-TYPE
			   SYNTAX           Float
			   ACCESS           read-only
			   STATUS           mandatory
			   DESCRIPTION
            "The value of this object provides the minimum value that the 3.7V anode voltage
             analog parameter can achieve. This value is a floating point number that is
             represented as an IEEE 32 Bit number."
			   ::= { gx2LitepsAnalogEntry 32}

		litepsmaxValue3Volt          OBJECT-TYPE
			   SYNTAX           Float
			   ACCESS           read-only
			   STATUS           mandatory
			   DESCRIPTION
            "The value of this object provides the maximum value that the 3.7V anode voltage
             analog parameter can achieve. This value is a floating point number that is
             represented as an IEEE 32 Bit number."
			   ::= { gx2LitepsAnalogEntry 33}

		litepsalarmState3Volt        OBJECT-TYPE
			   SYNTAX           INTEGER
									{
									noAlarm(1),
									majorLowAlarm(2),
									minorLowAlarm(3),
									minorHighAlarm(4),
									majorHighAlarm(5),
									informational(6)
									}
			   ACCESS           read-only
			   STATUS           mandatory
			   DESCRIPTION
            "The value of this object provides the curent alarm state of the 3.7V anode
             voltage analog parameter. "
			   ::= { gx2LitepsAnalogEntry 34}

-- ************************ Digital parameters **********************************

-- NONE     

-- ************************ Status parameters **********************************

-- // Section: Status parameter detail
		--*********** STATUS *****************
		gx2LitepsStatusTableIndex              OBJECT-TYPE
			   SYNTAX           INTEGER (1..4294967295)
			   ACCESS           read-only
			   STATUS           mandatory
			   DESCRIPTION
			   "The value of this object identifies the network
			    element. This index is equal to the
			    hfcCommonTableIndex for the same element."
			   ::= { gx2LitepsStatusEntry 1}


-- // New Parameter : Fan 1 Status
		litepslabelFan1Status             OBJECT-TYPE
			   SYNTAX       		DisplayString (SIZE (0..80))
			   ACCESS           	read-only
			   STATUS           	optional
			   DESCRIPTION
			   "The value of this object provides the label of the
			    Fan 1 Status parameter."
			   ::= { gx2LitepsStatusEntry 2}

		litepsvalueFan1Status           	OBJECT-TYPE
			   SYNTAX       		INTEGER
									{
									ok(1),
									undetermined(2),
									warning(3),
									minor(4),
									major(5),
									critical(6)
									}
			   ACCESS           	read-only
			   STATUS           	mandatory
			   DESCRIPTION
			   "The value of this object provides the current state of
			    the parameter (0-Ok, 1-Undetermined
			    2-Warning, 3-Minor, 4-Major, 5-Critical)."
			   ::= { gx2LitepsStatusEntry 3}

		litepsstateflagFan1Status     	OBJECT-TYPE
			   SYNTAX       		INTEGER
								{
								hidden(1),
								read-only(2),
								updateable(3)
								}
			   ACCESS           	read-only
			   STATUS           	mandatory
			   DESCRIPTION
			   "The value of this object provides the state
			    of the the parameter. (0-Hidden 1-Read-Only, 2-Updateable)."
			   ::= { gx2LitepsStatusEntry  4}

 
 -- // New Parameter : Fan 2 Status
		litepslabelFan2Status             OBJECT-TYPE
			   SYNTAX       		DisplayString (SIZE (0..80))
			   ACCESS           	read-only
			   STATUS           	optional
			   DESCRIPTION
			   "The value of this object provides the label of the
			    Fan 2 Status parameter."
			   ::= { gx2LitepsStatusEntry 5}

		litepsvalueFan2Status           	OBJECT-TYPE
			   SYNTAX       		INTEGER
									{
									ok(1),
									undetermined(2),
									warning(3),
									minor(4),
									major(5),
									critical(6)
									}
			   ACCESS           	read-only
			   STATUS           	mandatory
			   DESCRIPTION
			   "The value of this object provides the current state of
			    the parameter (0-Ok, 1-Undetermined
			    2-Warning, 3-Minor, 4-Major, 5-Critical)."
			   ::= { gx2LitepsStatusEntry 6}

		litepsstateflagFan2Status     	OBJECT-TYPE
			   SYNTAX       		INTEGER
								{
								hidden(1),
								read-only(2),
								updateable(3)
								}
			   ACCESS           	read-only
			   STATUS           	mandatory
			   DESCRIPTION
			   "The value of this object provides the state
			    of the the parameter. (0-Hidden 1-Read-Only, 2-Updateable)."
			   ::= { gx2LitepsStatusEntry  7}

-- ************************ Factory parameters **********************************

-- // Section: Factory parameter detail
-- // No Factory table  



-- // Section: Traps
-- ****************************************************************
--
-- TRAP DEFINITIONS
--
--
-- Every trap generated by an HFC agents will include first 9 identical
-- fields. If particular variable is not supported in
-- particular TRAP-TYPE then default value will be returned.
--
-- DESCRIPTION will include explanation of use of generic
-- variables (trapAdditionalInfo******.)  If no
-- DESCRIPTION is given then generic variables will contain
-- default values.
--
-- *****************************************************************
-- **************************************************************************
--                          Power Supply Module traps
-- **************************************************************************
-- // Trap 1  : integer congif change
   trapLitepsConfigChangeInteger TRAP-TYPE
       ENTERPRISE gx2Liteps
       VARIABLES
	       {
		trapIdentifier,
		trapNetworkElemModelNumber,
		trapNetworkElemSerialNum,
		trapPerceivedSeverity,
		trapNetworkElemOperState,
		trapNetworkElemAlarmStatus,
		trapNetworkElemAdminState,
		trapNetworkElemAvailStatus,
		trapText,
		trapChangedObjectId,
		trapChangedValueInteger,
		trapNETrapLastTrapTimeStamp
	       }
       DESCRIPTION
	"This trap is issued if configuration of a single variable
	 with integer type was changed (via ANY interface).
	 TrapChangedValueInteger variable may contain current reading
	 of that variable.
	 trapPerceivedSeverity - 'indeterminate'"
  ::= 1

-- // Trap 2  : string config change
   trapLitepsConfigChangeDisplayString TRAP-TYPE
       ENTERPRISE gx2Liteps
       VARIABLES
	       {
		trapIdentifier,
		trapNetworkElemModelNumber,
		trapNetworkElemSerialNum,
		trapPerceivedSeverity,
		trapNetworkElemOperState,
		trapNetworkElemAlarmStatus,
		trapNetworkElemAdminState,
		trapNetworkElemAvailStatus,
		trapText,
		trapChangedObjectId,
		trapChangedValueDisplayString,
		trapNETrapLastTrapTimeStamp
	       }
       DESCRIPTION
	"This trap is issued if configuration of a single variable
	 with DispalayString type was changed (via ANY interface).
	 TrapChangedValueDisplayString variable may contain current reading
	 of that variable.
	 trapPerceivedSeverity - 'indeterminate'"
  ::= 2

-- // Trap 3  : Fan 1 status
  trapLitepsFanCurrent1 TRAP-TYPE
	ENTERPRISE gx2Liteps
	VARIABLES
		{
		 trapIdentifier,
		 trapNetworkElemModelNumber,
		 trapNetworkElemSerialNum,
		 trapPerceivedSeverity,
		 trapNetworkElemOperState,
		 trapNetworkElemAlarmStatus,
		 trapNetworkElemAdminState,
		 trapNetworkElemAvailStatus,
		 trapText,
		 trapChangedObjectId,
		 trapChangedValueInteger,
		 trapNETrapLastTrapTimeStamp
		}
	DESCRIPTION
   "This trap is issued when Fan 1 is in an alarm condition."
  ::= 3

-- // Trap 4  : Fan 2 status
  trapLitepsFanCurrent2 TRAP-TYPE
	ENTERPRISE gx2Liteps
	VARIABLES
		{
		 trapIdentifier,
		 trapNetworkElemModelNumber,
		 trapNetworkElemSerialNum,
		 trapPerceivedSeverity,
		 trapNetworkElemOperState,
		 trapNetworkElemAlarmStatus,
		 trapNetworkElemAdminState,
		 trapNetworkElemAvailStatus,
		 trapText,
		 trapChangedObjectId,
		 trapChangedValueInteger,
		 trapNETrapLastTrapTimeStamp
		}
	DESCRIPTION
   "This trap is issued when Fan 2 is in an alarm condition."
  ::= 4

-- // Trap 5  : 12 Volt
  trapLiteps12Volt TRAP-TYPE
	ENTERPRISE gx2Liteps
	VARIABLES
		{
		 trapIdentifier,
		 trapNetworkElemModelNumber,
		 trapNetworkElemSerialNum,
		 trapPerceivedSeverity,
		 trapNetworkElemOperState,
		 trapNetworkElemAlarmStatus,
		 trapNetworkElemAdminState,
		 trapNetworkElemAvailStatus,
		 trapText,
		 trapChangedObjectId,
		 trapChangedValueInteger,
		 trapNETrapLastTrapTimeStamp
		}
	DESCRIPTION
   "This trap is issued when the 12 Volts is in an alarm condition."
  ::= 5

-- // Trap 6  : 5 Volt
  trapLiteps5Volt TRAP-TYPE
	ENTERPRISE gx2Liteps
	VARIABLES
		{
		 trapIdentifier,
		 trapNetworkElemModelNumber,
		 trapNetworkElemSerialNum,
		 trapPerceivedSeverity,
		 trapNetworkElemOperState,
		 trapNetworkElemAlarmStatus,
		 trapNetworkElemAdminState,
		 trapNetworkElemAvailStatus,
		 trapText,
		 trapChangedObjectId,
		 trapChangedValueInteger,
		 trapNETrapLastTrapTimeStamp
		}
	DESCRIPTION
   "This trap is issued when the 5.1 Volts is in an alarm condition."
  ::= 6

-- // Trap 7  : 3.7 Volt
  trapLiteps3Volt TRAP-TYPE
	ENTERPRISE gx2Liteps
	VARIABLES
		{
		 trapIdentifier,
		 trapNetworkElemModelNumber,
		 trapNetworkElemSerialNum,
		 trapPerceivedSeverity,
		 trapNetworkElemOperState,
		 trapNetworkElemAlarmStatus,
		 trapNetworkElemAdminState,
		 trapNetworkElemAvailStatus,
		 trapText,
		 trapChangedObjectId,
		 trapChangedValueInteger,
		 trapNETrapLastTrapTimeStamp
		}
	DESCRIPTION
   "This trap is issued when the 3.7 Volts is in an alarm condition."
  ::= 7



  END
