--          *****************************
--          *							*
--          *         ONEOS MIB			*
--          *							*
--          *****************************
--
--          ONEOS_MIB_STD_V05.2.R001_E001
--
--          Creation date : 05/04/2012

	ONEACCESS-VRF-TO-IF-MIB DEFINITIONS ::= BEGIN
		
		IMPORTS
			OBJECT-TYPE, MODULE-IDENTITY
				FROM SNMPv2-SMI
			oacExpIMIp
				FROM ONEACCESS-GLOBAL-REG	
			TEXTUAL-CONVENTION
				FROM SNMPv2-TC				
			ifIndex
				FROM IF-MIB;
				
     oacExpIMIPVrfToIf MODULE-IDENTITY
         LAST-UPDATED "1204051200Z"
         ORGANIZATION "ONE ACCESS"
         CONTACT-INFO
           "Pascal KESTELOOT
            Postal: ONE ACCESS
                    381 Avenue du General de Gaulle
                    92140 Clamart, France
		    FRANCE

            Tel: (+33) 01 41 87 70 54
            Fax: (+33) 01 41 87 74 39

            E-mail: pascal.kesteloot@oneaccess-net.com"

         DESCRIPTION
              "This MIB module lists all the interfaces attached to a configured VRF."

	::= { oacExpIMIp 11 }

--
-- Textual Conventions
--
	
	OacExpVrfName ::= TEXTUAL-CONVENTION
		DISPLAY-HINT "255a"
		STATUS       current
		DESCRIPTION
				"Textual convention for vrf name."
		SYNTAX       OCTET STRING (SIZE(1..32))

--
-- Node definitions
--
		
	oacExpIMIPVrfToIfTable OBJECT-TYPE
		SYNTAX SEQUENCE OF OacExpIMIPVrfToIfEntry
		MAX-ACCESS not-accessible
		STATUS current
		DESCRIPTION
           "Table of correspondance between VRF and interfaces"
	::= { oacExpIMIPVrfToIf 1 }
	
	oacExpIMIPVrfToIfEntry OBJECT-TYPE
        SYNTAX      OacExpIMIPVrfToIfEntry
        MAX-ACCESS  not-accessible
        STATUS      current
        DESCRIPTION
           "Each entry corresponds to a an interface and the VRF it belongs to"

        INDEX { ifIndex }
        ::= { oacExpIMIPVrfToIfTable 1 }
		
		OacExpIMIPVrfToIfEntry ::= SEQUENCE {
			oacVrfName OacExpVrfName
		}
	
		oacVrfName OBJECT-TYPE
			SYNTAX OacExpVrfName 
			MAX-ACCESS read-only
			STATUS current
			DESCRIPTION
				"The name of the VRF the interface belong to"
			::= { oacExpIMIPVrfToIfEntry 1 }

	END
--
