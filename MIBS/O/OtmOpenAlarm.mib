OtmOpenAlarm DEFINITIONS ::= BEGIN

--    Revision History
--    2004/06/30  For OTM 2.2, renamed otmNameSpace constants "succession" to 
--    "successionunused" ("callserver", "signalingserver" or "mediacard" should be
--    used instead of "succession"). Added otmNameSpace constant "bcmsrg".
--   
--    2003/03/21  For OTM 2.1, removed un-used trap definitions otmOpenAlarmEpxxx,
--    added extra items to otmNameSpace object.

-- *********************************************************************
--                          OTM Open Alarm MIB
-- *********************************************************************

--    Defines the OTM Open Alarm TRAP-TYPE and its varbinds.

--    Multiple definitions of traps with exactly the same
--    varbinds are given in order to get the effect of a variable
--    ENTERPRISE Object Identifier and to have the trap number 
--    identify the severity of the alarm.

--    For each device using this MIB, a developer must document the
--    format of each device-dependent object.  The DESCRIPTION
--    section indicates whether an object is device-dependent.

   IMPORTS
      OBJECT-TYPE, enterprises FROM SNMPv2-SMI
      TRAP-TYPE                FROM RFC-1215
      DisplayString            FROM SNMPv2-TC;

   nt OBJECT IDENTIFIER ::= { enterprises 562 }
      otm OBJECT IDENTIFIER ::= { nt 50 }
         otmOpenAlarm OBJECT IDENTIFIER              ::= { otm 1 }
           otmOpenAlarmEp OBJECT IDENTIFIER            ::= { otmOpenAlarm 1 }
           otmOpenAlarmObjects OBJECT IDENTIFIER       ::= { otmOpenAlarm 2 }
			

-- *********************************************************************
--		OTM Open Alarm Trap 
-- *********************************************************************

otmOpenAlarmCritical TRAP-TYPE
	  	ENTERPRISE otmOpenAlarmEp
		VARIABLES { 
			-- Mandatory
			otmSeqNumber,
			otmDateAndTime,
			otmSeverity,
			otmNameSpace,             -- device-dependent
			otmType,                  -- device-dependent
			otmSite,                  -- device-dependent
		 	otmSystem,                -- device-dependent
			otmSystemComponent,       -- device-dependent

			-- Optional
			otmOriginatingAgent,
			otmOptivityTrapType,
			otmAssocUser,             -- device-dependent
			otmProblemIsolationData1, -- device-dependent
			otmProblemIsolationData2, -- device-dependent
			otmProblemIsolationData3  -- device-dependent
		}
		DESCRIPTION "
			The OTM Open Alarm Trap with an otmSeverity 
                  of critical(1).

			This trap is intended to be internationalizable,
                  hence, it contains no natural language text.
		"
 ::= 1

otmOpenAlarmMajor TRAP-TYPE
	  	ENTERPRISE otmOpenAlarmEp
		VARIABLES { 
			-- Mandatory
			otmSeqNumber,
			otmDateAndTime,
			otmSeverity,
			otmNameSpace,             -- device-dependent
			otmType,                  -- device-dependent
			otmSite,                  -- device-dependent
		 	otmSystem,                -- device-dependent
			otmSystemComponent,       -- device-dependent

			-- Optional
			otmOriginatingAgent,
			otmOptivityTrapType,
			otmAssocUser,             -- device-dependent
			otmProblemIsolationData1, -- device-dependent
			otmProblemIsolationData2, -- device-dependent
			otmProblemIsolationData3  -- device-dependent
		}
		DESCRIPTION "
			The OTM Open Alarm Trap with a severity
                  of major(2).

			This trap is intended to be internationalizable,
                  hence, it contains no natural language text.
		"
 ::= 2

otmOpenAlarmMinor TRAP-TYPE
	  	ENTERPRISE otmOpenAlarmEp
		VARIABLES { 
			-- Mandatory
			otmSeqNumber,
			otmDateAndTime,
			otmSeverity,
			otmNameSpace,             -- device-dependent
			otmType,                  -- device-dependent
			otmSite,                  -- device-dependent
		 	otmSystem,                -- device-dependent
			otmSystemComponent,       -- device-dependent

			-- Optional
			otmOriginatingAgent,
			otmOptivityTrapType,
			otmAssocUser,             -- device-dependent
			otmProblemIsolationData1, -- device-dependent
			otmProblemIsolationData2, -- device-dependent
			otmProblemIsolationData3  -- device-dependent
		}
		DESCRIPTION "
			The OTM Open Alarm Trap with an otmSeverity
                  of minor(3).

			This trap is intended to be internationalizable,
                  hence, it contains no natural language text.
		"
 ::= 3

otmOpenAlarmWarning TRAP-TYPE
	  	ENTERPRISE otmOpenAlarmEp
		VARIABLES { 
			-- Mandatory
			otmSeqNumber,
			otmDateAndTime,
			otmSeverity,
			otmNameSpace,             -- device-dependent
			otmType,                  -- device-dependent
			otmSite,                  -- device-dependent
		 	otmSystem,                -- device-dependent
			otmSystemComponent,       -- device-dependent

			-- Optional
			otmOriginatingAgent,
			otmOptivityTrapType,
			otmAssocUser,             -- device-dependent
			otmProblemIsolationData1, -- device-dependent
			otmProblemIsolationData2, -- device-dependent
			otmProblemIsolationData3  -- device-dependent
		}
		DESCRIPTION "
			The OTM Open Alarm Trap with an otmSeverity 
                  of warning(4).

			This trap is intended to be internationalizable,
                  hence, it contains no natural language text.
		"
 ::= 4

otmOpenAlarmInfo TRAP-TYPE
		ENTERPRISE otmOpenAlarmEp
		VARIABLES { 
			-- Mandatory
			otmSeqNumber,
			otmDateAndTime,
			otmSeverity,
			otmNameSpace,             -- device-dependent
			otmType,                  -- device-dependent
			otmSite,                  -- device-dependent
		 	otmSystem,                -- device-dependent
			otmSystemComponent,       -- device-dependent

			-- Optional
			otmOriginatingAgent,
			otmOptivityTrapType,
			otmAssocUser,             -- device-dependent
			otmProblemIsolationData1, -- device-dependent
			otmProblemIsolationData2, -- device-dependent
			otmProblemIsolationData3  -- device-dependent
		}
		DESCRIPTION "
			The OTM Open Alarm Trap with an otmSeverity
                  of info(5).

			This trap is intended to be internationalizable,
                  hence, it contains no natural language text.
		"
 ::= 5

otmOpenAlarmClear TRAP-TYPE
	  	ENTERPRISE otmOpenAlarmEp
		VARIABLES { 
			-- Mandatory
			otmSeqNumber,
			otmDateAndTime,
			otmSeverity,
			otmNameSpace,             -- device-dependent
			otmType,                  -- device-dependent
			otmSite,                  -- device-dependent
		 	otmSystem,                -- device-dependent
			otmSystemComponent,       -- device-dependent

			-- Optional
			otmOriginatingAgent,
			otmOptivityTrapType,
			otmAssocUser,             -- device-dependent
			otmProblemIsolationData1, -- device-dependent
			otmProblemIsolationData2, -- device-dependent
			otmProblemIsolationData3  -- device-dependent
		}
		DESCRIPTION "
			The OTM Open Alarm Trap with a severity
                  of clear(6).

			This trap is intended to be internationalizable,
                  hence, it contains no natural language text.
		"
 ::= 6



-- *******************************************************
-- Mandatory Varbinds: all of these must be in each alarm.
-- *******************************************************

otmSeqNumber OBJECT-TYPE
		SYNTAX		INTEGER (SIZE(4))
		MAX-ACCESS		read-only
		STATUS		current
		DESCRIPTION "
			Sequence number of the alarm; starts at 1 and increments by 1; must be unique for all alarms 			received from otmSource.
		"
	::=  { otmOpenAlarmObjects 1 }

otmDateAndTime OBJECT-TYPE
		SYNTAX		DisplayString ( SIZE (22) )
		MAX-ACCESS		read-only
		STATUS		current
		DESCRIPTION "
			Time at which the alarm occurred. 
			Its format is YYYY MM DD HH MM SS hh;
			hh may equal 00.
		"
	::=  { otmOpenAlarmObjects 2 }

otmSeverity OBJECT-TYPE
		SYNTAX INTEGER {
			critical (1),
			major    (2),
			minor    (3),
			warning  (4),
			info     (5),
			clear    (6)

           	}
		MAX-ACCESS      read-only
		STATUS          current
		DESCRIPTION	"
			The severity of the alarm.
		"
	::= { otmOpenAlarmObjects 3 }

otmNameSpace OBJECT-TYPE
		SYNTAX INTEGER {
                  otm          (1),
                  meridian1    (2),
                  callPilot    (3),
                  meridianMail (4),
                  sl100        (5),
                  passport     (6),
                  itg          (7),
                  bravo        (8),
                  iss7         (9),
                  mdect        (10),
                  sccs         (11),
                  meridianMailLink (12),
                  genericOrUnknown (13),
                  callserver   (14),
                  mediacard    (15),
                  signalingserver (16),
                  successionunused (17),
                  bcmsrg       (18)
              }
		MAX-ACCESS	read-only
		STATUS		current
		DESCRIPTION  "
			This field, plus otmAlarmType, assigns a universally unique name to the trap.  Values of this field are allocated by personnel at Nortel Networks, MPK.
		"
	::=  { otmOpenAlarmObjects 4 }

otmType OBJECT-TYPE
		SYNTAX		DisplayString	 ( SIZE (1..16) )	
		MAX-ACCESS	read-only
		STATUS		current
		DESCRIPTION "
			The type of the alarm.

			The value of this field is unique within the name 			space defined by otmAlarmNameSpace.

			The format of this object is device-dependent.

			The Meridian 1 format is AAAA9999, where the numeric 			portion is unique within the alpha portion.

			The SL-100 format is AAAAA99999, where the numeric 			portion is unique within the alpha portion.
		"
	::=  { otmOpenAlarmObjects 5 }

otmSite OBJECT-TYPE
		SYNTAX		DisplayString ( SIZE (1..40) )
		MAX-ACCESS	read-only
		STATUS		current
		DESCRIPTION	"
			The site associated with otmSystem.  This site may contain or be a grouping of several systems.

			The format of this object is device-dependent.
		"
	::= { otmOpenAlarmObjects 6 }

otmSystem	OBJECT-TYPE
		SYNTAX		DisplayString ( SIZE (1..40) )
		MAX-ACCESS	read-only
		STATUS		current
		DESCRIPTION	"
			The alarm's source - the name of the 
			largest containing object to be identified as the alarm's emitter.

			The format of this object is device-dependent.
		"
	::= { otmOpenAlarmObjects 7 }

otmSystemComponent OBJECT-TYPE
		SYNTAX		DisplayString ( SIZE (1..40) )
		MAX-ACCESS	read-only
		STATUS		current
		DESCRIPTION	"
			A component within otmSystem emitting the alarm.

			The format of this object is device-dependent.
		"
::= { otmOpenAlarmObjects 8 }


-- **************************************************************
-- Optional Varbinds: 0ne or more of these may be in each alarm.
-- **************************************************************

otmOriginatingAgent OBJECT-TYPE
		SYNTAX          DisplayString (SIZE(7..15)) -- NetworkAddress	
		MAX-ACCESS      read-only
		STATUS          current
		DESCRIPTION "
			The IP address of the SNMP agent that originated the trap.
		"
	::= { otmOpenAlarmObjects 9}
			
otmOptivityTrapType OBJECT-TYPE
		SYNTAX INTEGER {
			toggle  (1),
			counter (2)  
           	}
		MAX-ACCESS      read-only
		STATUS          current
		DESCRIPTION "
			Indicates this trap fits the definition of a specific Optivity-defined trap type.
		"
	::= { otmOpenAlarmObjects 10 }

otmAssocUser	OBJECT-TYPE
		SYNTAX		DisplayString ( SIZE (0..40) )
		MAX-ACCESS		read-only
		STATUS		current
		DESCRIPTION	"
			Name of the user most closely associated with
			the alarm (e.g., the user of the application that 
			emits the alarm).

			The format of this object is device-dependent.
		"
	::= { otmOpenAlarmObjects 11 }

otmProblemIsolationData1	OBJECT-TYPE
		SYNTAX		OCTET STRING ( SIZE (0..1024) )
		MAX-ACCESS	read-only
		STATUS		current
		DESCRIPTION	"
			Data useful in isolating the problem
			represented by the alarm.

			The format of this object is device-dependent.
		"
	::= { otmOpenAlarmObjects 12 }
	
otmProblemIsolationData2	OBJECT-TYPE
		SYNTAX		OCTET STRING ( SIZE (0..1024) )
		MAX-ACCESS	read-only
		STATUS		current
		DESCRIPTION	"
			Data useful in isolating the problem 
			represented by the alarm.

			An extension to otmProblemIsolationData1.

			The format of this object is device-dependent.
		"
	::= { otmOpenAlarmObjects 13 }
	
otmProblemIsolationData3	OBJECT-TYPE
		SYNTAX		OCTET STRING ( SIZE (0..1024) )
		MAX-ACCESS	read-only
		STATUS		current
		DESCRIPTION	"
			Data useful in isolating the problem
			represented by the alarm.

			An extension to otmProblemIsolationData2.

			The format of this object is device-dependent.
		"
        ::= { otmOpenAlarmObjects 14 }
END
