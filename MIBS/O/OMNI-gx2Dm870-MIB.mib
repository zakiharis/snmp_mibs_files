OMNI-gx2Dm870-MIB DEFINITIONS ::= BEGIN

    IMPORTS
	IpAddress, TimeTicks, Counter            
					      FROM RFC1155-SMI
	OBJECT-TYPE                     
					      FROM RFC-1212
	sysUpTime, DisplayString        
					      FROM RFC1213-MIB
	TRAP-TYPE                       
					      FROM RFC-1215
	gi, motproxies                   
					      FROM NLS-BBNIDENT-MIB
	gx2Dm870
					      FROM GX2HFC-MIB

	trapIdentifier,trapNetworkElemModelNumber,
	trapNetworkElemSerialNum, trapPerceivedSeverity,
	trapNetworkElemOperState, trapNetworkElemAlarmStatus,
	trapNetworkElemAdminState, trapNetworkElemAvailStatus,
	trapText, trapNETrapLastTrapTimeStamp, trapChangedObjectId,
	trapChangedValueInteger, trapChangedValueDisplayString
					      FROM NLSBBN-TRAPS-MIB;



	       -- This MIB module uses the extended OBJECT-TYPE macro as
	       -- defined in RFC1212 and the TRAP-TYPE macro as defined
	       -- in RFC 1215.

		   --REVISION	"0" Sept 1, 2003
		   --DESCRIPTION
		   --			Added revision and description comment section


		--    OMNISTAR DM 1550 Laser Module (Forward Path Transmetter)  MIB MODULE

	-- This MIB module defines information for management of HFC networks
		-- 
		-- The MIB module assumes that all generic (static) network element
		-- information is defined in a different module such as the HFC module
		-- The MIB consists of two groups:
		-- the device type descriptor subgroup and 
		-- gx2Dm870 Network Elements subgroup.
		-- The device type descriptor subgroup is used to define 
		-- parameters specific to gx2Dm870 device type.
		-- These parameters are common across all network elements
		-- from gx2Dm870 device type.
		--
		-- The gx2Dm870 Network Elements subgroup is
		-- a list of gx2Dm870 type elements in the
		-- current network topology with nominal
		-- and current parameter values for the
		-- individual network elements; the individual
		-- network elements are identified by  
		-- index from hfcCommonTable.
		-- That implies what hfcCommonTableIndex and
		-- gx2Dm870TableIndex are equal for each individual
		-- network element.
		-- This table is an extension of the hfcCommonTable
		-- for all elements of gx2Dm870 type.
		--
		-- Both groups are mandatory for management of gx2Dm870 devices.

-- ****************************************************************************
		--
		-- All floating point numbers will be represented by an IEEE 32 Bit number.
		-- Conversion of this number must be done on the user interface to view the 
		-- actual floating point number. 
		--

		Float ::= Counter  -- UNSIGNED (32 BITS) 

-- ****************************************************************************

		-- gx2Dm870 Device Descriptor subgroup.

		-- The device type descriptor subgroup is used to define 
		-- parameters specific to gx2Dm870 device type.
		-- These parameters are common across all network elements
		-- from gx2Dm870 device type.


		gx2Dm870Descriptor OBJECT IDENTIFIER ::= {gx2Dm870 1}



--*****************************************************************************
		--              gx2Dm870 Table
		
		-- Contains a list of all gx2Dm870 type devices in
		-- the network. Each device is characterized with
		-- current network topology information, with nominal
		-- and current parameter values for the
		-- individual network elements;
		--
		-- The individual network elements indentified by  
		-- index from hfcCommonTable.
		-- That implies what hfcCommonTableIndex and
		-- gx2Dm870TableIndex are equal for each individual
		-- nettwork element.
		-- This table should be used as an extension of the hfcCommonTable
		-- for all elements of gx2Dm870 type.


	       gx2Dm870AnalogTable                    OBJECT-TYPE
			 SYNTAX             SEQUENCE OF Gx2Dm870AnalogEntry
			 ACCESS             not-accessible
			 STATUS             mandatory
			 DESCRIPTION
			 "This table contains gx2Dm870 specific parameters with
			  nominal and current values."
			 ::= { gx2Dm870 2 }


	       gx2Dm870AnalogEntry               OBJECT-TYPE
			 SYNTAX             Gx2Dm870AnalogEntry
			 ACCESS             not-accessible
			 STATUS             mandatory
			 DESCRIPTION
			 "This list contains the analog parameters and descriptions."
			 INDEX { gx2Dm870AnalogTableIndex }
			 ::= { gx2Dm870AnalogTable  1}

--*************************************************************************
	       gx2Dm870DigitalTable                    OBJECT-TYPE
			 SYNTAX             SEQUENCE OF Gx2Dm870DigitalEntry
			 ACCESS             not-accessible
			 STATUS             mandatory
			 DESCRIPTION
			 "This table contains gx2Dm870m specific parameters with
			  nominal and current values."
			 ::= { gx2Dm870 3 }

	       gx2Dm870DigitalEntry               OBJECT-TYPE
			 SYNTAX             Gx2Dm870DigitalEntry
			 ACCESS             not-accessible
			 STATUS             mandatory
			 DESCRIPTION
			 "This list contains digital parameters and descriptions."
			 INDEX { gx2Dm870DigitalTableIndex }
			 ::= { gx2Dm870DigitalTable  2}

--*************************************************************************
	       gx2Dm870StatusTable                    OBJECT-TYPE
			 SYNTAX             SEQUENCE OF Gx2Dm870StatusEntry
			 ACCESS             not-accessible
			 STATUS             mandatory
			 DESCRIPTION
			 "This table contains gx2Dm870 specific parameters with
			  nominal and current values."
			 ::= { gx2Dm870 4 }

	       gx2Dm870StatusEntry               OBJECT-TYPE
			 SYNTAX             Gx2Dm870StatusEntry
			 ACCESS             not-accessible
			 STATUS             mandatory
			 DESCRIPTION
			 "This list contains Status parameters and descriptions."
			 INDEX { gx2Dm870StatusTableIndex }
			 ::= { gx2Dm870StatusTable  3}

--*************************************************************************
	       gx2Dm870FactoryTable                    OBJECT-TYPE
			 SYNTAX             SEQUENCE OF Gx2Dm870FactoryEntry
			 ACCESS             not-accessible
			 STATUS             mandatory
			 DESCRIPTION
			 "This table contains gx2Dm870 specific parameters with
			  nominal and current values."
			 ::= { gx2Dm870 5 }

	       gx2Dm870FactoryEntry               OBJECT-TYPE
			 SYNTAX             Gx2Dm870FactoryEntry
			 ACCESS             not-accessible
			 STATUS             mandatory
			 DESCRIPTION
			 "This list contains Factory parameters and descriptions."
			 INDEX { gx2Dm870FactoryTableIndex }
			 ::= { gx2Dm870FactoryTable  4}
--*************************************************************************

	      Gx2Dm870AnalogEntry    ::= SEQUENCE  
	       {
		gx2Dm870AnalogTableIndex         INTEGER,
		
		--           Analog Parameters

		dm870labelOffsetNomMonitor			DisplayString (SIZE (0..80)),
		dm870uomOffsetNomMonitor			DisplayString (SIZE (0..80)),
		dm870majorHighOffsetNomMonitor 		Float, 
		dm870majorLowOffsetNomMonitor 		Float, 
		dm870minorHighOffsetNomMonitor 		Float,
		dm870minorLowOffsetNomMonitor 		Float, 
		dm870currentValueOffsetNomMonitor 	Float, 
		dm870stateFlagOffsetNomMonitor 		INTEGER,
		dm870minValueOffsetNomMonitor 		Float,
		dm870maxValueOffsetNomMonitor  		Float,
		dm870alarmStateOffsetNomMonitor 	INTEGER,

		dm870labelOffsetNomCnt				DisplayString (SIZE (0..80)),
		dm870uomOffsetNomCnt				DisplayString (SIZE (0..80)),
		dm870majorHighOffsetNomCnt			Float, 
		dm870majorLowOffsetNomCnt			Float, 
		dm870minorHighOffsetNomCnt			Float,
		dm870minorLowOffsetNomCnt			Float, 
		dm870currentValueOffsetNomCnt		Float, 
		dm870stateFlagOffsetNomCnt			INTEGER,
		dm870minValueOffsetNomCnt			Float,
		dm870maxValueOffsetNomCnt 			Float,
		dm870alarmStateOffsetNomCnt			INTEGER,

		dm870labelAttenSetting				DisplayString (SIZE (0..80)),
		dm870uomAttenSetting				DisplayString (SIZE (0..80)),
		dm870majorHighAttenSetting			Float, 
		dm870majorLowAttenSetting			Float, 
		dm870minorHighAttenSetting			Float,
		dm870minorLowAttenSetting			Float, 
		dm870currentValueAttenSetting		Float, 
		dm870stateFlagAttenSetting			INTEGER,
		dm870minValueAttenSetting			Float,
		dm870maxValueAttenSetting 			Float,
		dm870alarmStateAttenSetting			INTEGER,

		dm870labelLaserPower				DisplayString (SIZE (0..80)),
		dm870uomLaserPower					DisplayString (SIZE (0..80)),
		dm870majorHighLaserPower			Float, 
		dm870majorLowLaserPower				Float, 
		dm870minorHighLaserPower			Float,
		dm870minorLowLaserPower				Float, 
		dm870currentValueLaserPower			Float, 
		dm870stateFlagLaserPower			INTEGER,
		dm870minValueLaserPower				Float,
		dm870maxValueLaserPower 			Float,
		dm870alarmStateLaserPower			INTEGER,

		dm870labelLaserTemp					DisplayString (SIZE (0..80)),
		dm870uomLaserTemp					DisplayString (SIZE (0..80)),
		dm870majorHighLaserTemp				Float, 
		dm870majorLowLaserTemp				Float, 
		dm870minorHighLaserTemp				Float,
		dm870minorLowLaserTemp				Float, 
		dm870currentValueLaserTemp			Float, 
		dm870stateFlagLaserTemp				INTEGER,
		dm870minValueLaserTemp				Float,
		dm870maxValueLaserTemp 				Float,
		dm870alarmStateLaserTemp			INTEGER,

		dm870labelLaserCurrent				DisplayString (SIZE (0..80)),
		dm870uomLaserCurrent				DisplayString (SIZE (0..80)),
		dm870majorHighLaserCurrent			Float, 
		dm870majorLowLaserCurrent			Float, 
		dm870minorHighLaserCurrent			Float,
		dm870minorLowLaserCurrent			Float, 
		dm870currentValueLaserCurrent		Float, 
		dm870stateFlagLaserCurrent			INTEGER,
		dm870minValueLaserCurrent			Float,
		dm870maxValueLaserCurrent 			Float,
		dm870alarmStateLaserCurrent			INTEGER,

		dm870labelTecCurrent				DisplayString (SIZE (0..80)),
		dm870uomTecCurrent					DisplayString (SIZE (0..80)),
		dm870majorHighTecCurrent			Float, 
		dm870majorLowTecCurrent				Float, 
		dm870minorHighTecCurrent			Float,
		dm870minorLowTecCurrent				Float, 
		dm870currentValueTecCurrent			Float, 
		dm870stateFlagTecCurrent			INTEGER,
		dm870minValueTecCurrent				Float,
		dm870maxValueTecCurrent				Float,
		dm870alarmStateTecCurrent			INTEGER,

		dm870labelModTemp					DisplayString (SIZE (0..80)),
		dm870uomModTemp						DisplayString (SIZE (0..80)),
		dm870majorHighModTemp				Float, 
		dm870majorLowModTemp				Float, 
		dm870minorHighModTemp				Float,
		dm870minorLowModTemp				Float, 
		dm870currentValueModTemp			Float, 
		dm870stateFlagModTemp				INTEGER,
		dm870minValueModTemp				Float,
		dm870maxValueModTemp 				Float,
		dm870alarmStateModTemp				INTEGER,

		dm870labelFanCurrent				DisplayString (SIZE (0..80)),
		dm870uomFanCurrent					DisplayString (SIZE (0..80)),
		dm870majorHighFanCurrent			Float, 
		dm870majorLowFanCurrent				Float, 
		dm870minorHighFanCurrent			Float,
		dm870minorLowFanCurrent				Float, 
		dm870currentValueFanCurrent			Float, 
		dm870stateFlagFanCurrent			INTEGER,
		dm870minValueFanCurrent				Float,
		dm870maxValueFanCurrent				Float,
		dm870alarmStateFanCurrent			INTEGER
		}

		-- ****************  Digital Parameters ***********************

      Gx2Dm870DigitalEntry    ::= SEQUENCE  
      {
		gx2Dm870DigitalTableIndex         INTEGER,

		dm870labelRfInput				DisplayString (SIZE (0..80)),
		dm870enumRfInput				DisplayString (SIZE (0..80)),
		dm870valueRfInput				INTEGER,
		dm870stateflagRfInput  			INTEGER,

		dm870labelOptOutput				DisplayString (SIZE (0..80)),
		dm870enumOptOutput				DisplayString (SIZE (0..80)),
		dm870valueOptOutput				INTEGER,
		dm870stateflagOptOutput         INTEGER,

		dm870labelSbsControl			DisplayString (SIZE (0..80)),
		dm870enumSbsControl				DisplayString (SIZE (0..80)),
		dm870valueSbsControl			INTEGER,
		dm870stateflagSbsControl        INTEGER,

		dm870labelLaserMode				DisplayString (SIZE (0..80)),
		dm870enumLaserMode				DisplayString (SIZE (0..80)),
		dm870valueLaserMode				INTEGER,
		dm870stateflagLaserMode         INTEGER,

		dm870labelFactoryDefault		DisplayString (SIZE (0..80)),
		dm870enumFactoryDefault			DisplayString (SIZE (0..80)),
		dm870valueFactoryDefault		INTEGER,
		dm870stateflagFactoryDefault   	INTEGER
		}


		-- ****************  Status Parameters ************************************
	    Gx2Dm870StatusEntry    ::= SEQUENCE  
	    {
		gx2Dm870StatusTableIndex		INTEGER,

		dm870labelBoot					DisplayString (SIZE (0..80)),
		dm870valueBoot					INTEGER,
		dm870stateflagBoot				INTEGER,
		
		dm870labelFlash					DisplayString (SIZE (0..80)),
		dm870valueFlash					INTEGER,
		dm870stateflagFlash				INTEGER,

		dm870labelFactoryDataCRC 		DisplayString (SIZE (0..80)),
		dm870valueFactoryDataCRC		INTEGER,
		dm870stateflagFactoryDataCRC	INTEGER,

		dm870labelLaserDataCRC 			DisplayString (SIZE (0..80)),
		dm870valueLaserDataCRC 			INTEGER,
		dm870stateflagLaserDataCRC 		INTEGER,

		dm870labelAlarmDataCrc			DisplayString (SIZE (0..80)),
		dm870valueAlarmDataCrc			INTEGER,
		dm870stateflagAlarmDataCrc		INTEGER,

		dm870labelRFInputStatus			DisplayString (SIZE (0..80)),
		dm870valueRFInputStatus			INTEGER,
		dm870stateflagRFInputStatus		INTEGER
		}


		-- ****************  Factory Parameters *************************************
	    Gx2Dm870FactoryEntry    ::= SEQUENCE  
	    {
		gx2Dm870FactoryTableIndex		INTEGER,
		dm870bootControlByte  			INTEGER,
		dm870bootStatusByte   			INTEGER,
		dm870bank1CRC    				INTEGER,
		dm870bank2CRC    				INTEGER,
		dm870prgEEPROMByte    			INTEGER,
		dm870factoryCRC    				INTEGER,
		dm870calculateCRC    			INTEGER,
		dm870hourMeter    				INTEGER,
		dm870flashPrgCntA    			INTEGER,
		dm870flashPrgCntB    			INTEGER,
		dm870flashBankARev    			DisplayString (SIZE (0..80)),
		dm870flashBankBRev    			DisplayString (SIZE (0..80))


		}
            -- ************** Analog Parameters ****************************
		gx2Dm870AnalogTableIndex			OBJECT-TYPE
			   SYNTAX				INTEGER (1..4294967295)
			   ACCESS				read-only
			   STATUS				mandatory
			   DESCRIPTION			
			   "The value of this object identifies the network
			    element. This index is equal to the
			    hfcCommonTableIndex for the same element."
			   ::= { gx2Dm870AnalogEntry 1}

-- New Parameter

		dm870labelOffsetNomMonitor              OBJECT-TYPE
			   SYNTAX           DisplayString (SIZE (0..80))
			   ACCESS           read-only
			   STATUS           optional
			   DESCRIPTION
			   "The value of this object provides the label of the
			    Offset Monitor Analog parameter."
			   ::= { gx2Dm870AnalogEntry 2}

		dm870uomOffsetNomMonitor                OBJECT-TYPE
			   SYNTAX           DisplayString (SIZE (0..80))
			   ACCESS           read-only
			   STATUS           optional
			   DESCRIPTION
			   "The value of this object provides the Unit of Measure of the
			    Offset Monitor Analog parameter."
			   ::= { gx2Dm870AnalogEntry 3}

		dm870majorHighOffsetNomMonitor          OBJECT-TYPE
			   SYNTAX           Float 
			   ACCESS           read-only
			   STATUS           mandatory
			   DESCRIPTION
			   "The value of this object provides the Major High alarm value
			    of the Offset Monitor Analog parameter.
			   This value is a floating point number that is represented as 
			   an IEEE 32 bit number. All F's indicate the parameter is unused"
			   ::= { gx2Dm870AnalogEntry 4}


		dm870majorLowOffsetNomMonitor           OBJECT-TYPE
			   SYNTAX           Float 
			   ACCESS           read-only
			   STATUS           mandatory
			   DESCRIPTION
			   "The value of this object provides the Major Low alarm value
			    of the Offset Monitor Power Analog parameter.
			   This value is a floating point number that is represented as 
			   an IEEE 32 bit number. All F's indicate the parameter is unused"
			   ::= { gx2Dm870AnalogEntry 5}

		dm870minorHighOffsetNomMonitor          OBJECT-TYPE
			   SYNTAX           Float
			   ACCESS           read-only
			   STATUS           mandatory
			   DESCRIPTION
			   "The value of this object provides the Minor High alarm value
			    of the Offset Monitor Power Analog parameter.
			   This value is a floating point number that is represented as 
			   an IEEE 32 bit number. All F's indicate the parameter is unused"
			   ::= { gx2Dm870AnalogEntry 6}

		dm870minorLowOffsetNomMonitor           OBJECT-TYPE
			   SYNTAX           Float 
			   ACCESS           read-only
			   STATUS           mandatory
			   DESCRIPTION
			   "The value of this object provides the Minor Low alarm value
			    of the Offset Monitor Power Analog parameter.
			   This value is a floating point number that is represented as 
			   an IEEE 32 bit number. All F's indicate the parameter is unused"
			   ::= { gx2Dm870AnalogEntry 7}

		dm870currentValueOffsetNomMonitor       OBJECT-TYPE
			   SYNTAX           Float 
			   ACCESS           read-only
			   STATUS           mandatory
			   DESCRIPTION
			   "The value of this object provides the Current value
			    of the Offset Monitor Power Analog parameter.
			   This value is a floating point number that is represented as an IEEE 32 bit number."
			   ::= { gx2Dm870AnalogEntry 8}

		dm870stateFlagOffsetNomMonitor          OBJECT-TYPE
			   SYNTAX           INTEGER
								{
								hidden(1),
								read-only(2),
								updateable(3)
								}
			   ACCESS           read-only
			   STATUS           mandatory
			   DESCRIPTION
			   "The value of this object provides the state
			    of the Offset Monitor Power Analog parameter. (0-Hidden	
			          1-Read-Only, 2-Updateable)."
			   ::= { gx2Dm870AnalogEntry 9}

		dm870minValueOffsetNomMonitor           OBJECT-TYPE
			   SYNTAX           Float
			   ACCESS           read-only
			   STATUS           mandatory
			   DESCRIPTION
			   "The value of this object provides the minimum value
			    the Offset Monitor Power Analog parameter can achive.
			   This value is a floating point number that is represented as an IEEE 32 bit number."
			   ::= { gx2Dm870AnalogEntry 10}

		dm870maxValueOffsetNomMonitor           OBJECT-TYPE
			   SYNTAX           Float
			   ACCESS           read-only
			   STATUS           mandatory
			   DESCRIPTION
			   "The value of this object provides the maximum value
			    the Offset Monitor Power Analog parameter can achive.
			   This value is a floating point number that is represented as an IEEE 32 bit number."
			   ::= { gx2Dm870AnalogEntry 11}

		dm870alarmStateOffsetNomMonitor         OBJECT-TYPE
			   SYNTAX           INTEGER
									{
									noAlarm(1),
									majorLowAlarm(2),
									minorLowAlarm(3),
									minorHighAlarm(4),
									majorHighAlarm(5),
									informational(6)
									}
			   ACCESS           read-only
			   STATUS           mandatory
			   DESCRIPTION
			   "The value of this object provides the curent alarm state of
			    the Offset Monitor Power Analog parameter."
			   ::= { gx2Dm870AnalogEntry 12}
			   
-- New Parameter

		dm870labelOffsetNomCnt       OBJECT-TYPE
			   SYNTAX           DisplayString (SIZE (0..80))
			   ACCESS           read-only
			   STATUS           optional
			   DESCRIPTION
			   "The value of this object provides the label of the
			    Offset Control Analog parameter."
			   ::= { gx2Dm870AnalogEntry 13}

		dm870uomOffsetNomCnt             OBJECT-TYPE
			   SYNTAX           DisplayString (SIZE (0..80))
			   ACCESS           read-only
			   STATUS           optional
			   DESCRIPTION
			   "The value of this object provides the Unit of Measure of the
			    Offset Control Analog parameter.."
			   ::= { gx2Dm870AnalogEntry 14}

		dm870majorHighOffsetNomCnt       OBJECT-TYPE
			   SYNTAX           Float 
			   ACCESS           read-only
			   STATUS           obsolete
			   DESCRIPTION
			   "The value of this object provides the Major High alarm value
			    of the Offset Control  Analog parameter.
			   This value is a floating point number that is represented as 
			   an IEEE 32 bit number. All F's indicate the parameter is unused"
			   ::= { gx2Dm870AnalogEntry 15}


		dm870majorLowOffsetNomCnt        OBJECT-TYPE
			   SYNTAX           Float 
			   ACCESS           read-only
			   STATUS           obsolete
			   DESCRIPTION
			   "The value of this object provides the Major Low alarm value
			    of the Offset Control Analog parameter.
			   This value is a floating point number that is represented as 
			   an IEEE 32 bit number. All F's indicate the parameter is unused"
			   ::= { gx2Dm870AnalogEntry 16}

		dm870minorHighOffsetNomCnt       OBJECT-TYPE
			   SYNTAX           Float
			   ACCESS           read-only
			   STATUS           obsolete
			   DESCRIPTION
			   "The value of this object provides the Minor High alarm value
			    of the Offset Control Analog parameter.
			   This value is a floating point number that is represented as 
			   an IEEE 32 bit number. All F's indicate the parameter is unused"
			   ::= { gx2Dm870AnalogEntry 17}

		dm870minorLowOffsetNomCnt        OBJECT-TYPE
			   SYNTAX           Float 
			   ACCESS           read-only
			   STATUS           obsolete
			   DESCRIPTION
			   "The value of this object provides the Minor Low alarm value
			    of the Offset Control Analog parameter.
			   This value is a floating point number that is represented as 
			   an IEEE 32 bit number. All F's indicate the parameter is unused"
			   ::= { gx2Dm870AnalogEntry 18}

		dm870currentValueOffsetNomCnt    OBJECT-TYPE
			   SYNTAX           Float 
			   ACCESS           read-write
			   STATUS           mandatory
			   DESCRIPTION
			   "The value of this object provides the Current value
			    of the Offset Control Analog parameter.
			   This value is a floating point number that is represented as an IEEE 32 bit number."
			   ::= { gx2Dm870AnalogEntry 19}

		dm870stateFlagOffsetNomCnt       OBJECT-TYPE
			   SYNTAX           INTEGER
								{
								hidden(1),
								read-only(2),
								updateable(3)
								}
			   ACCESS           read-only
			   STATUS           mandatory
			   DESCRIPTION
			   "The value of this object provides the state
			    of the Offset Control Analog parameter. (0-Hidden	
			          1-Read-Only, 2-Updateable)."
			   ::= { gx2Dm870AnalogEntry 20}

		dm870minValueOffsetNomCnt        OBJECT-TYPE
			   SYNTAX           Float
			   ACCESS           read-only
			   STATUS           mandatory
			   DESCRIPTION
			   "The value of this object provides the minimum value
			    the Offset Control Analog parameter can achive.
	   		   This value is a floating point number that is represented as an IEEE 32 bit number."
			   ::= { gx2Dm870AnalogEntry 21}

		dm870maxValueOffsetNomCnt        OBJECT-TYPE
			   SYNTAX           Float
			   ACCESS           read-only
			   STATUS           mandatory
			   DESCRIPTION
			   "The value of this object provides the maximum value
			    the Offset Control Analog parameter can achive.
			   This value is a floating point number that is represented as an IEEE 32 bit number."
			   ::= { gx2Dm870AnalogEntry 22}

		dm870alarmStateOffsetNomCnt      OBJECT-TYPE
			   SYNTAX           INTEGER
									{
									noAlarm(1),
									majorLowAlarm(2),
									minorLowAlarm(3),
									minorHighAlarm(4),
									majorHighAlarm(5),
									informational(6)
									}
			   ACCESS           read-only
			   STATUS           obsolete
			   DESCRIPTION
			   "The value of this object provides the curent alarm state of
			    the Offset Control Analog parameter."
			   ::= { gx2Dm870AnalogEntry 23}
-- New Parameter

		dm870labelAttenSetting            OBJECT-TYPE
			   SYNTAX           DisplayString (SIZE (0..80))
			   ACCESS           read-only
			   STATUS           optional
			   DESCRIPTION
			   "The value of this object provides the label of the
			    Attenuator Setting Current Analog parameter."
			   ::= { gx2Dm870AnalogEntry 24}

		dm870uomAttenSetting              OBJECT-TYPE
			   SYNTAX           DisplayString (SIZE (0..80))
			   ACCESS           read-only
			   STATUS           optional
			   DESCRIPTION
			   "The value of this object provides the Unit of Measure of the
			    Attenuator Setting Analog parameter."
			   ::= { gx2Dm870AnalogEntry 25}

		dm870majorHighAttenSetting        OBJECT-TYPE
			   SYNTAX           Float 
			   ACCESS           read-only
			   STATUS           obsolete
			   DESCRIPTION
			   "The value of this object provides the Major High alarm value
			    of the Attenuator Setting Analog parameter.
			   This value is a floating point number that is represented as 
			   an IEEE 32 bit number. All F's indicate the parameter is unused"
			   ::= { gx2Dm870AnalogEntry 26}


		dm870majorLowAttenSetting         OBJECT-TYPE
			   SYNTAX           Float 
			   ACCESS           read-only
			   STATUS           obsolete
			   DESCRIPTION
			   "The value of this object provides the Major Low alarm value
			    of the Attenuator Setting Analog parameter.
			   This value is a floating point number that is represented as 
			   an IEEE 32 bit number. All F's indicate the parameter is unused"
			   ::= { gx2Dm870AnalogEntry 27}

		dm870minorHighAttenSetting        OBJECT-TYPE
			   SYNTAX           Float
			   ACCESS           read-only
			   STATUS           obsolete
			   DESCRIPTION
			   "The value of this object provides the Minor High alarm value
			    of the Attenuator Setting Analog parameter.
			   This value is a floating point number that is represented as 
			   an IEEE 32 bit number. All F's indicate the parameter is unused"
			   ::= { gx2Dm870AnalogEntry 28}

		dm870minorLowAttenSetting         OBJECT-TYPE
			   SYNTAX           Float 
			   ACCESS           read-only
			   STATUS           obsolete
			   DESCRIPTION
			   "The value of this object provides the Minor Low alarm value
			    of the Attenuator Setting Analog parameter.
			   This value is a floating point number that is represented as 
			   an IEEE 32 bit number. All F's indicate the parameter is unused"
			   ::= { gx2Dm870AnalogEntry 29}

		dm870currentValueAttenSetting     OBJECT-TYPE
			   SYNTAX           Float 
			   ACCESS           read-write
			   STATUS           mandatory
			   DESCRIPTION
			   "The value of this object provides the Current value
			    of the Attenuator Setting Analog parameter.
			   This value is a floating point number that is represented as an 
			   IEEE 32 bit number."
			   ::= { gx2Dm870AnalogEntry 30}

		dm870stateFlagAttenSetting        OBJECT-TYPE
			   SYNTAX           INTEGER
								{
								hidden(1),
								read-only(2),
								updateable(3)
								}
			   ACCESS           read-only
			   STATUS           mandatory
			   DESCRIPTION
			   "The value of this object provides the state
			    of the Attenuator Setting Analog parameter. (0-Hidden	
			          1-Read-Only, 2-Updateable)."
			   ::= { gx2Dm870AnalogEntry 31}

		dm870minValueAttenSetting         OBJECT-TYPE
			   SYNTAX           Float
			   ACCESS           read-only
			   STATUS           mandatory
			   DESCRIPTION
			   "The value of this object provides the minimum value
			    the Attenuator Setting Analog parameter can achive.
			   This value is a floating point number that is represented as 
			   an IEEE 32 bit number."
			   ::= { gx2Dm870AnalogEntry 32}

		dm870maxValueAttenSetting         OBJECT-TYPE
			   SYNTAX           Float
			   ACCESS           read-only
			   STATUS           mandatory
			   DESCRIPTION
			   "The value of this object provides the maximum value
			    the Attenuator Setting Analog parameter can achive.
   			   This value is a floating point number that is represented as 
			   an IEEE 32 bit number."
			   ::= { gx2Dm870AnalogEntry 33}

		dm870alarmStateAttenSetting       OBJECT-TYPE
			   SYNTAX           INTEGER
									{
									noAlarm(1),
									majorLowAlarm(2),
									minorLowAlarm(3),
									minorHighAlarm(4),
									majorHighAlarm(5),
									informational(6)
									}
			   ACCESS           read-only
			   STATUS           mandatory
			   DESCRIPTION
			   "The value of this object provides the curent alarm state of
			    the Attenuator Setting Analog parameter."
			   ::= { gx2Dm870AnalogEntry 34}


-- New Parameter

		dm870labelLaserPower            OBJECT-TYPE
			   SYNTAX           DisplayString (SIZE (0..80))
			   ACCESS           read-only
			   STATUS           optional
			   DESCRIPTION
			   "The value of this object provides the label of the
			    Laser Optical Power Analog parameter."
			   ::= { gx2Dm870AnalogEntry 35}

		dm870uomLaserPower              OBJECT-TYPE
			   SYNTAX           DisplayString (SIZE (0..80))
			   ACCESS           read-only
			   STATUS           optional
			   DESCRIPTION
			   "The value of this object provides the Unit of Measure of the
			    Laser Optical Power Analog parameter."
			   ::= { gx2Dm870AnalogEntry 36}

		dm870majorHighLaserPower        OBJECT-TYPE
			   SYNTAX           Float 
			   ACCESS           read-only
			   STATUS           mandatory
			   DESCRIPTION
			   "The value of this object provides the Major High alarm value
			    of the Laser Optical Power Analog parameter.
			   This value is a floating point number that is represented as 
			   an IEEE 32 bit number. All F's indicate the parameter is unused"
			   ::= { gx2Dm870AnalogEntry 37}


		dm870majorLowLaserPower         OBJECT-TYPE
			   SYNTAX           Float 
			   ACCESS           read-only
			   STATUS           mandatory
			   DESCRIPTION
			   "The value of this object provides the Major Low alarm value
			    of the Laser Optical Power Analog parameter.
			   This value is a floating point number that is represented as 
			   an IEEE 32 bit number. All F's indicate the parameter is unused"
			   ::= { gx2Dm870AnalogEntry 38}

		dm870minorHighLaserPower        OBJECT-TYPE
			   SYNTAX           Float
			   ACCESS           read-only
			   STATUS           obsolete
			   DESCRIPTION
			   "The value of this object provides the Minor High alarm value
			    of the Laser Optical Power Analog parameter.
			   This value is a floating point number that is represented as 
			   an IEEE 32 bit number. All F's indicate the parameter is unused"
			   ::= { gx2Dm870AnalogEntry 39}

		dm870minorLowLaserPower         OBJECT-TYPE
			   SYNTAX           Float 
			   ACCESS           read-only
			   STATUS           obsolete
			   DESCRIPTION
			   "The value of this object provides the Minor Low alarm value
			    of the Laser Optical Power Analog parameter.
			   This value is a floating point number that is represented as 
			   an IEEE 32 bit number. All F's indicate the parameter is unused"
			   ::= { gx2Dm870AnalogEntry 40}

		dm870currentValueLaserPower     OBJECT-TYPE
			   SYNTAX           Float 
			   ACCESS           read-only
			   STATUS           mandatory
			   DESCRIPTION
			   "The value of this object provides the Current value
			    of the Laser Optical Power Analog parameter.
			   This value is a floating point number that is represented as 
			   an IEEE 32 bit number."
			   ::= { gx2Dm870AnalogEntry 41}

		dm870stateFlagLaserPower        OBJECT-TYPE
			   SYNTAX           INTEGER
								{
								hidden(1),
								read-only(2),
								updateable(3)
								}
			   ACCESS           read-only
			   STATUS           mandatory
			   DESCRIPTION
			   "The value of this object provides the state
			    of the Laser Optical Power Analog parameter. (0-Hidden	
			          1-Read-Only, 2-Updateable)."
			   ::= { gx2Dm870AnalogEntry 42}

		dm870minValueLaserPower         OBJECT-TYPE
			   SYNTAX           Float
			   ACCESS           read-only
			   STATUS           mandatory
			   DESCRIPTION
			   "The value of this object provides the minimum value
			    the Laser Optical Power Analog parameter can achive.
			   This value is a floating point number that is represented as 
			   an IEEE 32 bit number."
			   ::= { gx2Dm870AnalogEntry 43}

		dm870maxValueLaserPower         OBJECT-TYPE
			   SYNTAX           Float
			   ACCESS           read-only
			   STATUS           mandatory
			   DESCRIPTION
			   "The value of this object provides the maximum value
			    the Laser Optical Power Analog parameter can achive.
   			   This value is a floating point number that is represented as 
			   an IEEE 32 bit number."
			   ::= { gx2Dm870AnalogEntry 44}

		dm870alarmStateLaserPower       OBJECT-TYPE
			   SYNTAX           INTEGER
									{
									noAlarm(1),
									majorLowAlarm(2),
									minorLowAlarm(3),
									minorHighAlarm(4),
									majorHighAlarm(5),
									informational(6)
									}
			   ACCESS           read-only
			   STATUS           mandatory
			   DESCRIPTION
			   "The value of this object provides the curent alarm state of
			    the Laser Optical Power Analog parameter."
			   ::= { gx2Dm870AnalogEntry 45}

-- New Parameter


		dm870labelLaserTemp           OBJECT-TYPE
			   SYNTAX           DisplayString (SIZE (0..80))
			   ACCESS           read-only
			   STATUS           optional
			   DESCRIPTION
			   "The value of this object provides the label of the
			    Laser Temperature Analog parameter."
			   ::= { gx2Dm870AnalogEntry 46}

		dm870uomLaserTemp             OBJECT-TYPE
			   SYNTAX           DisplayString (SIZE (0..80))
			   ACCESS           read-only
			   STATUS           optional
			   DESCRIPTION
			   "The value of this object provides the Unit of Measure of the
			    Laser Temperature Analog parameter.."
			   ::= { gx2Dm870AnalogEntry 47}

		dm870majorHighLaserTemp       OBJECT-TYPE
			   SYNTAX           Float 
			   ACCESS           read-only
			   STATUS           mandatory
			   DESCRIPTION
			   "The value of this object provides the Major High alarm value
			    of the Laser Temperature Analog parameter.
			   This value is a floating point number that is represented as 
			   an IEEE 32 bit number. All F's indicate the parameter is unused"
			   ::= { gx2Dm870AnalogEntry 48}


		dm870majorLowLaserTemp        OBJECT-TYPE
			   SYNTAX           Float 
			   ACCESS           read-only
			   STATUS           mandatory
			   DESCRIPTION
			   "The value of this object provides the Major Low alarm value
			    of the Laser Temperature Analog parameter.
			   This value is a floating point number that is represented as 
			   an IEEE 32 bit number. All F's indicate the parameter is unused"
			   ::= { gx2Dm870AnalogEntry 49}

		dm870minorHighLaserTemp       OBJECT-TYPE
			   SYNTAX           Float
			   ACCESS           read-only
			   STATUS           obsolete
			   DESCRIPTION
			   "The value of this object provides the Minor High alarm value
			    of the Laser Temperature Analog parameter.
			   This value is a floating point number that is represented as 
			   an IEEE 32 bit number. All F's indicate the parameter is unused"
			   ::= { gx2Dm870AnalogEntry 50}

		dm870minorLowLaserTemp        OBJECT-TYPE
			   SYNTAX           Float 
			   ACCESS           read-only
			   STATUS           obsolete
			   DESCRIPTION
			   "The value of this object provides the Minor Low alarm value
			    of the Laser Temperature Analog parameter.
			   This value is a floating point number that is represented as 
			   an IEEE 32 bit number. All F's indicate the parameter is unused"
			   ::= { gx2Dm870AnalogEntry 51}

		dm870currentValueLaserTemp    OBJECT-TYPE
			   SYNTAX           Float 
			   ACCESS           read-only
			   STATUS           mandatory
			   DESCRIPTION
			   "The value of this object provides the Current value
			    of the Laser Temperature Analog parameter.
			   This value is a floating point number that is represented as 
			   an IEEE 32 bit number."
			   ::= { gx2Dm870AnalogEntry 52}

		dm870stateFlagLaserTemp       OBJECT-TYPE
			   SYNTAX           INTEGER
								{
								hidden(1),
								read-only(2),
								updateable(3)
								}
			   ACCESS           read-only
			   STATUS           mandatory
			   DESCRIPTION
			   "The value of this object provides the state
			    of the Laser Temperature Analog parameter. (0-Hidden	
			          1-Read-Only, 2-Updateable)."
			   ::= { gx2Dm870AnalogEntry 53}

		dm870minValueLaserTemp        OBJECT-TYPE
			   SYNTAX           Float
			   ACCESS           read-only
			   STATUS           mandatory
			   DESCRIPTION
			   "The value of this object provides the minimum value
			    the Laser Temperature Analog parameter can achive.
	   		   This value is a floating point number that is represented as 
			   an IEEE 32 bit number."
			   ::= { gx2Dm870AnalogEntry 54}

		dm870maxValueLaserTemp        OBJECT-TYPE
			   SYNTAX           Float
			   ACCESS           read-only
			   STATUS           mandatory
			   DESCRIPTION
			   "The value of this object provides the maximum value
			    the Laser Temperature Analog parameter can achive.
			   This value is a floating point number that is represented as 
			   an IEEE 32 bit number."
			   ::= { gx2Dm870AnalogEntry 55}

		dm870alarmStateLaserTemp      OBJECT-TYPE
			   SYNTAX           INTEGER
									{
									noAlarm(1),
									majorLowAlarm(2),
									minorLowAlarm(3),
									minorHighAlarm(4),
									majorHighAlarm(5),
									informational(6)
									}
			   ACCESS           read-only
			   STATUS           mandatory
			   DESCRIPTION
			   "The value of this object provides the curent alarm state of
			    the Laser Temperature Analog parameter."
			   ::= { gx2Dm870AnalogEntry 56}

-- New Parameter

		dm870labelLaserCurrent            OBJECT-TYPE
			   SYNTAX           DisplayString (SIZE (0..80))
			   ACCESS           read-only
			   STATUS           optional
			   DESCRIPTION
			   "The value of this object provides the label of the
			    Laser Bias Current Analog parameter."
			   ::= { gx2Dm870AnalogEntry 57}

		dm870uomLaserCurrent              OBJECT-TYPE
			   SYNTAX           DisplayString (SIZE (0..80))
			   ACCESS           read-only
			   STATUS           optional
			   DESCRIPTION
			   "The value of this object provides the Unit of Measure of the
			    Laser Bias Current Analog parameter."
			   ::= { gx2Dm870AnalogEntry 58}

		dm870majorHighLaserCurrent        OBJECT-TYPE
			   SYNTAX           Float 
			   ACCESS           read-only
			   STATUS           mandatory
			   DESCRIPTION
			   "The value of this object provides the Major High alarm value
			    of the Laser Bias Current Analog parameter.
			   This value is a floating point number that is represented as 
			   an IEEE 32 bit number. All F's indicate the parameter is unused"
			   ::= { gx2Dm870AnalogEntry 59}


		dm870majorLowLaserCurrent         OBJECT-TYPE
			   SYNTAX           Float 
			   ACCESS           read-only
			   STATUS           mandatory
			   DESCRIPTION
			   "The value of this object provides the Major Low alarm value
			    of the Laser Bias Current Analog parameter.
			   This value is a floating point number that is represented as 
			   an IEEE 32 bit number. All F's indicate the parameter is unused"
			   ::= { gx2Dm870AnalogEntry 60}

		dm870minorHighLaserCurrent        OBJECT-TYPE
			   SYNTAX           Float
			   ACCESS           read-only
			   STATUS           obsolete
			   DESCRIPTION
			   "The value of this object provides the Minor High alarm value
			    of the Laser Bias Current Analog parameter.
			   This value is a floating point number that is represented as 
			   an IEEE 32 bit number. All F's indicate the parameter is unused"
			   ::= { gx2Dm870AnalogEntry 61}

		dm870minorLowLaserCurrent         OBJECT-TYPE
			   SYNTAX           Float 
			   ACCESS           read-only
			   STATUS           obsolete
			   DESCRIPTION
			   "The value of this object provides the Minor Low alarm value
			    of the Laser Bias Current Analog parameter.
			   This value is a floating point number that is represented as 
			   an IEEE 32 bit number. All F's indicate the parameter is unused"
			   ::= { gx2Dm870AnalogEntry 62}

		dm870currentValueLaserCurrent     OBJECT-TYPE
			   SYNTAX           Float 
			   ACCESS           read-only
			   STATUS           mandatory
			   DESCRIPTION
			   "The value of this object provides the Current value
			    of the Laser Bias Current Analog parameter.
			   This value is a floating point number that is represented as 
			   an IEEE 32 bit number."
			   ::= { gx2Dm870AnalogEntry 63}

		dm870stateFlagLaserCurrent        OBJECT-TYPE
			   SYNTAX           INTEGER
								{
								hidden(1),
								read-only(2),
								updateable(3)
								}
			   ACCESS           read-only
			   STATUS           mandatory
			   DESCRIPTION
			   "The value of this object provides the state
			    of the Laser Bias Current Analog parameter. (0-Hidden	
			          1-Read-Only, 2-Updateable)."
			   ::= { gx2Dm870AnalogEntry 64}

		dm870minValueLaserCurrent         OBJECT-TYPE
			   SYNTAX           Float
			   ACCESS           read-only
			   STATUS           mandatory
			   DESCRIPTION
			   "The value of this object provides the minimum value
			    the Laser Bias Current Analog parameter can achive.
			   This value is a floating point number that is represented as 
			   an IEEE 32 bit number."
			   ::= { gx2Dm870AnalogEntry 65}

		dm870maxValueLaserCurrent         OBJECT-TYPE
			   SYNTAX           Float
			   ACCESS           read-only
			   STATUS           mandatory
			   DESCRIPTION
			   "The value of this object provides the maximum value
			    the Laser Bias Current Analog parameter can achive.
   			   This value is a floating point number that is represented as 
			   an IEEE 32 bit number."
			   ::= { gx2Dm870AnalogEntry 66}

		dm870alarmStateLaserCurrent       OBJECT-TYPE
			   SYNTAX           INTEGER
									{
									noAlarm(1),
									majorLowAlarm(2),
									minorLowAlarm(3),
									minorHighAlarm(4),
									majorHighAlarm(5),
									informational(6)
									}
			   ACCESS           read-only
			   STATUS           mandatory
			   DESCRIPTION
			   "The value of this object provides the curent alarm state of
			    the Laser Bias Current Analog parameter."
			   ::= { gx2Dm870AnalogEntry 67}

-- New Parameter

		dm870labelTecCurrent              OBJECT-TYPE
			   SYNTAX           DisplayString (SIZE (0..80))
			   ACCESS           read-only
			   STATUS           optional
			   DESCRIPTION
			   "The value of this object provides the label of the
			    TEC Current Analog parameter."
			   ::= { gx2Dm870AnalogEntry 68}

		dm870uomTecCurrent                OBJECT-TYPE
			   SYNTAX           DisplayString (SIZE (0..80))
			   ACCESS           read-only
			   STATUS           optional
			   DESCRIPTION
			   "The value of this object provides the Unit of Measure of the
			    TEC Current Analog parameter."
			   ::= { gx2Dm870AnalogEntry 69}

		dm870majorHighTecCurrent          OBJECT-TYPE
			   SYNTAX           Float 
			   ACCESS           read-only
			   STATUS           mandatory
			   DESCRIPTION
			   "The value of this object provides the Major High alarm value
			    of the TEC Current Analog parameter.
			   This value is a floating point number that is represented as 
			   an IEEE 32 bit number. All F's indicate the parameter is unused"
			   ::= { gx2Dm870AnalogEntry 70}


		dm870majorLowTecCurrent           OBJECT-TYPE
			   SYNTAX           Float 
			   ACCESS           read-only
			   STATUS           mandatory
			   DESCRIPTION
			   "The value of this object provides the Major Low alarm value
			    of the TEC Current Analog parameter.
			   This value is a floating point number that is represented as 
			   an IEEE 32 bit number. All F's indicate the parameter is unused"
			   ::= { gx2Dm870AnalogEntry 71}

		dm870minorHighTecCurrent          OBJECT-TYPE
			   SYNTAX           Float
			   ACCESS           read-only
			   STATUS           obsolete
			   DESCRIPTION
			   "The value of this object provides the Minor High alarm value
			    of the TEC Current Analog parameter.
			   This value is a floating point number that is represented as 
			   an IEEE 32 bit number. All F's indicate the parameter is unused"
			   ::= { gx2Dm870AnalogEntry 72}

		dm870minorLowTecCurrent           OBJECT-TYPE
			   SYNTAX           Float 
			   ACCESS           read-only
			   STATUS           obsolete
			   DESCRIPTION
			   "The value of this object provides the Minor Low alarm value
			    of the TEC Current Analog parameter.
			   This value is a floating point number that is represented as 
			   an IEEE 32 bit number. All F's indicate the parameter is unused"
			   ::= { gx2Dm870AnalogEntry 73}

		dm870currentValueTecCurrent       OBJECT-TYPE
			   SYNTAX           Float 
			   ACCESS           read-only
			   STATUS           mandatory
			   DESCRIPTION
			   "The value of this object provides the Current value
			    of the TEC Current Analog parameter.
			   This value is a floating point number that is represented as 
			   an IEEE 32 bit number."
			   ::= { gx2Dm870AnalogEntry 74}

		dm870stateFlagTecCurrent          OBJECT-TYPE
			   SYNTAX           INTEGER
								{
								hidden(1),
								read-only(2),
								updateable(3)
								}
			   ACCESS           read-only
			   STATUS           mandatory
			   DESCRIPTION
			   "The value of this object provides the state
			    of the TEC Current Analog parameter. (0-Hidden	
			          1-Read-Only, 2-Updateable)."
			   ::= { gx2Dm870AnalogEntry 75}

		dm870minValueTecCurrent           OBJECT-TYPE
			   SYNTAX           Float
			   ACCESS           read-only
			   STATUS           mandatory
			   DESCRIPTION
			   "The value of this object provides the minimum value
			    the TEC Current Analog parameter can achive.
			   This value is a floating point number that is represented as 
			   an IEEE 32 bit number."
			   ::= { gx2Dm870AnalogEntry 76}

		dm870maxValueTecCurrent           OBJECT-TYPE
			   SYNTAX           Float
			   ACCESS           read-only
			   STATUS           mandatory
			   DESCRIPTION
			   "The value of this object provides the maximum value
			    the TEC Current Analog parameter can achive.
			   This value is a floating point number that is represented as 
			   an IEEE 32 bit number."
			   ::= { gx2Dm870AnalogEntry 77}

		dm870alarmStateTecCurrent         OBJECT-TYPE
			   SYNTAX           INTEGER
									{
									noAlarm(1),
									majorLowAlarm(2),
									minorLowAlarm(3),
									minorHighAlarm(4),
									majorHighAlarm(5),
									informational(6)
									}
			   ACCESS           read-only
			   STATUS           mandatory
			   DESCRIPTION
			   "The value of this object provides the curent alarm state of
			    the TEC Current Analog parameter."
			   ::= { gx2Dm870AnalogEntry 78}




-- New Parameter

		dm870labelModTemp           OBJECT-TYPE
			   SYNTAX           DisplayString (SIZE (0..80))
			   ACCESS           read-only
			   STATUS           optional
			   DESCRIPTION
			   "The value of this object provides the label of the
			    Module Temperature Analog parameter."
			   ::= { gx2Dm870AnalogEntry 79}

		dm870uomModTemp             OBJECT-TYPE
			   SYNTAX           DisplayString (SIZE (0..80))
			   ACCESS           read-only
			   STATUS           optional
			   DESCRIPTION
			   "The value of this object provides the Unit of Measure of the
			    Module Temperature Analog parameter."
			   ::= { gx2Dm870AnalogEntry 80}

		dm870majorHighModTemp       OBJECT-TYPE
			   SYNTAX           Float 
			   ACCESS           read-only
			   STATUS           mandatory
			   DESCRIPTION
			   "The value of this object provides the Major High alarm value
			    of the Module Temperature Analog parameter.
			   This value is a floating point number that is represented as 
			   an IEEE 32 bit number. All F's indicate the parameter is unused"
			   ::= { gx2Dm870AnalogEntry 81}


		dm870majorLowModTemp        OBJECT-TYPE
			   SYNTAX           Float 
			   ACCESS           read-only
			   STATUS           mandatory
			   DESCRIPTION
			   "The value of this object provides the Major Low alarm value
			    of the Module Temperature Analog parameter.
			   This value is a floating point number that is represented as 
			   an IEEE 32 bit number. All F's indicate the parameter is unused"
			   ::= { gx2Dm870AnalogEntry 82}

		dm870minorHighModTemp       OBJECT-TYPE
			   SYNTAX           Float
			   ACCESS           read-only
			   STATUS           mandatory
			   DESCRIPTION
			   "The value of this object provides the Minor High alarm value
			    of the Module Temperature Analog parameter.
			   This value is a floating point number that is represented as 
			   an IEEE 32 bit number. All F's indicate the parameter is unused"
			   ::= { gx2Dm870AnalogEntry 83}

		dm870minorLowModTemp        OBJECT-TYPE
			   SYNTAX           Float 
			   ACCESS           read-only
			   STATUS           mandatory
			   DESCRIPTION
			   "The value of this object provides the Minor Low alarm value
			    of the Module Temperature Analog parameter.
			   This value is a floating point number that is represented as 
			   an IEEE 32 bit number. All F's indicate the parameter is unused"
			   ::= { gx2Dm870AnalogEntry 84}

		dm870currentValueModTemp    OBJECT-TYPE
			   SYNTAX           Float 
			   ACCESS           read-only
			   STATUS           mandatory
			   DESCRIPTION
			   "The value of this object provides the Current value
			    of the Module Temperature Analog parameter.
			   This value is a floating point number that is represented as 
			   an IEEE 32 bit number."
			   ::= { gx2Dm870AnalogEntry 85}

		dm870stateFlagModTemp       OBJECT-TYPE
			   SYNTAX           INTEGER
								{
								hidden(1),
								read-only(2),
								updateable(3)
								}
			   ACCESS           read-only
			   STATUS           mandatory
			   DESCRIPTION
			   "The value of this object provides the state
			    of the Module Temperature Analog parameter. (0-Hidden	
			          1-Read-Only, 2-Updateable)."
			   ::= { gx2Dm870AnalogEntry 86}

		dm870minValueModTemp        OBJECT-TYPE
			   SYNTAX           Float
			   ACCESS           read-only
			   STATUS           mandatory
			   DESCRIPTION
			   "The value of this object provides the minimum value
			    the Module Temperature Analog parameter can achive.
			   This value is a floating point number that is represented as 
			   an IEEE 32 bit number."
			   ::= { gx2Dm870AnalogEntry 87}

		dm870maxValueModTemp        OBJECT-TYPE
			   SYNTAX           Float
			   ACCESS           read-only
			   STATUS           mandatory
			   DESCRIPTION
			   "The value of this object provides the maximum value
			    the Module Temperature Analog parameter can achive.
			   This value is a floating point number that is represented as 
			   an IEEE 32 bit number."
			   ::= { gx2Dm870AnalogEntry 88}

		dm870alarmStateModTemp      OBJECT-TYPE
			   SYNTAX           INTEGER
									{
									noAlarm(1),
									majorLowAlarm(2),
									minorLowAlarm(3),
									minorHighAlarm(4),
									majorHighAlarm(5),
									informational(6)
									}
			   ACCESS           read-only
			   STATUS           mandatory
			   DESCRIPTION
			   "The value of this object provides the curent alarm state of
			    the Module Temperature Analog parameter."
			   ::= { gx2Dm870AnalogEntry 89}

-- New Parameter

		dm870labelFanCurrent               OBJECT-TYPE
			   SYNTAX           DisplayString (SIZE (0..80))
			   ACCESS           read-only
			   STATUS           optional
			   DESCRIPTION
			   "The value of this object provides the label of the
			    Fan Current Analog parameter."
			   ::= { gx2Dm870AnalogEntry 90}

		dm870uomFanCurrent                 OBJECT-TYPE
			   SYNTAX           DisplayString (SIZE (0..80))
			   ACCESS           read-only
			   STATUS           optional
			   DESCRIPTION
			   "The value of this object provides the Unit of Measure of the
			    Fan Current Analog parameter."
			   ::= { gx2Dm870AnalogEntry 91}

		dm870majorHighFanCurrent           OBJECT-TYPE
			   SYNTAX           Float 
			   ACCESS           read-only
			   STATUS           mandatory
			   DESCRIPTION
			   "The value of this object provides the Major High alarm value
			    of the Fan Current Analog parameter.
			   This value is a floating point number that is represented as 
			   an IEEE 32 bit number. All F's indicate the parameter is unused"
			   ::= { gx2Dm870AnalogEntry 92}


		dm870majorLowFanCurrent            OBJECT-TYPE
			   SYNTAX           Float 
			   ACCESS           read-only
			   STATUS           mandatory
			   DESCRIPTION
			   "The value of this object provides the Major Low alarm value
			    of the Fan Current Analog parameter.
			   This value is a floating point number that is represented as 
			   an IEEE 32 bit number. All F's indicate the parameter is unused"
			   ::= { gx2Dm870AnalogEntry 93}

		dm870minorHighFanCurrent           OBJECT-TYPE
			   SYNTAX           Float
			   ACCESS           read-only
			   STATUS           obsolete
			   DESCRIPTION
			   "The value of this object provides the Minor High alarm value
			    of the Fan Current Analog parameter.
			   This value is a floating point number that is represented as 
			   an IEEE 32 bit number. All F's indicate the parameter is unused"
			   ::= { gx2Dm870AnalogEntry 94}

		dm870minorLowFanCurrent            OBJECT-TYPE
			   SYNTAX           Float 
			   ACCESS           read-only
			   STATUS           obsolete
			   DESCRIPTION
			   "The value of this object provides the Minor Low alarm value
			    of the Fan Current Analog parameter.
			   This value is a floating point number that is represented as 
			   an IEEE 32 bit number. All F's indicate the parameter is unused"
			   ::= { gx2Dm870AnalogEntry 95}

		dm870currentValueFanCurrent        OBJECT-TYPE
			   SYNTAX           Float 
			   ACCESS           read-only
			   STATUS           mandatory
			   DESCRIPTION
			   "The value of this object provides the Current value
			    of the Fan Current Analog parameter.
			   This value is a floating point number that is represented as 
			   an IEEE 32 bit number."
			   ::= { gx2Dm870AnalogEntry 96}

		dm870stateFlagFanCurrent           OBJECT-TYPE
			   SYNTAX           INTEGER
								{
								hidden(1),
								read-only(2),
								updateable(3)
								}
			   ACCESS           read-only
			   STATUS           mandatory
			   DESCRIPTION
			   "The value of this object provides the state
			    of the Fan Current Analog parameter. (0-Hidden	
			          1-Read-Only, 2-Updateable)."
			   ::= { gx2Dm870AnalogEntry 97}

		dm870minValueFanCurrent            OBJECT-TYPE
			   SYNTAX           Float
			   ACCESS           read-only
			   STATUS           mandatory
			   DESCRIPTION
			   "The value of this object provides the minimum value
			    the Fan Current Analog parameter can achive.
			   This value is a floating point number that is represented as 
			   an IEEE 32 bit number."
			   ::= { gx2Dm870AnalogEntry 98}

		dm870maxValueFanCurrent            OBJECT-TYPE
			   SYNTAX           Float
			   ACCESS           read-only
			   STATUS           mandatory
			   DESCRIPTION
			   "The value of this object provides the maximum value
			    the Fan Current Analog parameter can achive.
			   This value is a floating point number that is represented as 
			   an IEEE 32 bit number."
			   ::= { gx2Dm870AnalogEntry 99}

		dm870alarmStateFanCurrent          OBJECT-TYPE
			   SYNTAX           INTEGER
									{
									noAlarm(1),
									majorLowAlarm(2),
									minorLowAlarm(3),
									minorHighAlarm(4),
									majorHighAlarm(5),
									informational(6)
									}
			   ACCESS           read-only
			   STATUS           mandatory
			   DESCRIPTION
			   "The value of this object provides the curent alarm state of
			    the Fan Current Analog parameter."
			   ::= { gx2Dm870AnalogEntry 100}

-- ************************ Digital parameters **********************************

		gx2Dm870DigitalTableIndex              OBJECT-TYPE
			   SYNTAX           INTEGER (1..4294967295)
			   ACCESS           read-only
			   STATUS           mandatory
			   DESCRIPTION
			   "The value of this object identifies the network
			    element. This index is equal to the
			    hfcCommonTableIndex for the same element."
			   ::= { gx2Dm870DigitalEntry 1}

-- New parameter
		dm870labelRfInput                	OBJECT-TYPE
			   SYNTAX       		DisplayString (SIZE (0..80))         
			   ACCESS           	read-only
			   STATUS           	optional
			   DESCRIPTION
			   "The value of this object provides the label of the
			    RF Input Control  Digital parameter."
			   ::= { gx2Dm870DigitalEntry 2}

		dm870enumRfInput               		OBJECT-TYPE
			   SYNTAX       		DisplayString (SIZE (0..80))         
			   ACCESS           	read-only
			   STATUS           	optional
			   DESCRIPTION
			   "The value of this object represents the Enumeration values
			    possible for the Digital parameter. Each Enumerated values is
			    separated by a common. The first value has a enumerated value of 1."
			   ::= { gx2Dm870DigitalEntry 3}

		dm870valueRfInput                	OBJECT-TYPE
			   SYNTAX       		INTEGER
					    		{
							off(1),
							on(2)
					    		}
			   ACCESS           	read-write
			   STATUS           	mandatory
			   DESCRIPTION
			   "The value of this object is the current value of the parameter."
			   ::= { gx2Dm870DigitalEntry 4}

		dm870stateflagRfInput              OBJECT-TYPE
			   SYNTAX       		INTEGER
								{
								hidden(1),
								read-only(2),
								updateable(3)
								}
			   ACCESS           	read-only
			   STATUS           	mandatory
			   DESCRIPTION
			   "The value of this object provides the state
			    of the RF Input Control  Digital parameter. (0-Hidden	
			          1-Read-Only, 2-Updateable)."
			   ::= { gx2Dm870DigitalEntry 5}

-- New parameter
		dm870labelOptOutput                OBJECT-TYPE
			   SYNTAX       		DisplayString (SIZE (0..80))         
			   ACCESS           	read-only
			   STATUS           	optional
			   DESCRIPTION
			   "The value of this object provides the label of the
			    Optical Output Control  Digital parameter."
			   ::= { gx2Dm870DigitalEntry 6}

		dm870enumOptOutput               	      OBJECT-TYPE
			   SYNTAX          	DisplayString (SIZE (0..80))         
			   ACCESS           	read-only
			   STATUS           	optional
			   DESCRIPTION
			   "The value of this object represents the Enumeration values
			    possible for the Digital parameter. Each Enumerated values is
			    separated by a common. The first value has a enumerated value of 1."
			   ::= { gx2Dm870DigitalEntry 7}

		dm870valueOptOutput                OBJECT-TYPE
			   SYNTAX       		INTEGER
					    		{
							off(1),
							on(2)
					    		}
			   ACCESS           	read-write
			   STATUS           	mandatory
			   DESCRIPTION
			   "The value of this object is the current value of the parameter."
			   ::= { gx2Dm870DigitalEntry 8}

		dm870stateflagOptOutput            OBJECT-TYPE
			   SYNTAX      		INTEGER
								{
								hidden(1),
								read-only(2),
								updateable(3)
								}
			   ACCESS           	read-only
			   STATUS           	mandatory
			   DESCRIPTION
			   "The value of this object provides the state
			    of the the parameter. (0-Hidden 1-Read-Only, 2-Updateable)."
			   ::= { gx2Dm870DigitalEntry 9}
-- New parameter
		dm870labelSbsControl                OBJECT-TYPE
			   SYNTAX         	DisplayString (SIZE (0..80))         
			   ACCESS           	read-only
			   STATUS           	optional
			   DESCRIPTION
			   "The value of this object provides the label of the
			    SBS Control Digital parameter."
			   ::= { gx2Dm870DigitalEntry 10}

		dm870enumSbsControl               	OBJECT-TYPE
			   SYNTAX         	DisplayString (SIZE (0..80))         
			   ACCESS           	read-only
			   STATUS           	optional
			   DESCRIPTION
			   "The value of this object represents the Enumeration values
			    possible for the Digital parameter. Each Enumerated values is
			    separated by a common. The first value has a enumerated value of 1."
			   ::= { gx2Dm870DigitalEntry 11}

		dm870valueSbsControl                OBJECT-TYPE
			   SYNTAX       		INTEGER
					    		{
							off(1),
							on(2)
					    		}
			   ACCESS           	read-write
			   STATUS           	mandatory
			   DESCRIPTION
			   "The value of this object is the current value of the parameter."
			   ::= { gx2Dm870DigitalEntry 12}

		dm870stateflagSbsControl            OBJECT-TYPE
			   SYNTAX         	INTEGER
								{
								hidden(1),
								read-only(2),
								updateable(3)
								}
			   ACCESS           	read-only
			   STATUS           	mandatory
			   DESCRIPTION
			   "The value of this object provides the state
			    of the the parameter. (0-Hidden 1-Read-Only, 2-Updateable)."
			   ::= { gx2Dm870DigitalEntry 13}
-- New parameter
		dm870labelLaserMode             OBJECT-TYPE
			   SYNTAX         	DisplayString (SIZE (0..80))         
			   ACCESS           	read-only
			   STATUS           	optional
			   DESCRIPTION
			   "The value of this object provides the label of the
			    Laser Mode Digital parameter."
			   ::= { gx2Dm870DigitalEntry 14}

		dm870enumLaserMode               	OBJECT-TYPE
			   SYNTAX          	DisplayString (SIZE (0..80))         
			   ACCESS           	read-only
			   STATUS           	optional
			   DESCRIPTION
			   "The value of this object represents the Enumeration values
			    possible for the Digital parameter. Each Enumerated values is
			    separated by a common. The first value has a enumerated value of 1."
			   ::= { gx2Dm870DigitalEntry 15}

		dm870valueLaserMode           	OBJECT-TYPE
			   SYNTAX       		INTEGER
					    		{
							preset(1),
							set(2),
							setEquate(3),
							manual(4),
							manualEquate(5)
					    		}
			   ACCESS           	read-write
			   STATUS           	mandatory
			   DESCRIPTION
			   "The value of this object is the current value of the parameter."
			   ::= { gx2Dm870DigitalEntry 16}

		dm870stateflagLaserMode         OBJECT-TYPE
			   SYNTAX         	INTEGER
								{
								hidden(1),
								read-only(2),
								updateable(3)
								}
			   ACCESS           	read-only
			   STATUS           	mandatory
			   DESCRIPTION
			   "The value of this object provides the state
			    of the the parameter. (0-Hidden 1-Read-Only, 2-Updateable)."
			   ::= { gx2Dm870DigitalEntry 17}

-- New parameter
		dm870labelFactoryDefault            	OBJECT-TYPE
			   SYNTAX       	      DisplayString (SIZE (0..80))         
			   ACCESS           	read-only
			   STATUS           	optional
			   DESCRIPTION
			   "The value of this object provides the label of the
			    Factory Default Digital parameter."
			   ::= { gx2Dm870DigitalEntry 18}

		dm870enumFactoryDefault               	OBJECT-TYPE
			   SYNTAX       	      DisplayString (SIZE (0..80))         
			   ACCESS           	read-only
			   STATUS           	optional
			   DESCRIPTION
			   "The value of this object represents the Enumeration values
			    possible for the Digital parameter. Each Enumerated values is
			    separated by a common. The first value has a enumerated value 
				of 1.."
			   ::= { gx2Dm870DigitalEntry 19}

		dm870valueFactoryDefault              OBJECT-TYPE
			   SYNTAX       		INTEGER
					    		{
							off(1),
							on(2)
					    		}
			   ACCESS           	read-write
			   STATUS           	mandatory
			   DESCRIPTION
			   "The value of this object is the current value of the parameter.
			   Return value is meaningless"
			   ::= { gx2Dm870DigitalEntry 20}

		dm870stateflagFactoryDefault        	OBJECT-TYPE
			   SYNTAX       		INTEGER
								{
								hidden(1),
								read-only(2),
								updateable(3)
								}
			   ACCESS           	read-only
			   STATUS           	mandatory
			   DESCRIPTION
			   "The value of this object provides the state
			    of the the parameter. (0-Hidden 1-Read-Only, 2-Updateable)."
			   ::= { gx2Dm870DigitalEntry 21}

-- *********** STATUS *****************
		gx2Dm870StatusTableIndex			OBJECT-TYPE
			   SYNTAX				INTEGER (1..4294967295)
			   ACCESS				read-only
			   STATUS				mandatory
			   DESCRIPTION			
			   "The value of this object identifies the network
			    element. This index is equal to the
			    hfcCommonTableIndex for the same element."
			   ::= { gx2Dm870StatusEntry 1}

--New Parameter
		dm870labelBoot               	OBJECT-TYPE
			   SYNTAX       		DisplayString (SIZE (0..80))         
			   ACCESS           	read-only
			   STATUS           	optional
			   DESCRIPTION
			   "The value of this object provides the label of the
			    Boot Status  Status parameter."
			   ::= { gx2Dm870StatusEntry 2}

		dm870valueBoot              		OBJECT-TYPE
			   SYNTAX       		INTEGER
									{
									ok(1),
									undetermined(2),
									warning(3),
									minor(4),
									major(5),
									critical(6)
									}
			   ACCESS           	read-only
			   STATUS           	mandatory
			   DESCRIPTION
			   "The value of this object provides the current state of
			    the parameter (0-Ok, 1-Undetermined
			    2-Warning, 3-Minor, 4-Major, 5-Critical)."
			   ::= { gx2Dm870StatusEntry 3}

		dm870stateflagBoot     	OBJECT-TYPE
			   SYNTAX       		INTEGER
								{
								hidden(1),
								read-only(2),
								updateable(3)
								}
			   ACCESS           	read-only
			   STATUS           	mandatory
			   DESCRIPTION
			   "The value of this object provides the state
			    of the the parameter. (0-Hidden 1-Read-Only, 2-Updateable)."
			   ::= { gx2Dm870StatusEntry  4}



--New Parameter
		dm870labelFlash               	OBJECT-TYPE
			   SYNTAX       		DisplayString (SIZE (0..80))         
			   ACCESS           	read-only
			   STATUS           	optional
			   DESCRIPTION
			   "The value of this object provides the label of the
			    Flash Status  Status parameter."
			   ::= { gx2Dm870StatusEntry 5}

		dm870valueFlash              	OBJECT-TYPE
			   SYNTAX       		INTEGER
									{
									ok(1),
									undetermined(2),
									warning(3),
									minor(4),
									major(5),
									critical(6)
									}
			   ACCESS           	read-only
			   STATUS           	mandatory
			   DESCRIPTION
			   "The value of this object provides the current state of
			    the parameter (0-Ok, 1-Undetermined
			    2-Warning, 3-Minor, 4-Major, 5-Critical)."
			   ::= { gx2Dm870StatusEntry 6}

		dm870stateflagFlash     	OBJECT-TYPE
			   SYNTAX       		INTEGER
								{
								hidden(1),
								read-only(2),
								updateable(3)
								}
			   ACCESS           	read-only
			   STATUS           	mandatory
			   DESCRIPTION
			   "The value of this object provides the state
			    of the the parameter. (0-Hidden 1-Read-Only, 2-Updateable)."
			   ::= { gx2Dm870StatusEntry  7}

--New Parameter
		dm870labelFactoryDataCRC           OBJECT-TYPE
			   SYNTAX       		DisplayString (SIZE (0..80))         
			   ACCESS           	read-only
			   STATUS           	optional
			   DESCRIPTION
			   "The value of this object provides the label of the
			    Factory Data CRC Status parameter."
			   ::= { gx2Dm870StatusEntry 8}

		dm870valueFactoryDataCRC          	OBJECT-TYPE
			   SYNTAX       		INTEGER
									{
									ok(1),
									undetermined(2),
									warning(3),
									minor(4),
									major(5),
									critical(6)
									}
			   ACCESS           	read-only
			   STATUS           	mandatory
			   DESCRIPTION
			   "The value of this object provides the current state of
			    the parameter (0-Ok, 1-Undetermined
			    2-Warning, 3-Minor, 4-Major, 5-Critical)."
			   ::= { gx2Dm870StatusEntry 9}

		dm870stateflagFactoryDataCRC     	OBJECT-TYPE
			   SYNTAX       		INTEGER
								{
								hidden(1),
								read-only(2),
								updateable(3)
								}
			   ACCESS           	read-only
			   STATUS           	mandatory
			   DESCRIPTION
			   "The value of this object provides the state
			    of the the parameter. (0-Hidden 1-Read-Only, 2-Updateable)."
			   ::= { gx2Dm870StatusEntry  10}


--New Parameter
		dm870labelLaserDataCRC           OBJECT-TYPE
			   SYNTAX       		DisplayString (SIZE (0..80))         
			   ACCESS           	read-only
			   STATUS           	optional
			   DESCRIPTION
			   "The value of this object provides the label of the
			    Laser Data CRC Status parameter."
			   ::= { gx2Dm870StatusEntry 11}

		dm870valueLaserDataCRC          	OBJECT-TYPE
			   SYNTAX       		INTEGER
									{
									ok(1),
									undetermined(2),
									warning(3),
									minor(4),
									major(5),
									critical(6)
									}
			   ACCESS           	read-only
			   STATUS           	mandatory
			   DESCRIPTION
			   "The value of this object provides the current state of
			    the parameter (0-Ok, 1-Undetermined
			    2-Warning, 3-Minor, 4-Major, 5-Critical)."
			   ::= { gx2Dm870StatusEntry 12}

		dm870stateflagLaserDataCRC     	OBJECT-TYPE
			   SYNTAX       		INTEGER
								{
								hidden(1),
								read-only(2),
								updateable(3)
								}
			   ACCESS           	read-only
			   STATUS           	mandatory
			   DESCRIPTION
			   "The value of this object provides the state
			    of the the parameter. (0-Hidden 1-Read-Only, 2-Updateable)."
			   ::= { gx2Dm870StatusEntry  13}



--New Parameter
		dm870labelAlarmDataCrc               	      OBJECT-TYPE
			   SYNTAX       		DisplayString (SIZE (0..80))         
			   ACCESS           	read-only
			   STATUS           	optional
			   DESCRIPTION
			   "The value of this object provides the label of the
			    Alarm Data Crc parameter."
			   ::= { gx2Dm870StatusEntry 14}

		dm870valueAlarmDataCrc              		OBJECT-TYPE
			   SYNTAX       		INTEGER
									{
									ok(1),
									undetermined(2),
									warning(3),
									minor(4),
									major(5),
									critical(6)
									}
			   ACCESS           	read-only
			   STATUS           	mandatory
			   DESCRIPTION
			   "The value of this object provides the current state of
			    the parameter (0-Ok, 1-Undetermined
			    2-Warning, 3-Minor, 4-Major, 5-Critical)."
			   ::= { gx2Dm870StatusEntry 15}

		dm870stateflagAlarmDataCrc     	OBJECT-TYPE
			   SYNTAX       		INTEGER
								{
								hidden(1),
								read-only(2),
								updateable(3)
								}
			   ACCESS           	read-only
			   STATUS           	mandatory
			   DESCRIPTION
			   "The value of this object provides the state
			    of the the parameter. (0-Hidden 1-Read-Only, 2-Updateable)."
			   ::= { gx2Dm870StatusEntry  16}

 
 --New Parameter
		dm870labelRFInputStatus               	      OBJECT-TYPE
			   SYNTAX       		DisplayString (SIZE (0..80))         
			   ACCESS           	read-only
			   STATUS           	optional
			   DESCRIPTION
			   "The value of this object provides the label of the
			    Alarm Data Crc parameter."
			   ::= { gx2Dm870StatusEntry 17}

		dm870valueRFInputStatus              		OBJECT-TYPE
			   SYNTAX       		INTEGER
									{
									ok(1),
									undetermined(2),
									warning(3),
									minor(4),
									major(5),
									critical(6)
									}
			   ACCESS           	read-only
			   STATUS           	mandatory
			   DESCRIPTION
			   "The value of this object provides the current state of
			    the parameter (0-Ok, 1-Undetermined
			    2-Warning, 3-Minor, 4-Major, 5-Critical)."
			   ::= { gx2Dm870StatusEntry 18}

		dm870stateflagRFInputStatus     	OBJECT-TYPE
			   SYNTAX       		INTEGER
								{
								hidden(1),
								read-only(2),
								updateable(3)
								}
			   ACCESS           	read-only
			   STATUS           	mandatory
			   DESCRIPTION
			   "The value of this object provides the state
			    of the the parameter. (0-Hidden 1-Read-Only, 2-Updateable)."
			   ::= { gx2Dm870StatusEntry  19}        
			   
            -- ************ FACTORY DATA ****************
		gx2Dm870FactoryTableIndex			OBJECT-TYPE
			   SYNTAX				INTEGER (1..4294967295)
			   ACCESS				read-only
			   STATUS				mandatory
			   DESCRIPTION			
			   "The value of this object identifies the network
			    element. This index is equal to the
			    hfcCommonTableIndex for the same element."
			   ::= { gx2Dm870FactoryEntry 1}

		dm870bootControlByte          	OBJECT-TYPE
			   SYNTAX       		INTEGER
			   ACCESS           	read-only
			   STATUS           	mandatory
			   DESCRIPTION
			   "The value of this object indicates which bank the firmware
			    is currently being boot from."
			   ::= { gx2Dm870FactoryEntry 2}

		dm870bootStatusByte          	OBJECT-TYPE
			   SYNTAX       		INTEGER
			   ACCESS           	read-only
			   STATUS           	mandatory
			   DESCRIPTION
			   "This object indicates the status of the last boot.  Bit 2 = 
			   Bank 0/1 Active (0 = Bank 0, 1 = Bank 1), Bit 1 = Bank 1 Fail 
			   and Bit 0 = Bank 0 Fail (0 = Pass, 1 = Fail)"
			   ::= { gx2Dm870FactoryEntry 3}

		dm870bank1CRC          		OBJECT-TYPE
			   SYNTAX       		INTEGER
			   ACCESS           	read-only
			   STATUS           	mandatory
			   DESCRIPTION
			   "This object provides the CRC code of bank 0.  The display 
			   formate for the data is Hex."
			   ::= { gx2Dm870FactoryEntry 4}

		dm870bank2CRC          		OBJECT-TYPE
			   SYNTAX       		INTEGER
			   ACCESS           	read-only
			   STATUS           	mandatory
			   DESCRIPTION
			   "This object provides the CRC code of bank 1.The display 
			   formate for the data is Hex."
			   ::= { gx2Dm870FactoryEntry 5}

		dm870prgEEPROMByte          		OBJECT-TYPE
			   SYNTAX       		INTEGER
			   ACCESS           	read-only
			   STATUS           	mandatory
			   DESCRIPTION
			   "This object indicates if the EEPROM has been programmed"
			   ::= { gx2Dm870FactoryEntry 6}

		dm870factoryCRC          		OBJECT-TYPE
			   SYNTAX       		INTEGER
			   ACCESS           	read-only
			   STATUS           	mandatory
			   DESCRIPTION
			   "This object provides the CRC code for the Factory data."
			   ::= { gx2Dm870FactoryEntry 7}

		dm870calculateCRC          		OBJECT-TYPE
			   SYNTAX       		INTEGER
					    		{
							factory(1),
							na(2),
							alarm(3)
					    		}
			   ACCESS           	read-only
			   STATUS           	obsolete
			   DESCRIPTION
			   "This object indicates which of the Enums will have the CRC 
			   calculated."
			   ::= { gx2Dm870FactoryEntry 8}

		dm870hourMeter          		OBJECT-TYPE
			   SYNTAX       		INTEGER
			   ACCESS           	read-only
			   STATUS           	mandatory
			   DESCRIPTION
			   "This object provides the hour meter reading of the module."
			   ::= { gx2Dm870FactoryEntry 9}

		dm870flashPrgCntA          		OBJECT-TYPE
			   SYNTAX       		INTEGER
			   ACCESS           	read-only
			   STATUS           	mandatory
			   DESCRIPTION
			   "This object provides the number of times Bank 1 flash has been 
                      programmed."
			   ::= { gx2Dm870FactoryEntry 10}

		dm870flashPrgCntB          		OBJECT-TYPE
			   SYNTAX       		INTEGER
			   ACCESS           	read-only
			   STATUS           	mandatory
			   DESCRIPTION
			   "This object provides the number of times Bank 1 flash has been 
                      programmed."
			   ::= { gx2Dm870FactoryEntry 11}

		dm870flashBankARev          		OBJECT-TYPE
			   SYNTAX       		DisplayString (SIZE (0..80))
			   ACCESS           	read-only
			   STATUS           	mandatory
			   DESCRIPTION
			   "This object provides the revision of flash bank 0.  The rev is
			   2 characters."
			   ::= { gx2Dm870FactoryEntry 12}

		dm870flashBankBRev          		OBJECT-TYPE
			   SYNTAX       		DisplayString (SIZE (0..80))
			   ACCESS           	read-only
			   STATUS           	mandatory
			   DESCRIPTION
			   "This object provides the revision of flash bank 1.  The rev is
			   2 characters."
			   ::= { gx2Dm870FactoryEntry 13}



-- ****************************************************************
--
-- TRAP DEFINITIONS
--
--
-- Every trap generated by an HFC agents will include first 9 identical
-- fields. If particular variable is not supported in
-- particular TRAP-TYPE then default value will be returned.
--
-- DESCRIPTION will include explanation of use of generic
-- variables (trapAdditionalInfo******.)  If no
-- DESCRIPTION is given then generic variables will contain
-- default values.
--
-- *****************************************************************

--***************************************************************************
-- ***********!!! THE TRAP SECTION HAS NOT BEEN COMPLETED YET !!! ***********
--***************************************************************************

-- **************************************************************************
--                        DM870 Module traps
-- **************************************************************************
   trapDM870ConfigChangeInteger TRAP-TYPE
       ENTERPRISE gx2Dm870
       VARIABLES
	       {       
		trapIdentifier,
		trapNetworkElemModelNumber,
		trapNetworkElemSerialNum,
		trapPerceivedSeverity,
		trapNetworkElemOperState,
		trapNetworkElemAlarmStatus,  
		trapNetworkElemAdminState,
		trapNetworkElemAvailStatus,
		trapText,
		trapChangedObjectId,
		trapChangedValueInteger,
		trapNETrapLastTrapTimeStamp
	       }
       DESCRIPTION
	"This trap is issued if configuration of a single variable
	 with integer type was changed (via ANY interface).  
	 TrapChangedValueInteger variable may contain current reading
	 of that variable.
	 trapPerceivedSeverity - 'indeterminate'"
  ::= 1

   trapDM870ConfigChangeDisplayString TRAP-TYPE
       ENTERPRISE gx2Dm870
       VARIABLES
	       {       
		trapIdentifier,
		trapNetworkElemModelNumber,
		trapNetworkElemSerialNum,
		trapPerceivedSeverity,
		trapNetworkElemOperState,
		trapNetworkElemAlarmStatus,  
		trapNetworkElemAdminState,
		trapNetworkElemAvailStatus,
		trapText,
		trapChangedObjectId,
		trapChangedValueDisplayString,
		trapNETrapLastTrapTimeStamp
	       }
       DESCRIPTION
	"This trap is issued if configuration of a single variable
	 with DispalayString type was changed (via ANY interface).  
	 TrapChangedValueDisplayString variable may contain current reading
	 of that variable.
	 trapPerceivedSeverity - 'indeterminate'"
  ::= 2

  trapDM870fanCurrentAlarm TRAP-TYPE
	ENTERPRISE gx2Dm870
	VARIABLES
		{       
		 trapIdentifier,
		 trapNetworkElemModelNumber,
		 trapNetworkElemSerialNum,
		 trapPerceivedSeverity,
		 trapNetworkElemOperState,
		 trapNetworkElemAlarmStatus,  
		 trapNetworkElemAdminState,
		 trapNetworkElemAvailStatus,
		 trapText,
		 trapChangedObjectId,
		 trapChangedValueInteger,
		 trapNETrapLastTrapTimeStamp
		}
	DESCRIPTION
	"This trap is issued when the Fan Current 
	 parameter goes out of range.
	 trapAdditionalInfoInteger variable contains current reading of 
	 the this parameter."
  ::= 3

  trapDM870ModuleTempAlarm TRAP-TYPE
	ENTERPRISE gx2Dm870
	VARIABLES
		{       
		 trapIdentifier,
		 trapNetworkElemModelNumber,
		 trapNetworkElemSerialNum,
		 trapPerceivedSeverity,
		 trapNetworkElemOperState,
		 trapNetworkElemAlarmStatus,  
		 trapNetworkElemAdminState,
		 trapNetworkElemAvailStatus,
		 trapText,
		 trapChangedObjectId,
		 trapChangedValueInteger,
		 trapNETrapLastTrapTimeStamp
		}
	DESCRIPTION
	"This trap is issued when the Module Temperature parameter goes out of range.
	 trapAdditionalInfoInteger variable contains current reading of 
	 the this parameter."
  ::= 4

  trapDM870omiOffsetAlarm TRAP-TYPE
	ENTERPRISE gx2Dm870
	VARIABLES
		{       
		 trapIdentifier,
		 trapNetworkElemModelNumber,
		 trapNetworkElemSerialNum,
		 trapPerceivedSeverity,
		 trapNetworkElemOperState,
		 trapNetworkElemAlarmStatus,  
		 trapNetworkElemAdminState,
		 trapNetworkElemAvailStatus,
		 trapText,
		 trapChangedObjectId,
		 trapChangedValueInteger,
		 trapNETrapLastTrapTimeStamp
		}
	DESCRIPTION
	"This trap is issued when the OMI Offset goes out of range."
  ::= 5

  trapDM870tecCurrentAlarm TRAP-TYPE
	ENTERPRISE gx2Dm870
	VARIABLES
		{       
		 trapIdentifier,
		 trapNetworkElemModelNumber,
		 trapNetworkElemSerialNum,
		 trapPerceivedSeverity,
		 trapNetworkElemOperState,
		 trapNetworkElemAlarmStatus,  
		 trapNetworkElemAdminState,
		 trapNetworkElemAvailStatus,
		 trapText,
		 trapChangedObjectId,
		 trapChangedValueInteger,
		 trapNETrapLastTrapTimeStamp
		}
	DESCRIPTION
	"This trap is issued when the TEC Current parameter 
	 goes out of range.
	 trapAdditionalInfoInteger variable contains current reading of 
	 the this parameter."
  ::= 6

  trapDM870LaserCurrentAlarm TRAP-TYPE
	ENTERPRISE gx2Dm870
	VARIABLES
		{       
		 trapIdentifier,
		 trapNetworkElemModelNumber,
		 trapNetworkElemSerialNum,
		 trapPerceivedSeverity,
		 trapNetworkElemOperState,
		 trapNetworkElemAlarmStatus,  
		 trapNetworkElemAdminState,
		 trapNetworkElemAvailStatus,
		 trapText,
		 trapChangedObjectId,
		 trapChangedValueInteger,
		 trapNETrapLastTrapTimeStamp
		}
	DESCRIPTION
	"This trap is issued when the Laser Current parameter 
	 goes out of range.
	 trapAdditionalInfoInteger variable contains current reading of 
	 the this parameter."
  ::= 7

  trapDM870LaserTempAlarm TRAP-TYPE
	ENTERPRISE gx2Dm870
	VARIABLES
		{       
		 trapIdentifier,
		 trapNetworkElemModelNumber,
		 trapNetworkElemSerialNum,
		 trapPerceivedSeverity,
		 trapNetworkElemOperState,
		 trapNetworkElemAlarmStatus,  
		 trapNetworkElemAdminState,
		 trapNetworkElemAvailStatus,
		 trapText,
		 trapChangedObjectId,
		 trapChangedValueInteger,
		 trapNETrapLastTrapTimeStamp
		}
	DESCRIPTION
	"This trap is issued when the Laser Temp parameter 
	 goes out of range.
	 trapAdditionalInfoInteger variable contains current reading of 
	 the this parameter."
  ::= 8

  trapDM870LaserPowerAlarm TRAP-TYPE
	ENTERPRISE gx2Dm870
	VARIABLES
		{       
		 trapIdentifier,
		 trapNetworkElemModelNumber,
		 trapNetworkElemSerialNum,
		 trapPerceivedSeverity,
		 trapNetworkElemOperState,
		 trapNetworkElemAlarmStatus,  
		 trapNetworkElemAdminState,
		 trapNetworkElemAvailStatus,
		 trapText,
		 trapChangedObjectId,
		 trapChangedValueInteger,
		 trapNETrapLastTrapTimeStamp
		}
	DESCRIPTION
	"This trap is issued when the Laser Power parameter 
	 goes out of range.
	 trapAdditionalInfoInteger variable contains current reading of 
	 the this parameter."
  ::= 9

  trapDM870FlashAlarm TRAP-TYPE
	ENTERPRISE gx2Dm870
	VARIABLES
		{       
		 trapIdentifier,
		 trapNetworkElemModelNumber,
		 trapNetworkElemSerialNum,
		 trapPerceivedSeverity,
		 trapNetworkElemOperState,
		 trapNetworkElemAlarmStatus,  
		 trapNetworkElemAdminState,
		 trapNetworkElemAvailStatus,
		 trapText,
		 trapChangedObjectId,
		 trapChangedValueInteger,
		 trapNETrapLastTrapTimeStamp
		}
	DESCRIPTION
	"This trap is issued when the Laser Modules detects an error during
	Flash memory operations."
  ::= 10

  trapDM870BankBootAlarm TRAP-TYPE
	ENTERPRISE gx2Dm870
	VARIABLES
		{       
		 trapIdentifier,
		 trapNetworkElemModelNumber,
		 trapNetworkElemSerialNum,
		 trapPerceivedSeverity,
		 trapNetworkElemOperState,
		 trapNetworkElemAlarmStatus,  
		 trapNetworkElemAdminState,
		 trapNetworkElemAvailStatus,
		 trapText,
		 trapChangedObjectId,
		 trapChangedValueInteger,
		 trapNETrapLastTrapTimeStamp
		}
	DESCRIPTION
	"This trap is issued when the Laser Modules detects an error while booting
	from bank 0 or bank 1."
  ::= 11

	trapDM870AlarmDataCRCAlarm TRAP-TYPE
	ENTERPRISE gx2Dm870
	VARIABLES
		{       
		 trapIdentifier,
		 trapNetworkElemModelNumber,
		 trapNetworkElemSerialNum,
		 trapPerceivedSeverity,
		 trapNetworkElemOperState,
		 trapNetworkElemAlarmStatus,  
		 trapNetworkElemAdminState,
		 trapNetworkElemAvailStatus,
		 trapText,
		 trapChangedObjectId,
		 trapChangedValueInteger,
		 trapNETrapLastTrapTimeStamp
		}
	DESCRIPTION
	"This trap is issued when the Alarm Data CRC is incorrect."
  ::= 12

	trapDM870FactoryDataCRCAlarm TRAP-TYPE
	ENTERPRISE gx2Dm870
	VARIABLES
		{       
		 trapIdentifier,
		 trapNetworkElemModelNumber,
		 trapNetworkElemSerialNum,
		 trapPerceivedSeverity,
		 trapNetworkElemOperState,
		 trapNetworkElemAlarmStatus,  
		 trapNetworkElemAdminState,
		 trapNetworkElemAvailStatus,
		 trapText,
		 trapChangedObjectId,
		 trapChangedValueInteger,
		 trapNETrapLastTrapTimeStamp
		}
	DESCRIPTION
	"This trap is issued when the Factory Data CRC is incorrect."
  ::= 13

	trapDM870CalDataCRCAlarm TRAP-TYPE
	ENTERPRISE gx2Dm870
	VARIABLES
		{       
		 trapIdentifier,
		 trapNetworkElemModelNumber,
		 trapNetworkElemSerialNum,
		 trapPerceivedSeverity,
		 trapNetworkElemOperState,
		 trapNetworkElemAlarmStatus,  
		 trapNetworkElemAdminState,
		 trapNetworkElemAvailStatus,
		 trapText,
		 trapChangedObjectId,
		 trapChangedValueInteger,
		 trapNETrapLastTrapTimeStamp
		}
	DESCRIPTION
	"This trap is issued when the Cal Data CRC is incorrect."
  ::= 14


    trapDM870ResetFacDefault TRAP-TYPE
	ENTERPRISE gx2Dm870
	VARIABLES
		{       
		 trapIdentifier,
		 trapNetworkElemModelNumber,
		 trapNetworkElemSerialNum,
		 trapPerceivedSeverity,
		 trapNetworkElemOperState,
		 trapNetworkElemAlarmStatus,  
		 trapNetworkElemAdminState,
		 trapNetworkElemAvailStatus,
		 trapText,
		 trapChangedObjectId,
		 trapChangedValueInteger,
		 trapNETrapLastTrapTimeStamp
		}
      DESCRIPTION
      "This trap is issued when the DM870 resets to factory defaults"
  ::= 15

 	trapDM870UserRFOffAlarm TRAP-TYPE
	ENTERPRISE gx2Dm870
	VARIABLES
		{       
		 trapIdentifier,
		 trapNetworkElemModelNumber,
		 trapNetworkElemSerialNum,
		 trapPerceivedSeverity,
		 trapNetworkElemOperState,
		 trapNetworkElemAlarmStatus,  
		 trapNetworkElemAdminState,
		 trapNetworkElemAvailStatus,
		 trapText,
		 trapChangedObjectId,
		 trapChangedValueInteger,
		 trapNETrapLastTrapTimeStamp
		}
	DESCRIPTION
	"This trap is issued when the the User RF is turned off."
  ::= 16

	trapDM870UserOpticalOffAlarm TRAP-TYPE
	ENTERPRISE gx2Dm870
	VARIABLES
		{       
		 trapIdentifier,
		 trapNetworkElemModelNumber,
		 trapNetworkElemSerialNum,
		 trapPerceivedSeverity,
		 trapNetworkElemOperState,
		 trapNetworkElemAlarmStatus,  
		 trapNetworkElemAdminState,
		 trapNetworkElemAvailStatus,
		 trapText,
		 trapChangedObjectId,
		 trapChangedValueInteger,
		 trapNETrapLastTrapTimeStamp
		}
	DESCRIPTION
	"This trap is issued when the User Optical Power is turned off."
  ::= 17

	trapDM870UserSBSOffAlarm TRAP-TYPE
	ENTERPRISE gx2Dm870
	VARIABLES
		{       
		 trapIdentifier,
		 trapNetworkElemModelNumber,
		 trapNetworkElemSerialNum,
		 trapPerceivedSeverity,
		 trapNetworkElemOperState,
		 trapNetworkElemAlarmStatus,  
		 trapNetworkElemAdminState,
		 trapNetworkElemAvailStatus,
		 trapText,
		 trapChangedObjectId,
		 trapChangedValueInteger,
		 trapNETrapLastTrapTimeStamp
		}
	DESCRIPTION
	"This trap is issued when the User SBS is turned off."
  ::= 18

  trapDM870RFInputAlarm TRAP-TYPE
	ENTERPRISE gx2Dm870
	VARIABLES
		{       
		 trapIdentifier,
		 trapNetworkElemModelNumber,
		 trapNetworkElemSerialNum,
		 trapPerceivedSeverity,
		 trapNetworkElemOperState,
		 trapNetworkElemAlarmStatus,  
		 trapNetworkElemAdminState,
		 trapNetworkElemAvailStatus,
		 trapText,
		 trapChangedObjectId,
		 trapChangedValueInteger,
		 trapNETrapLastTrapTimeStamp
		}
	DESCRIPTION
	"This trap is issued when the Laser Modules RF input parameter 
	 goes out of range.
	 trapAdditionalInfoInteger variable contains current reading of 
	 the this parameter."
  ::= 19
  
  trapDM870RFOverloadAlarm TRAP-TYPE
	ENTERPRISE gx2Dm870
	VARIABLES
		{       
		 trapIdentifier,
		 trapNetworkElemModelNumber,
		 trapNetworkElemSerialNum,
		 trapPerceivedSeverity,
		 trapNetworkElemOperState,
		 trapNetworkElemAlarmStatus,  
		 trapNetworkElemAdminState,
		 trapNetworkElemAvailStatus,
		 trapText,
		 trapChangedObjectId,
		 trapChangedValueInteger,
		 trapNETrapLastTrapTimeStamp
		}
	DESCRIPTION
	"This trap is issued when the Laser Modules RF overload parameter 
	 goes out of range.
	 trapAdditionalInfoInteger variable contains current reading of 
	 the this parameter."
  ::= 20

  END
-- // Section: Header & History
