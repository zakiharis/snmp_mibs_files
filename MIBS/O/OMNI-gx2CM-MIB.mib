OMNI-gx2CM-MIB DEFINITIONS ::= BEGIN

    IMPORTS
	IpAddress, TimeTicks, Counter            
					      FROM RFC1155-SMI
	OBJECT-TYPE                     
					      FROM RFC-1212
	sysUpTime, DisplayString        
					      FROM RFC1213-MIB
	TRAP-TYPE                       
					      FROM RFC-1215
	gi, motproxies                   
					      FROM NLS-BBNIDENT-MIB
	gx2Cm
					      FROM GX2HFC-MIB

	trapIdentifier,trapNetworkElemModelNumber,
	trapNetworkElemSerialNum, trapPerceivedSeverity,
	trapNetworkElemOperState, trapNetworkElemAlarmStatus,
	trapNetworkElemAdminState, trapNetworkElemAvailStatus,
	trapText, trapNETrapLastTrapTimeStamp, trapChangedObjectId,
	trapChangedValueInteger, trapChangedValueDisplayString
					      FROM NLSBBN-TRAPS-MIB;



	       -- This MIB module uses the extended OBJECT-TYPE macro as
	       -- defined in RFC1212 and the TRAP-TYPE macro as defined
	       -- in RFC 1215.

		   --REVISION	"2" Jan 20, 2003
		   --DESCRIPTION
		   --			Added revision and description comment section
		   --REVISION	"2" Jan 20, 2003
		   --DESCRIPTION
		   --			Added parameter autoQuickSwapCnt to the quick swap table 


		--    GX2 Control Module MIB MODULE

	-- This MIB module defines information for management of HFC networks
		-- 
		-- The MIB module assumes that all generic (static) network element
		-- information is defined in a different module such as the HFC module
		-- The MIB consists of two groups:
		-- the device type descriptor subgroup and 
		-- gx2Cm Network Elements subgroup.
		-- The device type descriptor subgroup is used to define 
		-- parameters specific to gx2Cm device type.
		-- These parameters are common across all network elements
		-- from gx2Cm device type.
		--
		-- The gx2Cm Network Elements subgroup is
		-- a list of gx2Cm type elements in the
		-- current network topology with nominal
		-- and current parameter values for the
		-- individual network elements; the individual
		-- network elements are identified by  
		-- index from hfcCommonTable.
		-- That implies what hfcCommonTableIndex and
		-- gx2CmTableIndex are equal for each individual
		-- network element.
		-- This table is an extension of the hfcCommonTable
		-- for all elements of gx2Cm type.
		--
		-- Both groups are mandatory for management of gx2Cm devices.

-- ****************************************************************************
		--
		-- All floating point numbers will be represented by an IEEE 32 Bit number.
		-- Conversion of this number must be done on the user interface to view the 
		-- actual floating point number. 
		--

		Float ::= Counter  -- UNSIGNED (32 BITS) 

-- ****************************************************************************

		-- gx2Cm Device Descriptor subgroup.

		-- The device type descriptor subgroup is used to define 
		-- parameters specific to gx2Cm device type.
		-- These parameters are common across all network elements
		-- from gx2Cm device type.


		gx2cmDescriptor OBJECT IDENTIFIER ::= {gx2Cm 1}



--*****************************************************************************
		--              gx2Cm Table
		
		-- Contains a list of all gx2Cm type devices in
		-- the network. Each device is characterized with
		-- current network topology information, with nominal
		-- and current parameter values for the
		-- individual network elements;
		--
		-- The individual network elements indentified by  
		-- index from hfcCommonTable.
		-- That implies what hfcCommonTableIndex and
		-- gx2cmTableIndex are equal for each individual
		-- nettwork element.
		-- This table should be used as an extension of the hfcCommonTable
		-- for all elements of gx2Cm type.

--*******************************************************************

	       gx2cmFactoryTable                    OBJECT-TYPE
			 SYNTAX             SEQUENCE OF Gx2cmFactoryEntry
			 ACCESS             not-accessible
			 STATUS             mandatory
			 DESCRIPTION
			 "This table contains gx2Cm specific parameters with
			  nominal and current values."
			 ::= { gx2Cm 2 }

	       gx2cmFactoryEntry               OBJECT-TYPE
			 SYNTAX             Gx2cmFactoryEntry
			 ACCESS             not-accessible
			 STATUS             mandatory
			 DESCRIPTION
			 "This list contains Factory data and the
			  associated parameter descriptions."
			 INDEX { gx2cmFactoryTableIndex }
			 ::= { gx2cmFactoryTable  1}

--*******************************************************************

	       gx2cmNetworkTable                    OBJECT-TYPE
			 SYNTAX             SEQUENCE OF Gx2cmNetworkEntry
			 ACCESS             not-accessible
			 STATUS             mandatory
			 DESCRIPTION
			 "This table contains gx2Cm specific parameters with
			  nominal and current values."
			 ::= { gx2Cm 3 }

	       gx2cmNetworkEntry  OBJECT-TYPE
			 SYNTAX             Gx2cmNetworkEntry
			 ACCESS             not-accessible
			 STATUS             mandatory
			 DESCRIPTION
			 "This list contains Network parameters and the
			  associated parameter descriptions."
			 INDEX { gx2cmNetworkTableIndex }
			 ::= { gx2cmNetworkTable  2}

--*******************************************************************

	       gx2cmAnalogTable                    OBJECT-TYPE
			 SYNTAX             SEQUENCE OF Gx2cmAnalogEntry
			 ACCESS             not-accessible
			 STATUS             mandatory
			 DESCRIPTION
			 "This table contains gx2Cm specific parameters with
			  nominal and current values."
			 ::= { gx2Cm 4 }

	       gx2cmAnalogEntry               OBJECT-TYPE
			 SYNTAX             Gx2cmAnalogEntry
			 ACCESS             not-accessible
			 STATUS             mandatory
			 DESCRIPTION
			 "This list contains analog parameters and the 
			 associated parameter descriptions."
			 INDEX { gx2cmTableIndex }
			 ::= { gx2cmAnalogTable  3}

--*******************************************************************

	       gx2cmDigitalTable                    OBJECT-TYPE
			 SYNTAX             SEQUENCE OF Gx2cmDigitalEntry
			 ACCESS             not-accessible
			 STATUS             mandatory
			 DESCRIPTION
			 "This table contains gx2Cm specific parameters with
			  nominal and current values."
			 ::= { gx2Cm 5 }

	       gx2cmDigitalEntry               OBJECT-TYPE
			 SYNTAX             Gx2cmDigitalEntry
			 ACCESS             not-accessible
			 STATUS             mandatory
			 DESCRIPTION
			 "This list contains digital parameters and the 
			 associated parameter descriptions."
			 INDEX { gx2cmDigitalTableIndex }
			 ::= { gx2cmDigitalTable  4}

--*******************************************************************

	       gx2cmStatusTable                    OBJECT-TYPE
			 SYNTAX             SEQUENCE OF Gx2cmStatusEntry
			 ACCESS             not-accessible
			 STATUS             mandatory
			 DESCRIPTION
			 "This table contains gx2Cm specific parameters with
			  nominal and current values."
			 ::= { gx2Cm 6 }

	       gx2cmStatusEntry               OBJECT-TYPE
			 SYNTAX             Gx2cmStatusEntry
			 ACCESS             not-accessible
			 STATUS             mandatory
			 DESCRIPTION
			 "This list contains status parameters and the 
			 associated parameter descriptions."
			 INDEX { gx2cmStatusTableIndex }
			 ::= { gx2cmStatusTable  5}

--*******************************************************************

	       gx2cmAMCTable                    OBJECT-TYPE
			 SYNTAX             SEQUENCE OF Gx2cmAMCEntry
			 ACCESS             not-accessible
			 STATUS             mandatory
			 DESCRIPTION
			 "This table contains gx2Cm specific parameters with
			  nominal and current values."
			 ::= { gx2Cm 7 }

			gx2cmAMCEntry               OBJECT-TYPE
			 SYNTAX             Gx2cmAMCEntry
			 ACCESS             not-accessible
			 STATUS             mandatory
			 DESCRIPTION
			 "This list contains the AMC parameters and the 
			 associated parameter descriptions."
			 INDEX { gx2cmAMCTableIndex }
			 ::= { gx2cmAMCTable  6}

--*******************************************************************

	       gx2cmSecurityTable                    OBJECT-TYPE
			 SYNTAX             SEQUENCE OF Gx2cmSecurityEntry
			 ACCESS             not-accessible
			 STATUS             mandatory
			 DESCRIPTION
			 "This table contains gx2Cm specific parameters with
			  nominal and current values."
			 ::= { gx2Cm 8}

	       gx2cmSecurityEntry  OBJECT-TYPE
			 SYNTAX             Gx2cmSecurityEntry
			 ACCESS             not-accessible
			 STATUS             mandatory
			 DESCRIPTION
			 "This list contains Security parameters and the
			  associated parameter descriptions."
			 INDEX { gx2cmSecurityTableIndex }
			 ::= { gx2cmSecurityTable  7}
--*******************************************************************

	       gx2cmDiagnosticTable                    OBJECT-TYPE
			 SYNTAX             SEQUENCE OF Gx2cmDiagnosticEntry
			 ACCESS             not-accessible
			 STATUS             mandatory
			 DESCRIPTION
			 "This table contains gx2Cm specific parameters with
			  nominal and current values."
			 ::= { gx2Cm 9}

	       gx2cmDiagnosticEntry  OBJECT-TYPE
			 SYNTAX             Gx2cmDiagnosticEntry
			 ACCESS             not-accessible
			 STATUS             mandatory
			 DESCRIPTION
			 "This list contains Diagnostic parameters and the
			  associated parameter descriptions."
			 INDEX { gx2cmDiagnosticTableIndex }
			 ::= { gx2cmDiagnosticTable  8}

--*******************************************************************
	       gx2cmDownloadTable                    OBJECT-TYPE
			 SYNTAX             SEQUENCE OF Gx2cmDownloadEntry
			 ACCESS             not-accessible
			 STATUS             mandatory
			 DESCRIPTION
			 "This table contains gx2Cm specific parameters with
			  nominal and current values."
			 ::= { gx2Cm 10}


			gx2cmDownloadEntry  OBJECT-TYPE
			 SYNTAX             Gx2cmDownloadEntry
			 ACCESS             not-accessible
			 STATUS             mandatory
			 DESCRIPTION
			 "This list contains Download parameters and the
			  associated parameter descriptions."
			 INDEX { gx2cmDownloadTableIndex }
			 ::= { gx2cmDownloadTable  9}

--******************** Trap History Table ********************************

	       cmTrapHistoryTable                    OBJECT-TYPE
			 SYNTAX             SEQUENCE OF CmTrapHistoryEntry
			 ACCESS             not-accessible
			 STATUS             mandatory
			 DESCRIPTION
			 "This table contains the trap specific parameters."
			 ::= { gx2Cm 11}


			cmTrapHistoryEntry  OBJECT-TYPE
			 SYNTAX             CmTrapHistoryEntry
			 ACCESS             not-accessible
			 STATUS             mandatory
			 DESCRIPTION
			 "This list contains Trap History parameters and the
			  associated parameter descriptions."
			 INDEX { cmTrapHistoryTableIndex }
			 ::= { cmTrapHistoryTable  10}

--****************************************************************************

	      Gx2cmAnalogEntry    ::= SEQUENCE  
	       {
		gx2cmTableIndex         INTEGER,
				
		--           Analog Parameters

		labelModTemp 			DisplayString (SIZE (0..80)),
		uomModTemp				DisplayString (SIZE (0..80)),
		majorHighModTemp			Float, 
		majorLowModTemp			Float, 
		minorHighModTemp			Float,
		minorLowModTemp			Float, 
		currentValueModTemp		Float, 
		stateFlagModTemp			INTEGER,
		minValueModTemp			Float,
		maxValueModTemp 			Float,
		alarmStateModTemp			INTEGER
		}


		-- ****************  Digital Parameters ***********************
		Gx2cmDigitalEntry    ::= SEQUENCE  
       {
		gx2cmDigitalTableIndex         INTEGER,

		labelRemoteLocal		DisplayString (SIZE (0..80)),
		enumRemoteLocal			DisplayString (SIZE (0..80)),
		valueRemoteLocal		INTEGER,
		stateFlagRemoteLocal  	INTEGER,

		labelResetSlot			DisplayString (SIZE (0..80)),
		enumResetSlot			DisplayString (SIZE (0..80)),
		valueResetSlot			INTEGER,
		stateResetSlot	     	INTEGER,

		labelIdShelf				DisplayString (SIZE (0..80)),
		enumIdShelf				DisplayString (SIZE (0..80)),
		valueIdShelf				INTEGER,
		stateFlagIdShelf         	INTEGER,

		labelResetAlarm			DisplayString (SIZE (0..80)),
		enumResetAlarm			DisplayString (SIZE (0..80)),
		valueResetAlarm			INTEGER,
		stateFlagResetAlarm   	INTEGER
		
		}

		-- ****************  Status Parameters ************************************
		Gx2cmStatusEntry    ::= SEQUENCE  
       {
		gx2cmStatusTableIndex         INTEGER,

		labelShelfAlarm			DisplayString (SIZE (0..80)),
		valueShelfAlarm			INTEGER,
		stateShelfAlarm			INTEGER,

		labelDataCrc			DisplayString (SIZE (0..80)),
		valueDataCrc			INTEGER,
		stateDataCrc			INTEGER,

		labelFlashStatus	 	DisplayString (SIZE (0..80)),
		valueFlashStatus		INTEGER,
		stateFlashStatus		INTEGER,

		labelBootStatus	 		DisplayString (SIZE (0..80)),
		valueBootStatus 		INTEGER,
		stateBootStatus			INTEGER,

		labelAlmLimCrc			DisplayString (SIZE (0..80)),
		valueAlmLimCrc			INTEGER,
		stateAlmLimCrc			INTEGER

		}

		-- ****************  Factory Parameters *************************************
		Gx2cmFactoryEntry    ::= SEQUENCE  
       {
		gx2cmFactoryTableIndex         INTEGER,
		bootControlByte  		INTEGER,
		bootStatusByte   		INTEGER,
		bank0CRC    			INTEGER,
		bank1CRC    			INTEGER,
		prgEEPROMByte    		INTEGER,
		factoryCRC    			INTEGER,
		calculateCRC    		INTEGER,
		hourMeter    			INTEGER,
		flashPrgCnt0    		INTEGER,
		flashPrgCnt1    		INTEGER,
		flashBank0				DisplayString (SIZE (0..80)),
		flashBank1				DisplayString (SIZE (0..80)),
		localMacAdd				DisplayString (SIZE (0..80)),
		netWorkMacAdd			DisplayString (SIZE (0..80))

		}

            -- ************** Network info Parameters ****************************
		Gx2cmNetworkEntry    ::= SEQUENCE  
       {
		gx2cmNetworkTableIndex         INTEGER,

		labelLocalEthIPAdd		DisplayString (SIZE (0..80)),	
		valueLocalEthIPAdd		DisplayString (SIZE (0..80)),

		labelLocalEthMask		DisplayString (SIZE (0..80)),	
		valueLocalEthMask		DisplayString (SIZE (0..80)),

		labelNetworkEthAdd		DisplayString (SIZE (0..80)),	
		valueNetworkEthAdd		DisplayString (SIZE (0..80)),

		labelNetworkEthMask		DisplayString (SIZE (0..80)),	
		valueNetworkEthMask		DisplayString (SIZE (0..80)),

		labelShelfSerialNum		DisplayString (SIZE (0..80)),	
		valueShelfSerialNum		DisplayString (SIZE (0..80)),

		labelGateWayIPAdd		DisplayString (SIZE (0..80)),
		valueGateWayIPAdd		DisplayString (SIZE (0..80)),

		labelTrapDestination	DisplayString (SIZE (0..80)),
		valueTrapDestination	DisplayString (SIZE (0..80)),

		labelTFTPserver			DisplayString (SIZE (0..80)),
		valueTFTPserver			DisplayString (SIZE (0..80)),

		labelTrap2Destination	DisplayString (SIZE (0..80)),
		valueTrap2Destination	DisplayString (SIZE (0..80)),

		labelTrap3Destination	DisplayString (SIZE (0..80)),
		valueTrap3Destination	DisplayString (SIZE (0..80)),

		labelTrap4Destination	DisplayString (SIZE (0..80)),
		valueTrap4Destination	DisplayString (SIZE (0..80)),

		labelTrap5Destination	DisplayString (SIZE (0..80)),
		valueTrap5Destination	DisplayString (SIZE (0..80)),

-- ISDN parameters Rev k

		labelISDNMode		DisplayString (SIZE (0..80)),
		valueISDNMode		INTEGER,

		labelISDNModemIPAddress	DisplayString (SIZE (0..80)),
		valueISDNModemIPAddress	DisplayString (SIZE (0..80)),

		labelISDNTrapTimeout	DisplayString (SIZE (0..80)),
		valueISDNTrapTimeout	INTEGER,

		labelISDNPingTimeout	DisplayString (SIZE (0..80)),
		valueISDNPingTimeout	INTEGER,

		labelISDNBackoffTimer	DisplayString (SIZE (0..80)),
		valueISDNBackoffTimer	INTEGER

		}


            -- ************** AMC Parameters ****************************
		Gx2cmAMCEntry    ::= SEQUENCE  
       {
		gx2cmAMCTableIndex         INTEGER,
		valueAMCslot1			INTEGER,
		serialAMCslot1			DisplayString (SIZE (0..80)),
		agentIDAMCslot1			INTEGER,
		
		valueAMCslot2			INTEGER,
		serialAMCslot2			DisplayString (SIZE (0..80)),
		agentIDAMCslot2			INTEGER,

		valueAMCslot3			INTEGER,
		serialAMCslot3			DisplayString (SIZE (0..80)),
		agentIDAMCslot3			INTEGER,

		valueAMCslot4			INTEGER,
		serialAMCslot4			DisplayString (SIZE (0..80)),
		agentIDAMCslot4			INTEGER,

		valueAMCslot5			INTEGER,
		serialAMCslot5			DisplayString (SIZE (0..80)),
		agentIDAMCslot5			INTEGER,

		valueAMCslot6			INTEGER,
		serialAMCslot6			DisplayString (SIZE (0..80)),
		agentIDAMCslot6			INTEGER,

		valueAMCslot7			INTEGER,
		serialAMCslot7			DisplayString (SIZE (0..80)),
		agentIDAMCslot7			INTEGER,

		valueAMCslot8			INTEGER,
		serialAMCslot8			DisplayString (SIZE (0..80)),
		agentIDAMCslot8			INTEGER,

		valueAMCslot9			INTEGER,
		serialAMCslot9			DisplayString (SIZE (0..80)),
		agentIDAMCslot9			INTEGER,

		valueAMCslot10			INTEGER,
		serialAMCslot10			DisplayString (SIZE (0..80)),
		agentIDAMCslot10		INTEGER,

		valueAMCslot11			INTEGER,
		serialAMCslot11			DisplayString (SIZE (0..80)),
		agentIDAMCslot11		INTEGER,

		valueAMCslot12			INTEGER,
		serialAMCslot12			DisplayString (SIZE (0..80)),
		agentIDAMCslot12		INTEGER,

		valueAMCslot13			INTEGER,
		serialAMCslot13			DisplayString (SIZE (0..80)),
		agentIDAMCslot13		INTEGER,

		valueAMCslot14			INTEGER,
		serialAMCslot14			DisplayString (SIZE (0..80)),
		agentIDAMCslot14		INTEGER,

		valueAMCslot15			INTEGER,
		serialAMCslot15			DisplayString (SIZE (0..80)),
		agentIDAMCslot15			INTEGER,

		valueAMCslot16			INTEGER,
		serialAMCslot16			DisplayString (SIZE (0..80)),
		agentIDAMCslot16		INTEGER,

		valueAMCslot17			INTEGER,
		serialAMCslot17			DisplayString (SIZE (0..80)),
		agentIDAMCslot17		INTEGER,

		valueAMCslot18			INTEGER,
		serialAMCslot18			DisplayString (SIZE (0..80)),
		agentIDAMCslot18		INTEGER,

		autoQuickSwapCnt		INTEGER

		}

            -- ************** Security Parameters ****************************
		Gx2cmSecurityEntry    ::= SEQUENCE  
       {
		gx2cmSecurityTableIndex				INTEGER,
		labelSecurityMode			DisplayString (SIZE (0..80)),
		enumSecurityMode			DisplayString (SIZE (0..80)),
		valueSecurityMode			INTEGER,
		stateSecurityMode			INTEGER,
		
		labelPassword				DisplayString (SIZE (0..80)),
		valuePassword				DisplayString (SIZE (0..80)),
		statePassword				INTEGER,

		labelFactoryChgString		DisplayString (SIZE (0..80)),
		valueFactoryChgString		DisplayString (SIZE (0..80)),
		stateFactoryChgString		INTEGER,

		labelOperatorChgString		DisplayString (SIZE (0..80)),
		valueOperatorChgString		DisplayString (SIZE (0..80)),
		stateOperatorChgString		INTEGER,

		labelReadOnlyChgString		DisplayString (SIZE (0..80)),
		valueReadOnlyChgString		DisplayString (SIZE (0..80)),
		stateReadOnlyChgString		INTEGER,

		labelRemoteOnlyChgString	DisplayString (SIZE (0..80)),
		valueRemoteOnlyChgString	DisplayString (SIZE (0..80)),
		stateRemoteOnlyChgString	INTEGER,

		labelLocalOnlyChgString		DisplayString (SIZE (0..80)),
		valueLocalOnlyChgString		DisplayString (SIZE (0..80)),
		stateLocalOnlyChgString		INTEGER

		}


		--****************** Diagnostic Parameters ********************************
		Gx2cmDiagnosticEntry   ::= SEQUENCE  
       {

		gx2cmDiagnosticTableIndex   INTEGER,
		ledTestValue			INTEGER,
		bpTestCnt				INTEGER,
		successTransSlot1		INTEGER,
		successTransSlot2		INTEGER,
		successTransSlot3		INTEGER,
		successTransSlot4		INTEGER,
		successTransSlot5		INTEGER,
		successTransSlot6		INTEGER,
		successTransSlot7		INTEGER,
		successTransSlot8		INTEGER,
		successTransSlot9		INTEGER,
		successTransSlot10		INTEGER,
		successTransSlot11		INTEGER,
		successTransSlot12		INTEGER,
		successTransSlot13		INTEGER,
		successTransSlot14		INTEGER,
		successTransSlot15		INTEGER,
		successTransSlot16		INTEGER,
		successTransSlot17		INTEGER,
		successTransSlot18		INTEGER,

		failureTransSlot1		INTEGER,
		failureTransSlot2		INTEGER,
		failureTransSlot3		INTEGER,
		failureTransSlot4		INTEGER,
		failureTransSlot5		INTEGER,
		failureTransSlot6		INTEGER,
		failureTransSlot7		INTEGER,
		failureTransSlot8		INTEGER,
		failureTransSlot9		INTEGER,
		failureTransSlot10		INTEGER,
		failureTransSlot11		INTEGER,
		failureTransSlot12		INTEGER,
		failureTransSlot13		INTEGER,
		failureTransSlot14		INTEGER,
		failureTransSlot15		INTEGER,
		failureTransSlot16		INTEGER,
		failureTransSlot17		INTEGER,
		failureTransSlot18		INTEGER,

		fanTestMode				INTEGER,
		fanControl				INTEGER,
		relayTestMode			INTEGER,
		relayControl			INTEGER,
		slotPollMode			INTEGER,

		bootCount				INTEGER,
		objectTableData			DisplayString (SIZE (0..80)),
		setSysTime				INTEGER

		}

		--****************** Download Parameters ********************************
		Gx2cmDownloadEntry   ::= SEQUENCE  
       {
		gx2cmDownloadTableIndex         INTEGER,
	
		downloadValue			INTEGER,
		autoDownloadReset		INTEGER,
		downloadFilename		DisplayString (SIZE (0..80)),
		downloadState			INTEGER,
		switchFwBank			INTEGER
		}



		--****************** Trap History Parameters ********************************
		CmTrapHistoryEntry   ::= SEQUENCE  
       	{
		cmTrapHistoryTableIndex				INTEGER,	
		netrapId							INTEGER,
		netrapNetworkElemModelNumber		DisplayString (SIZE (0..80)),
		netrapNetworkElemSerialNum			DisplayString (SIZE (0..80)),
		netrapPerceivedSeverity				INTEGER,
		netrapNetworkElemOperState			INTEGER,
		netrapNetworkElemAlarmStatus		INTEGER,
		netrapNetworkElemAdminState			INTEGER,
		netrapNetworkElemAvailStatus		INTEGER,
		netrapText							DisplayString (SIZE (0..80)),
		netrapLastTrapTimeStamp				TimeTicks,
		netrapChangedObjectId				DisplayString (SIZE (0..80)),
		netrapAdditionalInfoInteger1		INTEGER,
		netrapAdditionalInfoInteger2		INTEGER,
		netrapAdditionalInfoInteger3		INTEGER,
		netrapChangedValueDisplayString		DisplayString (SIZE (0..80)),
		netrapChangedValueOID				DisplayString (SIZE (0..80)),
		netrapChangedValueIpAddress			INTEGER,
		netrapChangedValueInteger			INTEGER
		}




-- ************** Analog Parameters ****************************
		gx2cmTableIndex              OBJECT-TYPE
			   SYNTAX           INTEGER (1..4294967295)
			   ACCESS           read-only
			   STATUS           mandatory
			   DESCRIPTION
			   "The value of this object identifies the network
			    element. This index is equal to the
			    hfcCommonTableIndex for the same element."
			   ::= { gx2cmAnalogEntry 1}

-- New Parameter

		labelModTemp     OBJECT-TYPE
			   SYNTAX           DisplayString (SIZE (0..80))
			   ACCESS           read-only
			   STATUS           optional
			   DESCRIPTION
			   "The value of this object provides the label of the
			    Module Temp parameter."
			   ::= { gx2cmAnalogEntry 2}

		uomModTemp       OBJECT-TYPE
			   SYNTAX           DisplayString (SIZE (0..80))
			   ACCESS           read-only
			   STATUS           optional
			   DESCRIPTION
			   "The value of this object provides the Unit of Measure of the
			    Module Temp parameter."
			   ::= { gx2cmAnalogEntry 3}

		majorHighModTemp OBJECT-TYPE
			   SYNTAX           Float 
			   ACCESS           read-only
			   STATUS           mandatory
			   DESCRIPTION
			   "The value of this object provides the Major High alarm value
			    of the Module Temp parameter."
			   ::= { gx2cmAnalogEntry 4}


		majorLowModTemp  OBJECT-TYPE
			   SYNTAX           Float 
			   ACCESS           read-only
			   STATUS           mandatory
			   DESCRIPTION
			   "The value of this object provides the Major Low alarm value
			    of the Module Temp parameter."
			   ::= { gx2cmAnalogEntry 5}

		minorHighModTemp OBJECT-TYPE
			   SYNTAX           Float
			   ACCESS           read-only
			   STATUS           mandatory
			   DESCRIPTION
			   "The value of this object provides the Minor High alarm value
			    of the Module Temp parameter."
			   ::= { gx2cmAnalogEntry 6}

		minorLowModTemp  OBJECT-TYPE
			   SYNTAX           Float 
			   ACCESS           read-only
			   STATUS           mandatory
			   DESCRIPTION
			   "The value of this object provides the Minor Low alarm value
			    of the Module Temp parameter."
			   ::= { gx2cmAnalogEntry 7}

		currentValueModTemp  OBJECT-TYPE
			   SYNTAX           Float 
			   ACCESS           read-only
			   STATUS           mandatory
			   DESCRIPTION
			   "The value of this object provides the Current value
			    of the Module Temp parameter."
			   ::= { gx2cmAnalogEntry 8}

		stateFlagModTemp  OBJECT-TYPE
			   SYNTAX           INTEGER
								{
								hidden(1),
								read-only(2),
								updateable(3)
								}
			   ACCESS           read-only
			   STATUS           mandatory
			   DESCRIPTION
			   "The value of this object provides the state
			    of the Module Temp parameter. (0-Hidden	
			          1-Read-Only, 2-Updateable)"
			   ::= { gx2cmAnalogEntry 9}

		minValueModTemp  OBJECT-TYPE
			   SYNTAX           Float
			   ACCESS           read-only
			   STATUS           optional
			   DESCRIPTION
			   "The value of this object provides the minimum value
			    the Module Temp parameter can achive."
			   ::= { gx2cmAnalogEntry 10}

		maxValueModTemp  OBJECT-TYPE
			   SYNTAX           Float
			   ACCESS           read-only
			   STATUS           optional
			   DESCRIPTION
			   "The value of this object provides the maximum value
			    the Module Temp parameter can achive."
			   ::= { gx2cmAnalogEntry 11}

		alarmStateModTemp  OBJECT-TYPE
			   SYNTAX           INTEGER
									{
									noAlarm(1),
									majorLowAlarm(2),
									minorLowAlarm(3),
									minorHighAlarm(4),
									majorHighAlarm(5),
									informational(6)
									}
			   ACCESS           read-only
			   STATUS           mandatory
			   DESCRIPTION
			   "The value of this object provides the curent alarm state of
			    the Module Temp Analog parameter."
			   ::= { gx2cmAnalogEntry 12}


-- ************************ Digital parameters **********************************
		gx2cmDigitalTableIndex              OBJECT-TYPE
			   SYNTAX           INTEGER (1..4294967295)
			   ACCESS           read-only
			   STATUS           mandatory
			   DESCRIPTION
			   "The value of this object identifies the network
			    element. This index is equal to the
			    hfcCommonTableIndex for the same element."
			   ::= { gx2cmDigitalEntry 1}

-- New parameter

		labelRemoteLocal                	OBJECT-TYPE
			   SYNTAX       		DisplayString (SIZE (0..80))
			   ACCESS           	read-only
			   STATUS           	obsolete
			   DESCRIPTION
			   "The value of this object provides the label of the
			    Remote Local Control Digital parameter."
			   ::= { gx2cmDigitalEntry 2}

		enumRemoteLocal               		OBJECT-TYPE
			   SYNTAX       		DisplayString (SIZE (0..80))
			   ACCESS           	read-only
			   STATUS           	obsolete
			   DESCRIPTION
			   "The value of this object represents the Enumeration values
			    possible for the Digital parameter. Each Enumerated value is
			    separated by a common. The first value has a enumerated value of 1."
			   ::= { gx2cmDigitalEntry 3}

		valueRemoteLocal            OBJECT-TYPE
			   SYNTAX       		INTEGER
					    			{
									local(1),
									remote(2)
					    			}
			   ACCESS           	read-write
			   STATUS           	obsolete
			   DESCRIPTION
			   "The value of this object is the current value of the parameter."
			   ::= { gx2cmDigitalEntry 4}

		stateFlagRemoteLocal              OBJECT-TYPE
			   SYNTAX       		INTEGER
									{
									hidden(1),
									read-only(2),
									updateable(3)
									}
			   ACCESS           	read-only
			   STATUS           	obsolete
			   DESCRIPTION
			   "The value of this object provides the state
			    of the Remote Local Control Digital parameter. (0-Hidden	
			          1-Read-Only, 2-Updateable)."
			   ::= { gx2cmDigitalEntry 5}

-- New parameter
		labelResetSlot             OBJECT-TYPE
			   SYNTAX         	DisplayString (SIZE (0..80))         
			   ACCESS           	read-only
			   STATUS           	optional
			   DESCRIPTION
			   "The value of this object provides the label of the
			    Reset Slot Digital parameter."
			   ::= { gx2cmDigitalEntry 6}

		enumResetSlot              	OBJECT-TYPE
			   SYNTAX          	DisplayString (SIZE (0..80))         
			   ACCESS           	read-only
			   STATUS           	optional
			   DESCRIPTION
			   "The value of this object represents the Enumeration values
			    possible for the Digital parameter. Each Enumerated value is
			    separated by a common. The first value has a enumerated value of 1."
			   ::= { gx2cmDigitalEntry 7}

		valueResetSlot           	OBJECT-TYPE
			   SYNTAX       		INTEGER
			   ACCESS           	read-write
			   STATUS           	mandatory
			   DESCRIPTION
			   "The value of this object is the current value of the parameter. 
			    A write to this object will casue a hardware reset. 0-control module
			    1-18 selected slot. "
			   ::= { gx2cmDigitalEntry 8}

		stateResetSlot         OBJECT-TYPE
			   SYNTAX         	INTEGER
									{
									hidden(1),
									read-only(2),
									updateable(3)
									}
			   ACCESS           	read-only
			   STATUS           	mandatory
			   DESCRIPTION
			   "The value of this object provides the state
			    of the parameter. (0-Hidden 1-Read-Only, 2-Updateable)."
			   ::= { gx2cmDigitalEntry 9}

-- New parameter
		labelIdShelf            	OBJECT-TYPE
			   SYNTAX       	      DisplayString (SIZE (0..80))         
			   ACCESS           	read-only
			   STATUS           	optional
			   DESCRIPTION
			   "The value of this object provides the label of the
			    identify shelf Digital parameter."
			   ::= { gx2cmDigitalEntry 10}

		enumIdShelf               	OBJECT-TYPE
			   SYNTAX       	      DisplayString (SIZE (0..80))         
			   ACCESS           	read-only
			   STATUS           	optional
			   DESCRIPTION
			   "The value of this object represents the Enumeration values
			    possible for the Digital parameter. Each Enumerated value is
			    separated by a common. The first value has a enumerated value of 1.."
			   ::= { gx2cmDigitalEntry 11}

		valueIdShelf              OBJECT-TYPE
			   SYNTAX       		INTEGER
							{
							off(1),
							on(2)
							}
			   ACCESS           	read-write
			   STATUS           	mandatory
			   DESCRIPTION
			   "The value of this object is the current value of the parameter.
			    Writing any non zero value to this parameter will casue the CM to blink its front panel LED."
			   ::= { gx2cmDigitalEntry 12}

		stateFlagIdShelf        	OBJECT-TYPE
			   SYNTAX       		INTEGER
									{
									hidden(1),
									read-only(2),
									updateable(3)
									}
			   ACCESS           	read-only
			   STATUS           	mandatory
			   DESCRIPTION
			   "The value of this object provides the state
			    of the the parameter. (0-Hidden 1-Read-Only, 2-Updateable)."
			   ::= { gx2cmDigitalEntry 13}
-- New parameter
		labelResetAlarm           OBJECT-TYPE
			   SYNTAX       		DisplayString (SIZE (0..80))         
			   ACCESS           	read-only
			   STATUS           	optional
			   DESCRIPTION
			   "The value of this object provides the label of the
			    Reset Alarms Digital parameter."
			   ::= { gx2cmDigitalEntry 14}

		enumResetAlarm               	OBJECT-TYPE
			   SYNTAX       		DisplayString (SIZE (0..80))         
			   ACCESS           	read-only
			   STATUS           	optional
			   DESCRIPTION
			   "The value of this object represents the Enumeration values
			    possible for the Digital parameter. Each Enumerated value is
			    separated by a common. The first value has a enumerated value of 1."
			   ::= { gx2cmDigitalEntry 15}

		valueResetAlarm         	OBJECT-TYPE
			   SYNTAX       		INTEGER
			   ACCESS           	read-write
			   STATUS           	mandatory
			   DESCRIPTION
			   "The value of this object is the current value of the parameter.
			    Writing any non-zero value to this object will case the CM to
		   	    reset shelf alarm processing."
			   ::= { gx2cmDigitalEntry 16}

		stateFlagResetAlarm     	OBJECT-TYPE
			   SYNTAX       		INTEGER
									{
									hidden(1),
									read-only(2),
									updateable(3)
									}
			   ACCESS           	read-only
			   STATUS           	mandatory
			   DESCRIPTION
			   "The value of this object provides the state
			    of the the parameter. (0-Hidden 1-Read-Only, 2-Updateable)."
			   ::= { gx2cmDigitalEntry 17}


		--*********************** STATUS **************************************
		gx2cmStatusTableIndex              OBJECT-TYPE
			   SYNTAX           INTEGER (1..4294967295)
			   ACCESS           read-only
			   STATUS           mandatory
			   DESCRIPTION
			   "The value of this object identifies the network
			    element. This index is equal to the
			    hfcCommonTableIndex for the same element."
			   ::= { gx2cmStatusEntry 1}

--New Parameter

		labelShelfAlarm               	OBJECT-TYPE
			   SYNTAX       		DisplayString (SIZE (0..80))         
			   ACCESS           	read-only
			   STATUS           	optional
			   DESCRIPTION
			   "The value of this object provides the label of the
			    Shelf Alarm Status parameter."
			   ::= { gx2cmStatusEntry 2}

		valueShelfAlarm              		OBJECT-TYPE
			   SYNTAX       		INTEGER
									{
									ok(1),
									undetermined(2),
									warning(3),
									minor(4),
									major(5),
									critical(6)
									}
			   ACCESS           	read-only
			   STATUS           	mandatory
			   DESCRIPTION
			   "The value of this object provides the current status of
			    the parameter (0-Ok, 1-Undetermined
			    2-Warning, 3-Minor, 4-Major, 5-Critical)."
			   ::= { gx2cmStatusEntry 3}

		stateShelfAlarm              		OBJECT-TYPE
			   SYNTAX       		INTEGER
									{
									hidden(1),
									read-only(2),
									updateable(3)
									}
			   ACCESS           	read-only
			   STATUS           	mandatory
			   DESCRIPTION
			   "The value of this object provides the current state of
			    the parameter."
			   ::= { gx2cmStatusEntry 4}


--New Parameter
		labelDataCrc               	OBJECT-TYPE
			   SYNTAX       		DisplayString (SIZE (0..80))         
			   ACCESS           	read-only
			   STATUS           	optional
			   DESCRIPTION
			   "The value of this object provides the label of the
			    Data CRC parameter."
			   ::= { gx2cmStatusEntry 5}

		valueDataCrc              	OBJECT-TYPE
			   SYNTAX       		INTEGER
									{
									ok(1),
									undetermined(2),
									warning(3),
									minor(4),
									major(5),
									critical(6)
									}
			   ACCESS           	read-only
			   STATUS           	mandatory
			   DESCRIPTION
			   "The value of this object provides the current status of
			    the parameter (0-Ok, 1-Undetermined
			    2-Warning, 3-Minor, 4-Major, 5-Critical)."
			   ::= { gx2cmStatusEntry 6}

		stateDataCrc              	OBJECT-TYPE
			   SYNTAX       		INTEGER
									{
									hidden(1),
									read-only(2),
									updateable(3)
									}
			   ACCESS           	read-only
			   STATUS           	mandatory
			   DESCRIPTION
			   "The value of this object provides the current state of
			    the parameter."
			   ::= { gx2cmStatusEntry 7}



--New Parameter
		labelFlashStatus           OBJECT-TYPE
			   SYNTAX       		DisplayString (SIZE (0..80))         
			   ACCESS           	read-only
			   STATUS           	optional
			   DESCRIPTION
			   "The value of this object provides the label of the
			    Flash Status parameter."
			   ::= { gx2cmStatusEntry 8}

		valueFlashStatus          	OBJECT-TYPE
			   SYNTAX       		INTEGER
									{
									ok(1),
									undetermined(2),
									warning(3),
									minor(4),
									major(5),
									critical(6)
									}
			   ACCESS           	read-only
			   STATUS           	mandatory
			   DESCRIPTION
			   "The value of this object provides the current status of
			    the parameter (0-Ok, 1-Undetermined
			    2-Warning, 3-Minor, 4-Major, 5-Critical)."
			   ::= { gx2cmStatusEntry 9}

		stateFlashStatus          	OBJECT-TYPE
			   SYNTAX       		INTEGER
									{
									hidden(1),
									read-only(2),
									updateable(3)
									}
			   ACCESS           	read-only
			   STATUS           	mandatory
			   DESCRIPTION
			   "The value of this object provides the current state of
			    the parameter."
			   ::= { gx2cmStatusEntry 10}

--New Parameter
		labelBootStatus             OBJECT-TYPE
			   SYNTAX       		DisplayString (SIZE (0..80))         
			   ACCESS           	read-only
			   STATUS           	optional
			   DESCRIPTION
			   "The value of this object provides the label of the
			    Boot Status parameter."
			   ::= { gx2cmStatusEntry 11}

		valueBootStatus           	OBJECT-TYPE
			   SYNTAX       		INTEGER
									{
									ok(1),
									undetermined(2),
									warning(3),
									minor(4),
									major(5),
									critical(6)
									}
			   ACCESS           	read-only
			   STATUS           	mandatory
			   DESCRIPTION
			   "The value of this object provides the current status of
			    the parameter (0-Ok, 1-Undetermined
			    2-Warning, 3-Minor, 4-Major, 5-Critical)."
			   ::= { gx2cmStatusEntry 12}

		stateBootStatus           	OBJECT-TYPE
			   SYNTAX       		INTEGER
									{
									hidden(1),
									read-only(2),
									updateable(3)
									}
			   ACCESS           	read-only
			   STATUS           	mandatory
			   DESCRIPTION
			   "The value of this object provides the current state of
			    the parameter."
			   ::= { gx2cmStatusEntry 13}

--New Parameter
		labelAlmLimCrc             OBJECT-TYPE
			   SYNTAX       		DisplayString (SIZE (0..80))         
			   ACCESS           	read-only
			   STATUS           	optional
			   DESCRIPTION
			   "The value of this object provides the label of the
			    Alarm limit CRC parameter."
			   ::= { gx2cmStatusEntry 14}

		valueAlmLimCrc           	OBJECT-TYPE
			   SYNTAX       		INTEGER
									{
									ok(1),
									undetermined(2),
									warning(3),
									minor(4),
									major(5),
									critical(6)
									}
			   ACCESS           	read-only
			   STATUS           	mandatory
			   DESCRIPTION
			   "The value of this object provides the current status of
			    the parameter (0-Ok, 1-Undetermined
			    2-Warning, 3-Minor, 4-Major, 5-Critical)."
			   ::= { gx2cmStatusEntry 15}

		stateAlmLimCrc           	OBJECT-TYPE
			   SYNTAX       		INTEGER
									{
									hidden(1),
									read-only(2),
									updateable(3)
									}
			   ACCESS           	read-only
			   STATUS           	mandatory
			   DESCRIPTION
			   "The value of this object provides the current state of
			    the parameter."
			   ::= { gx2cmStatusEntry 16}

            -- ************ FACTORY DATA ****************
		gx2cmFactoryTableIndex              OBJECT-TYPE
			   SYNTAX           INTEGER (1..4294967295)
			   ACCESS           read-only
			   STATUS           mandatory
			   DESCRIPTION
			   "The value of this object identifies the network
			    element. This index is equal to the
			    hfcCommonTableIndex for the same element."
			   ::= { gx2cmFactoryEntry 1}

		bootControlByte          	OBJECT-TYPE
			   SYNTAX       		INTEGER
			   ACCESS           	read-only
			   STATUS           	mandatory
			   DESCRIPTION
			   "The value of this object indicates which bank the firmware
			    is currently being boot from."
			   ::= { gx2cmFactoryEntry 2}

		bootStatusByte          	OBJECT-TYPE
			   SYNTAX       		INTEGER
			   ACCESS           	read-only
			   STATUS           	mandatory
			   DESCRIPTION
			   "This object indicates the status of the last boot"
			   ::= { gx2cmFactoryEntry 3}

		bank0CRC          		OBJECT-TYPE
			   SYNTAX       		INTEGER
			   ACCESS           	read-only
			   STATUS           	mandatory
			   DESCRIPTION
			   "This object provides the CRC code of bank 1."
			   ::= { gx2cmFactoryEntry 4}

		bank1CRC          		OBJECT-TYPE
			   SYNTAX       		INTEGER
			   ACCESS           	read-only
			   STATUS           	mandatory
			   DESCRIPTION
			   "This object provides the CRC code of bank 2."
			   ::= { gx2cmFactoryEntry 5}

		prgEEPROMByte          		OBJECT-TYPE
			   SYNTAX       		INTEGER
			   ACCESS           	read-only
			   STATUS           	mandatory
			   DESCRIPTION
			   "This object indicates if the EEPROM has been programmed"
			   ::= { gx2cmFactoryEntry 6}

		factoryCRC          		OBJECT-TYPE
			   SYNTAX       		INTEGER
			   ACCESS           	read-only
			   STATUS           	mandatory
			   DESCRIPTION
			   "This object provides the CRC code for the Factory data."
			   ::= { gx2cmFactoryEntry 7}

		calculateCRC          		OBJECT-TYPE
			   SYNTAX       		INTEGER
			   ACCESS           	read-only
			   STATUS           	mandatory
			   DESCRIPTION
			   "This object provides the CRC value of the fimware."
			   ::= { gx2cmFactoryEntry 8}

		hourMeter          		OBJECT-TYPE
			   SYNTAX       		INTEGER
			   ACCESS           	read-only
			   STATUS           	mandatory
			   DESCRIPTION
			   "This object provides the hour meter reading of the module."
			   ::= { gx2cmFactoryEntry 9}

		flashPrgCnt0          		OBJECT-TYPE
			   SYNTAX       		INTEGER
			   ACCESS           	read-only
			   STATUS           	mandatory
			   DESCRIPTION
			   "This object provides the number of times the flash has been 
                      programmed on side A."
			   ::= { gx2cmFactoryEntry 10}

		flashPrgCnt1          		OBJECT-TYPE
			   SYNTAX       		INTEGER
			   ACCESS           	read-only
			   STATUS           	mandatory
			   DESCRIPTION
			   "This object provides the number of times the flash has been 
                      programmed on side B."
			   ::= { gx2cmFactoryEntry 11}

		flashBank0          		OBJECT-TYPE
			   SYNTAX       		DisplayString (SIZE (0..80))
			   ACCESS           	read-only
			   STATUS           	mandatory
			   DESCRIPTION
			   "This object provides the firmware revision of the firmware in bank 0."
			   ::= { gx2cmFactoryEntry 12}

		flashBank1          		OBJECT-TYPE
			   SYNTAX       		DisplayString (SIZE (0..80))
			   ACCESS           	read-only
			   STATUS           	mandatory
			   DESCRIPTION
			   "This object provides the firmware revision of the firmware in bank 1."
			   ::= { gx2cmFactoryEntry 13}


		localMacAdd          		OBJECT-TYPE
			   SYNTAX       		DisplayString (SIZE (0..80))
			   ACCESS           	read-only
			   STATUS           	mandatory
			   DESCRIPTION
			   "This object provides the local mac address number"
			   ::= { gx2cmFactoryEntry 14}

		netWorkMacAdd          		OBJECT-TYPE
			   SYNTAX       		DisplayString (SIZE (0..80))
			   ACCESS           	read-only
			   STATUS           	mandatory
			   DESCRIPTION
			   "This object provides the network mac address number."
			   ::= { gx2cmFactoryEntry 15}


		-- ************** Network info Parameters *********************
		gx2cmNetworkTableIndex              OBJECT-TYPE
			   SYNTAX           INTEGER (1..4294967295)
			   ACCESS           read-only
			   STATUS           mandatory
			   DESCRIPTION
			   "The value of this object identifies the network
			    element. This index is equal to the
			    hfcCommonTableIndex for the same element."
			   ::= { gx2cmNetworkEntry 1}

		labelLocalEthIPAdd     		OBJECT-TYPE
			   SYNTAX       		DisplayString (SIZE (0..80))
			   ACCESS           	read-only
			   STATUS           	optional
			   DESCRIPTION
			   "This object provides the label for the Ethernet IP Address field."
			   ::= { gx2cmNetworkEntry 2}

		valueLocalEthIPAdd     		OBJECT-TYPE
			   SYNTAX       		DisplayString (SIZE (0..80))
			   ACCESS           	read-write
			   STATUS           	mandatory
			   DESCRIPTION
			   "This object provides the Local Ethernet IP Address for the
			    Control Module."
			   ::= { gx2cmNetworkEntry 3}
--
		labelLocalEthMask      		OBJECT-TYPE
			   SYNTAX       		DisplayString (SIZE (0..80))
			   ACCESS           	read-only
			   STATUS           	optional
			   DESCRIPTION
			   "This object provides the label for the Local Ethernet Mask field."
			   ::= { gx2cmNetworkEntry 4}

		valueLocalEthMask      		OBJECT-TYPE
			   SYNTAX       		DisplayString (SIZE (0..80))
			   ACCESS           	read-write
			   STATUS           	mandatory
			   DESCRIPTION
			   "This object provides the Local Ethernet Mask value."
			   ::= { gx2cmNetworkEntry 5}
--
		labelNetworkEthAdd     		OBJECT-TYPE
			   SYNTAX       		DisplayString (SIZE (0..80))
			   ACCESS           	read-only
			   STATUS           	optional
			   DESCRIPTION
			   "This object provides the label for the Network Ethernet Address ."
			   ::= { gx2cmNetworkEntry 6}

		valueNetworkEthAdd		OBJECT-TYPE
			   SYNTAX       		DisplayString (SIZE (0..80))
			   ACCESS           	read-write
			   STATUS           	mandatory
			   DESCRIPTION
			   "This object provides the value of the Network Ethernet Address."
			   ::= { gx2cmNetworkEntry 7}
--
		labelNetworkEthMask    		OBJECT-TYPE
			   SYNTAX       		DisplayString (SIZE (0..80))
			   ACCESS           	read-only
			   STATUS           	optional
			   DESCRIPTION
			   "This object provides the label for the Network Mask Address."
			   ::= { gx2cmNetworkEntry 8}

		valueNetworkEthMask    		OBJECT-TYPE
			   SYNTAX       		DisplayString (SIZE (0..80))
			   ACCESS           	read-write
			   STATUS           	mandatory
			   DESCRIPTION
			   "This object provides the value of the Network Mask Address."
			   ::= { gx2cmNetworkEntry 9}
--
		labelShelfSerialNum   		OBJECT-TYPE
			   SYNTAX       		DisplayString (SIZE (0..80))
			   ACCESS           	read-only
			   STATUS           	optional
			   DESCRIPTION
			   "This object provides the label for the Shelf Serial Number."
			   ::= { gx2cmNetworkEntry 10}

		valueShelfSerialNum    		OBJECT-TYPE
			   SYNTAX       		DisplayString (SIZE (0..80))
			   ACCESS           	read-only
			   STATUS           	mandatory
			   DESCRIPTION
			   "This object provides the value for the Shelf Serial Number."
			   ::= { gx2cmNetworkEntry 11}

		labelGateWayIPAdd   		OBJECT-TYPE
			   SYNTAX       		DisplayString (SIZE (0..80))
			   ACCESS           	read-only
			   STATUS           	optional
			   DESCRIPTION
			   "This object provides the label for the Gateway IP address."
			   ::= { gx2cmNetworkEntry 12}

		valueGateWayIPAdd    		OBJECT-TYPE
			   SYNTAX       		DisplayString (SIZE (0..80))
			   ACCESS           	read-write
			   STATUS           	mandatory
			   DESCRIPTION
			   "This object provides the value for the IP address for the Gateway."
			   ::= { gx2cmNetworkEntry 13}

		labelTrapDestination   		OBJECT-TYPE
			   SYNTAX       		DisplayString (SIZE (0..80))
			   ACCESS           	read-only
			   STATUS           	optional
			   DESCRIPTION
			   "This object provides the label the trap destination field."
			   ::= { gx2cmNetworkEntry 14}

		valueTrapDestination    		OBJECT-TYPE
			   SYNTAX       		DisplayString (SIZE (0..80))
			   ACCESS           	read-write
			   STATUS           	mandatory
			   DESCRIPTION
			   "This object provides the address for the trap destination."
			   ::= { gx2cmNetworkEntry 15}

		labelTFTPserver   			OBJECT-TYPE
			   SYNTAX       		DisplayString (SIZE (0..80))
			   ACCESS           	read-only
			   STATUS           	optional
			   DESCRIPTION
			   "This object provides the label the TFTP Server address field."
			   ::= { gx2cmNetworkEntry 16}

		valueTFTPserver	    		OBJECT-TYPE
			   SYNTAX       		DisplayString (SIZE (0..80))
			   ACCESS           	read-write
			   STATUS           	mandatory
			   DESCRIPTION
			   "This object provides the address for the TFTP Server."
			   ::= { gx2cmNetworkEntry 17}

		labelTrap2Destination   		OBJECT-TYPE
			   SYNTAX       		DisplayString (SIZE (0..80))
			   ACCESS           	read-only
			   STATUS           	optional
			   DESCRIPTION
			   "This object provides the label the second trap destination field."
			   ::= { gx2cmNetworkEntry 18}

		valueTrap2Destination    		OBJECT-TYPE
			   SYNTAX       		DisplayString (SIZE (0..80))
			   ACCESS           	read-write
			   STATUS           	mandatory
			   DESCRIPTION
			   "This object provides the address for the second trap destination."
			   ::= { gx2cmNetworkEntry 19}

		labelTrap3Destination   		OBJECT-TYPE
			   SYNTAX       		DisplayString (SIZE (0..80))
			   ACCESS           	read-only
			   STATUS           	optional
			   DESCRIPTION
			   "This object provides the label the third trap destination field."
			   ::= { gx2cmNetworkEntry 20}

		valueTrap3Destination    		OBJECT-TYPE
			   SYNTAX       		DisplayString (SIZE (0..80))
			   ACCESS           	read-write
			   STATUS           	mandatory
			   DESCRIPTION
			   "This object provides the address for the third trap destination."
			   ::= { gx2cmNetworkEntry 21}

		labelTrap4Destination   		OBJECT-TYPE
			   SYNTAX       		DisplayString (SIZE (0..80))
			   ACCESS           	read-only
			   STATUS           	optional
			   DESCRIPTION
			   "This object provides the label the fourth trap destination field."
			   ::= { gx2cmNetworkEntry 22}

		valueTrap4Destination    		OBJECT-TYPE
			   SYNTAX       		DisplayString (SIZE (0..80))
			   ACCESS           	read-write
			   STATUS           	mandatory
			   DESCRIPTION
			   "This object provides the address for the fourth trap destination."
			   ::= { gx2cmNetworkEntry 23}

		labelTrap5Destination   		OBJECT-TYPE
			   SYNTAX       		DisplayString (SIZE (0..80))
			   ACCESS           	read-only
			   STATUS           	optional
			   DESCRIPTION
			   "This object provides the label the fifth trap destination field."
			   ::= { gx2cmNetworkEntry 24}

		valueTrap5Destination    		OBJECT-TYPE
			   SYNTAX       		DisplayString (SIZE (0..80))
			   ACCESS           	read-write
			   STATUS           	mandatory
			   DESCRIPTION
			   "This object provides the address for the fifth trap destination."
			   ::= { gx2cmNetworkEntry 25}

-- ISDN parameters Rev k

		labelISDNMode   		OBJECT-TYPE
			   SYNTAX       		DisplayString (SIZE (0..80))
			   ACCESS           	read-only
			   STATUS           	optional
			   DESCRIPTION
			   "This object provides the label for the ISDN mode setting."
			   ::= { gx2cmNetworkEntry 26}

		valueISDNMode    		OBJECT-TYPE
			   SYNTAX       		INTEGER
							{
								off(1),
								on(2)
					    		}
			   ACCESS           	read-write
			   STATUS           	mandatory
			   DESCRIPTION
			   "This object provides the value for the ISDN mode setting.
			    In order to activate the ISDN feature, the user must set
			    the ISDN mode to ON and provide a valid IP address. This address
				needs to be the IP address of the remote ISDN Modem."
			   ::= { gx2cmNetworkEntry 27}

		labelISDNModemIPAddress		OBJECT-TYPE
			   SYNTAX       		DisplayString (SIZE (0..80))
			   ACCESS           	read-only
			   STATUS           	optional
			   DESCRIPTION
			   "This object provides the label for the ISDN modem IP Address."
			   ::= { gx2cmNetworkEntry 28}

		valueISDNModemIPAddress		OBJECT-TYPE
			   SYNTAX       		DisplayString (SIZE (0..80))
			   ACCESS           	read-write
			   STATUS           	mandatory
			   DESCRIPTION
			   "This object provides the value for the ISDN modem IP Address. This Address is used by the control Module 
			   to ping the remote ISDN modem to determine if an ISDN connection is made. Only after a successful ping response
			   to this address and the ISDN Modem Mode object is set to ON will the Control Module send traps.  
			    Factory default value is 0.0.0.0."
			   ::= { gx2cmNetworkEntry 29}

		labelISDNTrapTimeout		OBJECT-TYPE
			   SYNTAX       		DisplayString (SIZE (0..80))
			   ACCESS           	read-only
			   STATUS           	optional
			   DESCRIPTION
			   "This object provides the label for the ISDN modem Timeout object."
			   ::= { gx2cmNetworkEntry 30}

		valueISDNTrapTimeout		OBJECT-TYPE
			   SYNTAX       		INTEGER (0 .. 3600)
			   ACCESS           	read-write
			   STATUS           	mandatory
			   DESCRIPTION
			   "This object provides the value for the ISDN modem Timeout.
			    The value of this object sets the time period that the communication 
				link is open for sending traps. This timer is started when the first trap is issued.
				The factory default for this value is 2 minutes. Unit of measure is in seconds."
			   ::= { gx2cmNetworkEntry 31}

		labelISDNPingTimeout		OBJECT-TYPE
			   SYNTAX       		DisplayString (SIZE (0..80))
			   ACCESS           	read-only
			   STATUS           	optional
			   DESCRIPTION
			   "This object provides the label for the ISDN ping timeout object."
			   ::= { gx2cmNetworkEntry 32}

		valueISDNPingTimeout		OBJECT-TYPE
			   SYNTAX       		INTEGER (100 .. 5000)
			   ACCESS           	read-write
			   STATUS           	mandatory
			   DESCRIPTION
			   "This object provides the value for the ISDN ping timeout.
			    Factory default value is 500 ms. User should set this 
			    value in milli-second"
			   ::= { gx2cmNetworkEntry 33}

		labelISDNBackoffTimer		OBJECT-TYPE
			   SYNTAX       		DisplayString (SIZE (0..80))
			   ACCESS           	read-only
			   STATUS           	optional
			   DESCRIPTION
			   "This object provides the label for the ISDN backoff timer object."
			   ::= { gx2cmNetworkEntry 34}

		valueISDNBackoffTimer		OBJECT-TYPE
			   SYNTAX       		INTEGER (0 .. 3600)
			   ACCESS           	read-write
			   STATUS           	mandatory
			   DESCRIPTION
			   "This object provides the value for the ISDN backoff timer.
			    The value in this object is a hold period used to prevent traps from being sent.
				It is used to allow other chassis to have time to connect and communicate over the ISDN modems.
				This hold period starts after the valueISDNTrapTimeout period has expired.
				NOTE: The value of this object should be set to a value greater than the ISDN Modem's idle connection timeout period.
				This will allow the Modem to break the ISDN Connection.
				Factory default value is 2 min (120 sec).  User should set this 
			    value in seconds"
			   ::= { gx2cmNetworkEntry 35}

		--**************** Security Parameters********************
		gx2cmSecurityTableIndex              OBJECT-TYPE
			   SYNTAX           INTEGER (1..4294967295)
			   ACCESS           read-only
			   STATUS           mandatory
			   DESCRIPTION
			   "The value of this object identifies the network
			    element. This index is equal to the
			    hfcCommonTableIndex for the same element."
			   ::= { gx2cmSecurityEntry 1}

		labelSecurityMode	          	OBJECT-TYPE
			   SYNTAX       		DisplayString (SIZE (0..80))
			   ACCESS           	read-only
			   STATUS           	optional
			   DESCRIPTION
			   "This object provides the label for the Current Security Mode."
			   ::= { gx2cmSecurityEntry 2}

		enumSecurityMode	 		OBJECT-TYPE
			   SYNTAX       		DisplayString (SIZE (0..80))
			   ACCESS           	read-only
			   STATUS           	optional
			   DESCRIPTION
			   "The value of this object represents the Enumeration values
			    possible for the security mode parameter. Each Enumerated value is
			    separated by a common. The first value has a enumerated value of 1."
			   ::= { gx2cmSecurityEntry 3}

		valueSecurityMode          	OBJECT-TYPE
			   SYNTAX       		INTEGER
							{
							read-only(1),
							operator-access(2),
							factory-access(3),
							remote-write-only(4),
							local-write-only(5)
					    	}
			   ACCESS           	read-only
			   STATUS           	mandatory
			   DESCRIPTION
			   "This object indicates the current Security Mode."
			   ::= { gx2cmSecurityEntry 4}

		stateSecurityMode	          	OBJECT-TYPE
			   SYNTAX       		INTEGER
								{
								hidden(1),
								read-only(2),
								updateable(3)
								}
			   ACCESS           	read-only
			   STATUS           	mandatory
			   DESCRIPTION
			   "This object indicates the state of the Security Mode parameter ."
			   ::= { gx2cmSecurityEntry 5}

		labelPassword		 	OBJECT-TYPE
			   SYNTAX       		DisplayString (SIZE (0..80))
			   ACCESS           	read-only
			   STATUS           	optional
			   DESCRIPTION
			   "This object provides the label for the Password field."
			   ::= { gx2cmSecurityEntry 6}

		valuePassword	          	OBJECT-TYPE
			   SYNTAX       		DisplayString (SIZE (0..80))
			   ACCESS           	read-write
			   STATUS           	mandatory
			   DESCRIPTION
			   "This object provides the value for the Password."
			   ::= { gx2cmSecurityEntry 7}

		statePassword	          	OBJECT-TYPE
			   SYNTAX       		INTEGER
								{
								hidden(1),
								read-only(2),
								updateable(3)
								}
			   ACCESS           	read-only
			   STATUS           	mandatory
			   DESCRIPTION
			   "This object provides the state of the password field."
			   ::= { gx2cmSecurityEntry 8}

		labelFactoryChgString        	OBJECT-TYPE
			   SYNTAX       		DisplayString (SIZE (0..80))
			   ACCESS           	read-only
			   STATUS           	optional
			   DESCRIPTION
			   "This object provides the lable for the Factory Change String field."
			   ::= { gx2cmSecurityEntry 9}

		valueFactoryChgString        	OBJECT-TYPE
			   SYNTAX       		DisplayString (SIZE (0..80))
			   ACCESS           	write-only
			   STATUS           	mandatory
			   DESCRIPTION
			   "This object provides the value for the Factory Change String."
			   ::= { gx2cmSecurityEntry 10}

		stateFactoryChgString        	OBJECT-TYPE
			   SYNTAX       		INTEGER
								{
								hidden(1),
								read-only(2),
								updateable(3)
								}
			   ACCESS           	read-only
			   STATUS           	mandatory
			   DESCRIPTION
			   "This object provides the state of the Factory Change String field."
			   ::= { gx2cmSecurityEntry 11}

		labelOperatorChgString        	OBJECT-TYPE
			   SYNTAX       		DisplayString (SIZE (0..80))
			   ACCESS           	read-only
			   STATUS           	optional
			   DESCRIPTION
			   "This object provides the lable for the Operator Change String field."
			   ::= { gx2cmSecurityEntry 12}

		valueOperatorChgString        	OBJECT-TYPE
			   SYNTAX       		DisplayString (SIZE (0..80))
			   ACCESS           	write-only
			   STATUS           	mandatory
			   DESCRIPTION
			   "This object provides the value for the Operator Change String."
			   ::= { gx2cmSecurityEntry 13}

		stateOperatorChgString        	OBJECT-TYPE
			   SYNTAX       		INTEGER
								{
								hidden(1),
								read-only(2),
								updateable(3)
								}
			   ACCESS           	read-only
			   STATUS           	mandatory
			   DESCRIPTION
			   "This object provides the state of the Operator Change String field."
			   ::= { gx2cmSecurityEntry 14}


		labelReadOnlyChgString        	OBJECT-TYPE
			   SYNTAX       		DisplayString (SIZE (0..80))
			   ACCESS           	read-only
			   STATUS           	optional
			   DESCRIPTION
			   "This object provides the lable for the Read Only Change String field."
			   ::= { gx2cmSecurityEntry 15}

		valueReadOnlyChgString        	OBJECT-TYPE
			   SYNTAX       		DisplayString (SIZE (0..80))
			   ACCESS           	write-only
			   STATUS           	mandatory
			   DESCRIPTION
			   "This object provides the value for the Read Only Change String."
			   ::= { gx2cmSecurityEntry 16}

		stateReadOnlyChgString        	OBJECT-TYPE
			   SYNTAX       		INTEGER
								{
								hidden(1),
								read-only(2),
								updateable(3)
								}
			   ACCESS           	read-only
			   STATUS           	mandatory
			   DESCRIPTION
			   "This object provides the state of the Read Only Change String field."
			   ::= { gx2cmSecurityEntry 17}

		labelRemoteOnlyChgString        	OBJECT-TYPE
			   SYNTAX       		DisplayString (SIZE (0..80))
			   ACCESS           	read-only
			   STATUS           	optional
			   DESCRIPTION
			   "This object provides the lable for the Remote Only Change String field."
			   ::= { gx2cmSecurityEntry 18}

		valueRemoteOnlyChgString        	OBJECT-TYPE
			   SYNTAX       		DisplayString (SIZE (0..80))
			   ACCESS           	write-only
			   STATUS           	mandatory
			   DESCRIPTION
			   "This object provides the value for the Remote Only Change String."
			   ::= { gx2cmSecurityEntry 19}

		stateRemoteOnlyChgString        	OBJECT-TYPE
			   SYNTAX       		INTEGER
								{
								hidden(1),
								read-only(2),
								updateable(3)
								}
			   ACCESS           	read-only
			   STATUS           	mandatory
			   DESCRIPTION
			   "This object provides the state of the Remote Only Change String field."
			   ::= { gx2cmSecurityEntry 20}


		labelLocalOnlyChgString        	OBJECT-TYPE
			   SYNTAX       		DisplayString (SIZE (0..80))
			   ACCESS           	read-only
			   STATUS           	optional
			   DESCRIPTION
			   "This object provides the lable for the Local Only Change String field."
			   ::= { gx2cmSecurityEntry 21}

		valueLocalOnlyChgString        	OBJECT-TYPE
			   SYNTAX       		DisplayString (SIZE (0..80))
			   ACCESS           	write-only
			   STATUS           	mandatory
			   DESCRIPTION
			   "This object provides the value for the Local Only Change String."
			   ::= { gx2cmSecurityEntry 22}

		stateLocalOnlyChgString        	OBJECT-TYPE
			   SYNTAX       		INTEGER
								{
								hidden(1),
								read-only(2),
								updateable(3)
								}
			   ACCESS           	read-only
			   STATUS           	mandatory
			   DESCRIPTION
			   "This object provides the state of the Local Only Change String field."
			   ::= { gx2cmSecurityEntry 23}

-- **************************AMC Parameters ********************************************		
		gx2cmAMCTableIndex              OBJECT-TYPE
			   SYNTAX           INTEGER (1..4294967295)
			   ACCESS           read-only
			   STATUS           mandatory
			   DESCRIPTION
			   "The value of this object identifies the network
			    element. This index is equal to the
			    hfcCommonTableIndex for the same element."
			   ::= { gx2cmAMCEntry 1}

		valueAMCslot1        	OBJECT-TYPE
			   SYNTAX       		INTEGER
								{
								disabled(1),
								enabled(2),
								force(3)
					    		}
			   ACCESS           read-write
			   STATUS           mandatory
			   DESCRIPTION
			   "This object provides control to enable or disable AMC for the
			   current device in the slot."
			   ::= { gx2cmAMCEntry 2}

		serialAMCslot1        	OBJECT-TYPE
			   SYNTAX       		DisplayString (SIZE (0..80))
			   ACCESS           	read-only
			   STATUS           	mandatory
			   DESCRIPTION
			   "This object provides the serial number for the AMC slot selected."
			   ::= { gx2cmAMCEntry 3}

		agentIDAMCslot1        	OBJECT-TYPE
			   SYNTAX       		INTEGER
			   ACCESS           	read-only
			   STATUS           	mandatory
			   DESCRIPTION
			   "This object provides the agentID of the AMC parameter for the selected slot."
			   ::= { gx2cmAMCEntry 4}

--
		valueAMCslot2        	OBJECT-TYPE
			   SYNTAX       		INTEGER
								{
								disabled(1),
								enabled(2),
								force(3)
					    		}
			   ACCESS           read-write
			   STATUS           mandatory
			   DESCRIPTION
			   "This object provides control to enable or disable AMC for the
			   current device in the slot."
			   ::= { gx2cmAMCEntry 5}

		serialAMCslot2        	OBJECT-TYPE
			   SYNTAX       		DisplayString (SIZE (0..80))
			   ACCESS           	read-only
			   STATUS           	mandatory
			   DESCRIPTION
			   "This object provides the serial number for the AMC slot selected."
			   ::= { gx2cmAMCEntry 6}

		agentIDAMCslot2        	OBJECT-TYPE
			   SYNTAX       		INTEGER
			   ACCESS           	read-only
			   STATUS           	mandatory
			   DESCRIPTION
			   "This object provides the agentID of the AMC parameter for the selected slot."
			   ::= { gx2cmAMCEntry 7}

--
		valueAMCslot3        	OBJECT-TYPE
			   SYNTAX       		INTEGER
								{
								disabled(1),
								enabled(2),
								force(3)
					    		}
			   ACCESS           read-write
			   STATUS           mandatory
			   DESCRIPTION
			   "This object provides control to enable or disable AMC for the
			   current device in the slot."
			   ::= { gx2cmAMCEntry 8}

		serialAMCslot3        	OBJECT-TYPE
			   SYNTAX       		DisplayString (SIZE (0..80))
			   ACCESS           	read-only
			   STATUS           	mandatory
			   DESCRIPTION
			   "This object provides the serial number for the AMC slot selected."
			   ::= { gx2cmAMCEntry 9}

		agentIDAMCslot3        	OBJECT-TYPE
			   SYNTAX       		INTEGER
			   ACCESS           	read-only
			   STATUS           	mandatory
			   DESCRIPTION
			   "This object provides the agentID of the AMC parameter for the selected slot."
			   ::= { gx2cmAMCEntry 10}

--
		valueAMCslot4        	OBJECT-TYPE
			   SYNTAX       		INTEGER
								{
								disabled(1),
								enabled(2),
								force(3)
					    		}
			   ACCESS           read-write
			   STATUS           mandatory
			   DESCRIPTION
			   "This object provides control to enable or disable AMC for the
			   current device in the slot."
			   ::= { gx2cmAMCEntry 11}

		serialAMCslot4        	OBJECT-TYPE
			   SYNTAX       		DisplayString (SIZE (0..80))
			   ACCESS           	read-only
			   STATUS           	mandatory
			   DESCRIPTION
			   "This object provides the serial number for the AMC slot selected."
			   ::= { gx2cmAMCEntry 12}

		agentIDAMCslot4        	OBJECT-TYPE
			   SYNTAX       		INTEGER
			   ACCESS           	read-only
			   STATUS           	mandatory
			   DESCRIPTION
			   "This object provides the agentID of the AMC parameter for the selected slot."
			   ::= { gx2cmAMCEntry 13}

--
		valueAMCslot5        	OBJECT-TYPE
			   SYNTAX       		INTEGER
								{
								disabled(1),
								enabled(2),
								force(3)
					    		}
			   ACCESS           read-write
			   STATUS           mandatory
			   DESCRIPTION
			   "This object provides control to enable or disable AMC for the
			   current device in the slot."
			   ::= { gx2cmAMCEntry 14}

		serialAMCslot5        	OBJECT-TYPE
			   SYNTAX       		DisplayString (SIZE (0..80))
			   ACCESS           	read-only
			   STATUS           	mandatory
			   DESCRIPTION
			   "This object provides the serial number for the AMC slot selected."
			   ::= { gx2cmAMCEntry 15}

		agentIDAMCslot5        	OBJECT-TYPE
			   SYNTAX       		INTEGER
			   ACCESS           	read-only
			   STATUS           	mandatory
			   DESCRIPTION
			   "This object provides the agentID of the AMC parameter for the selected slot."
			   ::= { gx2cmAMCEntry 16}

--
		valueAMCslot6        	OBJECT-TYPE
			   SYNTAX       		INTEGER
								{
								disabled(1),
								enabled(2),
								force(3)
					    		}
			   ACCESS           read-write
			   STATUS           mandatory
			   DESCRIPTION
			   "This object provides control to enable or disable AMC for the
			   current device in the slot."
			   ::= { gx2cmAMCEntry 17}

		serialAMCslot6        	OBJECT-TYPE
			   SYNTAX       		DisplayString (SIZE (0..80))
			   ACCESS           	read-only
			   STATUS           	mandatory
			   DESCRIPTION
			   "This object provides the serial number for the AMC slot selected."
			   ::= { gx2cmAMCEntry 18}

		agentIDAMCslot6        	OBJECT-TYPE
			   SYNTAX       		INTEGER
			   ACCESS           	read-only
			   STATUS           	mandatory
			   DESCRIPTION
			   "This object provides the agentID of the AMC parameter for the selected slot."
			   ::= { gx2cmAMCEntry 19}

--
		valueAMCslot7        	OBJECT-TYPE
			   SYNTAX       		INTEGER
								{
								disabled(1),
								enabled(2),
								force(3)
					    		}
			   ACCESS           read-write
			   STATUS           mandatory
			   DESCRIPTION
			   "This object provides control to enable or disable AMC for the
			   current device in the slot."
			   ::= { gx2cmAMCEntry 20}

		serialAMCslot7        	OBJECT-TYPE
			   SYNTAX       		DisplayString (SIZE (0..80))
			   ACCESS           	read-only
			   STATUS           	mandatory
			   DESCRIPTION
			   "This object provides the serial number for the AMC slot selected."
			   ::= { gx2cmAMCEntry 21}

		agentIDAMCslot7        	OBJECT-TYPE
			   SYNTAX       		INTEGER
			   ACCESS           	read-only
			   STATUS           	mandatory
			   DESCRIPTION
			   "This object provides the agentID of the AMC parameter for the selected slot."
			   ::= { gx2cmAMCEntry 22}

--
		valueAMCslot8        	OBJECT-TYPE
			   SYNTAX       		INTEGER
								{
								disabled(1),
								enabled(2),
								force(3)
					    		}
			   ACCESS           read-write
			   STATUS           mandatory
			   DESCRIPTION
			   "This object provides control to enable or disable AMC for the
			   current device in the slot."
			   ::= { gx2cmAMCEntry 23}

		serialAMCslot8        	OBJECT-TYPE
			   SYNTAX       		DisplayString (SIZE (0..80))
			   ACCESS           	read-only
			   STATUS           	mandatory
			   DESCRIPTION
			   "This object provides the serial number for the AMC slot selected."
			   ::= { gx2cmAMCEntry 24}

		agentIDAMCslot8        	OBJECT-TYPE
			   SYNTAX       		INTEGER
			   ACCESS           	read-only
			   STATUS           	mandatory
			   DESCRIPTION
			   "This object provides the agentID of the AMC parameter for the selected slot."
			   ::= { gx2cmAMCEntry 25}

--
		valueAMCslot9        	OBJECT-TYPE
			   SYNTAX       		INTEGER
								{
								disabled(1),
								enabled(2),
								force(3)
					    		}
			   ACCESS           read-write
			   STATUS           mandatory
			   DESCRIPTION
			   "This object provides control to enable or disable AMC for the
			   current device in the slot."
			   ::= { gx2cmAMCEntry 26}

		serialAMCslot9        	OBJECT-TYPE
			   SYNTAX       		DisplayString (SIZE (0..80))
			   ACCESS           	read-only
			   STATUS           	mandatory
			   DESCRIPTION
			   "This object provides the serial number for the AMC slot selected."
			   ::= { gx2cmAMCEntry 27}

		agentIDAMCslot9        	OBJECT-TYPE
			   SYNTAX       		INTEGER
			   ACCESS           	read-only
			   STATUS           	mandatory
			   DESCRIPTION
			   "This object provides the agentID of the AMC parameter for the selected slot."
			   ::= { gx2cmAMCEntry 28}

--
		valueAMCslot10        	OBJECT-TYPE
			   SYNTAX       		INTEGER
								{
								disabled(1),
								enabled(2),
								force(3)
					    		}
			   ACCESS           read-write
			   STATUS           mandatory
			   DESCRIPTION
			   "This object provides control to enable or disable AMC for the
			   current device in the slot."
			   ::= { gx2cmAMCEntry 29}

		serialAMCslot10        	OBJECT-TYPE
			   SYNTAX       		DisplayString (SIZE (0..80))
			   ACCESS           	read-only
			   STATUS           	mandatory
			   DESCRIPTION
			   "This object provides the serial number for the AMC slot selected."
			   ::= { gx2cmAMCEntry 30}

		agentIDAMCslot10        	OBJECT-TYPE
			   SYNTAX       		INTEGER
			   ACCESS           	read-only
			   STATUS           	mandatory
			   DESCRIPTION
			   "This object provides the agentID of the AMC parameter for the selected slot."
			   ::= { gx2cmAMCEntry 31}

--
		valueAMCslot11        	OBJECT-TYPE
			   SYNTAX       		INTEGER
								{
								disabled(1),
								enabled(2),
								force(3)
					    		}
			   ACCESS           read-write
			   STATUS           mandatory
			   DESCRIPTION
			   "This object provides control to enable or disable AMC for the
			   current device in the slot."
			   ::= { gx2cmAMCEntry 32}

		serialAMCslot11        	OBJECT-TYPE
			   SYNTAX       		DisplayString (SIZE (0..80))
			   ACCESS           	read-only
			   STATUS           	mandatory
			   DESCRIPTION
			   "This object provides the serial number for the AMC slot selected."
			   ::= { gx2cmAMCEntry 33}

		agentIDAMCslot11        	OBJECT-TYPE
			   SYNTAX       		INTEGER
			   ACCESS           	read-only
			   STATUS           	mandatory
			   DESCRIPTION
			   "This object provides the agentID of the AMC parameter for the selected slot."
			   ::= { gx2cmAMCEntry 34}

--
		valueAMCslot12        	OBJECT-TYPE
			   SYNTAX       		INTEGER
								{
								disabled(1),
								enabled(2),
								force(3)
					    		}
			   ACCESS           read-write
			   STATUS           mandatory
			   DESCRIPTION
			   "This object provides control to enable or disable AMC for the
			   current device in the slot."
			   ::= { gx2cmAMCEntry 35}

		serialAMCslot12        	OBJECT-TYPE
			   SYNTAX       		DisplayString (SIZE (0..80))
			   ACCESS           	read-only
			   STATUS           	mandatory
			   DESCRIPTION
			   "This object provides the serial number for the AMC slot selected."
			   ::= { gx2cmAMCEntry 36}

		agentIDAMCslot12        	OBJECT-TYPE
			   SYNTAX       		INTEGER
			   ACCESS           	read-only
			   STATUS           	mandatory
			   DESCRIPTION
			   "This object provides the agentID of the AMC parameter for the selected slot."
			   ::= { gx2cmAMCEntry 37}

--
		valueAMCslot13        	OBJECT-TYPE
			   SYNTAX       		INTEGER
								{
								disabled(1),
								enabled(2),
								force(3)
					    		}
			   ACCESS           read-write
			   STATUS           mandatory
			   DESCRIPTION
			   "This object provides control to enable or disable AMC for the
			   current device in the slot."
			   ::= { gx2cmAMCEntry 38}

		serialAMCslot13        	OBJECT-TYPE
			   SYNTAX       		DisplayString (SIZE (0..80))
			   ACCESS           	read-only
			   STATUS           	mandatory
			   DESCRIPTION
			   "This object provides the serial number for the AMC slot selected."
			   ::= { gx2cmAMCEntry 39}

		agentIDAMCslot13        	OBJECT-TYPE
			   SYNTAX       		INTEGER
			   ACCESS           	read-only
			   STATUS           	mandatory
			   DESCRIPTION
			   "This object provides the agentID of the AMC parameter for the selected slot."
			   ::= { gx2cmAMCEntry 40}

--
		valueAMCslot14        	OBJECT-TYPE
			   SYNTAX       		INTEGER
								{
								disabled(1),
								enabled(2),
								force(3)
					    		}
			   ACCESS           read-write
			   STATUS           mandatory
			   DESCRIPTION
			   "This object provides control to enable or disable AMC for the
			   current device in the slot."
			   ::= { gx2cmAMCEntry 41}

		serialAMCslot14        	OBJECT-TYPE
			   SYNTAX       		DisplayString (SIZE (0..80))
			   ACCESS           	read-only
			   STATUS           	mandatory
			   DESCRIPTION
			   "This object provides the serial number for the AMC slot selected."
			   ::= { gx2cmAMCEntry 42}

		agentIDAMCslot14        	OBJECT-TYPE
			   SYNTAX       		INTEGER
			   ACCESS           	read-only
			   STATUS           	mandatory
			   DESCRIPTION
			   "This object provides the agentID of the AMC parameter for the selected slot."
			   ::= { gx2cmAMCEntry 43}

--
		valueAMCslot15        	OBJECT-TYPE
			   SYNTAX       		INTEGER
								{
								disabled(1),
								enabled(2),
								force(3)
					    		}
			   ACCESS           read-write
			   STATUS           mandatory
			   DESCRIPTION
			   "This object provides control to enable or disable AMC for the
			   current device in the slot."
			   ::= { gx2cmAMCEntry 44}

		serialAMCslot15        	OBJECT-TYPE
			   SYNTAX       		DisplayString (SIZE (0..80))
			   ACCESS           	read-only
			   STATUS           	mandatory
			   DESCRIPTION
			   "This object provides the serial number for the AMC slot selected."
			   ::= { gx2cmAMCEntry 45}

		agentIDAMCslot15        	OBJECT-TYPE
			   SYNTAX       		INTEGER
			   ACCESS           	read-only
			   STATUS           	mandatory
			   DESCRIPTION
			   "This object provides the agentID of the AMC parameter for the selected slot."
			   ::= { gx2cmAMCEntry 46}

--
		valueAMCslot16        	OBJECT-TYPE
			   SYNTAX       		INTEGER
								{
								disabled(1),
								enabled(2),
								force(3)
					    		}
			   ACCESS           read-write
			   STATUS           mandatory
			   DESCRIPTION
			   "This object provides control to enable or disable AMC for the
			   current device in the slot."
			   ::= { gx2cmAMCEntry 47}

		serialAMCslot16        	OBJECT-TYPE
			   SYNTAX       		DisplayString (SIZE (0..80))
			   ACCESS           	read-only
			   STATUS           	mandatory
			   DESCRIPTION
			   "This object provides the serial number for the AMC slot selected."
			   ::= { gx2cmAMCEntry 48}



		agentIDAMCslot16        	OBJECT-TYPE
			   SYNTAX       		INTEGER
			   ACCESS           	read-only
			   STATUS           	mandatory
			   DESCRIPTION
			   "This object provides the agentID of the AMC parameter for the selected slot."
			   ::= { gx2cmAMCEntry 49}

--
		valueAMCslot17        	OBJECT-TYPE
			   SYNTAX       		INTEGER
								{
								disabled(1),
								enabled(2),
								force(3)
					    		}
			   ACCESS           read-write
			   STATUS           mandatory
			   DESCRIPTION
			   "This object provides control to enable or disable AMC for the
			   current device in the slot."
			   ::= { gx2cmAMCEntry 50}

		serialAMCslot17        	OBJECT-TYPE
			   SYNTAX       		DisplayString (SIZE (0..80))
			   ACCESS           	read-only
			   STATUS           	mandatory
			   DESCRIPTION
			   "This object provides the serial number for the AMC slot selected."
			   ::= { gx2cmAMCEntry 51}



		agentIDAMCslot17        	OBJECT-TYPE
			   SYNTAX       		INTEGER
			   ACCESS           	read-only
			   STATUS           	mandatory
			   DESCRIPTION
			   "This object provides the agentID of the AMC parameter for the selected slot."
			   ::= { gx2cmAMCEntry 52}
--

		valueAMCslot18        	OBJECT-TYPE
			   SYNTAX       		INTEGER
								{
								disabled(1),
								enabled(2),
								force(3)
					    		}
			   ACCESS           read-write
			   STATUS           mandatory
			   DESCRIPTION
			   "This object provides control to enable or disable AMC for the
			   current device in the slot."
			   ::= { gx2cmAMCEntry 53}

		serialAMCslot18        	OBJECT-TYPE
			   SYNTAX       		DisplayString (SIZE (0..80))
			   ACCESS           	read-only
			   STATUS           	mandatory
			   DESCRIPTION
			   "This object provides the serial number for the AMC slot selected."
			   ::= { gx2cmAMCEntry 54}



		agentIDAMCslot18        	OBJECT-TYPE
			   SYNTAX       		INTEGER
			   ACCESS           	read-only
			   STATUS           	mandatory
			   DESCRIPTION
			   "This object provides the agentID of the AMC parameter for the selected slot."
			   ::= { gx2cmAMCEntry 55}

		autoQuickSwapCnt        	OBJECT-TYPE
			   SYNTAX       		INTEGER
								{
								timeroff(1),
								onehour(2),
								oneday(3),
								oneweek(4)
					    		}
			   ACCESS           	read-write
			   STATUS           	mandatory
			   DESCRIPTION
			   "This object sets the time interval as to when the Control Module will update
				its memory with quick swap data. The Control Module will enable the quick swap feature for each
				module in the system. It will then retrieve the quick swap data from each module.
				The timer settings are as follows: 
				1=timeroff, 2=onehour, 3=oneday, 4=oneweek."
			   ::= { gx2cmAMCEntry 56}


		--****************** Diagnostic Parameters ********************************
		gx2cmDiagnosticTableIndex              OBJECT-TYPE
			   SYNTAX           INTEGER (1..4294967295)
			   ACCESS           read-only
			   STATUS           mandatory
			   DESCRIPTION
			   "The value of this object identifies the network
			    element. This index is equal to the
			    hfcCommonTableIndex for the same element."
			   ::= { gx2cmDiagnosticEntry 1}

		ledTestValue        	OBJECT-TYPE
			   SYNTAX       		INTEGER
									{
									off(1),
									on(2)
									}
			   ACCESS           	read-write
			   STATUS           	mandatory
			   DESCRIPTION
			   "This object provides the LED test pattern on/off control."
			   ::= { gx2cmDiagnosticEntry 2}

		bpTestCnt         	OBJECT-TYPE
			   SYNTAX       		INTEGER
			   ACCESS           	read-write
			   STATUS           	mandatory
			   DESCRIPTION
			   "The value of this object control which slot the alarm poll command
			   will be repeatedly sent to. During this operation normal polling is disabled.
			   0-off, 1-18 selects the slot."
			   ::= { gx2cmDiagnosticEntry 3}

		successTransSlot1        	OBJECT-TYPE
			   SYNTAX       		INTEGER
			   ACCESS           read-write
			   STATUS           mandatory
			   DESCRIPTION
			   "This object provides data on the number of time writing to the selected
			    slot passes."
			   ::= { gx2cmDiagnosticEntry 4}

		successTransSlot2        	OBJECT-TYPE
			   SYNTAX       		INTEGER
			   ACCESS           read-write
			   STATUS           mandatory
			   DESCRIPTION
			   "This object provides data on the number of time writing to the selected
			    slot passes."
			   ::= { gx2cmDiagnosticEntry 5}

		successTransSlot3        	OBJECT-TYPE
			   SYNTAX       		INTEGER
			   ACCESS           read-write
			   STATUS           mandatory
			   DESCRIPTION
			   "This object provides data on the number of time writing to the selected
			    slot passes."
			   ::= { gx2cmDiagnosticEntry 6}

		successTransSlot4        	OBJECT-TYPE
			   SYNTAX       		INTEGER
			   ACCESS           read-write
			   STATUS           mandatory
			   DESCRIPTION
			   "This object provides data on the number of time writing to the selected
			    slot passes."
			   ::= { gx2cmDiagnosticEntry 7}

		successTransSlot5        	OBJECT-TYPE
			   SYNTAX       		INTEGER
			   ACCESS           read-write
			   STATUS           mandatory
			   DESCRIPTION
			   "This object provides data on the number of time writing to the selected
			    slot passes."
			   ::= { gx2cmDiagnosticEntry 8}

		successTransSlot6        	OBJECT-TYPE
			   SYNTAX       		INTEGER
			   ACCESS           read-write
			   STATUS           mandatory
			   DESCRIPTION
			   "This object provides data on the number of time writing to the selected
			    slot passes."
			   ::= { gx2cmDiagnosticEntry 9}

		successTransSlot7        	OBJECT-TYPE
			   SYNTAX       		INTEGER
			   ACCESS           read-write
			   STATUS           mandatory
			   DESCRIPTION
			   "This object provides data on the number of time writing to the selected
			    slot passes."
			   ::= { gx2cmDiagnosticEntry 10}

		successTransSlot8        	OBJECT-TYPE
			   SYNTAX       		INTEGER
			   ACCESS           read-write
			   STATUS           mandatory
			   DESCRIPTION
			   "This object provides data on the number of time writing to the selected
			    slot passes."
			   ::= { gx2cmDiagnosticEntry 11}

		successTransSlot9        	OBJECT-TYPE
			   SYNTAX       		INTEGER
			   ACCESS           read-write
			   STATUS           mandatory
			   DESCRIPTION
			   "This object provides data on the number of time writing to the selected
			    slot passes."
			   ::= { gx2cmDiagnosticEntry 12}

		successTransSlot10        	OBJECT-TYPE
			   SYNTAX       		INTEGER
			   ACCESS           read-write
			   STATUS           mandatory
			   DESCRIPTION
			   "This object provides data on the number of time writing to the selected
			    slot passes."
			   ::= { gx2cmDiagnosticEntry 13}

		successTransSlot11        	OBJECT-TYPE
			   SYNTAX       		INTEGER
			   ACCESS           read-write
			   STATUS           mandatory
			   DESCRIPTION
			   "This object provides data on the number of time writing to the selected
			    slot passes."
			   ::= { gx2cmDiagnosticEntry 14}

		successTransSlot12        	OBJECT-TYPE
			   SYNTAX       		INTEGER
			   ACCESS           read-write
			   STATUS           mandatory
			   DESCRIPTION
			   "This object provides data on the number of time writing to the selected
			    slot passes."
			   ::= { gx2cmDiagnosticEntry 15}

		successTransSlot13        	OBJECT-TYPE
			   SYNTAX       		INTEGER
			   ACCESS           read-write
			   STATUS           mandatory
			   DESCRIPTION
			   "This object provides data on the number of time writing to the selected
			    slot passes."
			   ::= { gx2cmDiagnosticEntry 16}

		successTransSlot14        	OBJECT-TYPE
			   SYNTAX       		INTEGER
			   ACCESS           read-write
			   STATUS           mandatory
			   DESCRIPTION
			   "This object provides data on the number of time writing to the selected
			    slot passes."
			   ::= { gx2cmDiagnosticEntry 17}

		successTransSlot15        	OBJECT-TYPE
			   SYNTAX       		INTEGER
			   ACCESS           read-write
			   STATUS           mandatory
			   DESCRIPTION
			   "This object provides data on the number of time writing to the selected
			    slot passes."
			   ::= { gx2cmDiagnosticEntry 18}

		successTransSlot16        	OBJECT-TYPE
			   SYNTAX       		INTEGER
			   ACCESS           read-write
			   STATUS           mandatory
			   DESCRIPTION
			   "This object provides data on the number of time writing to the selected
			    slot passes."
			   ::= { gx2cmDiagnosticEntry 19}

		successTransSlot17        	OBJECT-TYPE
			   SYNTAX       		INTEGER
			   ACCESS           read-write
			   STATUS           mandatory
			   DESCRIPTION
			   "This object provides data on the number of time writing to the selected
			    slot passes."
			   ::= { gx2cmDiagnosticEntry 20}

		successTransSlot18        	OBJECT-TYPE
			   SYNTAX       		INTEGER
			   ACCESS           read-write
			   STATUS           mandatory
			   DESCRIPTION
			   "This object provides data on the number of time writing to the selected
			    slot passes."
			   ::= { gx2cmDiagnosticEntry 21}


		failureTransSlot1        	OBJECT-TYPE
			   SYNTAX       		INTEGER
			   ACCESS           read-write
			   STATUS           mandatory
			   DESCRIPTION
			   "This object provides data on the number of time writing to the selected
			    slot fails."
			   ::= { gx2cmDiagnosticEntry 22}

		failureTransSlot2        	OBJECT-TYPE
			   SYNTAX       		INTEGER
			   ACCESS           read-write
			   STATUS           mandatory
			   DESCRIPTION
			   "This object provides data on the number of time writing to the selected
			    slot fails."
			   ::= { gx2cmDiagnosticEntry 23}

		failureTransSlot3        	OBJECT-TYPE
			   SYNTAX       		INTEGER
			   ACCESS           read-write
			   STATUS           mandatory
			   DESCRIPTION
			   "This object provides data on the number of time writing to the selected
			    slot fails."
			   ::= { gx2cmDiagnosticEntry 24}

		failureTransSlot4        	OBJECT-TYPE
			   SYNTAX       		INTEGER
			   ACCESS           read-write
			   STATUS           mandatory
			   DESCRIPTION
			   "This object provides data on the number of time writing to the selected
			    slot fails."
			   ::= { gx2cmDiagnosticEntry 25}

		failureTransSlot5        	OBJECT-TYPE
			   SYNTAX       		INTEGER
			   ACCESS           read-write
			   STATUS           mandatory
			   DESCRIPTION
			   "This object provides data on the number of time writing to the selected
			    slot fails."
			   ::= { gx2cmDiagnosticEntry 26}

		failureTransSlot6        	OBJECT-TYPE
			   SYNTAX       		INTEGER
			   ACCESS           read-write
			   STATUS           mandatory
			   DESCRIPTION
			   "This object provides data on the number of time writing to the selected
			    slot fails."
			   ::= { gx2cmDiagnosticEntry 27}

		failureTransSlot7        	OBJECT-TYPE
			   SYNTAX       		INTEGER
			   ACCESS           read-write
			   STATUS           mandatory
			   DESCRIPTION
			   "This object provides data on the number of time writing to the selected
			    slot fails."
			   ::= { gx2cmDiagnosticEntry 28}

		failureTransSlot8        	OBJECT-TYPE
			   SYNTAX       		INTEGER
			   ACCESS           read-write
			   STATUS           mandatory
			   DESCRIPTION
			   "This object provides data on the number of time writing to the selected
			    slot fails."
			   ::= { gx2cmDiagnosticEntry 29}

		failureTransSlot9        	OBJECT-TYPE
			   SYNTAX       		INTEGER
			   ACCESS           read-write
			   STATUS           mandatory
			   DESCRIPTION
			   "This object provides data on the number of time writing to the selected
			    slot fails."
			   ::= { gx2cmDiagnosticEntry 30}

		failureTransSlot10        	OBJECT-TYPE
			   SYNTAX       		INTEGER
			   ACCESS           read-write
			   STATUS           mandatory
			   DESCRIPTION
			   "This object provides data on the number of time writing to the selected
			    slot fails."
			   ::= { gx2cmDiagnosticEntry 31}

		failureTransSlot11        	OBJECT-TYPE
			   SYNTAX       		INTEGER
			   ACCESS           read-write
			   STATUS           mandatory
			   DESCRIPTION
			   "This object provides data on the number of time writing to the selected
			    slot fails."
			   ::= { gx2cmDiagnosticEntry 32}

		failureTransSlot12        	OBJECT-TYPE
			   SYNTAX       		INTEGER
			   ACCESS           read-write
			   STATUS           mandatory
			   DESCRIPTION
			   "This object provides data on the number of time writing to the selected
			    slot fails."
			   ::= { gx2cmDiagnosticEntry 33}

		failureTransSlot13        	OBJECT-TYPE
			   SYNTAX       		INTEGER
			   ACCESS           read-write
			   STATUS           mandatory
			   DESCRIPTION
			   "This object provides data on the number of time writing to the selected
			    slot fails."
			   ::= { gx2cmDiagnosticEntry 34}

		failureTransSlot14        	OBJECT-TYPE
			   SYNTAX       		INTEGER
			   ACCESS           read-write
			   STATUS           mandatory
			   DESCRIPTION
			   "This object provides data on the number of time writing to the selected
			    slot fails."
			   ::= { gx2cmDiagnosticEntry 35}

		failureTransSlot15        	OBJECT-TYPE
			   SYNTAX       		INTEGER
			   ACCESS           read-write
			   STATUS           mandatory
			   DESCRIPTION
			   "This object provides data on the number of time writing to the selected
			    slot fails."
			   ::= { gx2cmDiagnosticEntry 36}

		failureTransSlot16        	OBJECT-TYPE
			   SYNTAX       		INTEGER
			   ACCESS           read-write
			   STATUS           mandatory
			   DESCRIPTION
			   "This object provides data on the number of time writing to the selected
			    slot fails."
			   ::= { gx2cmDiagnosticEntry 37}

		failureTransSlot17        	OBJECT-TYPE
			   SYNTAX       		INTEGER
			   ACCESS           read-write
			   STATUS           mandatory
			   DESCRIPTION
			   "This object provides data on the number of time writing to the selected
			    slot fails."
			   ::= { gx2cmDiagnosticEntry 38}

		failureTransSlot18        	OBJECT-TYPE
			   SYNTAX       		INTEGER
			   ACCESS           read-write
			   STATUS           mandatory
			   DESCRIPTION
			   "This object provides data on the number of time writing to the selected
			    slot fails."
			   ::= { gx2cmDiagnosticEntry 39}

		fanTestMode        		OBJECT-TYPE
			   SYNTAX       	INTEGER
			   ACCESS           read-write
			   STATUS           mandatory
			   DESCRIPTION
			   "This object provides control for putting the fan in manual 
			   test mode. Writing any non-zero value will set to on"
			   ::= { gx2cmDiagnosticEntry 40}


		fanControl		     	OBJECT-TYPE
			   SYNTAX      		INTEGER
			   					{
								off(1),
								on(2)
					    		}
			   ACCESS           read-write
			   STATUS           mandatory
			   DESCRIPTION
			   "This object provides control over the fan mode."
			   ::= { gx2cmDiagnosticEntry 41}

		relayTestMode        	OBJECT-TYPE
			   SYNTAX      		INTEGER
			   ACCESS           read-write
			   STATUS           mandatory
			   DESCRIPTION
			   "This object provides control for putting the relay in manual 
			   test mode. Writing any non-zero value will set to on"
			   ::= { gx2cmDiagnosticEntry 42}


		relayControl       		OBJECT-TYPE
			   SYNTAX       	INTEGER
			   					{
								open(1),
								closed(2)
					    		}
			   ACCESS           read-write
			   STATUS           mandatory
			   DESCRIPTION
			   "This object provides control for putting the relay in manual 
			   test mode."
			   ::= { gx2cmDiagnosticEntry 43}

		slotPollMode   		OBJECT-TYPE
			   SYNTAX       	INTEGER
			   			{
							off(1),
							on(2)
					    	}
			   ACCESS          read-write
			   STATUS          mandatory
			   DESCRIPTION
			   "This object provides control of the slotpoll test mode.
		          When on the slotpoll operation is disabled."
			   ::= { gx2cmDiagnosticEntry 44}


		bootCount   		OBJECT-TYPE
			   SYNTAX       	INTEGER
			   ACCESS          read-write
			   STATUS          mandatory
			   DESCRIPTION
			   "This object provides the value of how many times the CM went
			   though a boot/rest process."
			   ::= { gx2cmDiagnosticEntry 45}

		objectTableData          		OBJECT-TYPE
			   SYNTAX       		DisplayString (SIZE (0..80))
			   ACCESS           	read-only
			   STATUS           	mandatory
			   DESCRIPTION
			   "This object provides the OID for the start loations for the 
			   status, digital and analog tables. This data is used by the web
			   server application."
			   ::= { gx2cmDiagnosticEntry 46}

		setSysTime				OBJECT-TYPE
			   SYNTAX       	INTEGER
			   ACCESS          read-write
			   STATUS          mandatory
			   DESCRIPTION
			   "Writing any value to this object will reset sysUpTime to zero."
			   ::= { gx2cmDiagnosticEntry 47}


		--****************** Download Parameters ********************************
		gx2cmDownloadTableIndex              OBJECT-TYPE
			   SYNTAX           INTEGER (1..4294967295)
			   ACCESS           read-only
			   STATUS           mandatory
			   DESCRIPTION
			   "The value of this object identifies the network
			    element. This index is equal to the
			    hfcCommonTableIndex for the same element."
			   ::= { gx2cmDownloadEntry 1}
	
		downloadValue        	OBJECT-TYPE
			   SYNTAX      		INTEGER
			   ACCESS           read-write
			   STATUS           mandatory
			   DESCRIPTION
			   "This object provides the slot(s) to be downloaded. The slots to be downloaded
			   corresponds to the following bit map. bit 0 - control module, bits 1-18 to the 
			   corresponding slot. Any combination of bit may be set. If all bits are reset this
			   will halt the download."
			   ::= { gx2cmDownloadEntry 2}

		autoDownloadReset       OBJECT-TYPE
			   SYNTAX      		INTEGER
							{
							deactivate(1),
							activate(2)
					    	}
			   ACCESS           read-write
			   STATUS           mandatory
			   DESCRIPTION
			   "This object determines if the module will be reset directly after a successfull download.
			   0 - Deactivated, 1+ Activated"
			   ::= { gx2cmDownloadEntry 3}

		downloadFilename        OBJECT-TYPE
			   SYNTAX      		DisplayString (SIZE (0..80))
			   ACCESS           read-write
			   STATUS           mandatory
			   DESCRIPTION
			   "This object provides the name of the file for download"
			   ::= { gx2cmDownloadEntry 4}

		downloadState        OBJECT-TYPE
			   SYNTAX      		INTEGER
			   ACCESS           read-write
			   STATUS           mandatory
			   DESCRIPTION
			   "This object provides the current state of the download process."
			   ::= { gx2cmDownloadEntry 5}

		switchFwBank        OBJECT-TYPE
			   SYNTAX      		INTEGER
			   ACCESS           read-write
			   STATUS           mandatory
			   DESCRIPTION
			   "Writting to this object causes the firmware bank to switch and execute from that bank.
			   The range of values that can be entered for this object is from 0 to 18. Where 0 is 
			   slot 0, and 18 is slot 18."  
			   ::= { gx2cmDownloadEntry 6}		   		


-- **************** Trap history table ****************************

		cmTrapHistoryTableIndex        OBJECT-TYPE
			   SYNTAX      		INTEGER (0..65535)
			   ACCESS       read-only
			   STATUS           mandatory
			   DESCRIPTION
			   "This object identifies the trap issued by the
				network element."  
			   ::= { cmTrapHistoryEntry 1}
			   	
		netrapId			        OBJECT-TYPE
			   SYNTAX      		INTEGER (0..65535)
			   ACCESS       read-only
			   STATUS           mandatory
			   DESCRIPTION
			   "The value of this objest is the trap ID number
			    provided by network element."  
			   ::= { cmTrapHistoryEntry 2}


		netrapNetworkElemModelNumber      OBJECT-TYPE
			   SYNTAX      				DisplayString (SIZE (0..80))
			   ACCESS				read-only
			   STATUS					mandatory
			   DESCRIPTION
			   "The value of this object is the model number of
				 the network element.  Combination of Model # and Serial # is used as
				 the unique identifier of the NE."
			   ::= { cmTrapHistoryEntry 3}

		netrapNetworkElemSerialNum        OBJECT-TYPE
			   SYNTAX      				DisplayString (SIZE (0..80))
			   ACCESS				read-only
			   STATUS					mandatory
			   DESCRIPTION
			   "The value of this object is the serial number of
				the network element."
			   ::= { cmTrapHistoryEntry 4}

		netrapPerceivedSeverity   OBJECT-TYPE
			   SYNTAX      		INTEGER (0..65535)
			   ACCESS       read-only
			   STATUS           mandatory
			   DESCRIPTION
			   "This parameter defines five severity levels, which provide 
				an indication of the perceived status of the managed object."  
			   ::= { cmTrapHistoryEntry 5}

		netrapNetworkElemOperState        OBJECT-TYPE
			   SYNTAX      				INTEGER (0..65535)
			   ACCESS				read-only
			   STATUS					mandatory
			   DESCRIPTION
			   "The current Operational State of the Network Element
				which generated the trap.."  
			   ::= { cmTrapHistoryEntry 6}

		netrapNetworkElemAlarmStatus      OBJECT-TYPE
			   SYNTAX      				INTEGER (0..65535)
			   ACCESS				read-only
			   STATUS					mandatory
			   DESCRIPTION
			   "The current Alarm Status of the Network Element.
				Alarm Status is always equal to the highest severity
				level of all outstanding alarms in this NE.."  
			   ::= { cmTrapHistoryEntry 7}

		netrapNetworkElemAdminState       OBJECT-TYPE
			   SYNTAX      				INTEGER (0..65535)
			   ACCESS				read-only
			   STATUS					mandatory
			   DESCRIPTION
			   "The current Adminsitrative state of the network element."  
			   ::= { cmTrapHistoryEntry 8}

		netrapNetworkElemAvailStatus			OBJECT-TYPE
			   SYNTAX      					INTEGER (0..65535)
			   ACCESS					read-only
			   STATUS						mandatory
			   DESCRIPTION
			   "The current Operational state of the network elment"  
			   ::= { cmTrapHistoryEntry 9}

		netrapText				OBJECT-TYPE
			   SYNTAX      		DisplayString (SIZE (0..80))
			   ACCESS       read-only
			   STATUS           mandatory
			   DESCRIPTION
			   "This  variable contains trap text."
			   ::= { cmTrapHistoryEntry 10}

		netrapLastTrapTimeStamp        OBJECT-TYPE
			   SYNTAX      		TimeTicks
			   ACCESS       read-only
			   STATUS           mandatory
			   DESCRIPTION
			   "This OBJECT IDENTIFIER is used to hold time when trap was generated." 
			   ::= { cmTrapHistoryEntry 11}

		netrapChangedObjectId			OBJECT-TYPE
			   SYNTAX      			DisplayString (SIZE (0..80))
			   ACCESS           read-only
			   STATUS				mandatory
			   DESCRIPTION
			   "This  variable identifies the  object that
				has generated the trap."
			   ::= { cmTrapHistoryEntry 12}

		netrapAdditionalInfoInteger1      OBJECT-TYPE
			   SYNTAX      				INTEGER (0..65535)
			   ACCESS				read-only
			   STATUS					mandatory
			   DESCRIPTION
			   "This 32 bit integer is used to hold specific information about 
				the trap."  
			   ::= { cmTrapHistoryEntry 13}

		netrapAdditionalInfoInteger2      OBJECT-TYPE
			   SYNTAX      				INTEGER (0..65535)
			   ACCESS				read-only
			   STATUS					mandatory
			   DESCRIPTION
			   "this 32 bit integer is used to hold specific information about 
				the trap."  
			   ::= { cmTrapHistoryEntry 14}

		netrapAdditionalInfoInteger3      OBJECT-TYPE
			   SYNTAX      				INTEGER (0..65535)
			   ACCESS				read-only
			   STATUS					mandatory
			   DESCRIPTION
			   "This 32 bit integer is used to hold specific information about 
				the trap."  
			   ::= { cmTrapHistoryEntry 15}

		netrapChangedValueDisplayString        OBJECT-TYPE
			   SYNTAX      					DisplayString (SIZE (0..80))
			   ACCESS					read-only
			   STATUS						mandatory
			   DESCRIPTION
			   "This DisplayString is used to hold specific information about
				the trap"
			   ::= { cmTrapHistoryEntry 16}

		netrapChangedValueOID			OBJECT-TYPE
			   SYNTAX      			DisplayString (SIZE (0..80))
			   ACCESS           read-only
			   STATUS				mandatory
			   DESCRIPTION
			   "This OBJECT IDENTIFIER is used to hold specific information about 
				the trap"
			   ::= { cmTrapHistoryEntry 17}

		netrapChangedValueIpAddress        OBJECT-TYPE
			   SYNTAX      				INTEGER (0..65535)
			   ACCESS				read-only
			   STATUS					mandatory
			   DESCRIPTION
			   "This OBJECT IDENTIFIER is used to hold specific information about 
				the trap."  
			   ::= { cmTrapHistoryEntry 18}

		netrapChangedValueInteger			OBJECT-TYPE
			   SYNTAX      				INTEGER (0..65535)
			   ACCESS				read-only
			   STATUS					mandatory
			   DESCRIPTION
			   "this 32 bit integer is used to hold the data value that this object has been 
				changed too."  
			   ::= { cmTrapHistoryEntry 19}


-- ****************************************************************
--
-- TRAP DEFINITIONS
--
--
-- Every trap generated by an HFC agents will include first 9 identical
-- fields. If particular variable is not supported in
-- particular TRAP-TYPE then default value will be returned.
--
-- DESCRIPTION will include explanation of use of generic
-- variables (trapAdditionalInfo******.)  If no
-- DESCRIPTION is given then generic variables will contain
-- default values.
--
-- *****************************************************************

--***************************************************************************
--***************************************************************************

-- **************************************************************************
--                              Laser Module traps
-- **************************************************************************
   trapCMConfigChangeInteger TRAP-TYPE
       ENTERPRISE gx2Cm
       VARIABLES
	       {       
		trapIdentifier,
		trapNetworkElemModelNumber,
		trapNetworkElemSerialNum,
		trapPerceivedSeverity,
		trapNetworkElemOperState,
		trapNetworkElemAlarmStatus,  
		trapNetworkElemAdminState,
		trapNetworkElemAvailStatus,
		trapText,
		trapChangedObjectId,
		trapChangedValueInteger,
		trapNETrapLastTrapTimeStamp
	       }
       DESCRIPTION
	"This trap is issued if configuration of a single variable
	 with integer type was changed (via ANY interface).  
	 TrapChangedValueInteger variable may contain current reading
	 of that variable.
	 trapPerceivedSeverity - 'indeterminate'"
  ::= 1

   trapCMConfigChangeDisplayString TRAP-TYPE
       ENTERPRISE gx2Cm
       VARIABLES
	       {       
		trapIdentifier,
		trapNetworkElemModelNumber,
		trapNetworkElemSerialNum,
		trapPerceivedSeverity,
		trapNetworkElemOperState,
		trapNetworkElemAlarmStatus,  
		trapNetworkElemAdminState,
		trapNetworkElemAvailStatus,
		trapText,
		trapChangedObjectId,
		trapChangedValueDisplayString,
		trapNETrapLastTrapTimeStamp
	       }
       DESCRIPTION
	"This trap is issued if configuration of a single variable
	 with DispalayString type was changed (via ANY interface).  
	 TrapChangedValueDisplayString variable may contain current reading
	 of that variable.
	 trapPerceivedSeverity - 'indeterminate'"
  ::= 2
  
  trapCMModuleTempAlarm TRAP-TYPE
	ENTERPRISE gx2Cm
	VARIABLES
		{       
		 trapIdentifier,
		 trapNetworkElemModelNumber,
		 trapNetworkElemSerialNum,
		 trapPerceivedSeverity,
		 trapNetworkElemOperState,
		 trapNetworkElemAlarmStatus,  
		 trapNetworkElemAdminState,
		 trapNetworkElemAvailStatus,
		 trapText,
		 trapChangedObjectId,
		 trapChangedValueInteger,
		 trapNETrapLastTrapTimeStamp
		}
	DESCRIPTION
	"This trap is issued when the Module Temperature parameter 
	 goes out of range.
	 trapAdditionalInfoInteger variable contains current reading of 
	 the this parameter."
  ::= 3

   trapCMEEPROMAlarm TRAP-TYPE
	ENTERPRISE gx2Cm
	VARIABLES
		{       
		 trapIdentifier,
		 trapNetworkElemModelNumber,
		 trapNetworkElemSerialNum,
		 trapPerceivedSeverity,
		 trapNetworkElemOperState,
		 trapNetworkElemAlarmStatus,  
		 trapNetworkElemAdminState,
		 trapNetworkElemAvailStatus,
		 trapText,
		 trapChangedObjectId,
		 trapChangedValueInteger,
		 trapNETrapLastTrapTimeStamp
		}
	DESCRIPTION
	"This trap is issued when the EEPROM detectes an error.
	 trapAdditionalInfoInteger variable contains current reading of 
	 the this parameter."
  ::= 4

  trapCMFlashAlarm TRAP-TYPE
	ENTERPRISE gx2Cm
	VARIABLES
		{       
		 trapIdentifier,
		 trapNetworkElemModelNumber,
		 trapNetworkElemSerialNum,
		 trapPerceivedSeverity,
		 trapNetworkElemOperState,
		 trapNetworkElemAlarmStatus,  
		 trapNetworkElemAdminState,
		 trapNetworkElemAvailStatus,
		 trapText,
		 trapChangedObjectId,
		 trapChangedValueInteger,
		 trapNETrapLastTrapTimeStamp
		}
	DESCRIPTION
	"This trap is issued when the Flash device detects an error.
	 trapAdditionalInfoInteger variable contains current reading of 
	 the this parameter."
  ::= 5

  trapCMHardwareAlarm TRAP-TYPE
	ENTERPRISE gx2Cm
	VARIABLES
		{       
		 trapIdentifier,
		 trapNetworkElemModelNumber,
		 trapNetworkElemSerialNum,
		 trapPerceivedSeverity,
		 trapNetworkElemOperState,
		 trapNetworkElemAlarmStatus,  
		 trapNetworkElemAdminState,
		 trapNetworkElemAvailStatus,
		 trapText,
		 trapChangedObjectId,
		 trapChangedValueInteger,
		 trapNETrapLastTrapTimeStamp
		}
	DESCRIPTION
	"This trap is issued when the system hardware detectes an error.
	 trapAdditionalInfoInteger variable contains current reading of 
	 the this parameter."
  ::= 6

  trapCMInitEEPROMAlarm TRAP-TYPE
	ENTERPRISE gx2Cm
	VARIABLES
		{       
		 trapIdentifier,
		 trapNetworkElemModelNumber,
		 trapNetworkElemSerialNum,
		 trapPerceivedSeverity,
		 trapNetworkElemOperState,
		 trapNetworkElemAlarmStatus,  
		 trapNetworkElemAdminState,
		 trapNetworkElemAvailStatus,
		 trapText,
		 trapChangedObjectId,
		 trapChangedValueInteger,
		 trapNETrapLastTrapTimeStamp
		}
	DESCRIPTION
	"This trap is issued when the there is an EEPROM initializing error.
	 trapAdditionalInfoInteger variable contains current reading of 
	 the this parameter."
  ::= 7

  trapCMBootAlarm TRAP-TYPE
	ENTERPRISE gx2Cm
	VARIABLES
		{       
		 trapIdentifier,
		 trapNetworkElemModelNumber,
		 trapNetworkElemSerialNum,
		 trapPerceivedSeverity,
		 trapNetworkElemOperState,
		 trapNetworkElemAlarmStatus,  
		 trapNetworkElemAdminState,
		 trapNetworkElemAvailStatus,
		 trapText,
		 trapChangedObjectId,
		 trapChangedValueInteger,
		 trapNETrapLastTrapTimeStamp
		}
	DESCRIPTION
	"This trap is issued when the there is a boot error.
	 trapAdditionalInfoInteger variable contains current reading of 
	 the this parameter."
  ::= 8

  END
