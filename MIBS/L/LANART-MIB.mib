LANART-MIB DEFINITIONS ::= BEGIN

IMPORTS
--	enterprises, NetworkAddress, IpAddress,
--	Counter, Gauge, TimeTicks, DisplayString
--		FROM RFC1155-SMI

	Counter, TimeTicks, NetworkAddress, IpAddress, enterprises, Gauge
			FROM RFC1155-SMI
	DisplayString
			FROM RFC1213-MIB
	OBJECT-TYPE
			FROM RFC-1212
	TRAP-TYPE
			FROM RFC-1215
--  Why should I have to say this specific node? Why not use snmpDot3RptrMgt (still causes an error)?
	rptrPortOperStatus
			FROM SNMP-REPEATER-MIB ;

lanart		OBJECT IDENTIFIER ::= { enterprises 712 }

laMib1		OBJECT IDENTIFIER ::= { lanart 1 }

laProducts	OBJECT IDENTIFIER ::= { laMib1 1 }

laHubMib	OBJECT IDENTIFIER ::= { laMib1 2 }

laSys		OBJECT IDENTIFIER ::= { laHubMib 1 }
laTpPort	OBJECT IDENTIFIER ::= { laHubMib 2 }

	-- The following OIDs are used in sysOID
	--
laTpHub		OBJECT IDENTIFIER ::= { laProducts 1 }

	-- The following OIDs are used in groupOID
	--

-- laTpHub[1-3] were added to fill in missing nodes in the OID tree.

laTpHub1 	OBJECT IDENTIFIER ::= { laTpHub 1 }
etm120x		OBJECT IDENTIFIER ::= { laTpHub1 12 }
etm160x		OBJECT IDENTIFIER ::= { laTpHub1 16 }
etm240x		OBJECT IDENTIFIER ::= { laTpHub1 24 }

laTpHub2 	OBJECT IDENTIFIER ::= { laTpHub 2 }
ete120x		OBJECT IDENTIFIER ::= { laTpHub2 12 }
ete160x		OBJECT IDENTIFIER ::= { laTpHub2 16 }
ete240x		OBJECT IDENTIFIER ::= { laTpHub2 24 }

laTpHub3 	OBJECT IDENTIFIER ::= { laTpHub 3 }
bbAui		OBJECT IDENTIFIER ::= { laTpHub3 0 }
bbAuiTp		OBJECT IDENTIFIER ::= { laTpHub3 1 }
bbAuiBnc	OBJECT IDENTIFIER ::= { laTpHub3 2 }
bbAuiTpBnc	OBJECT IDENTIFIER ::= { laTpHub3 3 }
bbAui10BASE-FL	OBJECT IDENTIFIER ::= { laTpHub3 4 }


laSysConfig  OBJECT-TYPE
              SYNTAX  INTEGER {
			save(1),
			load(2),
			factory(3),
			ok(4),
			failed(5)
		      }
              ACCESS  read-write
              STATUS  mandatory
              DESCRIPTION
                       "Setting this object to save(1) will save all
			configuration variables to non-volatile memory.

			Setting this object to load(2) will configure
			the hub according to the stored configuration.

			Setting this object to factory(3) will configure
			the hub according to the factory settings.

			A return value of ok(4) means the non-volatile memory
			is operational.
			A return value of failed(5) means the non-volatile
			memory has failed."
              ::= { laSys 1 }

laJoystick    OBJECT-TYPE
              SYNTAX  INTEGER {
			enabled(1),
			disabled(2)
		      }
              ACCESS  read-write
              STATUS  mandatory
              DESCRIPTION
		       "Setting this object to disabled(2) prevents
			use of the four-position switch on the front
			panel.  Resetting this object to enabled(1)
			allows use of the switch."
              ::= { laSys 2 }

laLinkAlert   OBJECT-TYPE
              SYNTAX  INTEGER {
			enabled(1),
			disabled(2),
			not-applicable(3)
		      }
              ACCESS  read-write
              STATUS  mandatory
              DESCRIPTION
		       "Setting this object enables or disables the
			LinkALERT feature of the backbone 10BASE-T
			or 10BASE-FL port.

			A return value of not-applicable indicates that
			none of the backbone ports feature LinkALERT."
              ::= { laSys 3 }


laTpPortTable OBJECT-TYPE
       SYNTAX    SEQUENCE OF LaTpPortEntry
       ACCESS    not-accessible
       STATUS    mandatory
       DESCRIPTION
               "Table of descriptive and status information about
               the ports."
       ::= { laTpPort 1 }

laTpPortEntry OBJECT-TYPE
       SYNTAX    LaTpPortEntry
       ACCESS    not-accessible
       STATUS    mandatory
       DESCRIPTION
               "An entry in the table, containing information
               about a single port."
       INDEX    { laTpPortGroupIndex, laTpPortIndex }
       ::= { laTpPortTable 1 }

   LaTpPortEntry ::=
       SEQUENCE {
		laTpPortGroupIndex
			INTEGER,
		laTpPortIndex
			INTEGER,
		laTpLinkTest
			INTEGER,
		laTpAutoPolarity
			INTEGER
       }


   laTpPortGroupIndex OBJECT-TYPE
       SYNTAX    INTEGER (1..1024)
       ACCESS    read-only
       STATUS    mandatory
       DESCRIPTION
               "This object identifies the group containing the
               port for which this entry contains information."
       ::= { laTpPortEntry 1 }

   laTpPortIndex OBJECT-TYPE
       SYNTAX    INTEGER (1..1024)
       ACCESS    read-only
       STATUS    mandatory
       DESCRIPTION
               "This object identifies the port within the group
               for which this entry contains information."
       ::= { laTpPortEntry 2 }

   
   laTpLinkTest OBJECT-TYPE
       SYNTAX    INTEGER {
                     enabled(1),
                     disabled(2),
		     failed(3),
		     not-applicable(4)
                 }
       ACCESS    read-write
       STATUS    mandatory
       DESCRIPTION
               "Setting this object to disabled(2) disables the
		link test feature.  This may be useful for
		interoperation with pre-10BASE-T equipment.
		Setting this object to enabled(1) enables the
		feature.

		A return value of failed(3) indicates a link test
		failure for this port.
		A return value of not-applicable(4) indicates that
		the specified port does not have a link test."
       ::= { laTpPortEntry 3 }

   laTpAutoPolarity OBJECT-TYPE
       SYNTAX    INTEGER {
                     enabled(1),
                     disabled(2),
		     corrected(3),
		     not-applicable(4)
                 }
       ACCESS    read-write
       STATUS    mandatory
       DESCRIPTION
               "Setting this object to disabled(2) disables the
		auto polarity test for this port.
		Setting this object to enabled(1) enables the feature.

		A return value of corrected(3) indicates that the
		polarity test has sensed a reversal on the receive
		wiring pair, and has corrected this fault by inverting
		its receive signal.
		A return value of not-applicable(4) indicates that
		the specified port does not support polarity correction."
       ::= { laTpPortEntry 4 }

   laPortStatus TRAP-TYPE
       ENTERPRISE  lanart
       VARIABLES   { rptrPortOperStatus }
       DESCRIPTION
               "The laPortStatus trap conveys a change in status
		of a particular port.  This trap is sent for a
		given port when either of the following status
		variables change for that port:
		rptrPortAdminStatus, laTpLinkTest

		The rptrHealth trap contains the
		rptrPortOperStatus object."
       ::= 1
END
