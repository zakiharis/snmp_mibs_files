-- extracted from draft-ietf-mpls-bundle-mib-04.txt
-- at Wed Nov  6 06:11:20 2002

LINK-BUNDLING-MIB DEFINITIONS ::= BEGIN

IMPORTS
   MODULE-IDENTITY, OBJECT-TYPE, NOTIFICATION-TYPE,
   mib-2, Unsigned32
      FROM SNMPv2-SMI

   MODULE-COMPLIANCE, OBJECT-GROUP, NOTIFICATION-GROUP
      FROM SNMPv2-CONF

   TruthValue, RowStatus, StorageType
      FROM SNMPv2-TC

   InterfaceIndexOrZero, ifIndex
      FROM IF-MIB

   RouterID
      FROM OSPF-MIB

   InetAddressType, InetAddress
      FROM INET-ADDRESS-MIB;


linkBundlingMIB MODULE-IDENTITY
   LAST-UPDATED "200211011200Z"  -- 1 November 2002 12:00:00 EST
   ORGANIZATION "Multiprotocol Label Switching (MPLS) Working Group"
   CONTACT-INFO
       "        Martin Dubuc
        Email:  dubuc.consulting@rogers.com

                Sudheer Dharanikota
        Email:  sudheer@ieee.org

                Thomas D. Nadeau
        Postal: Cisco Systems, Inc.
                300 Apollo Drive
                Chelmsford, MA 01824
        Tel:    +1-978-244-3051
        Email:  tnadeau@cisco.com

                Jonathan P. Lang
        Postal: Calient Networks, Inc.
                25 Castilian Drive
                Goleta, CA 93117
        Email:  jplang@calient.net"

   DESCRIPTION
       "This MIB contains managed object definitions for
        MPLS traffic engineering link bundling as
        defined in: Kompella, K., Rekhter, Y., Berger, L.,
        Link Bundling in MPLS Traffic Engineering
        Internet Draft <draft-ietf-mpls-bundling-04.txt>,
        July 2002."

   -- Revision history.
   REVISION
       "200211011200Z"  -- 1 November 2002 12:00:00 EST
   DESCRIPTION
       "Initial version published as RFC xxxx (to be assigned by RFC Editor)"
   ::= { mib-2 1 } -- To be assigned by IANA (experimental 114 can be used
                     -- in the interim)


-- Textual Conventions


-- Top level components of this MIB

-- Notifications
linkBundlingNotifications OBJECT IDENTIFIER ::= { linkBundlingMIB 0 }
-- Tables, Scalars
linkBundlingObjects       OBJECT IDENTIFIER ::= { linkBundlingMIB 1 }
-- Conformance
linkBundlingConformance   OBJECT IDENTIFIER ::= { linkBundlingMIB 2 }

-- TE Link Table

teLinkTable OBJECT-TYPE
   SYNTAX        SEQUENCE OF TeLinkEntry
   MAX-ACCESS    not-accessible
   STATUS        current
   DESCRIPTION
       "This table specifies the grouping of component links into
        TE links and grouping of TE links into bundled links."
   ::= { linkBundlingObjects 1 }

teLinkEntry OBJECT-TYPE
   SYNTAX        TeLinkEntry
   MAX-ACCESS    not-accessible
   STATUS        current
   DESCRIPTION
       "An entry in this table exists for each ifEntry with an
        ifType of teLink(TBD), i.e. for every TE link. An ifEntry
        in the ifTable must exist before a teLinkEntry is created with
        the corresponding ifIndex. If a TE link entry in the ifTable is
        destroyed, then so is the corresponding entry in the
        teLinkTable. The administrative and operational status values
        are controlled from the ifEntry. If the link is unnumbered,
        ifIndex is also used as the outgoing interface identifier."
   INDEX         { ifIndex }
   ::= { teLinkTable 1 }

TeLinkEntry ::= SEQUENCE {
  teLinkIpAddrType             InetAddressType,
  teLinkIpAddr                 InetAddress,
  teLinkRemoteIpAddr           InetAddress,
  teLinkMetric                 Unsigned32,
  teLinkMuxCapability          INTEGER,
  teLinkProtectionType         INTEGER,
  teLinkWorkingPriority        Unsigned32,
  teLinkResourceClass          Unsigned32,
  teLinkIncomingIfId           InterfaceIndexOrZero,
  teLinkOutgoingIfId           InterfaceIndexOrZero,
  teLinkFlooding               InterfaceIndexOrZero,
  teLinkRowStatus              RowStatus,
  teLinkStorageType            StorageType
}

teLinkIpAddrType OBJECT-TYPE
   SYNTAX        InetAddressType
   MAX-ACCESS    read-create
   STATUS        current
   DESCRIPTION
       "For IPv4 and IPv6 numbered links, this object represents the
        IP address type associated with the TE link. For
        unnumbered links, a value of unknown(0) must be used."
   ::= { teLinkEntry 1 }

teLinkIpAddr OBJECT-TYPE
   SYNTAX        InetAddress
   MAX-ACCESS    read-create
   STATUS        current
   DESCRIPTION
       "For IPv4 and IPv6 numbered links, this object represents the
        IP address associated with the TE link."
   ::= { teLinkEntry 2 }

teLinkRemoteIpAddr OBJECT-TYPE
   SYNTAX        InetAddress
   MAX-ACCESS    read-create
   STATUS        current
   DESCRIPTION
       "The remote IP address associated with the TE link (IPv4 and
        IPv6 numbered links)."
   ::= { teLinkEntry 3 }

teLinkMetric OBJECT-TYPE
   SYNTAX        Unsigned32
   MAX-ACCESS    read-create
   STATUS        current
   DESCRIPTION
       "The traffic engineering metric for the TE link is
        derived from its component links. All component links
        within the TE link must have the same traffic
        engineering metric."
   REFERENCE
       "[BUNDLING]"
   ::= { teLinkEntry 4 }

teLinkMuxCapability OBJECT-TYPE
   SYNTAX        INTEGER {
                     packetSwitch1(1),
                     packetSwitch2(2),
                     packetSwitch3(3),
                     packetSwitch4(4),
                     layer2Switch(51),
                     tdm(100),
                     lambdaSwitch(150),
                     fiberSwitch(200)
                 }
   MAX-ACCESS    read-create
   STATUS        current
   DESCRIPTION
       "This attribute specifies link multiplex capability of the
        TE link, which is derived from its component links. All
        component links within the same TE link must have the
        same link multiplex capability."
   REFERENCE
       "[GMPLS-OSPF]"
   ::= { teLinkEntry 5 }

teLinkProtectionType OBJECT-TYPE
   SYNTAX        INTEGER {
                     extraTraffic(1),
                     unprotected(2),
                     shared(3),
                     dedicated1For1(4),
                     dedicated1Plus1(5),
                     enhanced(6)
                 }
   MAX-ACCESS    read-create
   STATUS        current
   DESCRIPTION
       "This attribute specifies link protection type of the
        TE link."
   REFERENCE
       "[GMPLS-OSPF]"
   ::= { teLinkEntry 6 }

teLinkWorkingPriority OBJECT-TYPE
   SYNTAX        Unsigned32 (0..7)
   MAX-ACCESS    read-create
   STATUS        current
   DESCRIPTION
       "This object represents a priority value such that a new
        connection with a higher priority, i.e. numerically lower than
        this value, is guaranteed to be setup on a primary link and
        not on a secondary link."
   REFERENCE
       "[GMPLS-OSPF]"
   ::= { teLinkEntry 7 }

teLinkResourceClass OBJECT-TYPE
   SYNTAX        Unsigned32
   MAX-ACCESS    read-create
   STATUS        current
   DESCRIPTION
       "This attribute specifies the TE link resource class.
        The resource class is a 32 bit bitfield. The resource class for
        a link bundle is derived from the resource class of its
        TE links. All TE links within a link bundle must have the
        same resource class."
   ::= { teLinkEntry 8 }

teLinkIncomingIfId OBJECT-TYPE
   SYNTAX        InterfaceIndexOrZero
   MAX-ACCESS    read-create
   STATUS        current
   DESCRIPTION
       "For unnumbered links, the incoming interface is set to the
        outgoing interface identifier chosen by the neighboring LSR
        for the reverse link corresponding to this TE link."
   REFERENCE
       "[BUNDLING]"
   ::= { teLinkEntry 9 }

teLinkOutgoingIfId OBJECT-TYPE
   SYNTAX        InterfaceIndexOrZero
   MAX-ACCESS    read-create
   STATUS        current
   DESCRIPTION
       "If the link is unnumbered, the outgoing interface identifier is
        set to the outgoing interface identifier chosen for the TE link
        by the advertising LSR."

   REFERENCE
       "[BUNDLING]"
   ::= { teLinkEntry 10 }

teLinkFlooding OBJECT-TYPE
   SYNTAX        InterfaceIndexOrZero
   MAX-ACCESS    read-create
   STATUS        current
   DESCRIPTION
       "This object only has significance for link bundles which
        encoding type is not clear. For these link bundles, this object
        identifies the TE link on which to restrict flooding. If the
        value is zero, then flooding must be done on all TE links
        within the link bundle."
   REFERENCE
       "[FLOOD]"
   DEFVAL        { 0 }
   ::= { teLinkEntry 11 }

teLinkRowStatus OBJECT-TYPE
   SYNTAX        RowStatus
   MAX-ACCESS    read-create
   STATUS        current
   DESCRIPTION
       "This variable is used to create, modify, and/or
        delete a row in this table. All read-create objects
        can only be changed when teLinkRowStatus is active."
   ::= { teLinkEntry 12 }

teLinkStorageType OBJECT-TYPE
   SYNTAX        StorageType
   MAX-ACCESS    read-create
   STATUS        current
   DESCRIPTION
       "The storage type for this conceptual row in the
        teLinkTable. Conceptual rows having the value
        'permanent' need not allow write-access to any
        columnar object in the row."
   ::= { teLinkEntry 13 }

-- End of teLinkTable


-- TE Link Descriptor Table

teLinkDescriptorTable OBJECT-TYPE
   SYNTAX        SEQUENCE OF TeLinkDescriptorEntry
   MAX-ACCESS    not-accessible
   STATUS        current
   DESCRIPTION
       "This table specifies the link descriptors associated with the
        TE links."
   ::= { linkBundlingObjects 2 }

teLinkDescriptorEntry OBJECT-TYPE
   SYNTAX        TeLinkDescriptorEntry
   MAX-ACCESS    not-accessible
   STATUS        current
   DESCRIPTION
       "An entry in this table is created for every TE link descriptor.
        An ifEntry in the ifTable must exist before a
        teLinkDescriptorEntry using the same ifIndex is created.
        If a TE link entry in the ifTable is destroyed, then so are all
        entries in the teLinkDescriptorTable that use the ifIndex of
        this TE link."
   INDEX         { ifIndex, teLinkDescriptorId }
   ::= { teLinkDescriptorTable 1 }

TeLinkDescriptorEntry ::= SEQUENCE {
  teLinkDescriptorId           Unsigned32,
  teLinkEncodingType           INTEGER,
  teLinkDescrPriority          Unsigned32,
  teLinkMinReservableBandwidth Unsigned32,
  teLinkMaxReservableBandwidth Unsigned32,
  teLinkDescrRowStatus         RowStatus,
  teLinkDescrStorageType       StorageType
}

teLinkDescriptorId OBJECT-TYPE
   SYNTAX        Unsigned32
   MAX-ACCESS    not-accessible
   STATUS        current
   DESCRIPTION
       "This object specifies the link descriptor identifier."
   ::= { teLinkDescriptorEntry 1 }

teLinkEncodingType OBJECT-TYPE
   SYNTAX        INTEGER {
                     packet(1),
                     ethernet(2),
                     ansiEtsiPdh(3),
                     sdhItuSonetAnsi(5),
                     digitalWrapper(7),
                     lambda(8),
                     fiber(9),
                     fiberChannel(11)

                 }
   MAX-ACCESS    read-create
   STATUS        current
   DESCRIPTION
       "This attribute specifies the TE link encoding type."
   REFERENCE
       "[GMPLS]"
   ::= { teLinkDescriptorEntry 2 }

teLinkDescrPriority OBJECT-TYPE
   SYNTAX        Unsigned32 (0..7)
   MAX-ACCESS    read-create
   STATUS        current
   DESCRIPTION
       "This object specifies the lowest priority at which that link
        encoding type is available."
   REFERENCE
       "[GMPLS-OSPF]"
   ::= { teLinkDescriptorEntry 3 }

teLinkMinReservableBandwidth OBJECT-TYPE
   SYNTAX        Unsigned32
   MAX-ACCESS    read-create
   STATUS        current
   DESCRIPTION
       "This attribute specifies the minimum reservable bandwidth on
        the TE link. This is derived from the union of the
        minimum reservable bandwidth of all the component links
        associated with the TE link that can be used to carry
        live traffic. This value is an estimate in units of 1,000 bits
        per second."
   REFERENCE
       "[GMPLS-OSPF]"
   ::= { teLinkDescriptorEntry 4 }

teLinkMaxReservableBandwidth OBJECT-TYPE
   SYNTAX        Unsigned32
   MAX-ACCESS    read-create
   STATUS        current
   DESCRIPTION
       "This attribute specifies the maximum reservable bandwidth on
        the TE link. This is the union of the maximum reservable
        bandwidth of all the component links within the
        TE link that can be used to carry live traffic. This value
        is an estimate in units of 1,000 bits per second."
   REFERENCE
       "[GMPLS-OSPF]"
   ::= { teLinkDescriptorEntry 5 }

teLinkDescrRowStatus OBJECT-TYPE
   SYNTAX        RowStatus
   MAX-ACCESS    read-create
   STATUS        current
   DESCRIPTION
       "This variable is used to create, modify, and/or
        delete a row in this table. All read-create objects
        can only be changed when teLinkDescrRowStatus is active."
   ::= { teLinkDescriptorEntry 6 }

teLinkDescrStorageType OBJECT-TYPE
   SYNTAX        StorageType
   MAX-ACCESS    read-create
   STATUS        current
   DESCRIPTION
       "The storage type for this conceptual row in the
        teLinkDescriptorTable. Conceptual rows having the value
        'permanent' need not allow write-access to any
        columnar object in the row."
   ::= { teLinkDescriptorEntry 7 }

-- End of teLinkDescriptorTable


-- OSPF Traffic Engineering Parameters for TE Links

teLinkOspfTeTable OBJECT-TYPE
   SYNTAX        SEQUENCE OF TeLinkOspfTeEntry
   MAX-ACCESS    not-accessible
   STATUS        current
   DESCRIPTION
       "This table specifies the OSPF traffic engineering information
        associated with TE links."
   ::= { linkBundlingObjects 3 }

teLinkOspfTeEntry OBJECT-TYPE
   SYNTAX        TeLinkOspfTeEntry
   MAX-ACCESS    not-accessible
   STATUS        current
   DESCRIPTION
       "If OSPF is enabled, an entry in this table is created for
        every TE link."
   AUGMENTS      { teLinkEntry }
   ::= { teLinkOspfTeTable 1 }

TeLinkOspfTeEntry ::= SEQUENCE {
  teLinkOspfLinkType INTEGER,
  teLinkOspfLinkId   RouterID

}

teLinkOspfLinkType OBJECT-TYPE
   SYNTAX        INTEGER {
                     pointToPoint(1),
                     multiAccess(2)
                 }
   MAX-ACCESS    read-create
   STATUS        current
   DESCRIPTION
       "This attribute specifies the OSPF link type for the TE link.
        All TE links within the same bundle must have the same
        link type."
   ::= { teLinkOspfTeEntry 1 }

teLinkOspfLinkId OBJECT-TYPE
   SYNTAX        RouterID
   MAX-ACCESS    read-create
   STATUS        current
   DESCRIPTION
       "On point-to-point link, the link identifier is the Router ID
        of the neighbor. For bundled link, is derived from the link
        identifier associated with its TE links."
   REFERENCE
       "[BUNDLING]"
   ::= { teLinkOspfTeEntry 2 }

-- End of teLinkOspfTeTable


-- TE Link Shared Risk Link Group Table

teLinkSrlgTable OBJECT-TYPE
   SYNTAX        SEQUENCE OF TeLinkSrlgEntry
   MAX-ACCESS    not-accessible
   STATUS        current
   DESCRIPTION
       "This table specifies the SRLGs associated with TE links."
   ::= { linkBundlingObjects 4 }

teLinkSrlgEntry OBJECT-TYPE
   SYNTAX        TeLinkSrlgEntry
   MAX-ACCESS    not-accessible
   STATUS        current
   DESCRIPTION
       "An entry in this table contains information about a
        SRLG associated with a TE link.
        An ifEntry in the ifTable must exist before a
        teLinkSrlgEntry using the same ifIndex is created.
        If a TE link entry in the ifTable is destroyed, then so are all
        entries in the teLinkSrlgTable that use the ifIndex of
        this TE link."
   INDEX         { ifIndex, srlg }
   ::= { teLinkSrlgTable 1 }

TeLinkSrlgEntry ::= SEQUENCE {
  srlg            Unsigned32,
  srlgRowStatus   RowStatus,
  srlgStorageType StorageType
}

srlg OBJECT-TYPE
   SYNTAX        Unsigned32
   MAX-ACCESS    not-accessible
   STATUS        current
   DESCRIPTION
       "This identifies a SRLG supported by the TE link."
   REFERENCE
       "[GMPLS-OSPF]"
   ::= { teLinkSrlgEntry 1 }

srlgRowStatus OBJECT-TYPE
   SYNTAX        RowStatus
   MAX-ACCESS    read-create
   STATUS        current
   DESCRIPTION
       "This variable is used to create, modify, and/or
        delete a row in this table. All read-create objects
        can only be changed when srlgRowStatus is active."
   ::= { teLinkSrlgEntry 2 }

srlgStorageType OBJECT-TYPE
   SYNTAX        StorageType
   MAX-ACCESS    read-create
   STATUS        current
   DESCRIPTION
       "The storage type for this conceptual row in the
        teLinkSrlgTable. Conceptual rows having the value
        'permanent' need not allow write-access to any
        columnar object in the row."
   ::= { teLinkSrlgEntry 3 }

-- End of teLinkSrlgTable


-- TE Link Bandwidth Table
teLinkBandwidthTable OBJECT-TYPE
   SYNTAX        SEQUENCE OF TeLinkBandwidthEntry
   MAX-ACCESS    not-accessible
   STATUS        current
   DESCRIPTION
       "This table specifies the priority-based bandwidth table
        for TE links."
   ::= { linkBundlingObjects 5 }

teLinkBandwidthEntry OBJECT-TYPE
   SYNTAX        TeLinkBandwidthEntry
   MAX-ACCESS    not-accessible
   STATUS        current
   DESCRIPTION
       "An entry in this table contains information about
        the priority-based bandwidth of TE links. An ifEntry in the
        ifTable must exist before a teLinkBandwidthEntry using the
        same ifIndex is created. If a TE link entry in the ifTable
        is destroyed, then so are all entries in the teLinkBandwidthTable
        that use the ifIndex of this TE link."
   INDEX         { ifIndex, teLinkPriority }
   ::= { teLinkBandwidthTable 1 }

TeLinkBandwidthEntry ::= SEQUENCE {
  teLinkPriority             Unsigned32,
  teLinkUnreservedBandwidth  Unsigned32,
  teLinkMaximumLspBandwidth  Unsigned32,
  teLinkBandwidthRowStatus   RowStatus,
  teLinkBandwidthStorageType StorageType
}

teLinkPriority OBJECT-TYPE
   SYNTAX        Unsigned32 (1..8)
   MAX-ACCESS    not-accessible
   STATUS        current
   DESCRIPTION
       "This attribute specifies the priority. It should be mapped
        to a number between 0 and 7"
   REFERENCE
       "[GMPLS-OSPF]"
   ::= { teLinkBandwidthEntry 1 }

teLinkUnreservedBandwidth OBJECT-TYPE
   SYNTAX        Unsigned32
   MAX-ACCESS    read-only
   STATUS        current
   DESCRIPTION
       "This attribute specifies the TE link unreserved
        bandwidth at priority p. It is the sum of the unreserved
        bandwidths at priority p of all component links associated
        with the TE link (excludes all links that are strictly
        used as protecting links). This value is an estimate in units
        of 1,000 bits per second."
   REFERENCE
       "[BUNDLING]"
   ::= { teLinkBandwidthEntry 2 }

teLinkMaximumLspBandwidth OBJECT-TYPE
   SYNTAX        Unsigned32
   MAX-ACCESS    read-create
   STATUS        current
   DESCRIPTION
       "This attribute specifies the TE link maximum
        LSP bandwidth at priority p. It is the maximum of all
        maximum LSP bandwidth at priority p of the component links
        associated with the TE link (excludes all links that are
        strictly used as protecting links). This value is an estimate
        in units of 1,000 bits per second."
   REFERENCE
       "[BUNDLING]"
   ::= { teLinkBandwidthEntry 3 }

teLinkBandwidthRowStatus OBJECT-TYPE
   SYNTAX        RowStatus
   MAX-ACCESS    read-create
   STATUS        current
   DESCRIPTION
       "This variable is used to create, modify, and/or
        delete a row in this table. All read-create objects
        can only be changed when teLinkBandwidthRowStatus is active."
   ::= { teLinkBandwidthEntry 4 }

teLinkBandwidthStorageType OBJECT-TYPE
   SYNTAX        StorageType
   MAX-ACCESS    read-create
   STATUS        current
   DESCRIPTION
       "The storage type for this conceptual row in the
        teLinkBandwidthTable. Conceptual rows having the value
        'permanent' need not allow write-access to any
        columnar object in the row."
   ::= { teLinkBandwidthEntry 5 }

-- End of teLinkBandwidthTable
-- Component Link Table

componentLinkTable  OBJECT-TYPE
   SYNTAX        SEQUENCE OF ComponentLinkEntry
   MAX-ACCESS    not-accessible
   STATUS        current
   DESCRIPTION
       "This table specifies the component link parameters."
   ::= { linkBundlingObjects 6 }

componentLinkEntry  OBJECT-TYPE
   SYNTAX        ComponentLinkEntry
   MAX-ACCESS    not-accessible
   STATUS        current
   DESCRIPTION
       "An entry in this table exists for each ifEntry that represents
        a component link. An ifEntry must exist in the ifTable
        before a componentLinkEntry is created with the
        corresponding ifIndex. If an entry representing a component
        link is destroyed in the ifTable, then so is the
        corresponding entry in the componentLinkTable. The
        administrative and operational status values are controlled
        from the ifEntry."
   INDEX         { ifIndex }
   ::= { componentLinkTable 1 }

ComponentLinkEntry ::= SEQUENCE {
  componentLinkMuxCapability       INTEGER,
  componentLinkPreferredProtection INTEGER,
  componentLinkCurrentProtection   INTEGER,
  componentLinkRowStatus           RowStatus,
  componentLinkStorageType         StorageType
}

componentLinkMuxCapability OBJECT-TYPE
   SYNTAX        INTEGER {
                     packetSwitch1(1),
                     packetSwitch2(2),
                     packetSwitch3(3),
                     packetSwitch4(4),
                     layer2Switch(51),
                     tdm(100),
                     lambdaSwitch(150),
                     fiberSwitch(200)
                 }
   MAX-ACCESS    read-create
   STATUS        current
   DESCRIPTION
       "This attribute specifies link multiplexing capabilities of the
        component link."
   REFERENCE
       "[GMPLS-OSPF]"
   ::= { componentLinkEntry 1 }

componentLinkPreferredProtection OBJECT-TYPE
   SYNTAX        INTEGER {
                     primary(1),
                     secondary(2)
                 }
   MAX-ACCESS    read-create
   STATUS        current
   DESCRIPTION
       "This attribute specifies whether this component link is
        a primary or secondary entity."
   ::= { componentLinkEntry 2 }

componentLinkCurrentProtection OBJECT-TYPE
   SYNTAX        INTEGER {
                     primary(1),
                     secondary(2)
                 }
   MAX-ACCESS    read-only
   STATUS        current
   DESCRIPTION
       "This attribute specifies whether this component link is
        currently used as primary or secondary link."
   ::= { componentLinkEntry 3 }

componentLinkRowStatus OBJECT-TYPE
   SYNTAX        RowStatus
   MAX-ACCESS    read-create
   STATUS        current
   DESCRIPTION
       "This variable is used to create, modify, and/or
        delete a row in this table. All read-create objects
        can only be changed when componentLinkRowStatus is active."
   ::= { componentLinkEntry 4 }

componentLinkStorageType OBJECT-TYPE
   SYNTAX        StorageType
   MAX-ACCESS    read-create
   STATUS        current
   DESCRIPTION
       "The storage type for this conceptual row in the
        componentLinkTable. Conceptual rows having the value
        'permanent' need not allow write-access to any
        columnar object in the row."
   ::= { componentLinkEntry 5 }

-- End of componentLinkTable


-- Component Link Descriptor Table

componentLinkDescriptorTable OBJECT-TYPE
   SYNTAX        SEQUENCE OF ComponentLinkDescriptorEntry
   MAX-ACCESS    not-accessible
   STATUS        current
   DESCRIPTION
       "This table specifies the link descriptors associated with the
        component links."
   ::= { linkBundlingObjects 7 }

componentLinkDescriptorEntry OBJECT-TYPE
   SYNTAX        ComponentLinkDescriptorEntry
   MAX-ACCESS    not-accessible
   STATUS        current
   DESCRIPTION
       "An entry in this table is created for every component link
        descriptor. An ifEntry in the ifTable must exist before a
        componentLinkDescriptorEntry using the same ifIndex is created.
        If a component link entry in the ifTable is destroyed,
        then so are all entries in the componentLinkDescriptorTable
        that use the ifIndex of this component link."
   INDEX         { ifIndex, componentLinkDescrId }
   ::= { componentLinkDescriptorTable 1 }

ComponentLinkDescriptorEntry ::= SEQUENCE {
  componentLinkDescrId             Unsigned32,
  componentLinkEncodingType        INTEGER,
  componentLinkDescrPriority       Unsigned32,
  componentLinkMinReservBandwidth  Unsigned32,
  componentLinkMaxReservBandwidth  Unsigned32,
  componentLinkDescrRowStatus      RowStatus,
  componentLinkDescrStorageType    StorageType
}

componentLinkDescrId OBJECT-TYPE
   SYNTAX        Unsigned32
   MAX-ACCESS    not-accessible
   STATUS        current
   DESCRIPTION
       "This object specifies the link descriptor identifier."
   ::= { componentLinkDescriptorEntry 1 }

componentLinkEncodingType OBJECT-TYPE
   SYNTAX        INTEGER {
                     packet(1),
                     ethernet(2),
                     ansiEtsiPdh(3),
                     sdhItuSonetAnsi(5),
                     digitalWrapper(7),
                     lambda(8),
                     fiber(9),
                     fiberChannel(11)
                 }
   MAX-ACCESS    read-create
   STATUS        current
   DESCRIPTION
       "This attribute specifies the component link encoding type."
   REFERENCE
       "[GMPLS]"
   ::= { componentLinkDescriptorEntry 2 }

componentLinkDescrPriority OBJECT-TYPE
   SYNTAX        Unsigned32 (0..7)
   MAX-ACCESS    read-create
   STATUS        current
   DESCRIPTION
       "This object specifies the lowest priority at which that link
        encoding type is available for the component link."
   REFERENCE
       "[GMPLS-OSPF]"
   ::= { componentLinkDescriptorEntry 3 }

componentLinkMinReservBandwidth OBJECT-TYPE
   SYNTAX        Unsigned32
   MAX-ACCESS    read-create
   STATUS        current
   DESCRIPTION
       "This attribute specifies the minimum reservable bandwidth on
        the component link. This value is an estimate
        in units of 1,000 bits per second."
   REFERENCE
       "[GMPLS-OSPF]"
   ::= { componentLinkDescriptorEntry 4 }

componentLinkMaxReservBandwidth OBJECT-TYPE
   SYNTAX        Unsigned32
   MAX-ACCESS    read-create
   STATUS        current
   DESCRIPTION
       "This attribute specifies the maximum reservable bandwidth on
        the component link. This value is an estimate
        in units of 1,000 bits per second."
   REFERENCE
       "[GMPLS-OSPF]"
   ::= { componentLinkDescriptorEntry 5 }

componentLinkDescrRowStatus OBJECT-TYPE
   SYNTAX        RowStatus
   MAX-ACCESS    read-create
   STATUS        current
   DESCRIPTION
       "This variable is used to create, modify, and/or
        delete a row in this table. All read-create objects
        can only be changed when componentLinkDescrRowStatus
        is active."
   ::= { componentLinkDescriptorEntry 6 }

componentLinkDescrStorageType OBJECT-TYPE
   SYNTAX        StorageType
   MAX-ACCESS    read-create
   STATUS        current
   DESCRIPTION
       "The storage type for this conceptual row in the
        componentLinkDescriptorTable. Conceptual rows
        having the value 'permanent' need not allow write-access
        to any columnar object in the row."
   ::= { componentLinkDescriptorEntry 7 }

-- End of componentLinkDescriptorTable


-- Component Link Bandwidth Table

componentLinkBandwidthTable OBJECT-TYPE
   SYNTAX        SEQUENCE OF ComponentLinkBandwidthEntry
   MAX-ACCESS    not-accessible
   STATUS        current
   DESCRIPTION
       "This table specifies the priority-based bandwidth
        for component links."
   ::= { linkBundlingObjects 8 }

componentLinkBandwidthEntry OBJECT-TYPE
   SYNTAX        ComponentLinkBandwidthEntry
   MAX-ACCESS    not-accessible
   STATUS        current
   DESCRIPTION
       "An entry in this table contains information about
        the priority-based bandwidth on component links.
        An ifEntry in the ifTable must exist before a
        componentLinkBandwidthEntry using the same ifIndex is
        created. If a component link entry in the ifTable is
        destroyed, then so are all entries in the
        componentLinkBandwidthTable that use the ifIndex of
        this component link."
   INDEX         { ifIndex, componentLinkPriority }
   ::= { componentLinkBandwidthTable 1 }

ComponentLinkBandwidthEntry ::= SEQUENCE {
  componentLinkPriority            Unsigned32,
  componentLinkUnreservedBandwidth Unsigned32,
  componentLinkMaximumLspBandwidth Unsigned32,
  componentLinkBandwidthRowStatus  RowStatus,
  componentLinkBwStorageType       StorageType
}

componentLinkPriority OBJECT-TYPE
   SYNTAX        Unsigned32 (1..8)
   MAX-ACCESS    not-accessible
   STATUS        current
   DESCRIPTION
       "This attribute specifies the priority. It should be mapped
        to a number between 0 and 7."
   REFERENCE
       "[GMPLS-OSPF]"
   ::= { componentLinkBandwidthEntry 1 }

componentLinkUnreservedBandwidth OBJECT-TYPE
   SYNTAX        Unsigned32
   MAX-ACCESS    read-only
   STATUS        current
   DESCRIPTION
       "This attribute specifies the component link unreserved
        bandwidth at priority p. This value is an estimate
        in units of 1,000 bits per second."
   REFERENCE
       "[GMPLS-OPSF]"
   ::= { componentLinkBandwidthEntry 2 }

componentLinkMaximumLspBandwidth OBJECT-TYPE
   SYNTAX        Unsigned32
   MAX-ACCESS    read-create
   STATUS        current
   DESCRIPTION
       "This attribute specifies the component link maximum
        LSP bandwidth at priority p. This value is an estimate
        in units of 1,000 bits per second."
   REFERENCE
       "[GMPLS-OSPF]"
   ::= { componentLinkBandwidthEntry 3 }

componentLinkBandwidthRowStatus OBJECT-TYPE
   SYNTAX        RowStatus
   MAX-ACCESS    read-create
   STATUS        current
   DESCRIPTION
       "This variable is used to create, modify, and/or
        delete a row in this table. All read-create objects can only
        be changed when componentLinkBandwidthRowStatus is active."
   ::= { componentLinkBandwidthEntry 4 }

componentLinkBwStorageType OBJECT-TYPE
   SYNTAX        StorageType
   MAX-ACCESS    read-create
   STATUS        current
   DESCRIPTION
       "The storage type for this conceptual row in the
        componentLinkBandwidthTable. Conceptual rows
        having the value 'permanent' need not allow write-access
        to any columnar object in the row."
   ::= { componentLinkBandwidthEntry 5 }

-- End of componentLinkBandwidthTable


-- Notification Configuration

linkBundlingNotifEnable OBJECT-TYPE
   SYNTAX        TruthValue
   MAX-ACCESS    read-write
   STATUS        current
   DESCRIPTION
       "If this object is true, then it enables the
        generation of the link bundling notifications,
        otherwise these notifications are not emitted."
   DEFVAL        { false }
   ::= { linkBundlingObjects 9 }


-- Notifications


-- Bundled Link Notifications
linkBundleMismatch NOTIFICATION-TYPE
   OBJECTS       { teLinkIpAddrType, teLinkIpAddr, teLinkRemoteIpAddr }
   STATUS        current
   DESCRIPTION
       "This notification is generated when a mismatch is found on a
        bundled link. Such mismatch can be detected for instance if one
        of the traffic engineering parameters is not consistent across
        all TE links within a bundled link (resource class,
        OSPF link type, etc.)."
   ::= { linkBundlingNotifications 1 }

-- End of notifications


-- Module compliance

linkBundlingGroups
   OBJECT IDENTIFIER ::= { linkBundlingConformance 1 }

linkBundlingCompliances
   OBJECT IDENTIFIER ::= { linkBundlingConformance 2 }

linkBundlingFullModuleCompliance MODULE-COMPLIANCE
   STATUS current
   DESCRIPTION
       "Compliance statement for agents that support the
        configuration and monitoring of link bundling MIB."
   MODULE -- this module

      -- The mandatory groups have to be implemented
      -- by all devices supporting link bundling. However, they may all
      -- be supported as read-only objects in the case where automatic
      -- configuration is supported.

      MANDATORY-GROUPS    { linkBundlingGroup,
                            teLinkBandwidthGroup,
                            componentLinkBandwidthGroup }

      GROUP teLinkOspfTeGroup
      DESCRIPTION
          "This group is mandatory for OSPF enabled devices."

      GROUP teLinkSrlgGroup
      DESCRIPTION
          "This group is mandatory for G-MPLS enabled devices."

      GROUP linkBundlingNotificationGroup
      DESCRIPTION
          "This group is mandatory for equipment that support
           link bundling notifications."

      -- teLinkTable

      OBJECT      teLinkIpAddrType
      SYNTAX      INTEGER { unknown(0), ipv4(1), ipv6(2) }
      MIN-ACCESS  read-only
      DESCRIPTION
          "The dns(16) address type need not be supported.
           The ipv4(1) and ipv6(2) address types need not be
           supported if numbered links are not supported. The
           unknown(0) address type need not be supported if
           unnumbered links are not supported."

      OBJECT      teLinkIpAddr
      SYNTAX      InetAddress (SIZE(0|4|16))
      DESCRIPTION
          "Size of TE link IP address depends on type of TE link.
           TE link IP address size is zero if link is unnumbered,
           four if link IP address is IPv4 and sixteen if link IP
           address is IPv6."

      OBJECT      teLinkRemoteIpAddr
      SYNTAX      InetAddress (SIZE(0|4|16))
      DESCRIPTION
          "Size of TE link IP address depends on type of TE link.
           TE link IP address size is zero if link is unnumbered,
           four if link IP address is IPv4 and sixteen if link IP
           address is IPv6."

      OBJECT      teLinkMuxCapability
      MIN-ACCESS  read-only
      DESCRIPTION
          "Write access is not required."

      OBJECT      teLinkProtectionType
      MIN-ACCESS  read-only
      DESCRIPTION
          "Write access is not required."

      OBJECT      teLinkRowStatus
      SYNTAX      INTEGER { active(1), notInService(2),
                            createAndGo(4), destroy(6) }
      DESCRIPTION
          "The notReady(3) state need not be supported."

      OBJECT      teLinkStorageType
      SYNTAX      INTEGER { other(1) }
      DESCRIPTION
          "Only other(1) needs to be supported."

      -- teLinkDescriptorTable

      OBJECT      teLinkEncodingType
      MIN-ACCESS  read-only
      DESCRIPTION
          "Write access is not required."

      OBJECT      teLinkDescrPriority
      MIN-ACCESS  read-only
      DESCRIPTION
          "Write access is not required."

      OBJECT      teLinkMinReservableBandwidth
      MIN-ACCESS  read-only
      DESCRIPTION
          "Write access is not required."

      OBJECT      teLinkMaxReservableBandwidth
      MIN-ACCESS  read-only
      DESCRIPTION
          "Write access is not required."

      OBJECT      teLinkDescrRowStatus
      SYNTAX      INTEGER { active(1), notInService(2),
                            createAndGo(4), destroy(6) }
      DESCRIPTION
          "The notReady(3) state need not be supported."

      OBJECT      teLinkDescrStorageType
      SYNTAX      INTEGER { other(1) }
      DESCRIPTION
          "Only other(1) needs to be supported."

      -- teLinkOspfTeTable

      OBJECT      teLinkOspfLinkType
      SYNTAX      INTEGER { pointToPoint(1) }
      MIN-ACCESS  read-only
      DESCRIPTION
          "A value of multiAccess(2) need not be supported."

      OBJECT      teLinkOspfLinkId
      MIN-ACCESS  read-only
      DESCRIPTION
          "Write access is not required."

      -- teLinkSrlgTable

      OBJECT      srlgRowStatus
      SYNTAX      INTEGER { active(1), notInService(2),
                            createAndGo(4), destroy(6) }
      DESCRIPTION
          "The notReady(3) and createAndWait(5) states need
           not be supported."

      OBJECT      srlgStorageType
      SYNTAX      INTEGER { other(1) }
      DESCRIPTION
          "Only other(1) needs to be supported."

      -- teLinkBandwidthTable

      OBJECT      teLinkMaximumLspBandwidth
      MIN-ACCESS  read-only
      DESCRIPTION
          "Write access is not required."

      OBJECT      teLinkBandwidthRowStatus
      SYNTAX      INTEGER { active(1), notInService(2),
                            createAndGo(4), destroy(6) }
      DESCRIPTION
          "The notReady(3) and createAndWait(5) states need
           not be supported."

      OBJECT      teLinkBandwidthStorageType
      SYNTAX      INTEGER { other(1) }
      DESCRIPTION
          "Only other(1) needs to be supported."

      -- componentLinkTable

      OBJECT      componentLinkMuxCapability
      MIN-ACCESS  read-only
      DESCRIPTION
          "Write access is not required."

      OBJECT      componentLinkMaxReservBandwidth
      MIN-ACCESS  read-only
      DESCRIPTION
          "Write access is not required."

      OBJECT      componentLinkRowStatus
      SYNTAX      INTEGER { active(1), notInService(2),
                            createAndGo(4), destroy(6) }
      DESCRIPTION
          "The notReady(3) and createAndWait(5) states need
           not be supported."

      OBJECT      componentLinkStorageType
      SYNTAX      INTEGER { other(1) }
      DESCRIPTION
          "Only other(1) needs to be supported."

      -- componentLinkDescriptorTable

      OBJECT      componentLinkDescrRowStatus
      SYNTAX      INTEGER { active(1), notInService(2),
                            createAndGo(4), destroy(6) }
      DESCRIPTION
          "The notReady(3) state need not be supported."

      OBJECT      componentLinkDescrStorageType
      SYNTAX      INTEGER { other(1) }
      DESCRIPTION
          "Only other(1) needs to be supported."

      -- componentLinkBandwidthTable

      OBJECT      componentLinkMaximumLspBandwidth
      MIN-ACCESS  read-only
      DESCRIPTION
          "Write access is not required."

      OBJECT      componentLinkBandwidthRowStatus
      SYNTAX      INTEGER { active(1), notInService(2),
                            createAndGo(4), destroy(6) }
      DESCRIPTION
          "The notReady(3) and createAndWait(5) states need
           not be supported."

      OBJECT      componentLinkBwStorageType
      SYNTAX      INTEGER { other(1) }
      DESCRIPTION
          "Only other(1) needs to be supported."

   ::= { linkBundlingCompliances 1 }

linkBundlingMonModuleCompliance MODULE-COMPLIANCE
   STATUS current
   DESCRIPTION
       "Compliance statement for agents that support the
        monitoring of link bundling MIB."
   MODULE -- this module

      -- The mandatory groups have to be implemented
      -- by all devices supporting link bundling. However, they may all
      -- be supported as read-only objects in the case where manual
      -- configuration is unsupported.

      MANDATORY-GROUPS    { linkBundlingGroup,
                            teLinkBandwidthGroup,
                            componentLinkBandwidthGroup }

      GROUP teLinkOspfTeGroup
      DESCRIPTION
          "This group is mandatory for OSPF enabled devices."

      GROUP teLinkSrlgGroup
      DESCRIPTION
          "This group is mandatory for G-MPLS enabled devices."

      GROUP linkBundlingNotificationGroup
      DESCRIPTION
          "This group is optional."

      -- teLinkTable

      OBJECT      teLinkIpAddrType
      SYNTAX      INTEGER { unknown(0), ipv4(1), ipv6(2) }
      MIN-ACCESS  read-only
      DESCRIPTION
          "The dns(16) address type need not be supported.
           The ipv4(1) and ipv6(2) address types need not be
           supported if numbered links are not supported. The
           unknown(0) address type need not be supported if
           unnumbered links are not supported."

      OBJECT      teLinkIpAddr
      SYNTAX      InetAddress (SIZE(0|4|16))
      DESCRIPTION
          "Size of TE link IP address depends on type of TE link.
           TE link IP address size is zero if link is unnumbered,
           four if link IP address is IPv4 and sixteen if link IP
           address is IPv6."

      OBJECT      teLinkRemoteIpAddr
      SYNTAX      InetAddress (SIZE(0|4|16))
      DESCRIPTION
          "Size of TE link IP address depends on type of TE link.
           TE link IP address size is zero if link is unnumbered,
           four if link IP address is IPv4 and sixteen if link IP
           address is IPv6."

      OBJECT      teLinkMuxCapability
      MIN-ACCESS  read-only
      DESCRIPTION
          "Write access is not required."

      OBJECT      teLinkProtectionType
      MIN-ACCESS  read-only
      DESCRIPTION
          "Write access is not required."

      OBJECT      teLinkWorkingPriority
      MIN-ACCESS  read-only
      DESCRIPTION
          "Write access is not required."

      OBJECT      teLinkFlooding
      MIN-ACCESS  read-only
      DESCRIPTION
          "Write access is not required."

      OBJECT      teLinkRowStatus
      SYNTAX      INTEGER { active(1), notInService(2),
                            createAndGo(4), destroy(6) }
      MIN-ACCESS  read-only
      DESCRIPTION
          "The notReady(3) state need not be supported."

      OBJECT      teLinkStorageType
      SYNTAX      INTEGER { other(1) }
      MIN-ACCESS  read-only
      DESCRIPTION
          "Only other(1) needs to be supported."

      -- teLinkDescriptorTable

      OBJECT      teLinkEncodingType
      MIN-ACCESS  read-only
      DESCRIPTION
          "Write access is not required."

      OBJECT      teLinkDescrPriority
      MIN-ACCESS  read-only
      DESCRIPTION
          "Write access is not required."

      OBJECT      teLinkMinReservableBandwidth
      MIN-ACCESS  read-only
      DESCRIPTION
          "Write access is not required."

      OBJECT      teLinkMaxReservableBandwidth
      MIN-ACCESS  read-only
      DESCRIPTION
          "Write access is not required."

      OBJECT      teLinkDescrRowStatus
      SYNTAX      INTEGER { active(1), notInService(2),
                            createAndGo(4), destroy(6) }
      MIN-ACCESS  read-only
      DESCRIPTION
          "The notReady(3) state need not be supported."

      OBJECT      teLinkDescrStorageType
      SYNTAX      INTEGER { other(1) }
      MIN-ACCESS  read-only
      DESCRIPTION
          "Only other(1) needs to be supported."

      -- teLinkOspfTeTable

      OBJECT      teLinkOspfLinkType
      SYNTAX      INTEGER { pointToPoint(1) }
      DESCRIPTION
          "A value of multiAccess(2) need not be supported."

      OBJECT      teLinkOspfLinkId
      MIN-ACCESS  read-only
      DESCRIPTION
          "Write access is not required."

      -- teLinkSrlgTable

      OBJECT      srlgRowStatus
      SYNTAX      INTEGER { active(1), notInService(2),
                            createAndGo(4), destroy(6) }
      MIN-ACCESS  read-only
      DESCRIPTION
          "The notReady(3) and createAndWait(5) states need
           not be supported."

      OBJECT      srlgStorageType
      SYNTAX      INTEGER { other(1) }
      MIN-ACCESS  read-only
      DESCRIPTION
          "Only other(1) needs to be supported."

      -- teLinkBandwidthTable

      OBJECT      teLinkMaximumLspBandwidth
      MIN-ACCESS  read-only
      DESCRIPTION
          "Write access is not required."

      OBJECT      teLinkBandwidthRowStatus
      SYNTAX      INTEGER { active(1), notInService(2),
                            createAndGo(4), destroy(6) }
      MIN-ACCESS  read-only
      DESCRIPTION
          "The notReady(3) and createAndWait(5) states need
           not be supported."

      OBJECT      teLinkBandwidthStorageType
      SYNTAX      INTEGER { other(1) }
      MIN-ACCESS  read-only
      DESCRIPTION
          "Only other(1) needs to be supported."

      -- componentLinkTable

      OBJECT      componentLinkMuxCapability
      MIN-ACCESS  read-only
      DESCRIPTION
          "Write access is not required."

      OBJECT      componentLinkPreferredProtection
      MIN-ACCESS  read-only
      DESCRIPTION
          "Write access is not required."

      OBJECT      componentLinkMaxReservBandwidth
      MIN-ACCESS  read-only
      DESCRIPTION
          "Write access is not required."

      OBJECT      componentLinkRowStatus
      SYNTAX      INTEGER { active(1), notInService(2),
                            createAndGo(4), destroy(6) }
      MIN-ACCESS  read-only
      DESCRIPTION
          "The notReady(3) and createAndWait(5) states need
           not be supported."

      OBJECT      componentLinkStorageType
      SYNTAX      INTEGER { other(1) }
      MIN-ACCESS  read-only
      DESCRIPTION
          "Only other(1) needs to be supported."

      -- componentLinkDescriptorTable

      OBJECT      componentLinkEncodingType
      MIN-ACCESS  read-only
      DESCRIPTION
          "Write access is not required."

      OBJECT      componentLinkDescrPriority
      MIN-ACCESS  read-only
      DESCRIPTION
          "Write access is not required."

      OBJECT      componentLinkMinReservBandwidth
      MIN-ACCESS  read-only
      DESCRIPTION
          "Write access is not required."

      OBJECT      componentLinkDescrRowStatus
      SYNTAX      INTEGER { active(1), notInService(2),
                            createAndGo(4), destroy(6) }
      MIN-ACCESS  read-only
      DESCRIPTION
          "The notReady(3) state need not be supported."

      OBJECT      componentLinkDescrStorageType
      SYNTAX      INTEGER { other(1) }
      MIN-ACCESS  read-only
      DESCRIPTION
          "Only other(1) needs to be supported."

      -- componentLinkBandwidthTable

      OBJECT      componentLinkMaximumLspBandwidth
      MIN-ACCESS  read-only
      DESCRIPTION
          "Write access is not required."

      OBJECT      componentLinkBandwidthRowStatus
      SYNTAX      INTEGER { active(1), notInService(2),
                            createAndGo(4), destroy(6) }
      MIN-ACCESS  read-only
      DESCRIPTION
          "The notReady(3) and createAndWait(5) states need
           not be supported."

      OBJECT      componentLinkBwStorageType
      SYNTAX      INTEGER { other(1) }
      MIN-ACCESS  read-only
      DESCRIPTION
          "Only other(1) needs to be supported."

   ::= { linkBundlingCompliances 2 }

-- Units of conformance

linkBundlingGroup OBJECT-GROUP
   OBJECTS { teLinkIpAddrType,
             teLinkIpAddr,
             teLinkRemoteIpAddr,
             teLinkMetric,
             teLinkMuxCapability,
             teLinkProtectionType,
             teLinkWorkingPriority,
             teLinkResourceClass,
             teLinkIncomingIfId,
             teLinkOutgoingIfId,
             teLinkFlooding,
             teLinkRowStatus,
             teLinkStorageType,
             teLinkEncodingType,
             teLinkDescrPriority,
             teLinkMinReservableBandwidth,
             teLinkMaxReservableBandwidth,
             teLinkDescrRowStatus,
             teLinkDescrStorageType,
             componentLinkMuxCapability,
             componentLinkPreferredProtection,
             componentLinkCurrentProtection,
             componentLinkRowStatus,
             componentLinkStorageType,
             linkBundlingNotifEnable
           }

   STATUS  current
   DESCRIPTION
          "Collection of objects needed for the monitoring of
           resources associated with TE links."
   ::= { linkBundlingGroups 1 }

teLinkOspfTeGroup OBJECT-GROUP
   OBJECTS { teLinkOspfLinkType,
             teLinkOspfLinkId
           }

   STATUS  current
   DESCRIPTION
          "Collection of objects needed for the OSPF traffic
           engineering parameters of TE links."
   ::= { linkBundlingGroups 2 }

teLinkSrlgGroup OBJECT-GROUP
   OBJECTS { srlgRowStatus,
             srlgStorageType
           }

   STATUS  current
   DESCRIPTION
          "Collection of objects needed for the monitoring of
           SRLG resources associated with TE links."
   ::= { linkBundlingGroups 3 }

teLinkBandwidthGroup OBJECT-GROUP
   OBJECTS { teLinkUnreservedBandwidth,
             teLinkMaximumLspBandwidth,
             teLinkBandwidthRowStatus,
             teLinkBandwidthStorageType
           }

   STATUS  current
   DESCRIPTION
          "Collection of objects needed for the monitoring of
           the priority-based bandwidth resources associated with
           TE links and component links."
   ::= { linkBundlingGroups 4 }

componentLinkBandwidthGroup OBJECT-GROUP
   OBJECTS { componentLinkEncodingType,
             componentLinkDescrPriority,
             componentLinkMinReservBandwidth,
             componentLinkMaxReservBandwidth,
             componentLinkDescrRowStatus,
             componentLinkDescrStorageType,
             componentLinkUnreservedBandwidth,
             componentLinkMaximumLspBandwidth,
             componentLinkBandwidthRowStatus,
             componentLinkBwStorageType
           }

   STATUS  current
   DESCRIPTION
          "Collection of objects needed for the monitoring of
           bandwidth parameters associated with component links."
   ::= { linkBundlingGroups 5 }

linkBundlingNotificationGroup NOTIFICATION-GROUP
   NOTIFICATIONS { linkBundleMismatch }
   STATUS  current
   DESCRIPTION
          "Set of notifications implemented in this module.
           None is mandatory."
   ::= { linkBundlingGroups 6 }

-- End of LINK-BUNDLING-MIB
END

-- 
-- 
--    Copyright (C) The Internet Society (2001). All Rights Reserved.
-- 
--    This document and translations of it may be copied and furnished to
--    others, and derivative works that comment on or otherwise explain it
--    or assist in its implementation may be prepared, copied, published
--    and distributed, in whole or in part, without restriction of any
--    kind, provided that the above copyright notice and this paragraph are
--    included on all such copies and derivative works. However, this docu-
--    ment itself may not be modified in any way, such as by removing the
--    copyright notice or references to the Internet Society or other
--    Internet organizations, except as needed for the purpose of develop-
--    ing Internet standards in which case the procedures for copyrights
--    defined in the Internet Standards process must be followed, or as
--    required to translate it into languages other than English.
-- 
--    The limited permissions granted above are perpetual and will not be
--    revoked by the Internet Society or its successors or assigns.  This
--    document and the information contained herein is provided on an "AS
--    IS" basis and THE INTERNET SOCIETY AND THE INTERNET ENGINEERING TASK
--    FORCE DISCLAIMS ALL WARRANTIES, EXPRESS OR IMPLIED, INCLUDING BUT NOT
--    LIMITED TO ANY WARRANTY THAT THE USE OF THE INFORMATION HEREIN WILL
--    NOT INFRINGE ANY RIGHTS OR ANY IMPLIED WARRANTIES OF MERCHANTABILITY
--    OR FITNESS FOR A PARTICULAR PURPOSE.
