--  Title:    LIEB_MIC.MIB
--  Version:  v1.0
--  Date:     05/30/95 10:45am
--
--  Copyright @ 1995 Liebert Corporation.  All rights reserved worldwide.
--
--  This MIB defines the objects for the Liebert Micro UPS SNMP Agent.
--

LIEBERT-MICRO-UPS-MIB DEFINITIONS ::= BEGIN

          IMPORTS
	      enterprises,
	      TimeTicks, Gauge                FROM RFC1155-SMI
              OBJECT-TYPE                     FROM RFC-1212
              sysUpTime, DisplayString		  FROM RFC1213-MIB
	      TRAP-TYPE                           FROM RFC-1215;

	  emerson OBJECT IDENTIFIER ::= { enterprises 476 }

--
-- Divisions of Emerson
--

         liebertCorp OBJECT IDENTIFIER ::= { emerson 1 }

--
--  Areas of Liebert Corporation
--
         liebertUps OBJECT IDENTIFIER ::= { liebertCorp 1 }

--
-- UPS
--
	luExtensions OBJECT IDENTIFIER ::= { liebertUps 1 }

	luExperimental OBJECT IDENTIFIER ::= { liebertUps 2 }

	luPrivate OBJECT IDENTIFIER ::= { liebertUps 3 }

--
-- UPS Extensions
--

	luCore OBJECT IDENTIFIER ::= { luExtensions 1 }

          --
          -- The Device Identification group.
          --      All objects in this group are determined at device
	  --      initialization and remain static.
          --

          lcUpsIdent        OBJECT IDENTIFIER ::= { luCore 1 }

          lcUpsIdentManufacturer OBJECT-TYPE
              SYNTAX DisplayString (SIZE (255))
              ACCESS read-only
              STATUS optional
              DESCRIPTION
                      "The UPS manufacturer."
              ::= { lcUpsIdent 1 }

          lcUpsIdentModel OBJECT-TYPE
              SYNTAX DisplayString (SIZE (255))
              ACCESS read-write
              STATUS optional
              DESCRIPTION
                      "The UPS Model designation."
              ::= { lcUpsIdent 2 }

          lcUpsIdentSoftwareVersion OBJECT-TYPE
              SYNTAX DisplayString (SIZE (255))
              ACCESS read-only
              STATUS optional
              DESCRIPTION
                      "The UPS SNMP Agent software version."
              ::= { lcUpsIdent 3 }

          lcUpsIdentSpecific OBJECT-TYPE
              SYNTAX OBJECT IDENTIFIER
              ACCESS read-only
              STATUS optional
              DESCRIPTION
                      "A reference to MIB definitions specific to the
                      particular UPS being managed. This object is
                      used to locate the product-specific MIB for this
                      device.

                      If this information is not present, its value
                      should be the OBJECT IDENTIFIER { 0 0 },
                      which is a syntactically valid object identifier,
                      and any conformant implementation of ASN.1 and BER
                      must be able to generate and recognize this
                      value."
              ::= { lcUpsIdent 4 }

          --
          -- The Alarm group.
          --

          lcUpsAlarm        OBJECT IDENTIFIER ::= { luCore 6 }

          lcUpsAlarms OBJECT-TYPE
              SYNTAX Gauge
              ACCESS read-only
              STATUS optional
              DESCRIPTION
                      "The current number of alarm conditions."
              ::= { lcUpsAlarm 1 }

          lcUpsAlarmTable OBJECT-TYPE
              SYNTAX SEQUENCE OF LcUpsAlarmEntry
              ACCESS not-accessible
              STATUS optional
DESCRIPTION ""
              ::= { lcUpsAlarm 2 }

          lcUpsAlarmEntry OBJECT-TYPE
              SYNTAX LcUpsAlarmEntry
              ACCESS not-accessible
              STATUS optional
DESCRIPTION ""
              INDEX { lcUpsAlarmId }
              ::= { lcUpsAlarmTable 1 }

          LcUpsAlarmEntry ::= SEQUENCE {
              lcUpsAlarmId              INTEGER,
              lcUpsAlarmDescr           OBJECT IDENTIFIER,
              lcUpsAlarmTime            TimeTicks
          }

          lcUpsAlarmId OBJECT-TYPE
              SYNTAX INTEGER (0..2147483647)
              ACCESS read-only
              STATUS optional
              DESCRIPTION
                      "A unique identifier for an alarm condition. This
                      value must remain constant between agent
		      initializations."
              ::= { lcUpsAlarmEntry 1 }

          lcUpsAlarmDescr OBJECT-TYPE
              SYNTAX OBJECT IDENTIFIER
              ACCESS read-only
              STATUS optional
              DESCRIPTION
                      "A reference to an alarm description object. The
                      object referenced should not be accessible, but
                      rather be used to provide a unique description of
                      the alarm condition."
              ::= { lcUpsAlarmEntry 2 }

          lcUpsAlarmTime OBJECT-TYPE
              SYNTAX TimeTicks
              ACCESS read-only
              STATUS optional
              DESCRIPTION
                      "The value of sysUpTime when the alarm condition
                      occured."
              ::= { lcUpsAlarmEntry 3 }

          --
          -- Well known alarm condtions.
          --

          lcUpsAlarmConditions      OBJECT IDENTIFIER ::= { lcUpsAlarm 3 }

          lcUpsAlarmLowBatteryWarning      OBJECT IDENTIFIER
		::= { lcUpsAlarmConditions 1 }
	  -- Battery capacity is low.

          lcUpsAlarmOnBattery       OBJECT IDENTIFIER
		::= { lcUpsAlarmConditions 10 }
	  -- The UPS is running on battery.

		  lcUpsAlarmStopNoticeIssued    OBJECT IDENTIFIER
		::= { lcUpsAlarmConditions 11 }
	  -- The UPS has been told to discontinue output.

          --
          -- The Control group.
          --

          lcUpsControl OBJECT IDENTIFIER ::= { luCore 8 }

          lcUpsControlUnixShutdownDelay OBJECT-TYPE
              SYNTAX INTEGER (0..2147483647)
              ACCESS read-write
              STATUS optional
              DESCRIPTION
                      "Setting this object causes the agent to instruct
		       the UPS to perform a UNIX Shutdown in the indicated
		       number of seconds.  The agent counts down the number
		       of seconds until the event will take place.  A Unix
		       shutdown is only valid if the UPS is on Battery.
		       During a UNIX Shutdown, the UPS will turn off the
		       output even if the Utility comes back on line before
		       the shutdown time arrives.  Note that different models
		       have different clock resolutions, usually greater
		       than 1 second.  As a result, the command will only
		       be accurate to the resolution of the UPS's clock.

		       The command can be cancelled by setting
		       lcUpsControlCancelCommand to the value 'cancel'."
              ::= { lcUpsControl 5 }

          lcUpsControlUnixShutdownTrapDelay OBJECT-TYPE
              SYNTAX INTEGER (0..2147483647)
              ACCESS read-write
              STATUS optional
              DESCRIPTION
                      "When 'lcUpsControlUnixShutdownDelay' reaches a value
                      less than or equal to this object's value, an
		      lcUpsUnixShutdownWarningTrap will be produced and
		      this object will be reset to 0."
              ::= { lcUpsControl 6 }

          lcUpsControlCancelCommands OBJECT-TYPE
              SYNTAX INTEGER { unknown (1), cancel (2) }
              ACCESS read-write
              STATUS optional
              DESCRIPTION
                      "Setting this variable to 'cancel' will cause the
		       agent to issue instructions to the UPS to cancel all
		       outstanding commands, such as lcUpsControlOutputOff,
		       lcUpsControlOutputOn, lcUpsControlUnixShutdown."
              ::= { lcUpsControl 7 }

          lcUpsControlRebootAgentDelay OBJECT-TYPE
              SYNTAX INTEGER (0..2147483647)
              ACCESS read-write
              STATUS optional
              DESCRIPTION
                      "Setting this object causes the agent to reboot after
		       the indicated number of seconds have expired.  The
		       value will count down until the event takes place.

		       The command can be cancelled by setting
		       lcUpsControlCancleCommand to the value cancel."
              ::= { lcUpsControl 8 }

          --
          -- The Nominal group.
          --

          lcUpsNominal  OBJECT IDENTIFIER ::= { luCore 9 }

          lcUpsNominalOutputVoltage OBJECT-TYPE
              SYNTAX INTEGER (0..65536)
              ACCESS read-write
              STATUS optional
              DESCRIPTION
                      "The nominal output voltage. (Unit of measure:
                      volt)"
              ::= { lcUpsNominal 1 }

          lcUpsNominalInputVoltage OBJECT-TYPE
              SYNTAX INTEGER (0..65536)
              ACCESS read-write
              STATUS optional
              DESCRIPTION
                      "The nominal input voltage. (Unit of measure:
                      volt)"
              ::= { lcUpsNominal 2 }

          lcUpsNominalOutputVA OBJECT-TYPE
              SYNTAX INTEGER (0..65536)
              ACCESS read-write
              STATUS optional
              DESCRIPTION
                      "The nominal Volt-Amp rating."
              ::= { lcUpsNominal 3 }

          lcUpsNominalOutputWatts OBJECT-TYPE
              SYNTAX INTEGER (0..65536)
              ACCESS read-write
              STATUS optional
              DESCRIPTION
                      "The nominal power rating. (Unit of measure:
                      watt)"
              ::= { lcUpsNominal 4 }

          lcUpsNominalOutputFreq OBJECT-TYPE
              SYNTAX INTEGER (0..65536)
              ACCESS read-write
              STATUS optional
              DESCRIPTION
                      "The nominal output frequency. (Unit of measure:
                      Hertz)"
              ::= { lcUpsNominal 5 }

          lcUpsNominalInputFreq OBJECT-TYPE
              SYNTAX INTEGER (0..65536)
              ACCESS read-write
              STATUS optional
              DESCRIPTION
                      "The nominal input frequency. (Unit of measure:
                      Hertz)"
              ::= { lcUpsNominal 6 }

--
--  The Core Liebert UPS traps
--
          lcUpsTraps        OBJECT IDENTIFIER ::= { luCore 11 }

lcUpsOnBatteryTrap      TRAP-TYPE
			ENTERPRISE	lcUpsTraps
			VARIABLES   	{ sysUpTime }
			DESCRIPTION
			"An lcUpsOnBatteryTrap signifies that the
 			 UPS is currently on Battery Power."

			::= 3

lcUpsLowBatteryWarningTrap     TRAP-TYPE
			ENTERPRISE	lcUpsTraps
			VARIABLES   	{ sysUpTime }
			DESCRIPTION
			"An lcUpsLowBatteryWarningTrap signifies that the
 			 UPS has entered a Low Battery state."

			::= 4

lcUpsAlarmTrap		TRAP-TYPE
			ENTERPRISE 	lcUpsTraps
			VARIABLES	{ sysUpTime }
			DESCRIPTION
			"An Alarm condition has occurred and is being reported
			 in the lcUpsAlarmTable."

			::= 11

lcUpsUnixShutdownTrap      TRAP-TYPE
			ENTERPRISE	lcUpsTraps
			VARIABLES   	{ sysUpTime  }
			DESCRIPTION
			"An lcUpsUnixShutodwnTrap is sent 2 seconds before
 			 the UPS is scheduled to perform a Unix Shutdown."

			::= 16

lcUpsUnixShutdownWarningTrap   TRAP-TYPE
			ENTERPRISE	lcUpsTraps
			VARIABLES   	{ sysUpTime }
			DESCRIPTION
			"An lcUpsUnixShutdownWarningTrap is sent when the
			 lcUpsControlUnixShudownDelay reaches the value of
			 lcUpsControlUnixShutdownTrapDelay."

			::= 17

--
-- The Proxy/MicroUPS Extension
--
	luExternal OBJECT IDENTIFIER ::= { luExtensions 6 }

END
