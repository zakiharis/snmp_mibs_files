-- extracted from draft-mcwalter-langtag-mib-01.txt
-- at Mon Nov 27 06:07:28 2006

LANGTAG-MIB DEFINITIONS ::= BEGIN

IMPORTS
    MODULE-IDENTITY, mib-2             FROM SNMPv2-SMI
    TEXTUAL-CONVENTION                 FROM SNMPv2-TC;

langTagMIB MODULE-IDENTITY
    LAST-UPDATED "200611210000Z" -- 21 November 2006
    ORGANIZATION "IETF Operations and Management Area"
    CONTACT-INFO "EMail: ops-area@ietf.org"
    DESCRIPTION
            "This MIB module defines a textual conventions for
            representing BCP 47 language tags."
    REVISION     "200611210000Z" -- 21 November 2006
    DESCRIPTION
           "Initial revision, published as RFC yyyy.

            Copyright (C) The IETF Trust (2006).  The initial version of
            this MIB module was published in RFC yyyy; for full legal
            notices see the RFC itself.  Supplementary information may
            be available at:
            http://www.ietf.org/copyrights/ianamib.html."
-- RFC Ed.: replace yyyy with actual RFC number & remove this note
    ::= { mib-2 1 }
-- RFC Ed.: replace XXX with IANA-assigned number & remove this note

LanguageTag ::= TEXTUAL-CONVENTION
   DISPLAY-HINT "60a"
   STATUS      current
   DESCRIPTION
            "A language tag, constructed in accordance with BCP 47.

            Only lowercase characters are allowed.  The purpose of this
            restriction is to provide unique language tags for use as
            indexes.  BCP 47 recommends case conventions for user
            interfaces, but objects using this textual convention MUST
            use only lowercase.

            Values MUST be well-formed language tags, in conformance
            with the definition of well-formed tags in BCP 47.  An
            implementation MAY further limit the values it accepts to
            those permitted by a 'validating' processor, as defined in
            BCP 47.

            In theory, BCP 47 language tags are of unlimited length.
            This language tag is of limited length.  The analysis of
            language tag lengths in BCP 47 confirms that this limit
            will not pose a problem in practice.  In particular, this
            length is greater than the minimum requirements set out in
            section 4.3.1."
   REFERENCE "RFC 4646 BCP 47"
   SYNTAX      OCTET STRING (SIZE (0..60))

END

-- 
--    Copyright (C) The IETF Trust (2006).  This document is subject to the
--    rights, licenses and restrictions contained in BCP 78, and except as
--    set forth therein, the authors retain all their rights.
-- 
-- 
-- Acknowledgment
-- 
--    Funding for the RFC Editor function is currently provided by the
--    Internet Society.
