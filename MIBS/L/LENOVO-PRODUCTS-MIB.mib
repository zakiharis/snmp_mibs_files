LENOVO-PRODUCTS-MIB DEFINITIONS ::= BEGIN

IMPORTS
    MODULE-IDENTITY
        FROM SNMPv2-SMI
    lenovoProducts, lenovoModules
        FROM LENOVO-SMI-MIB;

lenovoProductsMIB MODULE-IDENTITY
    LAST-UPDATED    "201604100000Z"
    ORGANIZATION "Lenovo"
    CONTACT-INFO
        "Lenovo
         Postal: 1009 Think Place
         Morrisville, NC 27560
         USA"
    DESCRIPTION
        "This module defines the object identifiers returned as values for
         sysObjectID for Lenovo hardware."
    REVISION      "201604100000Z"
    DESCRIPTION
        "Initial version."
    REVISION      "201705010000Z"
    DESCRIPTION
        "Add sysObjectIDs for G8332 CNOS, NE1032, NE1032T, NE1072, and 10032 switches."
    REVISION      "201705120000Z"
    DESCRIPTION
        "Remove obsolete email address and telephone number."
   ::= { lenovoModules 1 }
			
-- Lenovo Server Products
lenovoServerProducts OBJECT-IDENTITY
    STATUS current
    DESCRIPTION
        "Root object identifier for Lenovo server products."
    ::= { lenovoProducts 11 }

-- Lenovo Network Flex Products
flex OBJECT-IDENTITY   
    STATUS current
    DESCRIPTION
        "Root object identifier for Lenovo Flex network products."  
    ::= { lenovoProducts 18}	

-- Lenovo Flex System SI4091 10Gb System Interconnect Module
si4091 OBJECT IDENTIFIER ::= { flex 23}


-- Lenovo Network RackSwitch (ToR) Products
tor OBJECT-IDENTITY
    STATUS current
    DESCRIPTION
        "Root object identifier for Lenovo RackSwitch network products."
   ::= { lenovoProducts 7}
   
-- Lenovo RackSwitch G8296
g8296 OBJECT IDENTIFIER ::= { tor 22}

-- Lenovo RackSwitch G8272
g8272 OBJECT IDENTIFIER ::= { tor 24}

-- Lenovo RackSwitch NE1032
ne1032 OBJECT IDENTIFIER ::= { tor 26}

-- Lenovo RackSwitch NE1032T
ne1032T OBJECT IDENTIFIER ::= { tor 27}

-- Lenovo RackSwitch NE1072T
ne1072T OBJECT IDENTIFIER ::= { tor 28}

-- Lenovo RackSwitch G8296 CNOS
g8296-cnos OBJECT IDENTIFIER ::= { tor 29}

-- Lenovo RackSwitch G8272 CNOS
g8272-cnos OBJECT IDENTIFIER ::= { tor 30}

-- Lenovo RackSwitch G8332 CNOS
g8332-cnos OBJECT IDENTIFIER ::= { tor 31}

-- Lenovo ThinkSystem NE1032 RackSwitch
ne1032 OBJECT IDENTIFIER ::= { tor 32}

-- Lenovo ThinkSystem NE1032T RackSwitch
ne1032t OBJECT IDENTIFIER ::= { tor 33}

-- Lenovo ThinkSystem NE1072T RackSwitch
ne1072t OBJECT IDENTIFIER ::= { tor 34}

-- Lenovo ThinkSystem NE10032 RackSwitch
ne10032 OBJECT IDENTIFIER ::= { tor 36}

END
