-- linksys.mib

LINKSYS-MIB     DEFINITIONS ::= BEGIN

IMPORTS
                Counter64
                                        FROM SNMPv2-SMI
                enterprises,
                Counter                 FROM RFC1155-SMI
                OBJECT-TYPE             FROM RFC-1212;

linksys         OBJECT IDENTIFIER ::= { enterprises 3955 }


--linksysMib    MODULE-IDENTITY
--              LAST-UPDATED "9902010000Z"
--              ORGANIZATION "Network Working Group"
--              CONTACT-INFO
--                      ""
--              DESCRIPTION
--                      "The MIB module"
--              ::= { linksys 0 }

-- subtree under device interface
deviceId        OBJECT-TYPE
                SYNTAX  INTEGER       {	isEtherHub(1),
					isFastEtherHub(2),
                                        isDualSpeedHub(3),
                                        isNwayEtherSwitch(4) }
                ACCESS  read-only
                STATUS  mandatory
                DESCRIPTION
                        "The value is used to identify
				 what kind of device."
                ::= { linksys 1 }

  etherHub      OBJECT IDENTIFIER ::= { linksys 5 }

    ehHwVer     OBJECT-TYPE
                SYNTAX  INTEGER
                ACCESS  read-only
                STATUS  mandatory
                DESCRIPTION     "The hardware version of this device"
                ::= { etherHub 2 }

    ehSwVer     OBJECT-TYPE
                SYNTAX  INTEGER
                ACCESS  read-only
                STATUS  mandatory
                DESCRIPTION     "The software version of this device"
                ::= { etherHub 3 }

    ehNumber    OBJECT-TYPE
                SYNTAX  INTEGER
                ACCESS  read-only
                STATUS  mandatory
                DESCRIPTION
                        "Present the device number under this node"
                ::= { etherHub 4 }


    sp2Hub       OBJECT IDENTIFIER
                ::= { etherHub 5 }


-- subtree under sp2Hub

      sp2Statistic OBJECT IDENTIFIER
                ::= { sp2Hub 1 }

      sp2Control OBJECT-TYPE
                SYNTAX SEQUENCE OF Sp2CtlEntry
                ACCESS  not-accessible
                STATUS  mandatory
DESCRIPTION ""
                ::= { sp2Hub 2 }

      sp2Status  OBJECT-TYPE
                SYNTAX SEQUENCE OF Sp2StEntry
                ACCESS  not-accessible
                STATUS  mandatory
DESCRIPTION ""
                ::= { sp2Hub 3 }

      sp2Ports   OBJECT-TYPE
                SYNTAX SEQUENCE OF CounterEntry
                ACCESS not-accessible
                STATUS mandatory
DESCRIPTION ""
                ::= { sp2Hub 4 }


-- Subtree under sp2Statistic

        statsOctets  OBJECT-TYPE
                SYNTAX  Counter64              -- 5c + 5d
                ACCESS  read-write
                STATUS  mandatory
                DESCRIPTION
                      "The number of data octets including those in bad
                       packets and octets in FCS fields, but does not
                       include preamble or other framing bits."
                ::= { sp2Statistic 1 }

        statsPkts       OBJECT-TYPE
                SYNTAX  INTEGER                 -- 5e   , r/w
                ACCESS  read-write
                STATUS  mandatory
                DESCRIPTION
                      "The number of packets received from the network,
                       including errored packets."
                ::= { sp2Statistic 2 }

        statsBroadcastPkts OBJECT-TYPE
                SYNTAX  INTEGER                 -- 5f   , r/w
                ACCESS  read-write
                STATUS  mandatory
                DESCRIPTION
                      "The number of good broadcast packets received."
                ::= { sp2Statistic 3 }

        statsMulticastPkts OBJECT-TYPE
                SYNTAX  INTEGER                 -- 60   , r/w
                ACCESS  read-write
                STATUS  mandatory
                DESCRIPTION
                      "The number of good multicast packets received."
                ::= { sp2Statistic 4 }

        statsCrcAlignErrors OBJECT-TYPE
                SYNTAX  INTEGER                 -- 61   , r/w
                ACCESS  read-write
                STATUS  mandatory
                DESCRIPTION
                      "The number of valid-length packets (64 to 1518 bytes
                       inclusive) that had a bad Frame Check Sequence(FCS)."
                ::= { sp2Statistic 5 }

        statsUndersizePkts OBJECT-TYPE
                SYNTAX  INTEGER                 -- 62   , r/w
                ACCESS  read-write
                STATUS  mandatory
                DESCRIPTION
                      "The number of well-formed packets that were smaller
                       than 64 octets."
                ::= { sp2Statistic 6 }

        statsOversizePkts OBJECT-TYPE
                SYNTAX  INTEGER                 -- 63   , r/w
                ACCESS  read-write
                STATUS  mandatory
                DESCRIPTION
                      "The number of well-formed packets that were longer
                       than 1518 octets."
                ::= { sp2Statistic 7 }

        statsFragments  OBJECT-TYPE
                SYNTAX  INTEGER                 -- 64   , r/w
                ACCESS  read-write
                STATUS  mandatory
                DESCRIPTION
                      "The number of ill-formed packets less than 64 octets.
                       note: any event without a start-of-frame delimiter (0-
                       octet packet) will be counted as a fragment, no matter
                       how long it is"
                ::= { sp2Statistic 8 }

        statsJabbers    OBJECT-TYPE
                SYNTAX  INTEGER                 -- 65   , r/w
                ACCESS  read-write
                STATUS  mandatory
                DESCRIPTION
                      "The number of ill-formed packets longer than 1518 octets.
                       An ill-formed packet is one with an FCS error."
                ::= { sp2Statistic 9 }

        statsCollisions OBJECT-TYPE
                SYNTAX  INTEGER                 -- 66   , r/w
                ACCESS  read-write
                STATUS  mandatory
                DESCRIPTION
                      "The best estimate of the total number of collisions
                       on this interface"
                ::= { sp2Statistic 10 }

        statsPkts64Octets OBJECT-TYPE
                SYNTAX  INTEGER                 -- 67   , r/w
                ACCESS  read-write
                STATUS  mandatory
                DESCRIPTION
                      "The number of packets(good and bad) that were 64 octets
                       long."
                ::= { sp2Statistic 11 }

        statsPkts65to127Octets OBJECT-TYPE
                SYNTAX  INTEGER                 -- 68   , r/w
                ACCESS  read-write
                STATUS  mandatory
                DESCRIPTION
                      "The number of packets(good and bad) between 65 and 127
                       octets long"
                ::= { sp2Statistic 12 }

        statsPkts128to255Octets OBJECT-TYPE
                SYNTAX  INTEGER                 -- 69   , r/w
                ACCESS  read-write
                STATUS  mandatory
                DESCRIPTION
                      "The number of packets(good and bad) between 128 and 255
                       octets long"
                ::= { sp2Statistic 13 }

        statsPkts256to511Octets OBJECT-TYPE
                SYNTAX  INTEGER                 -- 6a   , r/w
                ACCESS  read-write
                STATUS  mandatory
                DESCRIPTION
                      "The number of packets(good and bad) between 256 and 511
                       octets long"
                ::= { sp2Statistic 14 }

        statsPkts512to1023Octets OBJECT-TYPE
                SYNTAX  INTEGER                 -- 6b   , r/w
                ACCESS  read-write
                STATUS  mandatory
                DESCRIPTION
                      "The number of packets(good and bad) between 512 and 1023
                       octets long"
                ::= { sp2Statistic 15 }

        statsPkts1024to1518Octets OBJECT-TYPE
                SYNTAX  INTEGER                 -- 6c   , r/w
                ACCESS  read-write
                STATUS  mandatory
                DESCRIPTION
                      "The number of packets(good and bad) between 1024 and 1518
                       octets long"
                ::= { sp2Statistic 16 }

        statsTotalValidOctets OBJECT-TYPE
                SYNTAX  Counter64               -- 6e+6f, r/w
                ACCESS  read-write
                STATUS  mandatory
                DESCRIPTION
                      "The total number of octets contained in valid frames
                       received on this segment"
                ::= { sp2Statistic 17 }

-- subtree under sp2Control

        resetModule     OBJECT-TYPE
                SYNTAX  INTEGER
                ACCESS  write-only
                STATUS  mandatory
                DESCRIPTION
                        "Writing any data value to this register is identical
                         to a hardware reset. Everything is reset except the
                         Source Address RAM."
                ::= { sp2Control 1 }

        sp2CtlEntry      OBJECT-TYPE
                SYNTAX  Sp2CtlEntry
                ACCESS  not-accessible
                STATUS  deprecated
DESCRIPTION ""
                INDEX   { ctlHubIdx,
                          ctlPortIdx }
                ::= { sp2Control 2 }

        Sp2CtlEntry ::= SEQUENCE {
          ctlHubIdx             INTEGER,
          ctlPortIdx            INTEGER,
          enable                INTEGER,
          linkEn                INTEGER,
          speedSet              INTEGER,
          nwayEn                INTEGER,
          nwayRestart           INTEGER
        }

-- subtree under sp2CtlEntry
          ctlHubIdx OBJECT-TYPE
                SYNTAX  INTEGER
                ACCESS  read-only
                STATUS  deprecated
DESCRIPTION ""
                ::= { sp2CtlEntry 1 }

          ctlPortIdx OBJECT-TYPE
                SYNTAX  INTEGER
                ACCESS  read-only
                STATUS  deprecated
DESCRIPTION ""
                ::= { sp2CtlEntry 2 }

          enable      OBJECT-TYPE
                SYNTAX  INTEGER   { enable(1), disable(0), na(-1) }
                ACCESS  read-write
                STATUS  mandatory
DESCRIPTION ""
                ::= { sp2CtlEntry 3 }

          linkEn      OBJECT-TYPE
                SYNTAX  INTEGER   { enable(1), disable(0), na(-1) }
                ACCESS  read-write
                STATUS  mandatory
DESCRIPTION ""
                ::= { sp2CtlEntry 4 }

          speedSet    OBJECT-TYPE
                SYNTAX  INTEGER   { na(-1), nway(0), ether10(1), ether100(3) }
                ACCESS  read-write
                STATUS  mandatory
DESCRIPTION ""
                ::= { sp2CtlEntry 5 }

          nwayEn      OBJECT-TYPE
                SYNTAX  INTEGER   { enable(1), disable(0), na(-1) }
                ACCESS  read-write
                STATUS  mandatory
DESCRIPTION ""
                ::= { sp2CtlEntry 6 }

          nwayRestart OBJECT-TYPE
                SYNTAX  INTEGER
                ACCESS  read-write
                STATUS  mandatory
DESCRIPTION ""
                ::= { sp2CtlEntry 7 }

-- subtree under sp2Status
        sp2StEntry OBJECT-TYPE
                SYNTAX  Sp2StEntry
                ACCESS  not-accessible
                STATUS  mandatory
DESCRIPTION ""
                INDEX   { statHubIdx,
                          statPortIdx }
                ::= { sp2Status 1 }

        Sp2StEntry ::= SEQUENCE {
          statHubIdx            INTEGER,
          statPortIdx           INTEGER,
          linkSt                INTEGER,
          polaritySt            INTEGER,
          partitionSt           INTEGER,
          speedSt               INTEGER,
          nwayPartner           INTEGER
        }

-- subtree under sp2StEntry
          statHubIdx    OBJECT-TYPE
                SYNTAX  INTEGER
                ACCESS  read-only
                STATUS  deprecated
DESCRIPTION ""
                ::= { sp2StEntry 1 }

          statPortIdx   OBJECT-TYPE
                SYNTAX  INTEGER
                ACCESS  read-only
                STATUS  deprecated
DESCRIPTION ""
                ::= { sp2StEntry 2 }

          linkSt        OBJECT-TYPE
                SYNTAX  INTEGER         { na(-1), fail(0), good(1) }
                ACCESS  read-only
                STATUS  mandatory
                DESCRIPTION
                      "Indicates every ports' link status."
                ::= { sp2StEntry 3 }

          polaritySt    OBJECT-TYPE
                SYNTAX  INTEGER         { na(-1), straight(0), cross(1) }
                ACCESS  read-only
                STATUS  mandatory
                DESCRIPTION
                      "A read of this register will reflect the current
                       polarity status."
                ::= { sp2StEntry 4 }

          partitionSt      OBJECT-TYPE
                SYNTAX  INTEGER         { na(-1), yes(0), no(1) }
                ACCESS  read-only
                STATUS  mandatory
                DESCRIPTION
                      "A read of this register will reflect the current
                       partition status."
                ::= { sp2StEntry 5 }

          speedSt       OBJECT-TYPE
                SYNTAX  INTEGER         { na(-1), is10M(0), is100M(1) }
                ACCESS  read-only
                STATUS  mandatory
                DESCRIPTION
                      "Indicates the current status of each port."
                ::= { sp2StEntry 6 }

          nwayPartner   OBJECT-TYPE
                SYNTAX  INTEGER         { na(-1), no(0), yes(1) }
                ACCESS  read-only
                STATUS  mandatory
DESCRIPTION ""
                ::= { sp2StEntry 7 }

-- subtree under Counter

          counterEntry OBJECT-TYPE
                SYNTAX  CounterEntry
                ACCESS  not-accessible
                STATUS  mandatory
DESCRIPTION ""
                INDEX   { cntHubIdx,
                          cntPortIdx }
                ::= { sp2Ports 1 }

          CounterEntry ::= SEQUENCE {
            cntHubIdx             INTEGER,
            cntPortIdx            INTEGER,
            portReadableFrames        Counter,        -- x0   , r
            portReadableOctets        Counter64,      -- x1+x2, r
            portFrameCheckSequence    Counter,
            portAlignmentErrors       Counter,
            portFramesTooLong         Counter,
            portShortEvents           Counter,
            portRunts                 Counter,
            portCollisions            Counter,
            portLateEvents            Counter,
            portVeryLongEvents        Counter,
            portDataRateMismatches    Counter,
            portAutoPartitions        Counter,
            portTrackSrcAddrChanges   Counter,
            portBroadcastPkts         Counter,        -- xe   , r
            portMulticastPkts         Counter         -- xf   , r
          }

-- Subtree under validCounterEntry

            cntHubIdx   OBJECT-TYPE
                SYNTAX  INTEGER
                ACCESS  read-only
                STATUS  deprecated
                DESCRIPTION
                      "A unique value for each family.  Its value
                      ranges between 1 and the value of ifNumber.  The
                      value for each interface must remain constant at
                      least from one re-initialization of the entity's
                      network management system to the next re-
                      initialization."
                ::= { counterEntry 1 }

            cntPortIdx    OBJECT-TYPE
                SYNTAX  INTEGER
                ACCESS  read-only
                STATUS  mandatory
                DESCRIPTION
                      "A unique value for each family.  Its value
                      ranges between 1 and the value of ifNumber.  The
                      value for each interface must remain constant at
                      least from one re-initialization of the entity's
                      network management system to the next re-
                      initialization."
                ::= { counterEntry 2 }

            portReadableFrames OBJECT-TYPE
                SYNTAX  Counter                 -- x0   , r
                ACCESS  read-only
                STATUS  mandatory
                DESCRIPTION
                        "Counts valid-length, valid-CRC, collision-free
                         packets."
                ::= { counterEntry 3 }

            portReadableOctets OBJECT-TYPE
                SYNTAX  Counter64               -- x1+x2, r
                ACCESS  read-only
                STATUS  mandatory
                DESCRIPTION
                        "Counts the number of octets in all valid-length,
                         valid-CRC, collision-free packets, not including
                         preamble and framing bits."
                ::= { counterEntry 4 }

            portFrameCheckSequence OBJECT-TYPE
                SYNTAX  Counter                 -- x3   , r
                ACCESS  read-only
                STATUS  mandatory
                DESCRIPTION
                        "Counts valid length, collision-free packets that
                         had FCS errors, but were correctly framed."
                ::= { counterEntry 5 }

            portAlignmentErrors OBJECT-TYPE
                SYNTAX  Counter                 -- x4   , r
                ACCESS  read-only
                STATUS  mandatory
                DESCRIPTION
                        "Counts valid length, collision-free packets that
                         had FCS errors and were incorrectly framed."
                ::= { counterEntry 6 }

            portFramesTooLong OBJECT-TYPE
                SYNTAX  Counter                 -- x5   , r
                ACCESS  read-only
                STATUS  mandatory
                DESCRIPTION
                        "Counts packets that had a length greater than 1518
                         octets."
                ::= { counterEntry 7 }

            portShortEvents OBJECT-TYPE
                SYNTAX  Counter                 -- x6   , r
                ACCESS  read-only
                STATUS  mandatory
                DESCRIPTION
                        "Counts events that lasted for 82 bit times or less."
                ::= { counterEntry 8 }

            portRunts       OBJECT-TYPE
                SYNTAX  Counter                 -- x7   , r
                ACCESS  read-only
                STATUS  mandatory
                DESCRIPTION
                        "Counts events longer than 82 bit times, but shorter
                         than 512 bit times"
                ::= { counterEntry 9 }

            portCollisions OBJECT-TYPE
                SYNTAX  Counter                 -- x8   , r
                ACCESS  read-only
                STATUS  mandatory
                DESCRIPTION
                        "Counts events longer than 82 bit times, but shorter
                         than 512 bit times"
                ::= { counterEntry 10 }

            portLateEvents  OBJECT-TYPE
                SYNTAX  Counter                 -- x9   , r
                ACCESS  read-only
                STATUS  mandatory
                DESCRIPTION
                        "Counts the number of times collisions was detected
                         more than 512 bit times adter the start or carrier"
                ::= { counterEntry 11 }

            portVeryLongEvents OBJECT-TYPE
                SYNTAX  Counter                 -- xa   , r
                ACCESS  read-only
                STATUS  mandatory
                DESCRIPTION
                        "Counts the number of times any activity continued
                         for more than 4 to 7.5 ms."
                ::= { counterEntry 12 }

            portDataRateMismatches OBJECT-TYPE
                SYNTAX  Counter                 -- xb   , r
                ACCESS  read-only
                STATUS  mandatory
                DESCRIPTION
                        "Counts the number of times the incoming data rate
                         mis-matched the local clock source enough to cause
                         a FIFO underflow or overflow."
                ::= { counterEntry 13 }

            portAutoPartitions OBJECT-TYPE
                SYNTAX  Counter                 -- xc   , r
                ACCESS  read-only
                STATUS  mandatory
                DESCRIPTION
                        "Counts the number of times this port has been parti-
                         tioned by the Auto-partition algorithm"
                ::= { counterEntry 14 }

            portTrackSrcAddrChanges OBJECT-TYPE
                SYNTAX  Counter                 -- xd   , r
                ACCESS  read-only
                STATUS  mandatory
                DESCRIPTION
                        "Counts the number of times the source address has
                         changed."
                ::= { counterEntry 15 }

            portBroadcastPkts OBJECT-TYPE
                SYNTAX  Counter                 -- xe   , r
                ACCESS  read-only
                STATUS  mandatory
                DESCRIPTION
                        "Counts the number of good broadcast packets received
                         by this port."
                ::= { counterEntry 16 }

            portMulticastPkts OBJECT-TYPE
                SYNTAX  Counter                 -- xf   , r
                ACCESS  read-only
                STATUS  mandatory
                DESCRIPTION
                        "Counts the number of good multicast packets received
                         by this port."
                ::= { counterEntry 17 }

END
