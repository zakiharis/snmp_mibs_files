-- *****************************************************************
-- DHCP-SERVER-MIB:  Cisco private MIB
-- ****************************************************************

CIE1000-DHCP-SERVER-MIB DEFINITIONS ::= BEGIN

IMPORTS
    NOTIFICATION-GROUP, MODULE-COMPLIANCE, OBJECT-GROUP FROM SNMPv2-CONF
    NOTIFICATION-TYPE, MODULE-IDENTITY, OBJECT-TYPE FROM SNMPv2-SMI
    TEXTUAL-CONVENTION FROM SNMPv2-TC
    cie1000SwitchMgmt FROM CISCO-IE1000-MIB
    CIE1000DisplayString FROM CIE1000-TC
    CIE1000InterfaceIndex FROM CIE1000-TC
    CIE1000RowEditorState FROM CIE1000-TC
    CIE1000Unsigned16 FROM CIE1000-TC
    Integer32 FROM SNMPv2-SMI
    IpAddress FROM SNMPv2-SMI
    Unsigned32 FROM SNMPv2-SMI
    MacAddress FROM SNMPv2-TC
    TruthValue FROM SNMPv2-TC
    ;

cie1000DhcpServerMib MODULE-IDENTITY
    LAST-UPDATED "201508240000Z"
    ORGANIZATION
        "Cisco Systems, Inc."
    CONTACT-INFO
        "Cisco Systems
	 Customer Service

	 Postal: 170 West Tasman Drive
	 San Jose, CA  95134
	 USA

	 Tel: +1 800 553-NETS

	 E-mail: cs-snmp@cisco.com"
    DESCRIPTION
        "This is a private version of DhcpServer"
    REVISION    "201508240000Z"
    DESCRIPTION
        "revise fqdn as name"
    REVISION    "201411270000Z"
    DESCRIPTION
        "revise descriptions by Palle"
    REVISION    "201407010000Z"
    DESCRIPTION
        "Initial version"
    ::= { cie1000SwitchMgmt 109 }


CIE1000DhcpServerBindingEnum ::= TEXTUAL-CONVENTION
    STATUS      current
    DESCRIPTION
        "This enumeration defines the type of binding."
    SYNTAX      INTEGER { none(0), automatic(1), manual(2),
                          expired(3) }

CIE1000DhcpServerBindingStateEnum ::= TEXTUAL-CONVENTION
    STATUS      current
    DESCRIPTION
        "This enumeration defines the state of binding."
    SYNTAX      INTEGER { none(0), allocated(1), committed(2),
                          expired(3) }

CIE1000DhcpServerClientIdentifierEnum ::= TEXTUAL-CONVENTION
    STATUS      current
    DESCRIPTION
        "This enumeration defines the type of client identifier."
    SYNTAX      INTEGER { none(0), name(1), mac(2) }

CIE1000DhcpServerNetbiosNodeEnum ::= TEXTUAL-CONVENTION
    STATUS      current
    DESCRIPTION
        "This enumeration defines the type of NetBIOS node."
    SYNTAX      INTEGER { nodeNone(0), nodeB(1), nodeP(2), nodeM(3),
                          nodeH(4) }

CIE1000DhcpServerPoolEnum ::= TEXTUAL-CONVENTION
    STATUS      current
    DESCRIPTION
        "This enumeration defines the type of DHCP pool."
    SYNTAX      INTEGER { none(0), network(1), host(2) }

cie1000DhcpServerMibObjects OBJECT IDENTIFIER
    ::= { cie1000DhcpServerMib 1 }

cie1000DhcpServerConfig OBJECT IDENTIFIER
    ::= { cie1000DhcpServerMibObjects 2 }

cie1000DhcpServerConfigGlobals OBJECT IDENTIFIER
    ::= { cie1000DhcpServerConfig 1 }

cie1000DhcpServerConfigGlobalsMode OBJECT-TYPE
    SYNTAX      TruthValue
    MAX-ACCESS  read-write
    STATUS      current
    DESCRIPTION
        "Global mode of DHCP server. true is to enable the functions of DHCP
         server and false is to disable it."
    ::= { cie1000DhcpServerConfigGlobals 1 }

cie1000DhcpServerConfigVlanTable OBJECT-TYPE
    SYNTAX      SEQUENCE OF CIE1000DhcpServerConfigVlanEntry
    MAX-ACCESS  not-accessible
    STATUS      current
    DESCRIPTION
        "This is the table of DHCP server VLAN configuration. The index is VLAN
         ID."
    ::= { cie1000DhcpServerConfig 2 }

cie1000DhcpServerConfigVlanEntry OBJECT-TYPE
    SYNTAX      CIE1000DhcpServerConfigVlanEntry
    MAX-ACCESS  not-accessible
    STATUS      current
    DESCRIPTION
        "Each VLAN has a set of parameters"
    INDEX       { cie1000DhcpServerConfigVlanIfIndex }
    ::= { cie1000DhcpServerConfigVlanTable 1 }

CIE1000DhcpServerConfigVlanEntry ::= SEQUENCE {
    cie1000DhcpServerConfigVlanIfIndex  CIE1000InterfaceIndex,
    cie1000DhcpServerConfigVlanMode     TruthValue
}

cie1000DhcpServerConfigVlanIfIndex OBJECT-TYPE
    SYNTAX      CIE1000InterfaceIndex
    MAX-ACCESS  accessible-for-notify
    STATUS      current
    DESCRIPTION
        "Logical interface number of VLAN."
    ::= { cie1000DhcpServerConfigVlanEntry 1 }

cie1000DhcpServerConfigVlanMode OBJECT-TYPE
    SYNTAX      TruthValue
    MAX-ACCESS  read-write
    STATUS      current
    DESCRIPTION
        "VLAN mode of DHCP server. true is to enable DHCP server per VLAN and
         false is to disable it per VLAN."
    ::= { cie1000DhcpServerConfigVlanEntry 2 }

cie1000DhcpServerConfigExcludedTable OBJECT-TYPE
    SYNTAX      SEQUENCE OF CIE1000DhcpServerConfigExcludedEntry
    MAX-ACCESS  not-accessible
    STATUS      current
    DESCRIPTION
        "The table is DHCP server excluded IP onfiguration table. The indexes
         are low IP and high IP address."
    ::= { cie1000DhcpServerConfig 3 }

cie1000DhcpServerConfigExcludedEntry OBJECT-TYPE
    SYNTAX      CIE1000DhcpServerConfigExcludedEntry
    MAX-ACCESS  not-accessible
    STATUS      current
    DESCRIPTION
        "Each entry has a set of parameters"
    INDEX       { cie1000DhcpServerConfigExcludedLowIpAddress,
                  cie1000DhcpServerConfigExcludedHighIpAddress }
    ::= { cie1000DhcpServerConfigExcludedTable 1 }

CIE1000DhcpServerConfigExcludedEntry ::= SEQUENCE {
    cie1000DhcpServerConfigExcludedLowIpAddress   IpAddress,
    cie1000DhcpServerConfigExcludedHighIpAddress  IpAddress,
    cie1000DhcpServerConfigExcludedAction         CIE1000RowEditorState
}

cie1000DhcpServerConfigExcludedLowIpAddress OBJECT-TYPE
    SYNTAX      IpAddress
    MAX-ACCESS  accessible-for-notify
    STATUS      current
    DESCRIPTION
        "Low IP address."
    ::= { cie1000DhcpServerConfigExcludedEntry 1 }

cie1000DhcpServerConfigExcludedHighIpAddress OBJECT-TYPE
    SYNTAX      IpAddress
    MAX-ACCESS  accessible-for-notify
    STATUS      current
    DESCRIPTION
        "High IP address."
    ::= { cie1000DhcpServerConfigExcludedEntry 2 }

cie1000DhcpServerConfigExcludedAction OBJECT-TYPE
    SYNTAX      CIE1000RowEditorState
    MAX-ACCESS  read-write
    STATUS      current
    DESCRIPTION
        "Action"
    ::= { cie1000DhcpServerConfigExcludedEntry 100 }

cie1000DhcpServerConfigExcludedIpTableRowEditor OBJECT IDENTIFIER
    ::= { cie1000DhcpServerConfig 4 }

cie1000DhcpServerConfigExcludedIpTableRowEditorLowIpAddress OBJECT-TYPE
    SYNTAX      IpAddress
    MAX-ACCESS  read-write
    STATUS      current
    DESCRIPTION
        "Low IP address."
    ::= { cie1000DhcpServerConfigExcludedIpTableRowEditor 1 }

cie1000DhcpServerConfigExcludedIpTableRowEditorHighIpAddress OBJECT-TYPE
    SYNTAX      IpAddress
    MAX-ACCESS  read-write
    STATUS      current
    DESCRIPTION
        "High IP address."
    ::= { cie1000DhcpServerConfigExcludedIpTableRowEditor 2 }

cie1000DhcpServerConfigExcludedIpTableRowEditorAction OBJECT-TYPE
    SYNTAX      CIE1000RowEditorState
    MAX-ACCESS  read-write
    STATUS      current
    DESCRIPTION
        "Action"
    ::= { cie1000DhcpServerConfigExcludedIpTableRowEditor 100 }

cie1000DhcpServerConfigPoolTable OBJECT-TYPE
    SYNTAX      SEQUENCE OF CIE1000DhcpServerConfigPoolEntry
    MAX-ACCESS  not-accessible
    STATUS      current
    DESCRIPTION
        "The table is DHCP server pool onfiguration table. The indexe is pool
         name."
    ::= { cie1000DhcpServerConfig 5 }

cie1000DhcpServerConfigPoolEntry OBJECT-TYPE
    SYNTAX      CIE1000DhcpServerConfigPoolEntry
    MAX-ACCESS  not-accessible
    STATUS      current
    DESCRIPTION
        "Each entry has a set of parameters"
    INDEX       { cie1000DhcpServerConfigPoolPoolName }
    ::= { cie1000DhcpServerConfigPoolTable 1 }

CIE1000DhcpServerConfigPoolEntry ::= SEQUENCE {
    cie1000DhcpServerConfigPoolPoolName               CIE1000DisplayString,
    cie1000DhcpServerConfigPoolPoolType               CIE1000DhcpServerPoolEnum,
    cie1000DhcpServerConfigPoolIpv4Address            IpAddress,
    cie1000DhcpServerConfigPoolSubnetMask             IpAddress,
    cie1000DhcpServerConfigPoolSubnetBroadcast        IpAddress,
    cie1000DhcpServerConfigPoolLeaseDay               Unsigned32,
    cie1000DhcpServerConfigPoolLeaseHour              Unsigned32,
    cie1000DhcpServerConfigPoolLeaseMinute            Unsigned32,
    cie1000DhcpServerConfigPoolDomainName             CIE1000DisplayString,
    cie1000DhcpServerConfigPoolDefaultRouter1         IpAddress,
    cie1000DhcpServerConfigPoolDefaultRouter2         IpAddress,
    cie1000DhcpServerConfigPoolDefaultRouter3         IpAddress,
    cie1000DhcpServerConfigPoolDefaultRouter4         IpAddress,
    cie1000DhcpServerConfigPoolDnsServer1             IpAddress,
    cie1000DhcpServerConfigPoolDnsServer2             IpAddress,
    cie1000DhcpServerConfigPoolDnsServer3             IpAddress,
    cie1000DhcpServerConfigPoolDnsServer4             IpAddress,
    cie1000DhcpServerConfigPoolNtpServer1             IpAddress,
    cie1000DhcpServerConfigPoolNtpServer2             IpAddress,
    cie1000DhcpServerConfigPoolNtpServer3             IpAddress,
    cie1000DhcpServerConfigPoolNtpServer4             IpAddress,
    cie1000DhcpServerConfigPoolNetbiosNodeType        CIE1000DhcpServerNetbiosNodeEnum,
    cie1000DhcpServerConfigPoolNetbiosScope           CIE1000DisplayString,
    cie1000DhcpServerConfigPoolNetbiosNameServer1     IpAddress,
    cie1000DhcpServerConfigPoolNetbiosNameServer2     IpAddress,
    cie1000DhcpServerConfigPoolNetbiosNameServer3     IpAddress,
    cie1000DhcpServerConfigPoolNetbiosNameServer4     IpAddress,
    cie1000DhcpServerConfigPoolNisDomainName          CIE1000DisplayString,
    cie1000DhcpServerConfigPoolNisServer1             IpAddress,
    cie1000DhcpServerConfigPoolNisServer2             IpAddress,
    cie1000DhcpServerConfigPoolNisServer3             IpAddress,
    cie1000DhcpServerConfigPoolNisServer4             IpAddress,
    cie1000DhcpServerConfigPoolClientIdentifierType   CIE1000DhcpServerClientIdentifierEnum,
    cie1000DhcpServerConfigPoolClientIdentifierName   CIE1000DisplayString,
    cie1000DhcpServerConfigPoolClientIdentifierMac    MacAddress,
    cie1000DhcpServerConfigPoolClientHardwareAddress  MacAddress,
    cie1000DhcpServerConfigPoolClientName             CIE1000DisplayString,
    cie1000DhcpServerConfigPoolVendorClassId1         CIE1000DisplayString,
    cie1000DhcpServerConfigPoolVendorSpecificInfo1    CIE1000DisplayString,
    cie1000DhcpServerConfigPoolVendorClassId2         CIE1000DisplayString,
    cie1000DhcpServerConfigPoolVendorSpecificInfo2    CIE1000DisplayString,
    cie1000DhcpServerConfigPoolVendorClassId3         CIE1000DisplayString,
    cie1000DhcpServerConfigPoolVendorSpecificInfo3    CIE1000DisplayString,
    cie1000DhcpServerConfigPoolVendorClassId4         CIE1000DisplayString,
    cie1000DhcpServerConfigPoolVendorSpecificInfo4    CIE1000DisplayString,
    cie1000DhcpServerConfigPoolAction                 CIE1000RowEditorState
}

cie1000DhcpServerConfigPoolPoolName OBJECT-TYPE
    SYNTAX      CIE1000DisplayString (SIZE(0..32))
    MAX-ACCESS  accessible-for-notify
    STATUS      current
    DESCRIPTION
        "Name of DHCP pool."
    ::= { cie1000DhcpServerConfigPoolEntry 1 }

cie1000DhcpServerConfigPoolPoolType OBJECT-TYPE
    SYNTAX      CIE1000DhcpServerPoolEnum
    MAX-ACCESS  read-write
    STATUS      current
    DESCRIPTION
        "Type of pool. none(0) means the pool type is not defined yet.
         network(1) means the pool defines a pool of IP addresses to service
         more than one DHCP client. host(2) means the pool services for a
         specific DHCP client identified by client identifier or hardware
         address."
    ::= { cie1000DhcpServerConfigPoolEntry 2 }

cie1000DhcpServerConfigPoolIpv4Address OBJECT-TYPE
    SYNTAX      IpAddress
    MAX-ACCESS  read-write
    STATUS      current
    DESCRIPTION
        "Network number of the subnet. If the pool type is of network, the IP
         address can be any general IP address. If the pool type is of host, the
         IP address must be a unicast IP address."
    ::= { cie1000DhcpServerConfigPoolEntry 3 }

cie1000DhcpServerConfigPoolSubnetMask OBJECT-TYPE
    SYNTAX      IpAddress
    MAX-ACCESS  read-write
    STATUS      current
    DESCRIPTION
        "Subnet Mask. DHCP option 1. Specify subnet mask of the DHCP address
         pool, excluding 0.0.0.0 and 255.255.255.255."
    ::= { cie1000DhcpServerConfigPoolEntry 4 }

cie1000DhcpServerConfigPoolSubnetBroadcast OBJECT-TYPE
    SYNTAX      IpAddress
    MAX-ACCESS  read-write
    STATUS      current
    DESCRIPTION
        "Broadcast IP address in the subnet. DHCP option 28. Specify the
         broadcast address in use on the client's subnet."
    ::= { cie1000DhcpServerConfigPoolEntry 5 }

cie1000DhcpServerConfigPoolLeaseDay OBJECT-TYPE
    SYNTAX      Unsigned32
    MAX-ACCESS  read-write
    STATUS      current
    DESCRIPTION
        "Number of days of lease time. DHCP option 51, 58 and 59. The value
         range is 0-365. Specify lease time that allows the client to request a
         lease time for the IP address. If all of LeaseDay, LeaseHour and
         LeaseMinute are 0's, then it means the lease time is infinite."
    ::= { cie1000DhcpServerConfigPoolEntry 6 }

cie1000DhcpServerConfigPoolLeaseHour OBJECT-TYPE
    SYNTAX      Unsigned32
    MAX-ACCESS  read-write
    STATUS      current
    DESCRIPTION
        "Number of hours of lease time. DHCP option 51, 58 and 59. The value
         range is 0-23. Specify lease time that allows the client to request a
         lease time for the IP address. If all of LeaseDay, LeaseHour and
         LeaseMinute are 0's, then it means the lease time is infinite."
    ::= { cie1000DhcpServerConfigPoolEntry 7 }

cie1000DhcpServerConfigPoolLeaseMinute OBJECT-TYPE
    SYNTAX      Unsigned32
    MAX-ACCESS  read-write
    STATUS      current
    DESCRIPTION
        "Number of minutes of lease time. DHCP option 51, 58 and 59. The value
         range is 0-59. Specify lease time that allows the client to request a
         lease time for the IP address. If all of LeaseDay, LeaseHour and
         LeaseMinute are 0's, then it means the lease time is infinite."
    ::= { cie1000DhcpServerConfigPoolEntry 8 }

cie1000DhcpServerConfigPoolDomainName OBJECT-TYPE
    SYNTAX      CIE1000DisplayString (SIZE(0..32))
    MAX-ACCESS  read-write
    STATUS      current
    DESCRIPTION
        "Domain name. DHCP option 15. Specify domain name that client should use
         when resolving hostname via DNS."
    ::= { cie1000DhcpServerConfigPoolEntry 9 }

cie1000DhcpServerConfigPoolDefaultRouter1 OBJECT-TYPE
    SYNTAX      IpAddress
    MAX-ACCESS  read-write
    STATUS      current
    DESCRIPTION
        "Default router 1."
    ::= { cie1000DhcpServerConfigPoolEntry 10 }

cie1000DhcpServerConfigPoolDefaultRouter2 OBJECT-TYPE
    SYNTAX      IpAddress
    MAX-ACCESS  read-write
    STATUS      current
    DESCRIPTION
        "Default router 2."
    ::= { cie1000DhcpServerConfigPoolEntry 11 }

cie1000DhcpServerConfigPoolDefaultRouter3 OBJECT-TYPE
    SYNTAX      IpAddress
    MAX-ACCESS  read-write
    STATUS      current
    DESCRIPTION
        "Default router 3."
    ::= { cie1000DhcpServerConfigPoolEntry 12 }

cie1000DhcpServerConfigPoolDefaultRouter4 OBJECT-TYPE
    SYNTAX      IpAddress
    MAX-ACCESS  read-write
    STATUS      current
    DESCRIPTION
        "Default router 4."
    ::= { cie1000DhcpServerConfigPoolEntry 13 }

cie1000DhcpServerConfigPoolDnsServer1 OBJECT-TYPE
    SYNTAX      IpAddress
    MAX-ACCESS  read-write
    STATUS      current
    DESCRIPTION
        "DNS server 1."
    ::= { cie1000DhcpServerConfigPoolEntry 14 }

cie1000DhcpServerConfigPoolDnsServer2 OBJECT-TYPE
    SYNTAX      IpAddress
    MAX-ACCESS  read-write
    STATUS      current
    DESCRIPTION
        "DNS server 2."
    ::= { cie1000DhcpServerConfigPoolEntry 15 }

cie1000DhcpServerConfigPoolDnsServer3 OBJECT-TYPE
    SYNTAX      IpAddress
    MAX-ACCESS  read-write
    STATUS      current
    DESCRIPTION
        "DNS server 3."
    ::= { cie1000DhcpServerConfigPoolEntry 16 }

cie1000DhcpServerConfigPoolDnsServer4 OBJECT-TYPE
    SYNTAX      IpAddress
    MAX-ACCESS  read-write
    STATUS      current
    DESCRIPTION
        "DNS server 4."
    ::= { cie1000DhcpServerConfigPoolEntry 17 }

cie1000DhcpServerConfigPoolNtpServer1 OBJECT-TYPE
    SYNTAX      IpAddress
    MAX-ACCESS  read-write
    STATUS      current
    DESCRIPTION
        "NTP server 1."
    ::= { cie1000DhcpServerConfigPoolEntry 18 }

cie1000DhcpServerConfigPoolNtpServer2 OBJECT-TYPE
    SYNTAX      IpAddress
    MAX-ACCESS  read-write
    STATUS      current
    DESCRIPTION
        "NTP server 2."
    ::= { cie1000DhcpServerConfigPoolEntry 19 }

cie1000DhcpServerConfigPoolNtpServer3 OBJECT-TYPE
    SYNTAX      IpAddress
    MAX-ACCESS  read-write
    STATUS      current
    DESCRIPTION
        "NTP server 3."
    ::= { cie1000DhcpServerConfigPoolEntry 20 }

cie1000DhcpServerConfigPoolNtpServer4 OBJECT-TYPE
    SYNTAX      IpAddress
    MAX-ACCESS  read-write
    STATUS      current
    DESCRIPTION
        "NTP server 4."
    ::= { cie1000DhcpServerConfigPoolEntry 21 }

cie1000DhcpServerConfigPoolNetbiosNodeType OBJECT-TYPE
    SYNTAX      CIE1000DhcpServerNetbiosNodeEnum
    MAX-ACCESS  read-write
    STATUS      current
    DESCRIPTION
        "Type of NetBIOS node. DHCP option 46. Specify NetBIOS node type option
         to allow Netbios over TCP/IP clients which are configurable to be
         configured as described in RFC 1001/1002. nodeNone(0) means the node
         type is not defined yet. nodeB(1) means the node type is type of B.
         nodeP(2) means the node type is type of P. nodeM(3) means the node type
         is type of M. nodeH(4) means the node type is type of H."
    ::= { cie1000DhcpServerConfigPoolEntry 22 }

cie1000DhcpServerConfigPoolNetbiosScope OBJECT-TYPE
    SYNTAX      CIE1000DisplayString (SIZE(0..32))
    MAX-ACCESS  read-write
    STATUS      current
    DESCRIPTION
        "NetBIOS scope. DHCP option 47. Specify the NetBIOS over TCP/IP scope
         parameter for the client as specified in RFC 1001/1002."
    ::= { cie1000DhcpServerConfigPoolEntry 23 }

cie1000DhcpServerConfigPoolNetbiosNameServer1 OBJECT-TYPE
    SYNTAX      IpAddress
    MAX-ACCESS  read-write
    STATUS      current
    DESCRIPTION
        "NetBIOS name server 1."
    ::= { cie1000DhcpServerConfigPoolEntry 24 }

cie1000DhcpServerConfigPoolNetbiosNameServer2 OBJECT-TYPE
    SYNTAX      IpAddress
    MAX-ACCESS  read-write
    STATUS      current
    DESCRIPTION
        "NetBIOS name server 2."
    ::= { cie1000DhcpServerConfigPoolEntry 25 }

cie1000DhcpServerConfigPoolNetbiosNameServer3 OBJECT-TYPE
    SYNTAX      IpAddress
    MAX-ACCESS  read-write
    STATUS      current
    DESCRIPTION
        "NetBIOS name server 3."
    ::= { cie1000DhcpServerConfigPoolEntry 26 }

cie1000DhcpServerConfigPoolNetbiosNameServer4 OBJECT-TYPE
    SYNTAX      IpAddress
    MAX-ACCESS  read-write
    STATUS      current
    DESCRIPTION
        "NetBIOS name server 4."
    ::= { cie1000DhcpServerConfigPoolEntry 27 }

cie1000DhcpServerConfigPoolNisDomainName OBJECT-TYPE
    SYNTAX      CIE1000DisplayString (SIZE(0..32))
    MAX-ACCESS  read-write
    STATUS      current
    DESCRIPTION
        "NIS Domain Name. DHCP option 40. Specify the name of the client's NIS
         domain."
    ::= { cie1000DhcpServerConfigPoolEntry 28 }

cie1000DhcpServerConfigPoolNisServer1 OBJECT-TYPE
    SYNTAX      IpAddress
    MAX-ACCESS  read-write
    STATUS      current
    DESCRIPTION
        "NIS server 1."
    ::= { cie1000DhcpServerConfigPoolEntry 29 }

cie1000DhcpServerConfigPoolNisServer2 OBJECT-TYPE
    SYNTAX      IpAddress
    MAX-ACCESS  read-write
    STATUS      current
    DESCRIPTION
        "NIS server 2."
    ::= { cie1000DhcpServerConfigPoolEntry 30 }

cie1000DhcpServerConfigPoolNisServer3 OBJECT-TYPE
    SYNTAX      IpAddress
    MAX-ACCESS  read-write
    STATUS      current
    DESCRIPTION
        "NIS server 3."
    ::= { cie1000DhcpServerConfigPoolEntry 31 }

cie1000DhcpServerConfigPoolNisServer4 OBJECT-TYPE
    SYNTAX      IpAddress
    MAX-ACCESS  read-write
    STATUS      current
    DESCRIPTION
        "NIS server 4."
    ::= { cie1000DhcpServerConfigPoolEntry 32 }

cie1000DhcpServerConfigPoolClientIdentifierType OBJECT-TYPE
    SYNTAX      CIE1000DhcpServerClientIdentifierEnum
    MAX-ACCESS  read-write
    STATUS      current
    DESCRIPTION
        "Type of client identifier. DHCP option 61. Specify client's unique
         identifier to be used when the pool is the type of host. none(0) means
         the client identifier type is not defined yet. name(1) means the client
         identifier type is other than hardware. mac(2) means the client
         identifier type is type of MAC address."
    ::= { cie1000DhcpServerConfigPoolEntry 33 }

cie1000DhcpServerConfigPoolClientIdentifierName OBJECT-TYPE
    SYNTAX      CIE1000DisplayString (SIZE(0..64))
    MAX-ACCESS  read-write
    STATUS      current
    DESCRIPTION
        "Client identifier which type is other than hardware. DHCP option 61.
         Specify client's unique identifier to be used when the pool is the type
         of host. This takes effect only if ClientIdentifierType is defined
         name(1)."
    ::= { cie1000DhcpServerConfigPoolEntry 34 }

cie1000DhcpServerConfigPoolClientIdentifierMac OBJECT-TYPE
    SYNTAX      MacAddress
    MAX-ACCESS  read-write
    STATUS      current
    DESCRIPTION
        "Client's MAC address. DHCP option 61. Specify client's unique
         identifier to be used when the pool is the type of host. This takes
         effect only if ClientIdentifierType is defined as mac(2)."
    ::= { cie1000DhcpServerConfigPoolEntry 35 }

cie1000DhcpServerConfigPoolClientHardwareAddress OBJECT-TYPE
    SYNTAX      MacAddress
    MAX-ACCESS  read-write
    STATUS      current
    DESCRIPTION
        "Client's hardware address. Specify client's hardware(MAC) address to be
         used when the pool is the type of host."
    ::= { cie1000DhcpServerConfigPoolEntry 36 }

cie1000DhcpServerConfigPoolClientName OBJECT-TYPE
    SYNTAX      CIE1000DisplayString (SIZE(0..32))
    MAX-ACCESS  read-write
    STATUS      current
    DESCRIPTION
        "Client name. DHCP option 12. Specify the name of client to be used when
         the pool is the type of host."
    ::= { cie1000DhcpServerConfigPoolEntry 37 }

cie1000DhcpServerConfigPoolVendorClassId1 OBJECT-TYPE
    SYNTAX      CIE1000DisplayString (SIZE(0..64))
    MAX-ACCESS  read-write
    STATUS      current
    DESCRIPTION
        "Vendor Class Identifier. DHCP option 60. Specify to be used by DHCP
         client to optionally identify the vendor type and configuration of a
         DHCP client. DHCP server will deliver the corresponding option 43
         specific information to the client that sends option 60 vendor class
         identifier."
    ::= { cie1000DhcpServerConfigPoolEntry 38 }

cie1000DhcpServerConfigPoolVendorSpecificInfo1 OBJECT-TYPE
    SYNTAX      CIE1000DisplayString (SIZE(0..66))
    MAX-ACCESS  read-write
    STATUS      current
    DESCRIPTION
        "Vendor Specific Information. DHCP option 43. Specify vendor specific
         information corresponding to option 60 vendor class identifier.
         Therefore, the corresponding vendor class identifier must be defined
         before this specific information."
    ::= { cie1000DhcpServerConfigPoolEntry 39 }

cie1000DhcpServerConfigPoolVendorClassId2 OBJECT-TYPE
    SYNTAX      CIE1000DisplayString (SIZE(0..64))
    MAX-ACCESS  read-write
    STATUS      current
    DESCRIPTION
        "Vendor Class Identifier. DHCP option 60. Specify to be used by DHCP
         client to optionally identify the vendor type and configuration of a
         DHCP client. DHCP server will deliver the corresponding option 43
         specific information to the client that sends option 60 vendor class
         identifier."
    ::= { cie1000DhcpServerConfigPoolEntry 40 }

cie1000DhcpServerConfigPoolVendorSpecificInfo2 OBJECT-TYPE
    SYNTAX      CIE1000DisplayString (SIZE(0..66))
    MAX-ACCESS  read-write
    STATUS      current
    DESCRIPTION
        "Vendor Specific Information. DHCP option 43. Specify vendor specific
         information corresponding to option 60 vendor class identifier.
         Therefore, the corresponding vendor class identifier must be defined
         before this specific information."
    ::= { cie1000DhcpServerConfigPoolEntry 41 }

cie1000DhcpServerConfigPoolVendorClassId3 OBJECT-TYPE
    SYNTAX      CIE1000DisplayString (SIZE(0..64))
    MAX-ACCESS  read-write
    STATUS      current
    DESCRIPTION
        "Vendor Class Identifier. DHCP option 60. Specify to be used by DHCP
         client to optionally identify the vendor type and configuration of a
         DHCP client. DHCP server will deliver the corresponding option 43
         specific information to the client that sends option 60 vendor class
         identifier."
    ::= { cie1000DhcpServerConfigPoolEntry 42 }

cie1000DhcpServerConfigPoolVendorSpecificInfo3 OBJECT-TYPE
    SYNTAX      CIE1000DisplayString (SIZE(0..66))
    MAX-ACCESS  read-write
    STATUS      current
    DESCRIPTION
        "Vendor Specific Information. DHCP option 43. Specify vendor specific
         information corresponding to option 60 vendor class identifier.
         Therefore, the corresponding vendor class identifier must be defined
         before this specific information."
    ::= { cie1000DhcpServerConfigPoolEntry 43 }

cie1000DhcpServerConfigPoolVendorClassId4 OBJECT-TYPE
    SYNTAX      CIE1000DisplayString (SIZE(0..64))
    MAX-ACCESS  read-write
    STATUS      current
    DESCRIPTION
        "Vendor Class Identifier. DHCP option 60. Specify to be used by DHCP
         client to optionally identify the vendor type and configuration of a
         DHCP client. DHCP server will deliver the corresponding option 43
         specific information to the client that sends option 60 vendor class
         identifier."
    ::= { cie1000DhcpServerConfigPoolEntry 44 }

cie1000DhcpServerConfigPoolVendorSpecificInfo4 OBJECT-TYPE
    SYNTAX      CIE1000DisplayString (SIZE(0..66))
    MAX-ACCESS  read-write
    STATUS      current
    DESCRIPTION
        "Vendor Specific Information. DHCP option 43. Specify vendor specific
         information corresponding to option 60 vendor class identifier.
         Therefore, the corresponding vendor class identifier must be defined
         before this specific information."
    ::= { cie1000DhcpServerConfigPoolEntry 45 }

cie1000DhcpServerConfigPoolAction OBJECT-TYPE
    SYNTAX      CIE1000RowEditorState
    MAX-ACCESS  read-write
    STATUS      current
    DESCRIPTION
        "Action"
    ::= { cie1000DhcpServerConfigPoolEntry 100 }

cie1000DhcpServerConfigPoolTableRowEditor OBJECT IDENTIFIER
    ::= { cie1000DhcpServerConfig 6 }

cie1000DhcpServerConfigPoolTableRowEditorPoolName OBJECT-TYPE
    SYNTAX      CIE1000DisplayString (SIZE(0..32))
    MAX-ACCESS  read-write
    STATUS      current
    DESCRIPTION
        "Name of DHCP pool."
    ::= { cie1000DhcpServerConfigPoolTableRowEditor 1 }

cie1000DhcpServerConfigPoolTableRowEditorPoolType OBJECT-TYPE
    SYNTAX      CIE1000DhcpServerPoolEnum
    MAX-ACCESS  read-write
    STATUS      current
    DESCRIPTION
        "Type of pool. none(0) means the pool type is not defined yet.
         network(1) means the pool defines a pool of IP addresses to service
         more than one DHCP client. host(2) means the pool services for a
         specific DHCP client identified by client identifier or hardware
         address."
    ::= { cie1000DhcpServerConfigPoolTableRowEditor 2 }

cie1000DhcpServerConfigPoolTableRowEditorIpv4Address OBJECT-TYPE
    SYNTAX      IpAddress
    MAX-ACCESS  read-write
    STATUS      current
    DESCRIPTION
        "Network number of the subnet. If the pool type is of network, the IP
         address can be any general IP address. If the pool type is of host, the
         IP address must be a unicast IP address."
    ::= { cie1000DhcpServerConfigPoolTableRowEditor 3 }

cie1000DhcpServerConfigPoolTableRowEditorSubnetMask OBJECT-TYPE
    SYNTAX      IpAddress
    MAX-ACCESS  read-write
    STATUS      current
    DESCRIPTION
        "Subnet Mask. DHCP option 1. Specify subnet mask of the DHCP address
         pool, excluding 0.0.0.0 and 255.255.255.255."
    ::= { cie1000DhcpServerConfigPoolTableRowEditor 4 }

cie1000DhcpServerConfigPoolTableRowEditorSubnetBroadcast OBJECT-TYPE
    SYNTAX      IpAddress
    MAX-ACCESS  read-write
    STATUS      current
    DESCRIPTION
        "Broadcast IP address in the subnet. DHCP option 28. Specify the
         broadcast address in use on the client's subnet."
    ::= { cie1000DhcpServerConfigPoolTableRowEditor 5 }

cie1000DhcpServerConfigPoolTableRowEditorLeaseDay OBJECT-TYPE
    SYNTAX      Unsigned32
    MAX-ACCESS  read-write
    STATUS      current
    DESCRIPTION
        "Number of days of lease time. DHCP option 51, 58 and 59. The value
         range is 0-365. Specify lease time that allows the client to request a
         lease time for the IP address. If all of LeaseDay, LeaseHour and
         LeaseMinute are 0's, then it means the lease time is infinite."
    ::= { cie1000DhcpServerConfigPoolTableRowEditor 6 }

cie1000DhcpServerConfigPoolTableRowEditorLeaseHour OBJECT-TYPE
    SYNTAX      Unsigned32
    MAX-ACCESS  read-write
    STATUS      current
    DESCRIPTION
        "Number of hours of lease time. DHCP option 51, 58 and 59. The value
         range is 0-23. Specify lease time that allows the client to request a
         lease time for the IP address. If all of LeaseDay, LeaseHour and
         LeaseMinute are 0's, then it means the lease time is infinite."
    ::= { cie1000DhcpServerConfigPoolTableRowEditor 7 }

cie1000DhcpServerConfigPoolTableRowEditorLeaseMinute OBJECT-TYPE
    SYNTAX      Unsigned32
    MAX-ACCESS  read-write
    STATUS      current
    DESCRIPTION
        "Number of minutes of lease time. DHCP option 51, 58 and 59. The value
         range is 0-59. Specify lease time that allows the client to request a
         lease time for the IP address. If all of LeaseDay, LeaseHour and
         LeaseMinute are 0's, then it means the lease time is infinite."
    ::= { cie1000DhcpServerConfigPoolTableRowEditor 8 }

cie1000DhcpServerConfigPoolTableRowEditorDomainName OBJECT-TYPE
    SYNTAX      CIE1000DisplayString (SIZE(0..32))
    MAX-ACCESS  read-write
    STATUS      current
    DESCRIPTION
        "Domain name. DHCP option 15. Specify domain name that client should use
         when resolving hostname via DNS."
    ::= { cie1000DhcpServerConfigPoolTableRowEditor 9 }

cie1000DhcpServerConfigPoolTableRowEditorDefaultRouter1 OBJECT-TYPE
    SYNTAX      IpAddress
    MAX-ACCESS  read-write
    STATUS      current
    DESCRIPTION
        "Default router 1."
    ::= { cie1000DhcpServerConfigPoolTableRowEditor 10 }

cie1000DhcpServerConfigPoolTableRowEditorDefaultRouter2 OBJECT-TYPE
    SYNTAX      IpAddress
    MAX-ACCESS  read-write
    STATUS      current
    DESCRIPTION
        "Default router 2."
    ::= { cie1000DhcpServerConfigPoolTableRowEditor 11 }

cie1000DhcpServerConfigPoolTableRowEditorDefaultRouter3 OBJECT-TYPE
    SYNTAX      IpAddress
    MAX-ACCESS  read-write
    STATUS      current
    DESCRIPTION
        "Default router 3."
    ::= { cie1000DhcpServerConfigPoolTableRowEditor 12 }

cie1000DhcpServerConfigPoolTableRowEditorDefaultRouter4 OBJECT-TYPE
    SYNTAX      IpAddress
    MAX-ACCESS  read-write
    STATUS      current
    DESCRIPTION
        "Default router 4."
    ::= { cie1000DhcpServerConfigPoolTableRowEditor 13 }

cie1000DhcpServerConfigPoolTableRowEditorDnsServer1 OBJECT-TYPE
    SYNTAX      IpAddress
    MAX-ACCESS  read-write
    STATUS      current
    DESCRIPTION
        "DNS server 1."
    ::= { cie1000DhcpServerConfigPoolTableRowEditor 14 }

cie1000DhcpServerConfigPoolTableRowEditorDnsServer2 OBJECT-TYPE
    SYNTAX      IpAddress
    MAX-ACCESS  read-write
    STATUS      current
    DESCRIPTION
        "DNS server 2."
    ::= { cie1000DhcpServerConfigPoolTableRowEditor 15 }

cie1000DhcpServerConfigPoolTableRowEditorDnsServer3 OBJECT-TYPE
    SYNTAX      IpAddress
    MAX-ACCESS  read-write
    STATUS      current
    DESCRIPTION
        "DNS server 3."
    ::= { cie1000DhcpServerConfigPoolTableRowEditor 16 }

cie1000DhcpServerConfigPoolTableRowEditorDnsServer4 OBJECT-TYPE
    SYNTAX      IpAddress
    MAX-ACCESS  read-write
    STATUS      current
    DESCRIPTION
        "DNS server 4."
    ::= { cie1000DhcpServerConfigPoolTableRowEditor 17 }

cie1000DhcpServerConfigPoolTableRowEditorNtpServer1 OBJECT-TYPE
    SYNTAX      IpAddress
    MAX-ACCESS  read-write
    STATUS      current
    DESCRIPTION
        "NTP server 1."
    ::= { cie1000DhcpServerConfigPoolTableRowEditor 18 }

cie1000DhcpServerConfigPoolTableRowEditorNtpServer2 OBJECT-TYPE
    SYNTAX      IpAddress
    MAX-ACCESS  read-write
    STATUS      current
    DESCRIPTION
        "NTP server 2."
    ::= { cie1000DhcpServerConfigPoolTableRowEditor 19 }

cie1000DhcpServerConfigPoolTableRowEditorNtpServer3 OBJECT-TYPE
    SYNTAX      IpAddress
    MAX-ACCESS  read-write
    STATUS      current
    DESCRIPTION
        "NTP server 3."
    ::= { cie1000DhcpServerConfigPoolTableRowEditor 20 }

cie1000DhcpServerConfigPoolTableRowEditorNtpServer4 OBJECT-TYPE
    SYNTAX      IpAddress
    MAX-ACCESS  read-write
    STATUS      current
    DESCRIPTION
        "NTP server 4."
    ::= { cie1000DhcpServerConfigPoolTableRowEditor 21 }

cie1000DhcpServerConfigPoolTableRowEditorNetbiosNodeType OBJECT-TYPE
    SYNTAX      CIE1000DhcpServerNetbiosNodeEnum
    MAX-ACCESS  read-write
    STATUS      current
    DESCRIPTION
        "Type of NetBIOS node. DHCP option 46. Specify NetBIOS node type option
         to allow Netbios over TCP/IP clients which are configurable to be
         configured as described in RFC 1001/1002. nodeNone(0) means the node
         type is not defined yet. nodeB(1) means the node type is type of B.
         nodeP(2) means the node type is type of P. nodeM(3) means the node type
         is type of M. nodeH(4) means the node type is type of H."
    ::= { cie1000DhcpServerConfigPoolTableRowEditor 22 }

cie1000DhcpServerConfigPoolTableRowEditorNetbiosScope OBJECT-TYPE
    SYNTAX      CIE1000DisplayString (SIZE(0..32))
    MAX-ACCESS  read-write
    STATUS      current
    DESCRIPTION
        "NetBIOS scope. DHCP option 47. Specify the NetBIOS over TCP/IP scope
         parameter for the client as specified in RFC 1001/1002."
    ::= { cie1000DhcpServerConfigPoolTableRowEditor 23 }

cie1000DhcpServerConfigPoolTableRowEditorNetbiosNameServer1 OBJECT-TYPE
    SYNTAX      IpAddress
    MAX-ACCESS  read-write
    STATUS      current
    DESCRIPTION
        "NetBIOS name server 1."
    ::= { cie1000DhcpServerConfigPoolTableRowEditor 24 }

cie1000DhcpServerConfigPoolTableRowEditorNetbiosNameServer2 OBJECT-TYPE
    SYNTAX      IpAddress
    MAX-ACCESS  read-write
    STATUS      current
    DESCRIPTION
        "NetBIOS name server 2."
    ::= { cie1000DhcpServerConfigPoolTableRowEditor 25 }

cie1000DhcpServerConfigPoolTableRowEditorNetbiosNameServer3 OBJECT-TYPE
    SYNTAX      IpAddress
    MAX-ACCESS  read-write
    STATUS      current
    DESCRIPTION
        "NetBIOS name server 3."
    ::= { cie1000DhcpServerConfigPoolTableRowEditor 26 }

cie1000DhcpServerConfigPoolTableRowEditorNetbiosNameServer4 OBJECT-TYPE
    SYNTAX      IpAddress
    MAX-ACCESS  read-write
    STATUS      current
    DESCRIPTION
        "NetBIOS name server 4."
    ::= { cie1000DhcpServerConfigPoolTableRowEditor 27 }

cie1000DhcpServerConfigPoolTableRowEditorNisDomainName OBJECT-TYPE
    SYNTAX      CIE1000DisplayString (SIZE(0..32))
    MAX-ACCESS  read-write
    STATUS      current
    DESCRIPTION
        "NIS Domain Name. DHCP option 40. Specify the name of the client's NIS
         domain."
    ::= { cie1000DhcpServerConfigPoolTableRowEditor 28 }

cie1000DhcpServerConfigPoolTableRowEditorNisServer1 OBJECT-TYPE
    SYNTAX      IpAddress
    MAX-ACCESS  read-write
    STATUS      current
    DESCRIPTION
        "NIS server 1."
    ::= { cie1000DhcpServerConfigPoolTableRowEditor 29 }

cie1000DhcpServerConfigPoolTableRowEditorNisServer2 OBJECT-TYPE
    SYNTAX      IpAddress
    MAX-ACCESS  read-write
    STATUS      current
    DESCRIPTION
        "NIS server 2."
    ::= { cie1000DhcpServerConfigPoolTableRowEditor 30 }

cie1000DhcpServerConfigPoolTableRowEditorNisServer3 OBJECT-TYPE
    SYNTAX      IpAddress
    MAX-ACCESS  read-write
    STATUS      current
    DESCRIPTION
        "NIS server 3."
    ::= { cie1000DhcpServerConfigPoolTableRowEditor 31 }

cie1000DhcpServerConfigPoolTableRowEditorNisServer4 OBJECT-TYPE
    SYNTAX      IpAddress
    MAX-ACCESS  read-write
    STATUS      current
    DESCRIPTION
        "NIS server 4."
    ::= { cie1000DhcpServerConfigPoolTableRowEditor 32 }

cie1000DhcpServerConfigPoolTableRowEditorClientIdentifierType OBJECT-TYPE
    SYNTAX      CIE1000DhcpServerClientIdentifierEnum
    MAX-ACCESS  read-write
    STATUS      current
    DESCRIPTION
        "Type of client identifier. DHCP option 61. Specify client's unique
         identifier to be used when the pool is the type of host. none(0) means
         the client identifier type is not defined yet. name(1) means the client
         identifier type is other than hardware. mac(2) means the client
         identifier type is type of MAC address."
    ::= { cie1000DhcpServerConfigPoolTableRowEditor 33 }

cie1000DhcpServerConfigPoolTableRowEditorClientIdentifierName OBJECT-TYPE
    SYNTAX      CIE1000DisplayString (SIZE(0..64))
    MAX-ACCESS  read-write
    STATUS      current
    DESCRIPTION
        "Client identifier which type is other than hardware. DHCP option 61.
         Specify client's unique identifier to be used when the pool is the type
         of host. This takes effect only if ClientIdentifierType is defined
         name(1)."
    ::= { cie1000DhcpServerConfigPoolTableRowEditor 34 }

cie1000DhcpServerConfigPoolTableRowEditorClientIdentifierMac OBJECT-TYPE
    SYNTAX      MacAddress
    MAX-ACCESS  read-write
    STATUS      current
    DESCRIPTION
        "Client's MAC address. DHCP option 61. Specify client's unique
         identifier to be used when the pool is the type of host. This takes
         effect only if ClientIdentifierType is defined as mac(2)."
    ::= { cie1000DhcpServerConfigPoolTableRowEditor 35 }

cie1000DhcpServerConfigPoolTableRowEditorClientHardwareAddress OBJECT-TYPE
    SYNTAX      MacAddress
    MAX-ACCESS  read-write
    STATUS      current
    DESCRIPTION
        "Client's hardware address. Specify client's hardware(MAC) address to be
         used when the pool is the type of host."
    ::= { cie1000DhcpServerConfigPoolTableRowEditor 36 }

cie1000DhcpServerConfigPoolTableRowEditorClientName OBJECT-TYPE
    SYNTAX      CIE1000DisplayString (SIZE(0..32))
    MAX-ACCESS  read-write
    STATUS      current
    DESCRIPTION
        "Client name. DHCP option 12. Specify the name of client to be used when
         the pool is the type of host."
    ::= { cie1000DhcpServerConfigPoolTableRowEditor 37 }

cie1000DhcpServerConfigPoolTableRowEditorVendorClassId1 OBJECT-TYPE
    SYNTAX      CIE1000DisplayString (SIZE(0..64))
    MAX-ACCESS  read-write
    STATUS      current
    DESCRIPTION
        "Vendor Class Identifier. DHCP option 60. Specify to be used by DHCP
         client to optionally identify the vendor type and configuration of a
         DHCP client. DHCP server will deliver the corresponding option 43
         specific information to the client that sends option 60 vendor class
         identifier."
    ::= { cie1000DhcpServerConfigPoolTableRowEditor 38 }

cie1000DhcpServerConfigPoolTableRowEditorVendorSpecificInfo1 OBJECT-TYPE
    SYNTAX      CIE1000DisplayString (SIZE(0..66))
    MAX-ACCESS  read-write
    STATUS      current
    DESCRIPTION
        "Vendor Specific Information. DHCP option 43. Specify vendor specific
         information corresponding to option 60 vendor class identifier.
         Therefore, the corresponding vendor class identifier must be defined
         before this specific information."
    ::= { cie1000DhcpServerConfigPoolTableRowEditor 39 }

cie1000DhcpServerConfigPoolTableRowEditorVendorClassId2 OBJECT-TYPE
    SYNTAX      CIE1000DisplayString (SIZE(0..64))
    MAX-ACCESS  read-write
    STATUS      current
    DESCRIPTION
        "Vendor Class Identifier. DHCP option 60. Specify to be used by DHCP
         client to optionally identify the vendor type and configuration of a
         DHCP client. DHCP server will deliver the corresponding option 43
         specific information to the client that sends option 60 vendor class
         identifier."
    ::= { cie1000DhcpServerConfigPoolTableRowEditor 40 }

cie1000DhcpServerConfigPoolTableRowEditorVendorSpecificInfo2 OBJECT-TYPE
    SYNTAX      CIE1000DisplayString (SIZE(0..66))
    MAX-ACCESS  read-write
    STATUS      current
    DESCRIPTION
        "Vendor Specific Information. DHCP option 43. Specify vendor specific
         information corresponding to option 60 vendor class identifier.
         Therefore, the corresponding vendor class identifier must be defined
         before this specific information."
    ::= { cie1000DhcpServerConfigPoolTableRowEditor 41 }

cie1000DhcpServerConfigPoolTableRowEditorVendorClassId3 OBJECT-TYPE
    SYNTAX      CIE1000DisplayString (SIZE(0..64))
    MAX-ACCESS  read-write
    STATUS      current
    DESCRIPTION
        "Vendor Class Identifier. DHCP option 60. Specify to be used by DHCP
         client to optionally identify the vendor type and configuration of a
         DHCP client. DHCP server will deliver the corresponding option 43
         specific information to the client that sends option 60 vendor class
         identifier."
    ::= { cie1000DhcpServerConfigPoolTableRowEditor 42 }

cie1000DhcpServerConfigPoolTableRowEditorVendorSpecificInfo3 OBJECT-TYPE
    SYNTAX      CIE1000DisplayString (SIZE(0..66))
    MAX-ACCESS  read-write
    STATUS      current
    DESCRIPTION
        "Vendor Specific Information. DHCP option 43. Specify vendor specific
         information corresponding to option 60 vendor class identifier.
         Therefore, the corresponding vendor class identifier must be defined
         before this specific information."
    ::= { cie1000DhcpServerConfigPoolTableRowEditor 43 }

cie1000DhcpServerConfigPoolTableRowEditorVendorClassId4 OBJECT-TYPE
    SYNTAX      CIE1000DisplayString (SIZE(0..64))
    MAX-ACCESS  read-write
    STATUS      current
    DESCRIPTION
        "Vendor Class Identifier. DHCP option 60. Specify to be used by DHCP
         client to optionally identify the vendor type and configuration of a
         DHCP client. DHCP server will deliver the corresponding option 43
         specific information to the client that sends option 60 vendor class
         identifier."
    ::= { cie1000DhcpServerConfigPoolTableRowEditor 44 }

cie1000DhcpServerConfigPoolTableRowEditorVendorSpecificInfo4 OBJECT-TYPE
    SYNTAX      CIE1000DisplayString (SIZE(0..66))
    MAX-ACCESS  read-write
    STATUS      current
    DESCRIPTION
        "Vendor Specific Information. DHCP option 43. Specify vendor specific
         information corresponding to option 60 vendor class identifier.
         Therefore, the corresponding vendor class identifier must be defined
         before this specific information."
    ::= { cie1000DhcpServerConfigPoolTableRowEditor 45 }

cie1000DhcpServerConfigPoolTableRowEditorAction OBJECT-TYPE
    SYNTAX      CIE1000RowEditorState
    MAX-ACCESS  read-write
    STATUS      current
    DESCRIPTION
        "Action"
    ::= { cie1000DhcpServerConfigPoolTableRowEditor 100 }

cie1000DhcpServerConfigReservedTable OBJECT-TYPE
    SYNTAX      SEQUENCE OF CIE1000DhcpServerConfigReservedEntry
    MAX-ACCESS  not-accessible
    STATUS      current
    DESCRIPTION
        "The table is DHCP server reserved entries. The index is the name of the
         pool and the ip address"
    ::= { cie1000DhcpServerConfig 7 }

cie1000DhcpServerConfigReservedEntry OBJECT-TYPE
    SYNTAX      CIE1000DhcpServerConfigReservedEntry
    MAX-ACCESS  not-accessible
    STATUS      current
    DESCRIPTION
        "Each entry has a set of parameters"
    INDEX       { cie1000DhcpServerConfigReservedPoolName,
                  cie1000DhcpServerConfigReservedIpAddress }
    ::= { cie1000DhcpServerConfigReservedTable 1 }

CIE1000DhcpServerConfigReservedEntry ::= SEQUENCE {
    cie1000DhcpServerConfigReservedPoolName   CIE1000DisplayString,
    cie1000DhcpServerConfigReservedIpAddress  IpAddress,
    cie1000DhcpServerConfigReservedIfIndex    CIE1000InterfaceIndex,
    cie1000DhcpServerConfigReservedAction     CIE1000RowEditorState
}

cie1000DhcpServerConfigReservedPoolName OBJECT-TYPE
    SYNTAX      CIE1000DisplayString (SIZE(0..32))
    MAX-ACCESS  accessible-for-notify
    STATUS      current
    DESCRIPTION
        "Name of DHCP pool."
    ::= { cie1000DhcpServerConfigReservedEntry 1 }

cie1000DhcpServerConfigReservedIpAddress OBJECT-TYPE
    SYNTAX      IpAddress
    MAX-ACCESS  accessible-for-notify
    STATUS      current
    DESCRIPTION
        "Reserved IP address."
    ::= { cie1000DhcpServerConfigReservedEntry 2 }

cie1000DhcpServerConfigReservedIfIndex OBJECT-TYPE
    SYNTAX      CIE1000InterfaceIndex
    MAX-ACCESS  read-write
    STATUS      current
    DESCRIPTION
        "Logical interface number for the interface for which the ip address is
         reserved."
    ::= { cie1000DhcpServerConfigReservedEntry 3 }

cie1000DhcpServerConfigReservedAction OBJECT-TYPE
    SYNTAX      CIE1000RowEditorState
    MAX-ACCESS  read-write
    STATUS      current
    DESCRIPTION
        "Action"
    ::= { cie1000DhcpServerConfigReservedEntry 100 }

cie1000DhcpServerConfigReservedIpTableRowEditor OBJECT IDENTIFIER
    ::= { cie1000DhcpServerConfig 8 }

cie1000DhcpServerConfigReservedIpTableRowEditorPoolName OBJECT-TYPE
    SYNTAX      CIE1000DisplayString (SIZE(0..32))
    MAX-ACCESS  read-write
    STATUS      current
    DESCRIPTION
        "Name of DHCP pool."
    ::= { cie1000DhcpServerConfigReservedIpTableRowEditor 1 }

cie1000DhcpServerConfigReservedIpTableRowEditorIpAddress OBJECT-TYPE
    SYNTAX      IpAddress
    MAX-ACCESS  read-write
    STATUS      current
    DESCRIPTION
        "Reserved IP address."
    ::= { cie1000DhcpServerConfigReservedIpTableRowEditor 2 }

cie1000DhcpServerConfigReservedIpTableRowEditorIfIndex OBJECT-TYPE
    SYNTAX      CIE1000InterfaceIndex
    MAX-ACCESS  read-write
    STATUS      current
    DESCRIPTION
        "Logical interface number for the interface for which the ip address is
         reserved."
    ::= { cie1000DhcpServerConfigReservedIpTableRowEditor 3 }

cie1000DhcpServerConfigReservedIpTableRowEditorAction OBJECT-TYPE
    SYNTAX      CIE1000RowEditorState
    MAX-ACCESS  read-write
    STATUS      current
    DESCRIPTION
        "Action"
    ::= { cie1000DhcpServerConfigReservedIpTableRowEditor 100 }

cie1000DhcpServerStatus OBJECT IDENTIFIER
    ::= { cie1000DhcpServerMibObjects 3 }

cie1000DhcpServerStatusDeclinedTable OBJECT-TYPE
    SYNTAX      SEQUENCE OF CIE1000DhcpServerStatusDeclinedEntry
    MAX-ACCESS  not-accessible
    STATUS      current
    DESCRIPTION
        "This is a table of IP addresses declined by DHCP client."
    ::= { cie1000DhcpServerStatus 1 }

cie1000DhcpServerStatusDeclinedEntry OBJECT-TYPE
    SYNTAX      CIE1000DhcpServerStatusDeclinedEntry
    MAX-ACCESS  not-accessible
    STATUS      current
    DESCRIPTION
        "Each entry has a declined IP address."
    INDEX       { cie1000DhcpServerStatusDeclinedEntryNo }
    ::= { cie1000DhcpServerStatusDeclinedTable 1 }

CIE1000DhcpServerStatusDeclinedEntry ::= SEQUENCE {
    cie1000DhcpServerStatusDeclinedEntryNo      Integer32,
    cie1000DhcpServerStatusDeclinedIpv4Address  IpAddress
}

cie1000DhcpServerStatusDeclinedEntryNo OBJECT-TYPE
    SYNTAX      Integer32 (0..2147483647)
    MAX-ACCESS  accessible-for-notify
    STATUS      current
    DESCRIPTION
        "The number of entry. The number starts from 1."
    ::= { cie1000DhcpServerStatusDeclinedEntry 1 }

cie1000DhcpServerStatusDeclinedIpv4Address OBJECT-TYPE
    SYNTAX      IpAddress
    MAX-ACCESS  read-only
    STATUS      current
    DESCRIPTION
        "IPv4 address declined by DHCP client."
    ::= { cie1000DhcpServerStatusDeclinedEntry 2 }

cie1000DhcpServerStatusStatistics OBJECT IDENTIFIER
    ::= { cie1000DhcpServerStatus 2 }

cie1000DhcpServerStatusStatisticsDiscoverCnt OBJECT-TYPE
    SYNTAX      Unsigned32
    MAX-ACCESS  read-only
    STATUS      current
    DESCRIPTION
        "Number of DHCP DISCOVER messages received."
    ::= { cie1000DhcpServerStatusStatistics 1 }

cie1000DhcpServerStatusStatisticsOfferCnt OBJECT-TYPE
    SYNTAX      Unsigned32
    MAX-ACCESS  read-only
    STATUS      current
    DESCRIPTION
        "Number of DHCP OFFER messages sent."
    ::= { cie1000DhcpServerStatusStatistics 2 }

cie1000DhcpServerStatusStatisticsRequestCnt OBJECT-TYPE
    SYNTAX      Unsigned32
    MAX-ACCESS  read-only
    STATUS      current
    DESCRIPTION
        "Number of DHCP REQUEST messages received."
    ::= { cie1000DhcpServerStatusStatistics 3 }

cie1000DhcpServerStatusStatisticsAckCnt OBJECT-TYPE
    SYNTAX      Unsigned32
    MAX-ACCESS  read-only
    STATUS      current
    DESCRIPTION
        "Number of DHCP ACK messages sent."
    ::= { cie1000DhcpServerStatusStatistics 4 }

cie1000DhcpServerStatusStatisticsNakCnt OBJECT-TYPE
    SYNTAX      Unsigned32
    MAX-ACCESS  read-only
    STATUS      current
    DESCRIPTION
        "Number of DHCP NAK messages sent."
    ::= { cie1000DhcpServerStatusStatistics 5 }

cie1000DhcpServerStatusStatisticsDeclineCnt OBJECT-TYPE
    SYNTAX      Unsigned32
    MAX-ACCESS  read-only
    STATUS      current
    DESCRIPTION
        "Number of DHCP DECLINE messages received."
    ::= { cie1000DhcpServerStatusStatistics 6 }

cie1000DhcpServerStatusStatisticsReleaseCnt OBJECT-TYPE
    SYNTAX      Unsigned32
    MAX-ACCESS  read-only
    STATUS      current
    DESCRIPTION
        "Number of DHCP RELEASE messages received."
    ::= { cie1000DhcpServerStatusStatistics 7 }

cie1000DhcpServerStatusStatisticsInformCnt OBJECT-TYPE
    SYNTAX      Unsigned32
    MAX-ACCESS  read-only
    STATUS      current
    DESCRIPTION
        "Number of DHCP INFORM messages received."
    ::= { cie1000DhcpServerStatusStatistics 8 }

cie1000DhcpServerStatusBindingTable OBJECT-TYPE
    SYNTAX      SEQUENCE OF CIE1000DhcpServerStatusBindingEntry
    MAX-ACCESS  not-accessible
    STATUS      current
    DESCRIPTION
        "This is a table of binding data."
    ::= { cie1000DhcpServerStatus 3 }

cie1000DhcpServerStatusBindingEntry OBJECT-TYPE
    SYNTAX      CIE1000DhcpServerStatusBindingEntry
    MAX-ACCESS  not-accessible
    STATUS      current
    DESCRIPTION
        "Each entry has the binding data."
    INDEX       { cie1000DhcpServerStatusBindingIpAddress }
    ::= { cie1000DhcpServerStatusBindingTable 1 }

CIE1000DhcpServerStatusBindingEntry ::= SEQUENCE {
    cie1000DhcpServerStatusBindingIpAddress             IpAddress,
    cie1000DhcpServerStatusBindingState                 CIE1000DhcpServerBindingStateEnum,
    cie1000DhcpServerStatusBindingType                  CIE1000DhcpServerBindingEnum,
    cie1000DhcpServerStatusBindingPoolName              CIE1000DisplayString,
    cie1000DhcpServerStatusBindingServerId              IpAddress,
    cie1000DhcpServerStatusBindingVlanId                CIE1000Unsigned16,
    cie1000DhcpServerStatusBindingSubnetMask            IpAddress,
    cie1000DhcpServerStatusBindingClientIdentifierType  CIE1000DhcpServerClientIdentifierEnum,
    cie1000DhcpServerStatusBindingClientIdentifierName  CIE1000DisplayString,
    cie1000DhcpServerStatusBindingClientIdentifierMac   MacAddress,
    cie1000DhcpServerStatusBindingMacAddress            MacAddress,
    cie1000DhcpServerStatusBindingLease                 CIE1000DisplayString,
    cie1000DhcpServerStatusBindingTimeToExpire          CIE1000DisplayString
}

cie1000DhcpServerStatusBindingIpAddress OBJECT-TYPE
    SYNTAX      IpAddress
    MAX-ACCESS  accessible-for-notify
    STATUS      current
    DESCRIPTION
        "IP address."
    ::= { cie1000DhcpServerStatusBindingEntry 1 }

cie1000DhcpServerStatusBindingState OBJECT-TYPE
    SYNTAX      CIE1000DhcpServerBindingStateEnum
    MAX-ACCESS  read-only
    STATUS      current
    DESCRIPTION
        "State of binding. none(0) means the binding is not in use. allocated(1)
         means the binding is allocated to the new DHCP client who send
         DHCPDISCOVER. committed(2) means the binding is committed as the DHCP
         process is completed successfully. expired(3) means the lease of the
         binding expired."
    ::= { cie1000DhcpServerStatusBindingEntry 2 }

cie1000DhcpServerStatusBindingType OBJECT-TYPE
    SYNTAX      CIE1000DhcpServerBindingEnum
    MAX-ACCESS  read-only
    STATUS      current
    DESCRIPTION
        "Type of binding. none(0) means the binding is not in use. automatic(1)
         means the binding is mapped to network-type pool. manual(2) means the
         binding is mapped to host-type pool. expired(3) means the lease of the
         binding expired."
    ::= { cie1000DhcpServerStatusBindingEntry 3 }

cie1000DhcpServerStatusBindingPoolName OBJECT-TYPE
    SYNTAX      CIE1000DisplayString (SIZE(0..32))
    MAX-ACCESS  read-only
    STATUS      current
    DESCRIPTION
        "Name of the pool that creates the binding."
    ::= { cie1000DhcpServerStatusBindingEntry 4 }

cie1000DhcpServerStatusBindingServerId OBJECT-TYPE
    SYNTAX      IpAddress
    MAX-ACCESS  read-only
    STATUS      current
    DESCRIPTION
        "IP address of the DHCP server to service the binding."
    ::= { cie1000DhcpServerStatusBindingEntry 5 }

cie1000DhcpServerStatusBindingVlanId OBJECT-TYPE
    SYNTAX      CIE1000Unsigned16
    MAX-ACCESS  read-only
    STATUS      current
    DESCRIPTION
        "The VLAN where the binding works on."
    ::= { cie1000DhcpServerStatusBindingEntry 6 }

cie1000DhcpServerStatusBindingSubnetMask OBJECT-TYPE
    SYNTAX      IpAddress
    MAX-ACCESS  read-only
    STATUS      current
    DESCRIPTION
        "Subnet mask of the DHCP client."
    ::= { cie1000DhcpServerStatusBindingEntry 7 }

cie1000DhcpServerStatusBindingClientIdentifierType OBJECT-TYPE
    SYNTAX      CIE1000DhcpServerClientIdentifierEnum
    MAX-ACCESS  read-only
    STATUS      current
    DESCRIPTION
        "Type of client identifier. DHCP option 61. Specify client's unique
         identifier to be used when the pool is the type of host. none(0) means
         the client identifier type is not defined yet. name(1) means the client
         identifier type is other than hardware. mac(2) means the client
         identifier type is type of MAC address."
    ::= { cie1000DhcpServerStatusBindingEntry 8 }

cie1000DhcpServerStatusBindingClientIdentifierName OBJECT-TYPE
    SYNTAX      CIE1000DisplayString (SIZE(0..64))
    MAX-ACCESS  read-only
    STATUS      current
    DESCRIPTION
        "Client identifier which type is other than hardware. DHCP option 61."
    ::= { cie1000DhcpServerStatusBindingEntry 9 }

cie1000DhcpServerStatusBindingClientIdentifierMac OBJECT-TYPE
    SYNTAX      MacAddress
    MAX-ACCESS  read-only
    STATUS      current
    DESCRIPTION
        "Client's MAC address. DHCP option 61."
    ::= { cie1000DhcpServerStatusBindingEntry 10 }

cie1000DhcpServerStatusBindingMacAddress OBJECT-TYPE
    SYNTAX      MacAddress
    MAX-ACCESS  read-only
    STATUS      current
    DESCRIPTION
        "MAC address of the DHCP client."
    ::= { cie1000DhcpServerStatusBindingEntry 11 }

cie1000DhcpServerStatusBindingLease OBJECT-TYPE
    SYNTAX      CIE1000DisplayString (SIZE(0..64))
    MAX-ACCESS  read-only
    STATUS      current
    DESCRIPTION
        "Lease time of the binding."
    ::= { cie1000DhcpServerStatusBindingEntry 12 }

cie1000DhcpServerStatusBindingTimeToExpire OBJECT-TYPE
    SYNTAX      CIE1000DisplayString (SIZE(0..64))
    MAX-ACCESS  read-only
    STATUS      current
    DESCRIPTION
        "remaining time to expire."
    ::= { cie1000DhcpServerStatusBindingEntry 13 }

cie1000DhcpServerControl OBJECT IDENTIFIER
    ::= { cie1000DhcpServerMibObjects 4 }

cie1000DhcpServerControlStatistics OBJECT IDENTIFIER
    ::= { cie1000DhcpServerControl 1 }

cie1000DhcpServerControlStatisticsClear OBJECT-TYPE
    SYNTAX      TruthValue
    MAX-ACCESS  read-write
    STATUS      current
    DESCRIPTION
        "Clear all statistics."
    ::= { cie1000DhcpServerControlStatistics 1 }

cie1000DhcpServerControlBinding OBJECT IDENTIFIER
    ::= { cie1000DhcpServerControl 2 }

cie1000DhcpServerControlBindingClearByIp OBJECT-TYPE
    SYNTAX      IpAddress
    MAX-ACCESS  read-write
    STATUS      current
    DESCRIPTION
        "Clear binding with the IP address. If 0.0.0.0 then do nothing."
    ::= { cie1000DhcpServerControlBinding 1 }

cie1000DhcpServerControlBindingClearByType OBJECT-TYPE
    SYNTAX      CIE1000DhcpServerBindingEnum
    MAX-ACCESS  read-write
    STATUS      current
    DESCRIPTION
        "Clear binding by binding type. If none(0) then do nothing."
    ::= { cie1000DhcpServerControlBinding 2 }

cie1000DhcpServerMibConformance OBJECT IDENTIFIER
    ::= { cie1000DhcpServerMib 2 }

cie1000DhcpServerMibCompliances OBJECT IDENTIFIER
    ::= { cie1000DhcpServerMibConformance 1 }

cie1000DhcpServerMibGroups OBJECT IDENTIFIER
    ::= { cie1000DhcpServerMibConformance 2 }

cie1000DhcpServerConfigGlobalsInfoGroup OBJECT-GROUP
    OBJECTS     { cie1000DhcpServerConfigGlobalsMode }
    STATUS      current
    DESCRIPTION
        "A collection of objects."
    ::= { cie1000DhcpServerMibGroups 1 }

cie1000DhcpServerConfigVlanTableInfoGroup OBJECT-GROUP
    OBJECTS     { cie1000DhcpServerConfigVlanIfIndex,
                  cie1000DhcpServerConfigVlanMode }
    STATUS      current
    DESCRIPTION
        "A collection of objects."
    ::= { cie1000DhcpServerMibGroups 2 }

cie1000DhcpServerConfigExcludedTableInfoGroup OBJECT-GROUP
    OBJECTS     { cie1000DhcpServerConfigExcludedLowIpAddress,
                  cie1000DhcpServerConfigExcludedHighIpAddress,
                  cie1000DhcpServerConfigExcludedAction }
    STATUS      current
    DESCRIPTION
        "A collection of objects."
    ::= { cie1000DhcpServerMibGroups 3 }

cie1000DhcpServerConfigExcludedIpTableRowEditorInfoGroup OBJECT-GROUP
    OBJECTS     {                   cie1000DhcpServerConfigExcludedIpTableRowEditorLowIpAddress,
                  cie1000DhcpServerConfigExcludedIpTableRowEditorHighIpAddress,
                  cie1000DhcpServerConfigExcludedIpTableRowEditorAction }
    STATUS      current
    DESCRIPTION
        "A collection of objects."
    ::= { cie1000DhcpServerMibGroups 4 }

cie1000DhcpServerConfigPoolTableInfoGroup OBJECT-GROUP
    OBJECTS     { cie1000DhcpServerConfigPoolPoolName,
                  cie1000DhcpServerConfigPoolPoolType,
                  cie1000DhcpServerConfigPoolIpv4Address,
                  cie1000DhcpServerConfigPoolSubnetMask,
                  cie1000DhcpServerConfigPoolSubnetBroadcast,
                  cie1000DhcpServerConfigPoolLeaseDay,
                  cie1000DhcpServerConfigPoolLeaseHour,
                  cie1000DhcpServerConfigPoolLeaseMinute,
                  cie1000DhcpServerConfigPoolDomainName,
                  cie1000DhcpServerConfigPoolDefaultRouter1,
                  cie1000DhcpServerConfigPoolDefaultRouter2,
                  cie1000DhcpServerConfigPoolDefaultRouter3,
                  cie1000DhcpServerConfigPoolDefaultRouter4,
                  cie1000DhcpServerConfigPoolDnsServer1,
                  cie1000DhcpServerConfigPoolDnsServer2,
                  cie1000DhcpServerConfigPoolDnsServer3,
                  cie1000DhcpServerConfigPoolDnsServer4,
                  cie1000DhcpServerConfigPoolNtpServer1,
                  cie1000DhcpServerConfigPoolNtpServer2,
                  cie1000DhcpServerConfigPoolNtpServer3,
                  cie1000DhcpServerConfigPoolNtpServer4,
                  cie1000DhcpServerConfigPoolNetbiosNodeType,
                  cie1000DhcpServerConfigPoolNetbiosScope,
                  cie1000DhcpServerConfigPoolNetbiosNameServer1,
                  cie1000DhcpServerConfigPoolNetbiosNameServer2,
                  cie1000DhcpServerConfigPoolNetbiosNameServer3,
                  cie1000DhcpServerConfigPoolNetbiosNameServer4,
                  cie1000DhcpServerConfigPoolNisDomainName,
                  cie1000DhcpServerConfigPoolNisServer1,
                  cie1000DhcpServerConfigPoolNisServer2,
                  cie1000DhcpServerConfigPoolNisServer3,
                  cie1000DhcpServerConfigPoolNisServer4,
                  cie1000DhcpServerConfigPoolClientIdentifierType,
                  cie1000DhcpServerConfigPoolClientIdentifierName,
                  cie1000DhcpServerConfigPoolClientIdentifierMac,
                  cie1000DhcpServerConfigPoolClientHardwareAddress,
                  cie1000DhcpServerConfigPoolClientName,
                  cie1000DhcpServerConfigPoolVendorClassId1,
                  cie1000DhcpServerConfigPoolVendorSpecificInfo1,
                  cie1000DhcpServerConfigPoolVendorClassId2,
                  cie1000DhcpServerConfigPoolVendorSpecificInfo2,
                  cie1000DhcpServerConfigPoolVendorClassId3,
                  cie1000DhcpServerConfigPoolVendorSpecificInfo3,
                  cie1000DhcpServerConfigPoolVendorClassId4,
                  cie1000DhcpServerConfigPoolVendorSpecificInfo4,
                  cie1000DhcpServerConfigPoolAction }
    STATUS      current
    DESCRIPTION
        "A collection of objects."
    ::= { cie1000DhcpServerMibGroups 5 }

cie1000DhcpServerConfigPoolTableRowEditorInfoGroup OBJECT-GROUP
    OBJECTS     { cie1000DhcpServerConfigPoolTableRowEditorPoolName,
                  cie1000DhcpServerConfigPoolTableRowEditorPoolType,
                  cie1000DhcpServerConfigPoolTableRowEditorIpv4Address,
                  cie1000DhcpServerConfigPoolTableRowEditorSubnetMask,
                  cie1000DhcpServerConfigPoolTableRowEditorSubnetBroadcast,
                  cie1000DhcpServerConfigPoolTableRowEditorLeaseDay,
                  cie1000DhcpServerConfigPoolTableRowEditorLeaseHour,
                  cie1000DhcpServerConfigPoolTableRowEditorLeaseMinute,
                  cie1000DhcpServerConfigPoolTableRowEditorDomainName,
                  cie1000DhcpServerConfigPoolTableRowEditorDefaultRouter1,
                  cie1000DhcpServerConfigPoolTableRowEditorDefaultRouter2,
                  cie1000DhcpServerConfigPoolTableRowEditorDefaultRouter3,
                  cie1000DhcpServerConfigPoolTableRowEditorDefaultRouter4,
                  cie1000DhcpServerConfigPoolTableRowEditorDnsServer1,
                  cie1000DhcpServerConfigPoolTableRowEditorDnsServer2,
                  cie1000DhcpServerConfigPoolTableRowEditorDnsServer3,
                  cie1000DhcpServerConfigPoolTableRowEditorDnsServer4,
                  cie1000DhcpServerConfigPoolTableRowEditorNtpServer1,
                  cie1000DhcpServerConfigPoolTableRowEditorNtpServer2,
                  cie1000DhcpServerConfigPoolTableRowEditorNtpServer3,
                  cie1000DhcpServerConfigPoolTableRowEditorNtpServer4,
                  cie1000DhcpServerConfigPoolTableRowEditorNetbiosNodeType,
                  cie1000DhcpServerConfigPoolTableRowEditorNetbiosScope,
                  cie1000DhcpServerConfigPoolTableRowEditorNetbiosNameServer1,
                  cie1000DhcpServerConfigPoolTableRowEditorNetbiosNameServer2,
                  cie1000DhcpServerConfigPoolTableRowEditorNetbiosNameServer3,
                  cie1000DhcpServerConfigPoolTableRowEditorNetbiosNameServer4,
                  cie1000DhcpServerConfigPoolTableRowEditorNisDomainName,
                  cie1000DhcpServerConfigPoolTableRowEditorNisServer1,
                  cie1000DhcpServerConfigPoolTableRowEditorNisServer2,
                  cie1000DhcpServerConfigPoolTableRowEditorNisServer3,
                  cie1000DhcpServerConfigPoolTableRowEditorNisServer4,
                  cie1000DhcpServerConfigPoolTableRowEditorClientIdentifierType,
                  cie1000DhcpServerConfigPoolTableRowEditorClientIdentifierName,
                  cie1000DhcpServerConfigPoolTableRowEditorClientIdentifierMac,
                  cie1000DhcpServerConfigPoolTableRowEditorClientHardwareAddress,
                  cie1000DhcpServerConfigPoolTableRowEditorClientName,
                  cie1000DhcpServerConfigPoolTableRowEditorVendorClassId1,
                  cie1000DhcpServerConfigPoolTableRowEditorVendorSpecificInfo1,
                  cie1000DhcpServerConfigPoolTableRowEditorVendorClassId2,
                  cie1000DhcpServerConfigPoolTableRowEditorVendorSpecificInfo2,
                  cie1000DhcpServerConfigPoolTableRowEditorVendorClassId3,
                  cie1000DhcpServerConfigPoolTableRowEditorVendorSpecificInfo3,
                  cie1000DhcpServerConfigPoolTableRowEditorVendorClassId4,
                  cie1000DhcpServerConfigPoolTableRowEditorVendorSpecificInfo4,
                  cie1000DhcpServerConfigPoolTableRowEditorAction }
    STATUS      current
    DESCRIPTION
        "A collection of objects."
    ::= { cie1000DhcpServerMibGroups 6 }

cie1000DhcpServerConfigReservedTableInfoGroup OBJECT-GROUP
    OBJECTS     { cie1000DhcpServerConfigReservedPoolName,
                  cie1000DhcpServerConfigReservedIpAddress,
                  cie1000DhcpServerConfigReservedIfIndex,
                  cie1000DhcpServerConfigReservedAction }
    STATUS      current
    DESCRIPTION
        "A collection of objects."
    ::= { cie1000DhcpServerMibGroups 7 }

cie1000DhcpServerConfigReservedIpTableRowEditorInfoGroup OBJECT-GROUP
    OBJECTS     {                   cie1000DhcpServerConfigReservedIpTableRowEditorPoolName,
                  cie1000DhcpServerConfigReservedIpTableRowEditorIpAddress,
                  cie1000DhcpServerConfigReservedIpTableRowEditorIfIndex,
                  cie1000DhcpServerConfigReservedIpTableRowEditorAction }
    STATUS      current
    DESCRIPTION
        "A collection of objects."
    ::= { cie1000DhcpServerMibGroups 8 }

cie1000DhcpServerStatusDeclinedTableInfoGroup OBJECT-GROUP
    OBJECTS     { cie1000DhcpServerStatusDeclinedEntryNo,
                  cie1000DhcpServerStatusDeclinedIpv4Address }
    STATUS      current
    DESCRIPTION
        "A collection of objects."
    ::= { cie1000DhcpServerMibGroups 9 }

cie1000DhcpServerStatusStatisticsInfoGroup OBJECT-GROUP
    OBJECTS     { cie1000DhcpServerStatusStatisticsDiscoverCnt,
                  cie1000DhcpServerStatusStatisticsOfferCnt,
                  cie1000DhcpServerStatusStatisticsRequestCnt,
                  cie1000DhcpServerStatusStatisticsAckCnt,
                  cie1000DhcpServerStatusStatisticsNakCnt,
                  cie1000DhcpServerStatusStatisticsDeclineCnt,
                  cie1000DhcpServerStatusStatisticsReleaseCnt,
                  cie1000DhcpServerStatusStatisticsInformCnt }
    STATUS      current
    DESCRIPTION
        "A collection of objects."
    ::= { cie1000DhcpServerMibGroups 10 }

cie1000DhcpServerStatusBindingTableInfoGroup OBJECT-GROUP
    OBJECTS     { cie1000DhcpServerStatusBindingIpAddress,
                  cie1000DhcpServerStatusBindingState,
                  cie1000DhcpServerStatusBindingType,
                  cie1000DhcpServerStatusBindingPoolName,
                  cie1000DhcpServerStatusBindingServerId,
                  cie1000DhcpServerStatusBindingVlanId,
                  cie1000DhcpServerStatusBindingSubnetMask,
                  cie1000DhcpServerStatusBindingClientIdentifierType,
                  cie1000DhcpServerStatusBindingClientIdentifierName,
                  cie1000DhcpServerStatusBindingClientIdentifierMac,
                  cie1000DhcpServerStatusBindingMacAddress,
                  cie1000DhcpServerStatusBindingLease,
                  cie1000DhcpServerStatusBindingTimeToExpire }
    STATUS      current
    DESCRIPTION
        "A collection of objects."
    ::= { cie1000DhcpServerMibGroups 11 }

cie1000DhcpServerControlStatisticsInfoGroup OBJECT-GROUP
    OBJECTS     { cie1000DhcpServerControlStatisticsClear }
    STATUS      current
    DESCRIPTION
        "A collection of objects."
    ::= { cie1000DhcpServerMibGroups 12 }

cie1000DhcpServerControlBindingInfoGroup OBJECT-GROUP
    OBJECTS     { cie1000DhcpServerControlBindingClearByIp,
                  cie1000DhcpServerControlBindingClearByType }
    STATUS      current
    DESCRIPTION
        "A collection of objects."
    ::= { cie1000DhcpServerMibGroups 13 }

cie1000DhcpServerMibCompliance MODULE-COMPLIANCE
    STATUS      current
    DESCRIPTION
        "The compliance statement for the implementation."

    MODULE      -- this module

    MANDATORY-GROUPS { cie1000DhcpServerConfigGlobalsInfoGroup,
                       cie1000DhcpServerConfigVlanTableInfoGroup,
                       cie1000DhcpServerConfigExcludedTableInfoGroup,
                       cie1000DhcpServerConfigExcludedIpTableRowEditorInfoGroup,
                       cie1000DhcpServerConfigPoolTableInfoGroup,
                       cie1000DhcpServerConfigPoolTableRowEditorInfoGroup,
                       cie1000DhcpServerConfigReservedTableInfoGroup,
                       cie1000DhcpServerConfigReservedIpTableRowEditorInfoGroup,
                       cie1000DhcpServerStatusDeclinedTableInfoGroup,
                       cie1000DhcpServerStatusStatisticsInfoGroup,
                       cie1000DhcpServerStatusBindingTableInfoGroup,
                       cie1000DhcpServerControlStatisticsInfoGroup,
                       cie1000DhcpServerControlBindingInfoGroup }

    ::= { cie1000DhcpServerMibCompliances 1 }

END
