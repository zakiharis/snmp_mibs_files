-- *****************************************************************
-- CISCO-ITP-GSP2-CAPABILITY.my:  ITP Gateway Signalling Point 
--                           Additional Information capability MIB
--
-- March 2003, Shekhar Acharya, John Linton
--
-- Copyright (c) 2003 by cisco Systems, Inc.
-- All rights reserved.
-- *****************************************************************
CISCO-ITP-GSP2-CAPABILITY DEFINITIONS ::= BEGIN

IMPORTS
        MODULE-IDENTITY
                FROM SNMPv2-SMI
                
        AGENT-CAPABILITIES
                FROM SNMPv2-CONF
                
        ciscoAgentCapability
                FROM CISCO-SMI; 
                

ciscoGsp2Capability MODULE-IDENTITY
        LAST-UPDATED    "200408250000Z"
        ORGANIZATION    "Cisco Systems, Inc."
        CONTACT-INFO
                        "Cisco Systems
                         Customer Service
                        
                         Postal: 170 West Tasman Drive
                                 San Jose, CA  95134
                                 USA
                        
                         Tel: +1 800 553-NETS
                        
                         E-mail: cs-ss7@cisco.com"
        DESCRIPTION
                "Agent capabilities for the CISCO-ITP-GSP2-MIB."
                
        REVISION        "200408250000Z"
        DESCRIPTION
             "Added support for objects to indicate whether device 
              support non-stop operations feature.  Added 
              ciscoGsp2CapabilityV12R023000SW1 agent capability 
              statement."
                        
        REVISION        "200311240000Z"
        DESCRIPTION
           "Added ciscoGsp2Mtp3ErrorsGroup.
            Added ciscoGsp2CapabilityV12R022004SW agent capability 
            statement. This capability contains groups from 
            ciscoGsp2CapabilityV12R0204MB4 agent capability 
            statement as well as ciscoGsp2Mtp3ErrorsGroup."
                        
        REVISION        "200307170000Z"
        DESCRIPTION
                "Initial version of this MIB module."
        ::= { ciscoAgentCapability 307 }

ciscoGsp2CapabilityV12R0204MB4 AGENT-CAPABILITIES

        PRODUCT-RELEASE "Cisco IOS 12.2(4)MB10"
        STATUS          current
        DESCRIPTION
           "IOS 12.2(4)MB10 Cisco CISCO-ITP-GSP2-MIB.my
            User Agent MIB capabilities."

        SUPPORTS    CISCO-ITP-GSP2-MIB
        INCLUDES    { 
                           ciscoGsp2EventsGroup, 
                           ciscoGsp2QosGroup,
                           ciscoGsp2LocalPeerGroup
                    }  
                    
--      Table cgsp2EventAsTable 
        VARIATION    cgsp2EventAsText
        ACCESS       not-implemented
        DESCRIPTION "Not implemented."
        
        VARIATION    cgsp2EventAsTimestamp
        ACCESS       not-implemented
        DESCRIPTION "Not implemented."
        

--      Table cgsp2EventAspTable
        VARIATION    cgsp2EventAspText
        ACCESS       not-implemented
        DESCRIPTION "Not implemented."
        
        VARIATION    cgsp2EventAspTimestamp
        ACCESS       not-implemented
        DESCRIPTION "Not implemented."
        
        
--      Table cgsp2EventPcTable
        VARIATION    cgsp2EventPcText
        ACCESS       not-implemented
        DESCRIPTION "Not implemented."
        
        VARIATION   cgsp2EventPcTimestamp  
        ACCESS       not-implemented
        DESCRIPTION "Not implemented."
::= { ciscoGsp2Capability 1 }


ciscoGsp2CapabilityV12R022004SW AGENT-CAPABILITIES

        PRODUCT-RELEASE "Cisco IOS 12.2(20.4)SW"
        STATUS          current
        DESCRIPTION
           "IOS 12.2(20.4)SW Cisco CISCO-ITP-GSP2-MIB.my
            User Agent MIB capabilities."

        SUPPORTS    CISCO-ITP-GSP2-MIB
        INCLUDES    { 
                           ciscoGsp2EventsGroup, 
                           ciscoGsp2QosGroup,
                           ciscoGsp2LocalPeerGroup,
                           ciscoGsp2Mtp3ErrorsGroup
                    }  
                    
--      Table cgsp2EventAsTable 
        VARIATION    cgsp2EventAsText
        ACCESS       not-implemented
        DESCRIPTION "Not implemented."
        
        VARIATION    cgsp2EventAsTimestamp
        ACCESS       not-implemented
        DESCRIPTION "Not implemented."
        

--      Table cgsp2EventAspTable
        VARIATION    cgsp2EventAspText
        ACCESS       not-implemented
        DESCRIPTION "Not implemented."
        
        VARIATION    cgsp2EventAspTimestamp
        ACCESS       not-implemented
        DESCRIPTION "Not implemented."
        
        
--      Table cgsp2EventPcTable
        VARIATION    cgsp2EventPcText
        ACCESS       not-implemented
        DESCRIPTION "Not implemented."
        
        VARIATION   cgsp2EventPcTimestamp  
        ACCESS       not-implemented
        DESCRIPTION "Not implemented."
::= { ciscoGsp2Capability 2 }
        
ciscoGsp2CapabilityV12R022300SW1 AGENT-CAPABILITIES

        PRODUCT-RELEASE "Cisco IOS 12.2(23)SW1"
        STATUS          current
        DESCRIPTION
           "IOS 12.2(23)SW1 Cisco CISCO-ITP-GSP2-MIB.my
            User Agent MIB capabilities."

        SUPPORTS    CISCO-ITP-GSP2-MIB
        INCLUDES    { 
                           ciscoGsp2EventsGroup, 
                           ciscoGsp2QosGroup,
                           ciscoGsp2LocalPeerGroup,
                           ciscoGsp2Mtp3ErrorsGroup,
                           ciscoGsp2OperationGroup
                    }  
                    
--      Table cgsp2EventAsTable 
        VARIATION    cgsp2EventAsText
        ACCESS       not-implemented
        DESCRIPTION "Not implemented."
        
        VARIATION    cgsp2EventAsTimestamp
        ACCESS       not-implemented
        DESCRIPTION "Not implemented."
        

--      Table cgsp2EventAspTable
        VARIATION    cgsp2EventAspText
        ACCESS       not-implemented
        DESCRIPTION "Not implemented."
        
        VARIATION    cgsp2EventAspTimestamp
        ACCESS       not-implemented
        DESCRIPTION "Not implemented."
        
        
--      Table cgsp2EventPcTable
        VARIATION    cgsp2EventPcText
        ACCESS       not-implemented
        DESCRIPTION "Not implemented."
        
        VARIATION   cgsp2EventPcTimestamp  
        ACCESS       not-implemented
        DESCRIPTION "Not implemented."
::= { ciscoGsp2Capability 3 }

END
