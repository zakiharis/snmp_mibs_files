CISCO-PRODUCTS-MIB-CORRECTIONS DEFINITIONS ::= BEGIN

IMPORTS
    MODULE-IDENTITY
        FROM SNMPv2-SMI
    ciscoModules,
    ciscoProducts
        FROM CISCO-SMI;

ciscoProductsMIBCorrections MODULE-IDENTITY
    LAST-UPDATED "201411270000Z"
    ORGANIZATION "The Netdisco project"
    CONTACT-INFO "
        Mailing list: netdisco-users@lists.sourceforge.net
        IRC: #netdisco on Freenode
    "
    DESCRIPTION "
        This module augments the CISCO-PRODUCTS-MIB. It
        defines additional object identifiers that are
        assigned to various hardware platforms, and hence are
        returned as values for sysObjectID.
    "
        REVISION "201411270000Z"
        DESCRIPTION "
            Initial version for the netdisco-mibs distribution.
            Added OIDs for the Catalyst 3650 platform.
        "
    ::= { ciscoModules 65535 }

-- Objects for the Catalyst 3650 series.
-- CISCO-PRODUCTS-MIB dated 20140415 through at least 20141106 don't have these, some MIB revisions
-- had objects for the 3650 but with incorrect OIDs (different from what the devices actually reported).
-- Reaching out to Cisco didn't yield any results in the past 7 months...
-- Correct values determined from a Cisco Prime LMS support document
catalyst365024TS                     OBJECT IDENTIFIER ::= { ciscoProducts 1823 } -- WS-C3650-24TS Catalyst 3650 Series Switch with 24 GE and 4 GE Interfaces
catalyst365048TS                     OBJECT IDENTIFIER ::= { ciscoProducts 1824 } -- WS-C3650-48TS Catalyst 3650 Series Switch with 48 GE and 4 GE Interfaces
catalyst365024PS                     OBJECT IDENTIFIER ::= { ciscoProducts 1825 } -- WS-C3650-24PS Catalyst 3650 Series Switch with 24 GE POE and 4 GE Interfaces
catalyst365048PS                     OBJECT IDENTIFIER ::= { ciscoProducts 1826 } -- WS-C3650-48PS Catalyst 3650 Series Switch with 48 GE POE and 4 GE Interfaces
catalyst365024TD                     OBJECT IDENTIFIER ::= { ciscoProducts 1827 } -- WS-C3650-24TD Catalyst 3650 Series Switch with 24 GE and 2GE+2TenGE Interfaces
catalyst365048TD                     OBJECT IDENTIFIER ::= { ciscoProducts 1828 } -- WS-C3650-48TD Catalyst 3650 Series Switch with 48 GE and 2GE+2TenGE Interfaces
catalyst365024PD                     OBJECT IDENTIFIER ::= { ciscoProducts 1829 } -- WS-C3650-24PD Catalyst 3650 Series Switch with 24 GE POE and 2GE+2TenGE Interfaces
catalyst365048PD                     OBJECT IDENTIFIER ::= { ciscoProducts 1830 } -- WS-C3650-48PD Catalyst 3650 Series Switch with 48 GE POE and 2GE+2TenGE Interfaces


END
