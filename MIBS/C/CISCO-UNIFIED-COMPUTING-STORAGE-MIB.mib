-- *********************************************************************
-- CISCO-UNIFIED-COMPUTING-STORAGE-MIB.my
-- 
-- MIB representation of the Cisco Unified Computing System
-- STORAGE management information model package
-- 
-- Created October 2017 by Charles Bullis
-- 
-- Copyright (c) 2005-2017 Cisco Systems, Inc. All rights reserved.
-- 
-- *********************************************************************

CISCO-UNIFIED-COMPUTING-STORAGE-MIB DEFINITIONS ::= BEGIN

IMPORTS
    MODULE-IDENTITY,
    OBJECT-TYPE,
    Counter32,
    Gauge32,
    TimeTicks,
    Counter64,
    Unsigned32
        FROM SNMPv2-SMI
    TEXTUAL-CONVENTION,
    RowPointer,
    DateAndTime,
    DisplayString,
    MacAddress,
    TimeInterval,
    TimeStamp,
    TruthValue
        FROM SNMPv2-TC
    SnmpAdminString
        FROM SNMP-FRAMEWORK-MIB
    InetAddressIPv4,
    InetAddressIPv6
        FROM INET-ADDRESS-MIB
    ciscoMgmt
        FROM CISCO-SMI
    CiscoNetworkAddress,
    Unsigned64,
    CiscoInetAddressMask,
    CiscoAlarmSeverity,
    TimeIntervalSec
        FROM CISCO-TC
    ciscoUnifiedComputingMIBObjects,
    CucsManagedObjectId,
    CucsManagedObjectDn
        FROM CISCO-UNIFIED-COMPUTING-MIB
    CucsAaaConfigState,
    CucsConditionRemoteInvRslt,
    CucsEquipmentOperability,
    CucsEquipmentPowerState,
    CucsEquipmentPresence,
    CucsEquipmentSensorThresholdStatus,
    CucsFabricZoningState,
    CucsFsmCompletion,
    CucsFsmFlags,
    CucsFsmFsmStageStatus,
    CucsFsmLifecycle,
    CucsLstorageBootDevice,
    CucsPolicyPolicyOwner,
    CucsSesScsiDriveStatus,
    CucsStorageAccessType,
    CucsStorageActualWriteType,
    CucsStorageAdminActionTrigger,
    CucsStorageAdminActionType,
    CucsStorageAdminCtrlActionType,
    CucsStorageAdminState,
    CucsStorageAlarmType,
    CucsStorageBatteryType,
    CucsStorageBbuStatus,
    CucsStorageBootableType,
    CucsStorageCacheType,
    CucsStorageConfigCheckPoint,
    CucsStorageConfigState,
    CucsStorageConfiguration,
    CucsStorageConfiguredWriteType,
    CucsStorageConnectionProtocol,
    CucsStorageControllerControllerFlags,
    CucsStorageControllerFaultMonitoring,
    CucsStorageControllerFlags,
    CucsStorageControllerId,
    CucsStorageControllerJBODMode,
    CucsStorageControllerMode,
    CucsStorageControllerPinnedCacheStatus,
    CucsStorageControllerRefControllerType,
    CucsStorageControllerStatus,
    CucsStorageControllerSubType,
    CucsStorageControllerType,
    CucsStorageDeployAction,
    CucsStorageDiskEnvStatsHistThresholded,
    CucsStorageDiskEnvStatsThresholded,
    CucsStorageDiskRole,
    CucsStorageDisklessAction,
    CucsStorageDriveFlags,
    CucsStorageEnclosureAdminState,
    CucsStorageEnclosureAssociation,
    CucsStorageEnclosureDiskSlotEpAutoZoneCause,
    CucsStorageEnclosureDiskSlotEpOwnership,
    CucsStorageEnclosureFsmCurrentFsm,
    CucsStorageEnclosureFsmStageName,
    CucsStorageEnclosureFsmTaskItem,
    CucsStorageEpAccess,
    CucsStorageEpLinkState,
    CucsStorageEtherIfVlanType,
    CucsStorageExpanderState,
    CucsStorageFFCardHealth,
    CucsStorageFFCardMode,
    CucsStorageFFCardSizeMismatch,
    CucsStorageFFCardState,
    CucsStorageFFCardSync,
    CucsStorageFFCardWriteEnable,
    CucsStorageFFControllerHealth,
    CucsStorageFFControllerState,
    CucsStorageFFDriveRemovable,
    CucsStorageFFDriveState,
    CucsStorageFFDriveType,
    CucsStorageFFDriveVisible,
    CucsStorageFFFormatRunning,
    CucsStorageFFHasError,
    CucsStorageFFRAIDHealth,
    CucsStorageFFRAIDState,
    CucsStorageFFRWType,
    CucsStorageFFRaidSyncSupport,
    CucsStorageFFSlotENUM,
    CucsStorageFFType,
    CucsStorageFcZoningType,
    CucsStorageFileSystemStatus,
    CucsStorageFlexFlashControllerFsmCurrentFsm,
    CucsStorageFlexFlashControllerFsmStageName,
    CucsStorageFlexFlashControllerFsmTaskItem,
    CucsStorageFlexFlashControllerId,
    CucsStorageHddMotherBoardTempStatsHistThresholded,
    CucsStorageHddMotherBoardTempStatsThresholded,
    CucsStorageIOType,
    CucsStorageIniGroupOperProtocol,
    CucsStorageIniGroupOwner,
    CucsStorageIniGroupProtocol,
    CucsStorageKeyType,
    CucsStorageLearnCycleRequested,
    CucsStorageLearnMode,
    CucsStorageLinkSpeed,
    CucsStorageLocalDiskConfigFlexFlashRAIDReportingState,
    CucsStorageLocalDiskConfigFlexFlashState,
    CucsStorageLocalDiskDiscoveredPath,
    CucsStorageLocalDiskFsmCurrentFsm,
    CucsStorageLocalDiskFsmStageName,
    CucsStorageLocalDiskFsmTaskFlags,
    CucsStorageLocalDiskFsmTaskItem,
    CucsStorageLocalDiskMode,
    CucsStorageLunType,
    CucsStorageMiniStorageId,
    CucsStorageNvmeStatsHistThresholded,
    CucsStorageNvmeStatsThresholded,
    CucsStorageOnBoardMemoryPresent,
    CucsStorageOnboardDeviceType,
    CucsStorageOperState,
    CucsStorageOperatingModeType,
    CucsStorageOperationRequestType,
    CucsStorageOperationState,
    CucsStorageOperationStateType,
    CucsStorageOperationType,
    CucsStorageOptionRomBootStatus,
    CucsStoragePDriveStatus,
    CucsStoragePhysicalHolder,
    CucsStoragePowerState,
    CucsStorageProtocol,
    CucsStorageRaidBatteryOperabilityQualifier,
    CucsStorageReadType,
    CucsStorageSasLinkDescriptorControllerType,
    CucsStorageSasUpLinkControllerType,
    CucsStorageSelectionDecisionType,
    CucsStorageSelectionResultType,
    CucsStorageSsdHealthStatsHistThresholded,
    CucsStorageSsdHealthStatsThresholded,
    CucsStorageSupportedControllerOp,
    CucsStorageSupportedLocalDiskOp,
    CucsStorageSupportedRaidBatteryOp,
    CucsStorageSupportedStripSizeBitmask,
    CucsStorageSupportedVirtualDriveOp,
    CucsStorageSystemFsmCurrentFsm,
    CucsStorageSystemFsmStageName,
    CucsStorageSystemFsmTaskItem,
    CucsStorageTargetPath,
    CucsStorageTechnology,
    CucsStorageUnitOperState,
    CucsStorageVDriveState,
    CucsStorageVdChangeQualifierType,
    CucsStorageVdMemberConfigQualifierType,
    CucsStorageVirtualDriveRefAdminState,
    CucsStorageVsanRefSwitchId,
    CucsVnicConfigIssues
        FROM CISCO-UNIFIED-COMPUTING-TC-MIB;

cucsStorageObjects MODULE-IDENTITY
    LAST-UPDATED    "201710060000Z"
    ORGANIZATION    "Cisco Systems Inc."
    CONTACT-INFO
        "Cisco Systems
        Customer Service
        
        Postal: 170 W Tasman Drive
        San Jose, CA  95134
        USA
        
        Tel: +1 800 553 -NETS
        
        E-mail: cs-san@cisco.com, cs-lan-switch-snmp@cisco.com"
    DESCRIPTION
        "MIB representation of the Cisco Unified Computing System
        STORAGE management information model package"
    ::= { ciscoUnifiedComputingMIBObjects 45 }

cucsStorageAuthKeyTable OBJECT-TYPE
    SYNTAX           SEQUENCE OF CucsStorageAuthKeyEntry
    MAX-ACCESS       not-accessible
    STATUS           current
    DESCRIPTION
        "Cisco UCS storage:AuthKey managed object table"
    ::= { cucsStorageObjects 14 }

cucsStorageAuthKeyEntry OBJECT-TYPE
    SYNTAX           CucsStorageAuthKeyEntry
    MAX-ACCESS       not-accessible
    STATUS           current
    DESCRIPTION
        "Entry for the cucsStorageAuthKeyTable table."
    INDEX { cucsStorageAuthKeyInstanceId }
    ::= { cucsStorageAuthKeyTable 1 }

CucsStorageAuthKeyEntry ::= SEQUENCE {
    cucsStorageAuthKeyInstanceId                                     CucsManagedObjectId,
    cucsStorageAuthKeyDn                                             CucsManagedObjectDn,
    cucsStorageAuthKeyRn                                             SnmpAdminString,
    cucsStorageAuthKeyDescr                                          SnmpAdminString,
    cucsStorageAuthKeyIntId                                          SnmpAdminString,
    cucsStorageAuthKeyName                                           SnmpAdminString,
    cucsStorageAuthKeyPassword                                       SnmpAdminString,
    cucsStorageAuthKeyPolicyLevel                                    Gauge32,
    cucsStorageAuthKeyPolicyOwner                                    CucsPolicyPolicyOwner,
    cucsStorageAuthKeyType                                           CucsStorageKeyType,
    cucsStorageAuthKeyUserId                                         SnmpAdminString
}

cucsStorageAuthKeyInstanceId OBJECT-TYPE
    SYNTAX       CucsManagedObjectId
    MAX-ACCESS   not-accessible
    STATUS       current
    DESCRIPTION
        "Instance identifier of the managed object."
    ::= { cucsStorageAuthKeyEntry 1 }

cucsStorageAuthKeyDn OBJECT-TYPE
    SYNTAX       CucsManagedObjectDn
    MAX-ACCESS   read-only
    STATUS       current
    DESCRIPTION
        "Cisco UCS storage:AuthKey:dn managed object property"
    ::= { cucsStorageAuthKeyEntry 2 }

cucsStorageAuthKeyRn OBJECT-TYPE
    SYNTAX       SnmpAdminString
    MAX-ACCESS   read-only
    STATUS       current
    DESCRIPTION
        "Cisco UCS storage:AuthKey:rn managed object property"
    ::= { cucsStorageAuthKeyEntry 3 }

cucsStorageAuthKeyDescr OBJECT-TYPE
    SYNTAX       SnmpAdminString
    MAX-ACCESS   read-only
    STATUS       current
    DESCRIPTION
        "Cisco UCS storage:AuthKey:descr managed object property"
    ::= { cucsStorageAuthKeyEntry 4 }

cucsStorageAuthKeyIntId OBJECT-TYPE
    SYNTAX       SnmpAdminString
    MAX-ACCESS   read-only
    STATUS       current
    DESCRIPTION
        "Cisco UCS storage:AuthKey:intId managed object property"
    ::= { cucsStorageAuthKeyEntry 5 }

cucsStorageAuthKeyName OBJECT-TYPE
    SYNTAX       SnmpAdminString
    MAX-ACCESS   read-only
    STATUS       current
    DESCRIPTION
        "Cisco UCS storage:AuthKey:name managed object property"
    ::= { cucsStorageAuthKeyEntry 6 }

cucsStorageAuthKeyPassword OBJECT-TYPE
    SYNTAX       SnmpAdminString
    MAX-ACCESS   read-only
    STATUS       current
    DESCRIPTION
        "Cisco UCS storage:AuthKey:password managed object property"
    ::= { cucsStorageAuthKeyEntry 7 }

cucsStorageAuthKeyPolicyLevel OBJECT-TYPE
    SYNTAX       Gauge32
    MAX-ACCESS   read-only
    STATUS       current
    DESCRIPTION
        "Cisco UCS storage:AuthKey:policyLevel managed object property"
    ::= { cucsStorageAuthKeyEntry 8 }

cucsStorageAuthKeyPolicyOwner OBJECT-TYPE
    SYNTAX       CucsPolicyPolicyOwner
    MAX-ACCESS   read-only
    STATUS       current
    DESCRIPTION
        "Cisco UCS storage:AuthKey:policyOwner managed object property"
    ::= { cucsStorageAuthKeyEntry 9 }

cucsStorageAuthKeyType OBJECT-TYPE
    SYNTAX       CucsStorageKeyType
    MAX-ACCESS   read-only
    STATUS       current
    DESCRIPTION
        "Cisco UCS storage:AuthKey:type managed object property"
    ::= { cucsStorageAuthKeyEntry 10 }

cucsStorageAuthKeyUserId OBJECT-TYPE
    SYNTAX       SnmpAdminString
    MAX-ACCESS   read-only
    STATUS       current
    DESCRIPTION
        "Cisco UCS storage:AuthKey:userId managed object property"
    ::= { cucsStorageAuthKeyEntry 11 }

cucsStorageConnectionDefTable OBJECT-TYPE
    SYNTAX           SEQUENCE OF CucsStorageConnectionDefEntry
    MAX-ACCESS       not-accessible
    STATUS           current
    DESCRIPTION
        "Cisco UCS storage:ConnectionDef managed object table"
    ::= { cucsStorageObjects 15 }

cucsStorageConnectionDefEntry OBJECT-TYPE
    SYNTAX           CucsStorageConnectionDefEntry
    MAX-ACCESS       not-accessible
    STATUS           current
    DESCRIPTION
        "Entry for the cucsStorageConnectionDefTable table."
    INDEX { cucsStorageConnectionDefInstanceId }
    ::= { cucsStorageConnectionDefTable 1 }

CucsStorageConnectionDefEntry ::= SEQUENCE {
    cucsStorageConnectionDefInstanceId                               CucsManagedObjectId,
    cucsStorageConnectionDefDn                                       CucsManagedObjectDn,
    cucsStorageConnectionDefRn                                       SnmpAdminString,
    cucsStorageConnectionDefDescr                                    SnmpAdminString,
    cucsStorageConnectionDefIntId                                    SnmpAdminString,
    cucsStorageConnectionDefName                                     SnmpAdminString,
    cucsStorageConnectionDefOperState                                CucsStorageOperState,
    cucsStorageConnectionDefPolicyLevel                              Gauge32,
    cucsStorageConnectionDefPolicyOwner                              CucsPolicyPolicyOwner,
    cucsStorageConnectionDefZoningType                               CucsStorageFcZoningType
}

cucsStorageConnectionDefInstanceId OBJECT-TYPE
    SYNTAX       CucsManagedObjectId
    MAX-ACCESS   not-accessible
    STATUS       current
    DESCRIPTION
        "Instance identifier of the managed object."
    ::= { cucsStorageConnectionDefEntry 1 }

cucsStorageConnectionDefDn OBJECT-TYPE
    SYNTAX       CucsManagedObjectDn
    MAX-ACCESS   read-only
    STATUS       current
    DESCRIPTION
        "Cisco UCS storage:ConnectionDef:dn managed object property"
    ::= { cucsStorageConnectionDefEntry 2 }

cucsStorageConnectionDefRn OBJECT-TYPE
    SYNTAX       SnmpAdminString
    MAX-ACCESS   read-only
    STATUS       current
    DESCRIPTION
        "Cisco UCS storage:ConnectionDef:rn managed object property"
    ::= { cucsStorageConnectionDefEntry 3 }

cucsStorageConnectionDefDescr OBJECT-TYPE
    SYNTAX       SnmpAdminString
    MAX-ACCESS   read-only
    STATUS       current
    DESCRIPTION
        "Cisco UCS storage:ConnectionDef:descr managed object property"
    ::= { cucsStorageConnectionDefEntry 4 }

cucsStorageConnectionDefIntId OBJECT-TYPE
    SYNTAX       SnmpAdminString
    MAX-ACCESS   read-only
    STATUS       current
    DESCRIPTION
        "Cisco UCS storage:ConnectionDef:intId managed object property"
    ::= { cucsStorageConnectionDefEntry 5 }

cucsStorageConnectionDefName OBJECT-TYPE
    SYNTAX       SnmpAdminString
    MAX-ACCESS   read-only
    STATUS       current
    DESCRIPTION
        "Cisco UCS storage:ConnectionDef:name managed object property"
    ::= { cucsStorageConnectionDefEntry 6 }

cucsStorageConnectionDefOperState OBJECT-TYPE
    SYNTAX       CucsStorageOperState
    MAX-ACCESS   read-only
    STATUS       current
    DESCRIPTION
        "Cisco UCS storage:ConnectionDef:operState managed
        object property"
    ::= { cucsStorageConnectionDefEntry 7 }

cucsStorageConnectionDefPolicyLevel OBJECT-TYPE
    SYNTAX       Gauge32
    MAX-ACCESS   read-only
    STATUS       current
    DESCRIPTION
        "Cisco UCS storage:ConnectionDef:policyLevel managed
        object property"
    ::= { cucsStorageConnectionDefEntry 8 }

cucsStorageConnectionDefPolicyOwner OBJECT-TYPE
    SYNTAX       CucsPolicyPolicyOwner
    MAX-ACCESS   read-only
    STATUS       current
    DESCRIPTION
        "Cisco UCS storage:ConnectionDef:policyOwner managed
        object property"
    ::= { cucsStorageConnectionDefEntry 9 }

cucsStorageConnectionDefZoningType OBJECT-TYPE
    SYNTAX       CucsStorageFcZoningType
    MAX-ACCESS   read-only
    STATUS       current
    DESCRIPTION
        "Cisco UCS storage:ConnectionDef:zoningType managed
        object property"
    ::= { cucsStorageConnectionDefEntry 10 }

cucsStorageConnectionPolicyTable OBJECT-TYPE
    SYNTAX           SEQUENCE OF CucsStorageConnectionPolicyEntry
    MAX-ACCESS       not-accessible
    STATUS           current
    DESCRIPTION
        "Cisco UCS storage:ConnectionPolicy managed object table"
    ::= { cucsStorageObjects 16 }

cucsStorageConnectionPolicyEntry OBJECT-TYPE
    SYNTAX           CucsStorageConnectionPolicyEntry
    MAX-ACCESS       not-accessible
    STATUS           current
    DESCRIPTION
        "Entry for the cucsStorageConnectionPolicyTable table."
    INDEX { cucsStorageConnectionPolicyInstanceId }
    ::= { cucsStorageConnectionPolicyTable 1 }

CucsStorageConnectionPolicyEntry ::= SEQUENCE {
    cucsStorageConnectionPolicyInstanceId                            CucsManagedObjectId,
    cucsStorageConnectionPolicyDn                                    CucsManagedObjectDn,
    cucsStorageConnectionPolicyRn                                    SnmpAdminString,
    cucsStorageConnectionPolicyDescr                                 SnmpAdminString,
    cucsStorageConnectionPolicyIntId                                 SnmpAdminString,
    cucsStorageConnectionPolicyName                                  SnmpAdminString,
    cucsStorageConnectionPolicyOperState                             CucsStorageOperState,
    cucsStorageConnectionPolicyPolicyLevel                           Gauge32,
    cucsStorageConnectionPolicyPolicyOwner                           CucsPolicyPolicyOwner,
    cucsStorageConnectionPolicyZoningType                            CucsStorageFcZoningType
}

cucsStorageConnectionPolicyInstanceId OBJECT-TYPE
    SYNTAX       CucsManagedObjectId
    MAX-ACCESS   not-accessible
    STATUS       current
    DESCRIPTION
        "Instance identifier of the managed object."
    ::= { cucsStorageConnectionPolicyEntry 1 }

cucsStorageConnectionPolicyDn OBJECT-TYPE
    SYNTAX       CucsManagedObjectDn
    MAX-ACCESS   read-only
    STATUS       current
    DESCRIPTION
        "Cisco UCS storage:ConnectionPolicy:dn managed object property"
    ::= { cucsStorageConnectionPolicyEntry 2 }

cucsStorageConnectionPolicyRn OBJECT-TYPE
    SYNTAX       SnmpAdminString
    MAX-ACCESS   read-only
    STATUS       current
    DESCRIPTION
        "Cisco UCS storage:ConnectionPolicy:rn managed object property"
    ::= { cucsStorageConnectionPolicyEntry 3 }

cucsStorageConnectionPolicyDescr OBJECT-TYPE
    SYNTAX       SnmpAdminString
    MAX-ACCESS   read-only
    STATUS       current
    DESCRIPTION
        "Cisco UCS storage:ConnectionPolicy:descr managed object property"
    ::= { cucsStorageConnectionPolicyEntry 4 }

cucsStorageConnectionPolicyIntId OBJECT-TYPE
    SYNTAX       SnmpAdminString
    MAX-ACCESS   read-only
    STATUS       current
    DESCRIPTION
        "Cisco UCS storage:ConnectionPolicy:intId managed object property"
    ::= { cucsStorageConnectionPolicyEntry 5 }

cucsStorageConnectionPolicyName OBJECT-TYPE
    SYNTAX       SnmpAdminString
    MAX-ACCESS   read-only
    STATUS       current
    DESCRIPTION
        "Cisco UCS storage:ConnectionPolicy:name managed object property"
    ::= { cucsStorageConnectionPolicyEntry 6 }

cucsStorageConnectionPolicyOperState OBJECT-TYPE
    SYNTAX       CucsStorageOperState
    MAX-ACCESS   read-only
    STATUS       current
    DESCRIPTION
        "Cisco UCS storage:ConnectionPolicy:operState managed
        object property"
    ::= { cucsStorageConnectionPolicyEntry 7 }

cucsStorageConnectionPolicyPolicyLevel OBJECT-TYPE
    SYNTAX       Gauge32
    MAX-ACCESS   read-only
    STATUS       current
    DESCRIPTION
        "Cisco UCS storage:ConnectionPolicy:policyLevel
        managed object property"
    ::= { cucsStorageConnectionPolicyEntry 8 }

cucsStorageConnectionPolicyPolicyOwner OBJECT-TYPE
    SYNTAX       CucsPolicyPolicyOwner
    MAX-ACCESS   read-only
    STATUS       current
    DESCRIPTION
        "Cisco UCS storage:ConnectionPolicy:policyOwner
        managed object property"
    ::= { cucsStorageConnectionPolicyEntry 9 }

cucsStorageConnectionPolicyZoningType OBJECT-TYPE
    SYNTAX       CucsStorageFcZoningType
    MAX-ACCESS   read-only
    STATUS       current
    DESCRIPTION
        "Cisco UCS storage:ConnectionPolicy:zoningType
        managed object property"
    ::= { cucsStorageConnectionPolicyEntry 10 }

cucsStorageControllerTable OBJECT-TYPE
    SYNTAX           SEQUENCE OF CucsStorageControllerEntry
    MAX-ACCESS       not-accessible
    STATUS           current
    DESCRIPTION
        "Cisco UCS storage:Controller managed object table"
    ::= { cucsStorageObjects 1 }

cucsStorageControllerEntry OBJECT-TYPE
    SYNTAX           CucsStorageControllerEntry
    MAX-ACCESS       not-accessible
    STATUS           current
    DESCRIPTION
        "Entry for the cucsStorageControllerTable table."
    INDEX { cucsStorageControllerInstanceId }
    ::= { cucsStorageControllerTable 1 }

CucsStorageControllerEntry ::= SEQUENCE {
    cucsStorageControllerInstanceId                                  CucsManagedObjectId,
    cucsStorageControllerDn                                          CucsManagedObjectDn,
    cucsStorageControllerRn                                          SnmpAdminString,
    cucsStorageControllerId                                          CucsStorageControllerId,
    cucsStorageControllerModel                                       SnmpAdminString,
    cucsStorageControllerOperState                                   CucsEquipmentOperability,
    cucsStorageControllerOperability                                 CucsEquipmentOperability,
    cucsStorageControllerPciAddr                                     SnmpAdminString,
    cucsStorageControllerPciSlot                                     SnmpAdminString,
    cucsStorageControllerPerf                                        CucsEquipmentSensorThresholdStatus,
    cucsStorageControllerPower                                       CucsEquipmentPowerState,
    cucsStorageControllerPresence                                    CucsEquipmentPresence,
    cucsStorageControllerRevision                                    SnmpAdminString,
    cucsStorageControllerSerial                                      SnmpAdminString,
    cucsStorageControllerThermal                                     CucsEquipmentSensorThresholdStatus,
    cucsStorageControllerType                                        CucsStorageControllerType,
    cucsStorageControllerVendor                                      SnmpAdminString,
    cucsStorageControllerVoltage                                     CucsEquipmentSensorThresholdStatus,
    cucsStorageControllerRaidSupport                                 SnmpAdminString,
    cucsStorageControllerFaultMonitoring                             CucsStorageControllerFaultMonitoring,
    cucsStorageControllerHwRevision                                  SnmpAdminString,
    cucsStorageControllerDeviceRaidSupport                           SnmpAdminString,
    cucsStorageControllerOperQualifierReason                         SnmpAdminString,
    cucsStorageControllerControllerStatus                            CucsStorageControllerStatus,
    cucsStorageControllerLc                                          CucsFsmLifecycle,
    cucsStorageControllerOobControllerId                             Gauge32,
    cucsStorageControllerOobInterfaceSupported                       TruthValue,
    cucsStorageControllerRebuildRate                                 Gauge32,
    cucsStorageControllerLocationDn                                  SnmpAdminString,
    cucsStorageControllerPartNumber                                  SnmpAdminString,
    cucsStorageControllerVid                                         SnmpAdminString,
    cucsStorageControllerAdminAction                                 CucsStorageAdminCtrlActionType,
    cucsStorageControllerAdminActionTrigger                          CucsStorageAdminActionTrigger,
    cucsStorageControllerConfigState                                 CucsStorageConfigState,
    cucsStorageControllerOpromBootStatus                             CucsStorageOptionRomBootStatus,
    cucsStorageControllerPciSlotRawName                              SnmpAdminString,
    cucsStorageControllerIdCount                                     Gauge32,
    cucsStorageControllerPinnedCacheStatus                           CucsStorageControllerPinnedCacheStatus,
    cucsStorageControllerMode                                        CucsStorageControllerMode,
    cucsStorageControllerControllerOps                               CucsStorageSupportedControllerOp,
    cucsStorageControllerDefaultStripSize                            CucsStorageSupportedStripSizeBitmask,
    cucsStorageControllerDiskOps                                     CucsStorageSupportedLocalDiskOp,
    cucsStorageControllerOnBoardMemoryPresent                        CucsStorageOnBoardMemoryPresent,
    cucsStorageControllerOnBoardMemorySize                           Unsigned64,
    cucsStorageControllerRaidBatteryOps                              CucsStorageSupportedRaidBatteryOp,
    cucsStorageControllerSubOemId                                    Gauge32,
    cucsStorageControllerSupportedStripSizes                         CucsStorageSupportedStripSizeBitmask,
    cucsStorageControllerVirtualDriveOps                             CucsStorageSupportedVirtualDriveOp,
    cucsStorageControllerVariantType                                 SnmpAdminString,
    cucsStorageControllerAdminSecurityKey                            SnmpAdminString,
    cucsStorageControllerAssetTag                                    SnmpAdminString,
    cucsStorageControllerControllerFlags                             CucsStorageControllerControllerFlags,
    cucsStorageControllerErrDescription                              SnmpAdminString,
    cucsStorageControllerJbodMode                                    CucsStorageControllerJBODMode,
    cucsStorageControllerSubType                                     CucsStorageControllerSubType
}

cucsStorageControllerInstanceId OBJECT-TYPE
    SYNTAX       CucsManagedObjectId
    MAX-ACCESS   not-accessible
    STATUS       current
    DESCRIPTION
        "Instance identifier of the managed object."
    ::= { cucsStorageControllerEntry 1 }

cucsStorageControllerDn OBJECT-TYPE
    SYNTAX       CucsManagedObjectDn
    MAX-ACCESS   read-only
    STATUS       current
    DESCRIPTION
        "Cisco UCS storage:Controller:dn managed object property"
    ::= { cucsStorageControllerEntry 2 }

cucsStorageControllerRn OBJECT-TYPE
    SYNTAX       SnmpAdminString
    MAX-ACCESS   read-only
    STATUS       current
    DESCRIPTION
        "Cisco UCS storage:Controller:rn managed object property"
    ::= { cucsStorageControllerEntry 3 }

cucsStorageControllerId OBJECT-TYPE
    SYNTAX       CucsStorageControllerId
    MAX-ACCESS   read-only
    STATUS       current
    DESCRIPTION
        "Cisco UCS storage:Controller:id managed object property"
    ::= { cucsStorageControllerEntry 4 }

cucsStorageControllerModel OBJECT-TYPE
    SYNTAX       SnmpAdminString
    MAX-ACCESS   read-only
    STATUS       current
    DESCRIPTION
        "Cisco UCS storage:Controller:model managed object property"
    ::= { cucsStorageControllerEntry 5 }

cucsStorageControllerOperState OBJECT-TYPE
    SYNTAX       CucsEquipmentOperability
    MAX-ACCESS   read-only
    STATUS       current
    DESCRIPTION
        "Cisco UCS storage:Controller:operState managed object property"
    ::= { cucsStorageControllerEntry 6 }

cucsStorageControllerOperability OBJECT-TYPE
    SYNTAX       CucsEquipmentOperability
    MAX-ACCESS   read-only
    STATUS       current
    DESCRIPTION
        "Cisco UCS storage:Controller:operability managed object property"
    ::= { cucsStorageControllerEntry 7 }

cucsStorageControllerPciAddr OBJECT-TYPE
    SYNTAX       SnmpAdminString
    MAX-ACCESS   read-only
    STATUS       current
    DESCRIPTION
        "Cisco UCS storage:Controller:pciAddr managed object property"
    ::= { cucsStorageControllerEntry 8 }

cucsStorageControllerPciSlot OBJECT-TYPE
    SYNTAX       SnmpAdminString
    MAX-ACCESS   read-only
    STATUS       current
    DESCRIPTION
        "Cisco UCS storage:Controller:pciSlot managed object property"
    ::= { cucsStorageControllerEntry 9 }

cucsStorageControllerPerf OBJECT-TYPE
    SYNTAX       CucsEquipmentSensorThresholdStatus
    MAX-ACCESS   read-only
    STATUS       current
    DESCRIPTION
        "Cisco UCS storage:Controller:perf managed object property"
    ::= { cucsStorageControllerEntry 10 }

cucsStorageControllerPower OBJECT-TYPE
    SYNTAX       CucsEquipmentPowerState
    MAX-ACCESS   read-only
    STATUS       current
    DESCRIPTION
        "Cisco UCS storage:Controller:power managed object property"
    ::= { cucsStorageControllerEntry 11 }

cucsStorageControllerPresence OBJECT-TYPE
    SYNTAX       CucsEquipmentPresence
    MAX-ACCESS   read-only
    STATUS       current
    DESCRIPTION
        "Cisco UCS storage:Controller:presence managed object property"
    ::= { cucsStorageControllerEntry 12 }

cucsStorageControllerRevision OBJECT-TYPE
    SYNTAX       SnmpAdminString
    MAX-ACCESS   read-only
    STATUS       current
    DESCRIPTION
        "Cisco UCS storage:Controller:revision managed object property"
    ::= { cucsStorageControllerEntry 13 }

cucsStorageControllerSerial OBJECT-TYPE
    SYNTAX       SnmpAdminString
    MAX-ACCESS   read-only
    STATUS       current
    DESCRIPTION
        "Cisco UCS storage:Controller:serial managed object property"
    ::= { cucsStorageControllerEntry 14 }

cucsStorageControllerThermal OBJECT-TYPE
    SYNTAX       CucsEquipmentSensorThresholdStatus
    MAX-ACCESS   read-only
    STATUS       current
    DESCRIPTION
        "Cisco UCS storage:Controller:thermal managed object property"
    ::= { cucsStorageControllerEntry 15 }

cucsStorageControllerType OBJECT-TYPE
    SYNTAX       CucsStorageControllerType
    MAX-ACCESS   read-only
    STATUS       current
    DESCRIPTION
        "Cisco UCS storage:Controller:type managed object property"
    ::= { cucsStorageControllerEntry 16 }

cucsStorageControllerVendor OBJECT-TYPE
    SYNTAX       SnmpAdminString
    MAX-ACCESS   read-only
    STATUS       current
    DESCRIPTION
        "Cisco UCS storage:Controller:vendor managed object property"
    ::= { cucsStorageControllerEntry 17 }

cucsStorageControllerVoltage OBJECT-TYPE
    SYNTAX       CucsEquipmentSensorThresholdStatus
    MAX-ACCESS   read-only
    STATUS       current
    DESCRIPTION
        "Cisco UCS storage:Controller:voltage managed object property"
    ::= { cucsStorageControllerEntry 18 }

cucsStorageControllerRaidSupport OBJECT-TYPE
    SYNTAX       SnmpAdminString
    MAX-ACCESS   read-only
    STATUS       current
    DESCRIPTION
        "Cisco UCS storage:Controller:raidSupport managed object property"
    ::= { cucsStorageControllerEntry 19 }

cucsStorageControllerFaultMonitoring OBJECT-TYPE
    SYNTAX       CucsStorageControllerFaultMonitoring
    MAX-ACCESS   read-only
    STATUS       current
    DESCRIPTION
        "Cisco UCS storage:Controller:faultMonitoring managed
        object property"
    ::= { cucsStorageControllerEntry 20 }

cucsStorageControllerHwRevision OBJECT-TYPE
    SYNTAX       SnmpAdminString
    MAX-ACCESS   read-only
    STATUS       current
    DESCRIPTION
        "Cisco UCS storage:Controller:hwRevision managed object property"
    ::= { cucsStorageControllerEntry 21 }

cucsStorageControllerDeviceRaidSupport OBJECT-TYPE
    SYNTAX       SnmpAdminString
    MAX-ACCESS   read-only
    STATUS       current
    DESCRIPTION
        "Cisco UCS storage:Controller:deviceRaidSupport
        managed object property"
    ::= { cucsStorageControllerEntry 23 }

cucsStorageControllerOperQualifierReason OBJECT-TYPE
    SYNTAX       SnmpAdminString
    MAX-ACCESS   read-only
    STATUS       current
    DESCRIPTION
        "Cisco UCS storage:Controller:operQualifierReason
        managed object property"
    ::= { cucsStorageControllerEntry 24 }

cucsStorageControllerControllerStatus OBJECT-TYPE
    SYNTAX       CucsStorageControllerStatus
    MAX-ACCESS   read-only
    STATUS       current
    DESCRIPTION
        "Cisco UCS storage:Controller:controllerStatus
        managed object property"
    ::= { cucsStorageControllerEntry 25 }

cucsStorageControllerLc OBJECT-TYPE
    SYNTAX       CucsFsmLifecycle
    MAX-ACCESS   read-only
    STATUS       current
    DESCRIPTION
        "Cisco UCS storage:Controller:lc managed object property"
    ::= { cucsStorageControllerEntry 26 }

cucsStorageControllerOobControllerId OBJECT-TYPE
    SYNTAX       Gauge32
    MAX-ACCESS   read-only
    STATUS       current
    DESCRIPTION
        "Cisco UCS storage:Controller:oobControllerId managed
        object property"
    ::= { cucsStorageControllerEntry 27 }

cucsStorageControllerOobInterfaceSupported OBJECT-TYPE
    SYNTAX       TruthValue
    MAX-ACCESS   read-only
    STATUS       current
    DESCRIPTION
        "Cisco UCS storage:Controller:oobInterfaceSupported
        managed object property"
    ::= { cucsStorageControllerEntry 28 }

cucsStorageControllerRebuildRate OBJECT-TYPE
    SYNTAX       Gauge32
    MAX-ACCESS   read-only
    STATUS       current
    DESCRIPTION
        "Cisco UCS storage:Controller:rebuildRate managed object property"
    ::= { cucsStorageControllerEntry 29 }

cucsStorageControllerLocationDn OBJECT-TYPE
    SYNTAX       SnmpAdminString
    MAX-ACCESS   read-only
    STATUS       current
    DESCRIPTION
        "Cisco UCS storage:Controller:locationDn managed object property"
    ::= { cucsStorageControllerEntry 30 }

cucsStorageControllerPartNumber OBJECT-TYPE
    SYNTAX       SnmpAdminString
    MAX-ACCESS   read-only
    STATUS       current
    DESCRIPTION
        "Cisco UCS storage:Controller:partNumber managed object property"
    ::= { cucsStorageControllerEntry 31 }

cucsStorageControllerVid OBJECT-TYPE
    SYNTAX       SnmpAdminString
    MAX-ACCESS   read-only
    STATUS       current
    DESCRIPTION
        "Cisco UCS storage:Controller:vid managed object property"
    ::= { cucsStorageControllerEntry 32 }

cucsStorageControllerAdminAction OBJECT-TYPE
    SYNTAX       CucsStorageAdminCtrlActionType
    MAX-ACCESS   read-only
    STATUS       current
    DESCRIPTION
        "Cisco UCS storage:Controller:adminAction managed object property"
    ::= { cucsStorageControllerEntry 33 }

cucsStorageControllerAdminActionTrigger OBJECT-TYPE
    SYNTAX       CucsStorageAdminActionTrigger
    MAX-ACCESS   read-only
    STATUS       current
    DESCRIPTION
        "Cisco UCS storage:Controller:adminActionTrigger
        managed object property"
    ::= { cucsStorageControllerEntry 34 }

cucsStorageControllerConfigState OBJECT-TYPE
    SYNTAX       CucsStorageConfigState
    MAX-ACCESS   read-only
    STATUS       current
    DESCRIPTION
        "Cisco UCS storage:Controller:configState managed object property"
    ::= { cucsStorageControllerEntry 35 }

cucsStorageControllerOpromBootStatus OBJECT-TYPE
    SYNTAX       CucsStorageOptionRomBootStatus
    MAX-ACCESS   read-only
    STATUS       current
    DESCRIPTION
        "Cisco UCS storage:Controller:opromBootStatus managed
        object property"
    ::= { cucsStorageControllerEntry 36 }

cucsStorageControllerPciSlotRawName OBJECT-TYPE
    SYNTAX       SnmpAdminString
    MAX-ACCESS   read-only
    STATUS       current
    DESCRIPTION
        "Cisco UCS storage:Controller:pciSlotRawName managed
        object property"
    ::= { cucsStorageControllerEntry 37 }

cucsStorageControllerIdCount OBJECT-TYPE
    SYNTAX       Gauge32
    MAX-ACCESS   read-only
    STATUS       current
    DESCRIPTION
        "Cisco UCS storage:Controller:idCount managed object property"
    ::= { cucsStorageControllerEntry 38 }

cucsStorageControllerPinnedCacheStatus OBJECT-TYPE
    SYNTAX       CucsStorageControllerPinnedCacheStatus
    MAX-ACCESS   read-only
    STATUS       current
    DESCRIPTION
        "Cisco UCS storage:Controller:pinnedCacheStatus
        managed object property"
    ::= { cucsStorageControllerEntry 39 }

cucsStorageControllerMode OBJECT-TYPE
    SYNTAX       CucsStorageControllerMode
    MAX-ACCESS   read-only
    STATUS       current
    DESCRIPTION
        "Cisco UCS storage:Controller:mode managed object property"
    ::= { cucsStorageControllerEntry 40 }

cucsStorageControllerControllerOps OBJECT-TYPE
    SYNTAX       CucsStorageSupportedControllerOp
    MAX-ACCESS   read-only
    STATUS       current
    DESCRIPTION
        "Cisco UCS storage:Controller:controllerOps managed
        object property"
    ::= { cucsStorageControllerEntry 41 }

cucsStorageControllerDefaultStripSize OBJECT-TYPE
    SYNTAX       CucsStorageSupportedStripSizeBitmask
    MAX-ACCESS   read-only
    STATUS       current
    DESCRIPTION
        "Cisco UCS storage:Controller:defaultStripSize
        managed object property"
    ::= { cucsStorageControllerEntry 42 }

cucsStorageControllerDiskOps OBJECT-TYPE
    SYNTAX       CucsStorageSupportedLocalDiskOp
    MAX-ACCESS   read-only
    STATUS       current
    DESCRIPTION
        "Cisco UCS storage:Controller:diskOps managed object property"
    ::= { cucsStorageControllerEntry 43 }

cucsStorageControllerOnBoardMemoryPresent OBJECT-TYPE
    SYNTAX       CucsStorageOnBoardMemoryPresent
    MAX-ACCESS   read-only
    STATUS       current
    DESCRIPTION
        "Cisco UCS storage:Controller:onBoardMemoryPresent
        managed object property"
    ::= { cucsStorageControllerEntry 44 }

cucsStorageControllerOnBoardMemorySize OBJECT-TYPE
    SYNTAX       Unsigned64
    MAX-ACCESS   read-only
    STATUS       current
    DESCRIPTION
        "Cisco UCS storage:Controller:onBoardMemorySize
        managed object property"
    ::= { cucsStorageControllerEntry 45 }

cucsStorageControllerRaidBatteryOps OBJECT-TYPE
    SYNTAX       CucsStorageSupportedRaidBatteryOp
    MAX-ACCESS   read-only
    STATUS       current
    DESCRIPTION
        "Cisco UCS storage:Controller:raidBatteryOps managed
        object property"
    ::= { cucsStorageControllerEntry 46 }

cucsStorageControllerSubOemId OBJECT-TYPE
    SYNTAX       Gauge32
    MAX-ACCESS   read-only
    STATUS       current
    DESCRIPTION
        "Cisco UCS storage:Controller:subOemId managed object property"
    ::= { cucsStorageControllerEntry 47 }

cucsStorageControllerSupportedStripSizes OBJECT-TYPE
    SYNTAX       CucsStorageSupportedStripSizeBitmask
    MAX-ACCESS   read-only
    STATUS       current
    DESCRIPTION
        "Cisco UCS storage:Controller:supportedStripSizes
        managed object property"
    ::= { cucsStorageControllerEntry 48 }

cucsStorageControllerVirtualDriveOps OBJECT-TYPE
    SYNTAX       CucsStorageSupportedVirtualDriveOp
    MAX-ACCESS   read-only
    STATUS       current
    DESCRIPTION
        "Cisco UCS storage:Controller:virtualDriveOps managed
        object property"
    ::= { cucsStorageControllerEntry 49 }

cucsStorageControllerVariantType OBJECT-TYPE
    SYNTAX       SnmpAdminString
    MAX-ACCESS   read-only
    STATUS       current
    DESCRIPTION
        "Cisco UCS storage:Controller:variantType managed object property"
    ::= { cucsStorageControllerEntry 50 }

cucsStorageControllerAdminSecurityKey OBJECT-TYPE
    SYNTAX       SnmpAdminString
    MAX-ACCESS   read-only
    STATUS       current
    DESCRIPTION
        "Cisco UCS storage:Controller:adminSecurityKey
        managed object property"
    ::= { cucsStorageControllerEntry 51 }

cucsStorageControllerAssetTag OBJECT-TYPE
    SYNTAX       SnmpAdminString
    MAX-ACCESS   read-only
    STATUS       current
    DESCRIPTION
        "Cisco UCS storage:Controller:assetTag managed object property"
    ::= { cucsStorageControllerEntry 52 }

cucsStorageControllerControllerFlags OBJECT-TYPE
    SYNTAX       CucsStorageControllerControllerFlags
    MAX-ACCESS   read-only
    STATUS       current
    DESCRIPTION
        "Cisco UCS storage:Controller:controllerFlags managed
        object property"
    ::= { cucsStorageControllerEntry 53 }

cucsStorageControllerErrDescription OBJECT-TYPE
    SYNTAX       SnmpAdminString
    MAX-ACCESS   read-only
    STATUS       current
    DESCRIPTION
        "Cisco UCS storage:Controller:errDescription managed
        object property"
    ::= { cucsStorageControllerEntry 54 }

cucsStorageControllerJbodMode OBJECT-TYPE
    SYNTAX       CucsStorageControllerJBODMode
    MAX-ACCESS   read-only
    STATUS       current
    DESCRIPTION
        "Cisco UCS storage:Controller:jbodMode managed object property"
    ::= { cucsStorageControllerEntry 55 }

cucsStorageControllerSubType OBJECT-TYPE
    SYNTAX       CucsStorageControllerSubType
    MAX-ACCESS   read-only
    STATUS       current
    DESCRIPTION
        "Cisco UCS storage:Controller:subType managed object property"
    ::= { cucsStorageControllerEntry 56 }

cucsStorageControllerEpTable OBJECT-TYPE
    SYNTAX           SEQUENCE OF CucsStorageControllerEpEntry
    MAX-ACCESS       not-accessible
    STATUS           current
    DESCRIPTION
        "Cisco UCS storage:ControllerEp managed object table"
    ::= { cucsStorageObjects 109 }

cucsStorageControllerEpEntry OBJECT-TYPE
    SYNTAX           CucsStorageControllerEpEntry
    MAX-ACCESS       not-accessible
    STATUS           current
    DESCRIPTION
        "Entry for the cucsStorageControllerEpTable table."
    INDEX { cucsStorageControllerEpInstanceId }
    ::= { cucsStorageControllerEpTable 1 }

CucsStorageControllerEpEntry ::= SEQUENCE {
    cucsStorageControllerEpInstanceId                                CucsManagedObjectId,
    cucsStorageControllerEpDn                                        CucsManagedObjectDn,
    cucsStorageControllerEpRn                                        SnmpAdminString,
    cucsStorageControllerEpControllerDn                              SnmpAdminString,
    cucsStorageControllerEpId                                        Gauge32
}

cucsStorageControllerEpInstanceId OBJECT-TYPE
    SYNTAX       CucsManagedObjectId
    MAX-ACCESS   not-accessible
    STATUS       current
    DESCRIPTION
        "Instance identifier of the managed object."
    ::= { cucsStorageControllerEpEntry 1 }

cucsStorageControllerEpDn OBJECT-TYPE
    SYNTAX       CucsManagedObjectDn
    MAX-ACCESS   read-only
    STATUS       current
    DESCRIPTION
        "Cisco UCS storage:ControllerEp:dn managed object property"
    ::= { cucsStorageControllerEpEntry 2 }

cucsStorageControllerEpRn OBJECT-TYPE
    SYNTAX       SnmpAdminString
    MAX-ACCESS   read-only
    STATUS       current
    DESCRIPTION
        "Cisco UCS storage:ControllerEp:rn managed object property"
    ::= { cucsStorageControllerEpEntry 3 }

cucsStorageControllerEpControllerDn OBJECT-TYPE
    SYNTAX       SnmpAdminString
    MAX-ACCESS   read-only
    STATUS       current
    DESCRIPTION
        "Cisco UCS storage:ControllerEp:controllerDn managed
        object property"
    ::= { cucsStorageControllerEpEntry 4 }

cucsStorageControllerEpId OBJECT-TYPE
    SYNTAX       Gauge32
    MAX-ACCESS   read-only
    STATUS       current
    DESCRIPTION
        "Cisco UCS storage:ControllerEp:id managed object property"
    ::= { cucsStorageControllerEpEntry 5 }

cucsStorageControllerRefTable OBJECT-TYPE
    SYNTAX           SEQUENCE OF CucsStorageControllerRefEntry
    MAX-ACCESS       not-accessible
    STATUS           current
    DESCRIPTION
        "Cisco UCS storage:ControllerRef managed object table"
    ::= { cucsStorageObjects 93 }

cucsStorageControllerRefEntry OBJECT-TYPE
    SYNTAX           CucsStorageControllerRefEntry
    MAX-ACCESS       not-accessible
    STATUS           current
    DESCRIPTION
        "Entry for the cucsStorageControllerRefTable table."
    INDEX { cucsStorageControllerRefInstanceId }
    ::= { cucsStorageControllerRefTable 1 }

CucsStorageControllerRefEntry ::= SEQUENCE {
    cucsStorageControllerRefInstanceId                               CucsManagedObjectId,
    cucsStorageControllerRefDn                                       CucsManagedObjectDn,
    cucsStorageControllerRefRn                                       SnmpAdminString,
    cucsStorageControllerRefControllerId                             Gauge32,
    cucsStorageControllerRefLc                                       CucsFsmLifecycle,
    cucsStorageControllerRefServerId                                 Gauge32,
    cucsStorageControllerRefControllerType                           CucsStorageControllerRefControllerType
}

cucsStorageControllerRefInstanceId OBJECT-TYPE
    SYNTAX       CucsManagedObjectId
    MAX-ACCESS   not-accessible
    STATUS       current
    DESCRIPTION
        "Instance identifier of the managed object."
    ::= { cucsStorageControllerRefEntry 1 }

cucsStorageControllerRefDn OBJECT-TYPE
    SYNTAX       CucsManagedObjectDn
    MAX-ACCESS   read-only
    STATUS       current
    DESCRIPTION
        "Cisco UCS storage:ControllerRef:dn managed object property"
    ::= { cucsStorageControllerRefEntry 2 }

cucsStorageControllerRefRn OBJECT-TYPE
    SYNTAX       SnmpAdminString
    MAX-ACCESS   read-only
    STATUS       current
    DESCRIPTION
        "Cisco UCS storage:ControllerRef:rn managed object property"
    ::= { cucsStorageControllerRefEntry 3 }

cucsStorageControllerRefControllerId OBJECT-TYPE
    SYNTAX       Gauge32
    MAX-ACCESS   read-only
    STATUS       current
    DESCRIPTION
        "Cisco UCS storage:ControllerRef:controllerId managed
        object property"
    ::= { cucsStorageControllerRefEntry 4 }

cucsStorageControllerRefLc OBJECT-TYPE
    SYNTAX       CucsFsmLifecycle
    MAX-ACCESS   read-only
    STATUS       current
    DESCRIPTION
        "Cisco UCS storage:ControllerRef:lc managed object property"
    ::= { cucsStorageControllerRefEntry 5 }

cucsStorageControllerRefServerId OBJECT-TYPE
    SYNTAX       Gauge32
    MAX-ACCESS   read-only
    STATUS       current
    DESCRIPTION
        "Cisco UCS storage:ControllerRef:serverId managed object property"
    ::= { cucsStorageControllerRefEntry 6 }

cucsStorageControllerRefControllerType OBJECT-TYPE
    SYNTAX       CucsStorageControllerRefControllerType
    MAX-ACCESS   read-only
    STATUS       current
    DESCRIPTION
        "Cisco UCS storage:ControllerRef:controllerType
        managed object property"
    ::= { cucsStorageControllerRefEntry 7 }

cucsStorageControllerReferenceTable OBJECT-TYPE
    SYNTAX           SEQUENCE OF CucsStorageControllerReferenceEntry
    MAX-ACCESS       not-accessible
    STATUS           current
    DESCRIPTION
        "Cisco UCS storage:ControllerReference managed object table"
    ::= { cucsStorageObjects 129 }

cucsStorageControllerReferenceEntry OBJECT-TYPE
    SYNTAX           CucsStorageControllerReferenceEntry
    MAX-ACCESS       not-accessible
    STATUS           current
    DESCRIPTION
        "Entry for the cucsStorageControllerReferenceTable table."
    INDEX { cucsStorageControllerReferenceInstanceId }
    ::= { cucsStorageControllerReferenceTable 1 }

CucsStorageControllerReferenceEntry ::= SEQUENCE {
    cucsStorageControllerReferenceInstanceId                         CucsManagedObjectId,
    cucsStorageControllerReferenceDn                                 CucsManagedObjectDn,
    cucsStorageControllerReferenceRn                                 SnmpAdminString,
    cucsStorageControllerReferenceControllerId                       Gauge32,
    cucsStorageControllerReferenceControllerType                     CucsStorageControllerType,
    cucsStorageControllerReferenceReferencedRn                       SnmpAdminString
}

cucsStorageControllerReferenceInstanceId OBJECT-TYPE
    SYNTAX       CucsManagedObjectId
    MAX-ACCESS   not-accessible
    STATUS       current
    DESCRIPTION
        "Instance identifier of the managed object."
    ::= { cucsStorageControllerReferenceEntry 1 }

cucsStorageControllerReferenceDn OBJECT-TYPE
    SYNTAX       CucsManagedObjectDn
    MAX-ACCESS   read-only
    STATUS       current
    DESCRIPTION
        "Cisco UCS storage:ControllerReference:dn managed object property"
    ::= { cucsStorageControllerReferenceEntry 2 }

cucsStorageControllerReferenceRn OBJECT-TYPE
    SYNTAX       SnmpAdminString
    MAX-ACCESS   read-only
    STATUS       current
    DESCRIPTION
        "Cisco UCS storage:ControllerReference:rn managed object property"
    ::= { cucsStorageControllerReferenceEntry 3 }

cucsStorageControllerReferenceControllerId OBJECT-TYPE
    SYNTAX       Gauge32
    MAX-ACCESS   read-only
    STATUS       current
    DESCRIPTION
        "Cisco UCS storage:ControllerReference:controllerId
        managed object property"
    ::= { cucsStorageControllerReferenceEntry 4 }

cucsStorageControllerReferenceControllerType OBJECT-TYPE
    SYNTAX       CucsStorageControllerType
    MAX-ACCESS   read-only
    STATUS       current
    DESCRIPTION
        "Cisco UCS storage:ControllerReference:controllerType
        managed object property"
    ::= { cucsStorageControllerReferenceEntry 5 }

cucsStorageControllerReferenceReferencedRn OBJECT-TYPE
    SYNTAX       SnmpAdminString
    MAX-ACCESS   read-only
    STATUS       current
    DESCRIPTION
        "Cisco UCS storage:ControllerReference:referencedRn
        managed object property"
    ::= { cucsStorageControllerReferenceEntry 6 }

cucsStorageDiskEnvStatsTable OBJECT-TYPE
    SYNTAX           SEQUENCE OF CucsStorageDiskEnvStatsEntry
    MAX-ACCESS       not-accessible
    STATUS           current
    DESCRIPTION
        "Cisco UCS storage:DiskEnvStats managed object table"
    ::= { cucsStorageObjects 50 }

cucsStorageDiskEnvStatsEntry OBJECT-TYPE
    SYNTAX           CucsStorageDiskEnvStatsEntry
    MAX-ACCESS       not-accessible
    STATUS           current
    DESCRIPTION
        "Entry for the cucsStorageDiskEnvStatsTable table."
    INDEX { cucsStorageDiskEnvStatsInstanceId }
    ::= { cucsStorageDiskEnvStatsTable 1 }

CucsStorageDiskEnvStatsEntry ::= SEQUENCE {
    cucsStorageDiskEnvStatsInstanceId                                CucsManagedObjectId,
    cucsStorageDiskEnvStatsDn                                        CucsManagedObjectDn,
    cucsStorageDiskEnvStatsRn                                        SnmpAdminString,
    cucsStorageDiskEnvStatsIntervals                                 Gauge32,
    cucsStorageDiskEnvStatsSuspect                                   TruthValue,
    cucsStorageDiskEnvStatsTemperature                               SnmpAdminString,
    cucsStorageDiskEnvStatsTemperatureAvg                            SnmpAdminString,
    cucsStorageDiskEnvStatsTemperatureMax                            SnmpAdminString,
    cucsStorageDiskEnvStatsTemperatureMin                            SnmpAdminString,
    cucsStorageDiskEnvStatsThresholded                               CucsStorageDiskEnvStatsThresholded,
    cucsStorageDiskEnvStatsTimeCollected                             DateAndTime,
    cucsStorageDiskEnvStatsUpdate                                    Gauge32,
    cucsStorageDiskEnvStatsWearPercentage                            Gauge32,
    cucsStorageDiskEnvStatsWearPercentageAvg                         Gauge32,
    cucsStorageDiskEnvStatsWearPercentageMax                         Gauge32,
    cucsStorageDiskEnvStatsWearPercentageMin                         Gauge32
}

cucsStorageDiskEnvStatsInstanceId OBJECT-TYPE
    SYNTAX       CucsManagedObjectId
    MAX-ACCESS   not-accessible
    STATUS       current
    DESCRIPTION
        "Instance identifier of the managed object."
    ::= { cucsStorageDiskEnvStatsEntry 1 }

cucsStorageDiskEnvStatsDn OBJECT-TYPE
    SYNTAX       CucsManagedObjectDn
    MAX-ACCESS   read-only
    STATUS       current
    DESCRIPTION
        "Cisco UCS storage:DiskEnvStats:dn managed object property"
    ::= { cucsStorageDiskEnvStatsEntry 2 }

cucsStorageDiskEnvStatsRn OBJECT-TYPE
    SYNTAX       SnmpAdminString
    MAX-ACCESS   read-only
    STATUS       current
    DESCRIPTION
        "Cisco UCS storage:DiskEnvStats:rn managed object property"
    ::= { cucsStorageDiskEnvStatsEntry 3 }

cucsStorageDiskEnvStatsIntervals OBJECT-TYPE
    SYNTAX       Gauge32
    MAX-ACCESS   read-only
    STATUS       current
    DESCRIPTION
        "Cisco UCS storage:DiskEnvStats:intervals managed object property"
    ::= { cucsStorageDiskEnvStatsEntry 4 }

cucsStorageDiskEnvStatsSuspect OBJECT-TYPE
    SYNTAX       TruthValue
    MAX-ACCESS   read-only
    STATUS       current
    DESCRIPTION
        "Cisco UCS storage:DiskEnvStats:suspect managed object property"
    ::= { cucsStorageDiskEnvStatsEntry 5 }

cucsStorageDiskEnvStatsTemperature OBJECT-TYPE
    SYNTAX       SnmpAdminString
    MAX-ACCESS   read-only
    STATUS       current
    DESCRIPTION
        "Cisco UCS storage:DiskEnvStats:temperature managed
        object property"
    ::= { cucsStorageDiskEnvStatsEntry 6 }

cucsStorageDiskEnvStatsTemperatureAvg OBJECT-TYPE
    SYNTAX       SnmpAdminString
    MAX-ACCESS   read-only
    STATUS       current
    DESCRIPTION
        "Cisco UCS storage:DiskEnvStats:temperatureAvg
        managed object property"
    ::= { cucsStorageDiskEnvStatsEntry 7 }

cucsStorageDiskEnvStatsTemperatureMax OBJECT-TYPE
    SYNTAX       SnmpAdminString
    MAX-ACCESS   read-only
    STATUS       current
    DESCRIPTION
        "Cisco UCS storage:DiskEnvStats:temperatureMax
        managed object property"
    ::= { cucsStorageDiskEnvStatsEntry 8 }

cucsStorageDiskEnvStatsTemperatureMin OBJECT-TYPE
    SYNTAX       SnmpAdminString
    MAX-ACCESS   read-only
    STATUS       current
    DESCRIPTION
        "Cisco UCS storage:DiskEnvStats:temperatureMin
        managed object property"
    ::= { cucsStorageDiskEnvStatsEntry 9 }

cucsStorageDiskEnvStatsThresholded OBJECT-TYPE
    SYNTAX       CucsStorageDiskEnvStatsThresholded
    MAX-ACCESS   read-only
    STATUS       current
    DESCRIPTION
        "Cisco UCS storage:DiskEnvStats:thresholded managed
        object property"
    ::= { cucsStorageDiskEnvStatsEntry 10 }

cucsStorageDiskEnvStatsTimeCollected OBJECT-TYPE
    SYNTAX       DateAndTime
    MAX-ACCESS   read-only
    STATUS       current
    DESCRIPTION
        "Cisco UCS storage:DiskEnvStats:timeCollected managed
        object property"
    ::= { cucsStorageDiskEnvStatsEntry 11 }

cucsStorageDiskEnvStatsUpdate OBJECT-TYPE
    SYNTAX       Gauge32
    MAX-ACCESS   read-only
    STATUS       current
    DESCRIPTION
        "Cisco UCS storage:DiskEnvStats:update managed object property"
    ::= { cucsStorageDiskEnvStatsEntry 12 }

cucsStorageDiskEnvStatsWearPercentage OBJECT-TYPE
    SYNTAX       Gauge32
    MAX-ACCESS   read-only
    STATUS       current
    DESCRIPTION
        "Cisco UCS storage:DiskEnvStats:wearPercentage
        managed object property"
    ::= { cucsStorageDiskEnvStatsEntry 13 }

cucsStorageDiskEnvStatsWearPercentageAvg OBJECT-TYPE
    SYNTAX       Gauge32
    MAX-ACCESS   read-only
    STATUS       current
    DESCRIPTION
        "Cisco UCS storage:DiskEnvStats:wearPercentageAvg
        managed object property"
    ::= { cucsStorageDiskEnvStatsEntry 14 }

cucsStorageDiskEnvStatsWearPercentageMax OBJECT-TYPE
    SYNTAX       Gauge32
    MAX-ACCESS   read-only
    STATUS       current
    DESCRIPTION
        "Cisco UCS storage:DiskEnvStats:wearPercentageMax
        managed object property"
    ::= { cucsStorageDiskEnvStatsEntry 15 }

cucsStorageDiskEnvStatsWearPercentageMin OBJECT-TYPE
    SYNTAX       Gauge32
    MAX-ACCESS   read-only
    STATUS       current
    DESCRIPTION
        "Cisco UCS storage:DiskEnvStats:wearPercentageMin
        managed object property"
    ::= { cucsStorageDiskEnvStatsEntry 16 }

cucsStorageDiskEnvStatsHistTable OBJECT-TYPE
    SYNTAX           SEQUENCE OF CucsStorageDiskEnvStatsHistEntry
    MAX-ACCESS       not-accessible
    STATUS           current
    DESCRIPTION
        "Cisco UCS storage:DiskEnvStatsHist managed object table"
    ::= { cucsStorageObjects 51 }

cucsStorageDiskEnvStatsHistEntry OBJECT-TYPE
    SYNTAX           CucsStorageDiskEnvStatsHistEntry
    MAX-ACCESS       not-accessible
    STATUS           current
    DESCRIPTION
        "Entry for the cucsStorageDiskEnvStatsHistTable table."
    INDEX { cucsStorageDiskEnvStatsHistInstanceId }
    ::= { cucsStorageDiskEnvStatsHistTable 1 }

CucsStorageDiskEnvStatsHistEntry ::= SEQUENCE {
    cucsStorageDiskEnvStatsHistInstanceId                            CucsManagedObjectId,
    cucsStorageDiskEnvStatsHistDn                                    CucsManagedObjectDn,
    cucsStorageDiskEnvStatsHistRn                                    SnmpAdminString,
    cucsStorageDiskEnvStatsHistId                                    Unsigned64,
    cucsStorageDiskEnvStatsHistMostRecent                            TruthValue,
    cucsStorageDiskEnvStatsHistSuspect                               TruthValue,
    cucsStorageDiskEnvStatsHistTemperature                           SnmpAdminString,
    cucsStorageDiskEnvStatsHistTemperatureAvg                        SnmpAdminString,
    cucsStorageDiskEnvStatsHistTemperatureMax                        SnmpAdminString,
    cucsStorageDiskEnvStatsHistTemperatureMin                        SnmpAdminString,
    cucsStorageDiskEnvStatsHistThresholded                           CucsStorageDiskEnvStatsHistThresholded,
    cucsStorageDiskEnvStatsHistTimeCollected                         DateAndTime,
    cucsStorageDiskEnvStatsHistWearPercentage                        Gauge32,
    cucsStorageDiskEnvStatsHistWearPercentageAvg                     Gauge32,
    cucsStorageDiskEnvStatsHistWearPercentageMax                     Gauge32,
    cucsStorageDiskEnvStatsHistWearPercentageMin                     Gauge32
}

cucsStorageDiskEnvStatsHistInstanceId OBJECT-TYPE
    SYNTAX       CucsManagedObjectId
    MAX-ACCESS   not-accessible
    STATUS       current
    DESCRIPTION
        "Instance identifier of the managed object."
    ::= { cucsStorageDiskEnvStatsHistEntry 1 }

cucsStorageDiskEnvStatsHistDn OBJECT-TYPE
    SYNTAX       CucsManagedObjectDn
    MAX-ACCESS   read-only
    STATUS       current
    DESCRIPTION
        "Cisco UCS storage:DiskEnvStatsHist:dn managed object property"
    ::= { cucsStorageDiskEnvStatsHistEntry 2 }

cucsStorageDiskEnvStatsHistRn OBJECT-TYPE
    SYNTAX       SnmpAdminString
    MAX-ACCESS   read-only
    STATUS       current
    DESCRIPTION
        "Cisco UCS storage:DiskEnvStatsHist:rn managed object property"
    ::= { cucsStorageDiskEnvStatsHistEntry 3 }

cucsStorageDiskEnvStatsHistId OBJECT-TYPE
    SYNTAX       Unsigned64
    MAX-ACCESS   read-only
    STATUS       current
    DESCRIPTION
        "Cisco UCS storage:DiskEnvStatsHist:id managed object property"
    ::= { cucsStorageDiskEnvStatsHistEntry 4 }

cucsStorageDiskEnvStatsHistMostRecent OBJECT-TYPE
    SYNTAX       TruthValue
    MAX-ACCESS   read-only
    STATUS       current
    DESCRIPTION
        "Cisco UCS storage:DiskEnvStatsHist:mostRecent
        managed object property"
    ::= { cucsStorageDiskEnvStatsHistEntry 5 }

cucsStorageDiskEnvStatsHistSuspect OBJECT-TYPE
    SYNTAX       TruthValue
    MAX-ACCESS   read-only
    STATUS       current
    DESCRIPTION
        "Cisco UCS storage:DiskEnvStatsHist:suspect managed
        object property"
    ::= { cucsStorageDiskEnvStatsHistEntry 6 }

cucsStorageDiskEnvStatsHistTemperature OBJECT-TYPE
    SYNTAX       SnmpAdminString
    MAX-ACCESS   read-only
    STATUS       current
    DESCRIPTION
        "Cisco UCS storage:DiskEnvStatsHist:temperature
        managed object property"
    ::= { cucsStorageDiskEnvStatsHistEntry 7 }

cucsStorageDiskEnvStatsHistTemperatureAvg OBJECT-TYPE
    SYNTAX       SnmpAdminString
    MAX-ACCESS   read-only
    STATUS       current
    DESCRIPTION
        "Cisco UCS storage:DiskEnvStatsHist:temperatureAvg
        managed object property"
    ::= { cucsStorageDiskEnvStatsHistEntry 8 }

cucsStorageDiskEnvStatsHistTemperatureMax OBJECT-TYPE
    SYNTAX       SnmpAdminString
    MAX-ACCESS   read-only
    STATUS       current
    DESCRIPTION
        "Cisco UCS storage:DiskEnvStatsHist:temperatureMax
        managed object property"
    ::= { cucsStorageDiskEnvStatsHistEntry 9 }

cucsStorageDiskEnvStatsHistTemperatureMin OBJECT-TYPE
    SYNTAX       SnmpAdminString
    MAX-ACCESS   read-only
    STATUS       current
    DESCRIPTION
        "Cisco UCS storage:DiskEnvStatsHist:temperatureMin
        managed object property"
    ::= { cucsStorageDiskEnvStatsHistEntry 10 }

cucsStorageDiskEnvStatsHistThresholded OBJECT-TYPE
    SYNTAX       CucsStorageDiskEnvStatsHistThresholded
    MAX-ACCESS   read-only
    STATUS       current
    DESCRIPTION
        "Cisco UCS storage:DiskEnvStatsHist:thresholded
        managed object property"
    ::= { cucsStorageDiskEnvStatsHistEntry 11 }

cucsStorageDiskEnvStatsHistTimeCollected OBJECT-TYPE
    SYNTAX       DateAndTime
    MAX-ACCESS   read-only
    STATUS       current
    DESCRIPTION
        "Cisco UCS storage:DiskEnvStatsHist:timeCollected
        managed object property"
    ::= { cucsStorageDiskEnvStatsHistEntry 12 }

cucsStorageDiskEnvStatsHistWearPercentage OBJECT-TYPE
    SYNTAX       Gauge32
    MAX-ACCESS   read-only
    STATUS       current
    DESCRIPTION
        "Cisco UCS storage:DiskEnvStatsHist:wearPercentage
        managed object property"
    ::= { cucsStorageDiskEnvStatsHistEntry 13 }

cucsStorageDiskEnvStatsHistWearPercentageAvg OBJECT-TYPE
    SYNTAX       Gauge32
    MAX-ACCESS   read-only
    STATUS       current
    DESCRIPTION
        "Cisco UCS storage:DiskEnvStatsHist:wearPercentageAvg
        managed object property"
    ::= { cucsStorageDiskEnvStatsHistEntry 14 }

cucsStorageDiskEnvStatsHistWearPercentageMax OBJECT-TYPE
    SYNTAX       Gauge32
    MAX-ACCESS   read-only
    STATUS       current
    DESCRIPTION
        "Cisco UCS storage:DiskEnvStatsHist:wearPercentageMax
        managed object property"
    ::= { cucsStorageDiskEnvStatsHistEntry 15 }

cucsStorageDiskEnvStatsHistWearPercentageMin OBJECT-TYPE
    SYNTAX       Gauge32
    MAX-ACCESS   read-only
    STATUS       current
    DESCRIPTION
        "Cisco UCS storage:DiskEnvStatsHist:wearPercentageMin
        managed object property"
    ::= { cucsStorageDiskEnvStatsHistEntry 16 }

cucsStorageDomainEpTable OBJECT-TYPE
    SYNTAX           SEQUENCE OF CucsStorageDomainEpEntry
    MAX-ACCESS       not-accessible
    STATUS           current
    DESCRIPTION
        "Cisco UCS storage:DomainEp managed object table"
    ::= { cucsStorageObjects 17 }

cucsStorageDomainEpEntry OBJECT-TYPE
    SYNTAX           CucsStorageDomainEpEntry
    MAX-ACCESS       not-accessible
    STATUS           current
    DESCRIPTION
        "Entry for the cucsStorageDomainEpTable table."
    INDEX { cucsStorageDomainEpInstanceId }
    ::= { cucsStorageDomainEpTable 1 }

CucsStorageDomainEpEntry ::= SEQUENCE {
    cucsStorageDomainEpInstanceId                                    CucsManagedObjectId,
    cucsStorageDomainEpDn                                            CucsManagedObjectDn,
    cucsStorageDomainEpRn                                            SnmpAdminString
}

cucsStorageDomainEpInstanceId OBJECT-TYPE
    SYNTAX       CucsManagedObjectId
    MAX-ACCESS   not-accessible
    STATUS       current
    DESCRIPTION
        "Instance identifier of the managed object."
    ::= { cucsStorageDomainEpEntry 1 }

cucsStorageDomainEpDn OBJECT-TYPE
    SYNTAX       CucsManagedObjectDn
    MAX-ACCESS   read-only
    STATUS       current
    DESCRIPTION
        "Cisco UCS storage:DomainEp:dn managed object property"
    ::= { cucsStorageDomainEpEntry 2 }

cucsStorageDomainEpRn OBJECT-TYPE
    SYNTAX       SnmpAdminString
    MAX-ACCESS   read-only
    STATUS       current
    DESCRIPTION
        "Cisco UCS storage:DomainEp:rn managed object property"
    ::= { cucsStorageDomainEpEntry 3 }

cucsStorageDriveTable OBJECT-TYPE
    SYNTAX           SEQUENCE OF CucsStorageDriveEntry
    MAX-ACCESS       not-accessible
    STATUS           current
    DESCRIPTION
        "Cisco UCS storage:Drive managed object table"
    ::= { cucsStorageObjects 2 }

cucsStorageDriveEntry OBJECT-TYPE
    SYNTAX           CucsStorageDriveEntry
    MAX-ACCESS       not-accessible
    STATUS           current
    DESCRIPTION
        "Entry for the cucsStorageDriveTable table."
    INDEX { cucsStorageDriveInstanceId }
    ::= { cucsStorageDriveTable 1 }

CucsStorageDriveEntry ::= SEQUENCE {
    cucsStorageDriveInstanceId                                       CucsManagedObjectId,
    cucsStorageDriveDn                                               CucsManagedObjectDn,
    cucsStorageDriveRn                                               SnmpAdminString,
    cucsStorageDriveId                                               Gauge32,
    cucsStorageDriveModel                                            SnmpAdminString,
    cucsStorageDrivePciAddr                                          SnmpAdminString,
    cucsStorageDriveRevision                                         SnmpAdminString,
    cucsStorageDriveSerial                                           SnmpAdminString,
    cucsStorageDriveVendor                                           SnmpAdminString
}

cucsStorageDriveInstanceId OBJECT-TYPE
    SYNTAX       CucsManagedObjectId
    MAX-ACCESS   not-accessible
    STATUS       current
    DESCRIPTION
        "Instance identifier of the managed object."
    ::= { cucsStorageDriveEntry 1 }

cucsStorageDriveDn OBJECT-TYPE
    SYNTAX       CucsManagedObjectDn
    MAX-ACCESS   read-only
    STATUS       current
    DESCRIPTION
        "Cisco UCS storage:Drive:dn managed object property"
    ::= { cucsStorageDriveEntry 2 }

cucsStorageDriveRn OBJECT-TYPE
    SYNTAX       SnmpAdminString
    MAX-ACCESS   read-only
    STATUS       current
    DESCRIPTION
        "Cisco UCS storage:Drive:rn managed object property"
    ::= { cucsStorageDriveEntry 3 }

cucsStorageDriveId OBJECT-TYPE
    SYNTAX       Gauge32
    MAX-ACCESS   read-only
    STATUS       current
    DESCRIPTION
        "Cisco UCS storage:Drive:id managed object property"
    ::= { cucsStorageDriveEntry 4 }

cucsStorageDriveModel OBJECT-TYPE
    SYNTAX       SnmpAdminString
    MAX-ACCESS   read-only
    STATUS       current
    DESCRIPTION
        "Cisco UCS storage:Drive:model managed object property"
    ::= { cucsStorageDriveEntry 5 }

cucsStorageDrivePciAddr OBJECT-TYPE
    SYNTAX       SnmpAdminString
    MAX-ACCESS   read-only
    STATUS       current
    DESCRIPTION
        "Cisco UCS storage:Drive:pciAddr managed object property"
    ::= { cucsStorageDriveEntry 6 }

cucsStorageDriveRevision OBJECT-TYPE
    SYNTAX       SnmpAdminString
    MAX-ACCESS   read-only
    STATUS       current
    DESCRIPTION
        "Cisco UCS storage:Drive:revision managed object property"
    ::= { cucsStorageDriveEntry 7 }

cucsStorageDriveSerial OBJECT-TYPE
    SYNTAX       SnmpAdminString
    MAX-ACCESS   read-only
    STATUS       current
    DESCRIPTION
        "Cisco UCS storage:Drive:serial managed object property"
    ::= { cucsStorageDriveEntry 8 }

cucsStorageDriveVendor OBJECT-TYPE
    SYNTAX       SnmpAdminString
    MAX-ACCESS   read-only
    STATUS       current
    DESCRIPTION
        "Cisco UCS storage:Drive:vendor managed object property"
    ::= { cucsStorageDriveEntry 9 }

cucsStorageEmbeddedStorageTable OBJECT-TYPE
    SYNTAX           SEQUENCE OF CucsStorageEmbeddedStorageEntry
    MAX-ACCESS       not-accessible
    STATUS           current
    DESCRIPTION
        "Cisco UCS storage:EmbeddedStorage managed object table"
    ::= { cucsStorageObjects 110 }

cucsStorageEmbeddedStorageEntry OBJECT-TYPE
    SYNTAX           CucsStorageEmbeddedStorageEntry
    MAX-ACCESS       not-accessible
    STATUS           current
    DESCRIPTION
        "Entry for the cucsStorageEmbeddedStorageTable table."
    INDEX { cucsStorageEmbeddedStorageInstanceId }
    ::= { cucsStorageEmbeddedStorageTable 1 }

CucsStorageEmbeddedStorageEntry ::= SEQUENCE {
    cucsStorageEmbeddedStorageInstanceId                             CucsManagedObjectId,
    cucsStorageEmbeddedStorageDn                                     CucsManagedObjectDn,
    cucsStorageEmbeddedStorageRn                                     SnmpAdminString,
    cucsStorageEmbeddedStorageBlockSize                              Gauge32,
    cucsStorageEmbeddedStorageConnectionProtocol                     CucsStorageConnectionProtocol,
    cucsStorageEmbeddedStorageNumberOfBlocks                         Unsigned64,
    cucsStorageEmbeddedStorageOperQualifierReason                    SnmpAdminString,
    cucsStorageEmbeddedStorageOperability                            CucsEquipmentOperability,
    cucsStorageEmbeddedStoragePhysicalBlockSize                      Gauge32,
    cucsStorageEmbeddedStoragePresence                               CucsEquipmentPresence,
    cucsStorageEmbeddedStorageSize                                   Unsigned64
}

cucsStorageEmbeddedStorageInstanceId OBJECT-TYPE
    SYNTAX       CucsManagedObjectId
    MAX-ACCESS   not-accessible
    STATUS       current
    DESCRIPTION
        "Instance identifier of the managed object."
    ::= { cucsStorageEmbeddedStorageEntry 1 }

cucsStorageEmbeddedStorageDn OBJECT-TYPE
    SYNTAX       CucsManagedObjectDn
    MAX-ACCESS   read-only
    STATUS       current
    DESCRIPTION
        "Cisco UCS storage:EmbeddedStorage:dn managed object property"
    ::= { cucsStorageEmbeddedStorageEntry 2 }

cucsStorageEmbeddedStorageRn OBJECT-TYPE
    SYNTAX       SnmpAdminString
    MAX-ACCESS   read-only
    STATUS       current
    DESCRIPTION
        "Cisco UCS storage:EmbeddedStorage:rn managed object property"
    ::= { cucsStorageEmbeddedStorageEntry 3 }

cucsStorageEmbeddedStorageBlockSize OBJECT-TYPE
    SYNTAX       Gauge32
    MAX-ACCESS   read-only
    STATUS       current
    DESCRIPTION
        "Cisco UCS storage:EmbeddedStorage:blockSize managed
        object property"
    ::= { cucsStorageEmbeddedStorageEntry 4 }

cucsStorageEmbeddedStorageConnectionProtocol OBJECT-TYPE
    SYNTAX       CucsStorageConnectionProtocol
    MAX-ACCESS   read-only
    STATUS       current
    DESCRIPTION
        "Cisco UCS storage:EmbeddedStorage:connectionProtocol
        managed object property"
    ::= { cucsStorageEmbeddedStorageEntry 5 }

cucsStorageEmbeddedStorageNumberOfBlocks OBJECT-TYPE
    SYNTAX       Unsigned64
    MAX-ACCESS   read-only
    STATUS       current
    DESCRIPTION
        "Cisco UCS storage:EmbeddedStorage:numberOfBlocks
        managed object property"
    ::= { cucsStorageEmbeddedStorageEntry 6 }

cucsStorageEmbeddedStorageOperQualifierReason OBJECT-TYPE
    SYNTAX       SnmpAdminString
    MAX-ACCESS   read-only
    STATUS       current
    DESCRIPTION
        "Cisco UCS storage:EmbeddedStorage:operQualifierReason
        managed object property"
    ::= { cucsStorageEmbeddedStorageEntry 7 }

cucsStorageEmbeddedStorageOperability OBJECT-TYPE
    SYNTAX       CucsEquipmentOperability
    MAX-ACCESS   read-only
    STATUS       current
    DESCRIPTION
        "Cisco UCS storage:EmbeddedStorage:operability
        managed object property"
    ::= { cucsStorageEmbeddedStorageEntry 8 }

cucsStorageEmbeddedStoragePhysicalBlockSize OBJECT-TYPE
    SYNTAX       Gauge32
    MAX-ACCESS   read-only
    STATUS       current
    DESCRIPTION
        "Cisco UCS storage:EmbeddedStorage:physicalBlockSize
        managed object property"
    ::= { cucsStorageEmbeddedStorageEntry 9 }

cucsStorageEmbeddedStoragePresence OBJECT-TYPE
    SYNTAX       CucsEquipmentPresence
    MAX-ACCESS   read-only
    STATUS       current
    DESCRIPTION
        "Cisco UCS storage:EmbeddedStorage:presence managed
        object property"
    ::= { cucsStorageEmbeddedStorageEntry 10 }

cucsStorageEmbeddedStorageSize OBJECT-TYPE
    SYNTAX       Unsigned64
    MAX-ACCESS   read-only
    STATUS       current
    DESCRIPTION
        "Cisco UCS storage:EmbeddedStorage:size managed object property"
    ::= { cucsStorageEmbeddedStorageEntry 11 }

cucsStorageEnclosureTable OBJECT-TYPE
    SYNTAX           SEQUENCE OF CucsStorageEnclosureEntry
    MAX-ACCESS       not-accessible
    STATUS           current
    DESCRIPTION
        "Cisco UCS storage:Enclosure managed object table"
    ::= { cucsStorageObjects 12 }

cucsStorageEnclosureEntry OBJECT-TYPE
    SYNTAX           CucsStorageEnclosureEntry
    MAX-ACCESS       not-accessible
    STATUS           current
    DESCRIPTION
        "Entry for the cucsStorageEnclosureTable table."
    INDEX { cucsStorageEnclosureInstanceId }
    ::= { cucsStorageEnclosureTable 1 }

CucsStorageEnclosureEntry ::= SEQUENCE {
    cucsStorageEnclosureInstanceId                                   CucsManagedObjectId,
    cucsStorageEnclosureDn                                           CucsManagedObjectDn,
    cucsStorageEnclosureRn                                           SnmpAdminString,
    cucsStorageEnclosureId                                           Gauge32,
    cucsStorageEnclosureModel                                        SnmpAdminString,
    cucsStorageEnclosureNumSlots                                     Gauge32,
    cucsStorageEnclosureRevision                                     SnmpAdminString,
    cucsStorageEnclosureSerial                                       SnmpAdminString,
    cucsStorageEnclosureVendor                                       SnmpAdminString,
    cucsStorageEnclosureLc                                           CucsFsmLifecycle,
    cucsStorageEnclosureDescr                                        SnmpAdminString,
    cucsStorageEnclosureType                                         CucsStoragePhysicalHolder,
    cucsStorageEnclosureAdminState                                   CucsStorageEnclosureAdminState,
    cucsStorageEnclosureChassisId                                    Gauge32,
    cucsStorageEnclosureOperQualifierReason                          SnmpAdminString,
    cucsStorageEnclosureOperState                                    CucsEquipmentOperability,
    cucsStorageEnclosureOperability                                  CucsEquipmentOperability,
    cucsStorageEnclosurePerf                                         CucsEquipmentSensorThresholdStatus,
    cucsStorageEnclosurePower                                        CucsEquipmentPowerState,
    cucsStorageEnclosurePresence                                     CucsEquipmentPresence,
    cucsStorageEnclosureServerId                                     Gauge32,
    cucsStorageEnclosureThermal                                      CucsEquipmentSensorThresholdStatus,
    cucsStorageEnclosureVoltage                                      CucsEquipmentSensorThresholdStatus,
    cucsStorageEnclosureFsmDescr                                     SnmpAdminString,
    cucsStorageEnclosureFsmPrev                                      SnmpAdminString,
    cucsStorageEnclosureFsmProgr                                     Gauge32,
    cucsStorageEnclosureFsmRmtInvErrCode                             Gauge32,
    cucsStorageEnclosureFsmRmtInvErrDescr                            SnmpAdminString,
    cucsStorageEnclosureFsmRmtInvRslt                                CucsConditionRemoteInvRslt,
    cucsStorageEnclosureFsmStageDescr                                SnmpAdminString,
    cucsStorageEnclosureFsmStamp                                     DateAndTime,
    cucsStorageEnclosureFsmStatus                                    SnmpAdminString,
    cucsStorageEnclosureFsmTry                                       Gauge32
}

cucsStorageEnclosureInstanceId OBJECT-TYPE
    SYNTAX       CucsManagedObjectId
    MAX-ACCESS   not-accessible
    STATUS       current
    DESCRIPTION
        "Instance identifier of the managed object."
    ::= { cucsStorageEnclosureEntry 1 }

cucsStorageEnclosureDn OBJECT-TYPE
    SYNTAX       CucsManagedObjectDn
    MAX-ACCESS   read-only
    STATUS       current
    DESCRIPTION
        "Cisco UCS storage:Enclosure:dn managed object property"
    ::= { cucsStorageEnclosureEntry 2 }

cucsStorageEnclosureRn OBJECT-TYPE
    SYNTAX       SnmpAdminString
    MAX-ACCESS   read-only
    STATUS       current
    DESCRIPTION
        "Cisco UCS storage:Enclosure:rn managed object property"
    ::= { cucsStorageEnclosureEntry 3 }

cucsStorageEnclosureId OBJECT-TYPE
    SYNTAX       Gauge32
    MAX-ACCESS   read-only
    STATUS       current
    DESCRIPTION
        "Cisco UCS storage:Enclosure:id managed object property"
    ::= { cucsStorageEnclosureEntry 4 }

cucsStorageEnclosureModel OBJECT-TYPE
    SYNTAX       SnmpAdminString
    MAX-ACCESS   read-only
    STATUS       current
    DESCRIPTION
        "Cisco UCS storage:Enclosure:model managed object property"
    ::= { cucsStorageEnclosureEntry 5 }

cucsStorageEnclosureNumSlots OBJECT-TYPE
    SYNTAX       Gauge32
    MAX-ACCESS   read-only
    STATUS       current
    DESCRIPTION
        "Cisco UCS storage:Enclosure:numSlots managed object property"
    ::= { cucsStorageEnclosureEntry 6 }

cucsStorageEnclosureRevision OBJECT-TYPE
    SYNTAX       SnmpAdminString
    MAX-ACCESS   read-only
    STATUS       current
    DESCRIPTION
        "Cisco UCS storage:Enclosure:revision managed object property"
    ::= { cucsStorageEnclosureEntry 7 }

cucsStorageEnclosureSerial OBJECT-TYPE
    SYNTAX       SnmpAdminString
    MAX-ACCESS   read-only
    STATUS       current
    DESCRIPTION
        "Cisco UCS storage:Enclosure:serial managed object property"
    ::= { cucsStorageEnclosureEntry 8 }

cucsStorageEnclosureVendor OBJECT-TYPE
    SYNTAX       SnmpAdminString
    MAX-ACCESS   read-only
    STATUS       current
    DESCRIPTION
        "Cisco UCS storage:Enclosure:vendor managed object property"
    ::= { cucsStorageEnclosureEntry 9 }

cucsStorageEnclosureLc OBJECT-TYPE
    SYNTAX       CucsFsmLifecycle
    MAX-ACCESS   read-only
    STATUS       current
    DESCRIPTION
        "Cisco UCS storage:Enclosure:lc managed object property"
    ::= { cucsStorageEnclosureEntry 10 }

cucsStorageEnclosureDescr OBJECT-TYPE
    SYNTAX       SnmpAdminString
    MAX-ACCESS   read-only
    STATUS       current
    DESCRIPTION
        "Cisco UCS storage:Enclosure:descr managed object property"
    ::= { cucsStorageEnclosureEntry 11 }

cucsStorageEnclosureType OBJECT-TYPE
    SYNTAX       CucsStoragePhysicalHolder
    MAX-ACCESS   read-only
    STATUS       current
    DESCRIPTION
        "Cisco UCS storage:Enclosure:type managed object property"
    ::= { cucsStorageEnclosureEntry 13 }

cucsStorageEnclosureAdminState OBJECT-TYPE
    SYNTAX       CucsStorageEnclosureAdminState
    MAX-ACCESS   read-only
    STATUS       current
    DESCRIPTION
        "Cisco UCS storage:Enclosure:adminState managed object property"
    ::= { cucsStorageEnclosureEntry 14 }

cucsStorageEnclosureChassisId OBJECT-TYPE
    SYNTAX       Gauge32
    MAX-ACCESS   read-only
    STATUS       current
    DESCRIPTION
        "Cisco UCS storage:Enclosure:chassisId managed object property"
    ::= { cucsStorageEnclosureEntry 15 }

cucsStorageEnclosureOperQualifierReason OBJECT-TYPE
    SYNTAX       SnmpAdminString
    MAX-ACCESS   read-only
    STATUS       current
    DESCRIPTION
        "Cisco UCS storage:Enclosure:operQualifierReason
        managed object property"
    ::= { cucsStorageEnclosureEntry 16 }

cucsStorageEnclosureOperState OBJECT-TYPE
    SYNTAX       CucsEquipmentOperability
    MAX-ACCESS   read-only
    STATUS       current
    DESCRIPTION
        "Cisco UCS storage:Enclosure:operState managed object property"
    ::= { cucsStorageEnclosureEntry 17 }

cucsStorageEnclosureOperability OBJECT-TYPE
    SYNTAX       CucsEquipmentOperability
    MAX-ACCESS   read-only
    STATUS       current
    DESCRIPTION
        "Cisco UCS storage:Enclosure:operability managed object property"
    ::= { cucsStorageEnclosureEntry 18 }

cucsStorageEnclosurePerf OBJECT-TYPE
    SYNTAX       CucsEquipmentSensorThresholdStatus
    MAX-ACCESS   read-only
    STATUS       current
    DESCRIPTION
        "Cisco UCS storage:Enclosure:perf managed object property"
    ::= { cucsStorageEnclosureEntry 19 }

cucsStorageEnclosurePower OBJECT-TYPE
    SYNTAX       CucsEquipmentPowerState
    MAX-ACCESS   read-only
    STATUS       current
    DESCRIPTION
        "Cisco UCS storage:Enclosure:power managed object property"
    ::= { cucsStorageEnclosureEntry 20 }

cucsStorageEnclosurePresence OBJECT-TYPE
    SYNTAX       CucsEquipmentPresence
    MAX-ACCESS   read-only
    STATUS       current
    DESCRIPTION
        "Cisco UCS storage:Enclosure:presence managed object property"
    ::= { cucsStorageEnclosureEntry 21 }

cucsStorageEnclosureServerId OBJECT-TYPE
    SYNTAX       Gauge32
    MAX-ACCESS   read-only
    STATUS       current
    DESCRIPTION
        "Cisco UCS storage:Enclosure:serverId managed object property"
    ::= { cucsStorageEnclosureEntry 22 }

cucsStorageEnclosureThermal OBJECT-TYPE
    SYNTAX       CucsEquipmentSensorThresholdStatus
    MAX-ACCESS   read-only
    STATUS       current
    DESCRIPTION
        "Cisco UCS storage:Enclosure:thermal managed object property"
    ::= { cucsStorageEnclosureEntry 23 }

cucsStorageEnclosureVoltage OBJECT-TYPE
    SYNTAX       CucsEquipmentSensorThresholdStatus
    MAX-ACCESS   read-only
    STATUS       current
    DESCRIPTION
        "Cisco UCS storage:Enclosure:voltage managed object property"
    ::= { cucsStorageEnclosureEntry 24 }

cucsStorageEnclosureFsmDescr OBJECT-TYPE
    SYNTAX       SnmpAdminString
    MAX-ACCESS   read-only
    STATUS       current
    DESCRIPTION
        "Cisco UCS storage:Enclosure:fsmDescr managed object property"
    ::= { cucsStorageEnclosureEntry 25 }

cucsStorageEnclosureFsmPrev OBJECT-TYPE
    SYNTAX       SnmpAdminString
    MAX-ACCESS   read-only
    STATUS       current
    DESCRIPTION
        "Cisco UCS storage:Enclosure:fsmPrev managed object property"
    ::= { cucsStorageEnclosureEntry 26 }

cucsStorageEnclosureFsmProgr OBJECT-TYPE
    SYNTAX       Gauge32
    MAX-ACCESS   read-only
    STATUS       current
    DESCRIPTION
        "Cisco UCS storage:Enclosure:fsmProgr managed object property"
    ::= { cucsStorageEnclosureEntry 27 }

cucsStorageEnclosureFsmRmtInvErrCode OBJECT-TYPE
    SYNTAX       Gauge32
    MAX-ACCESS   read-only
    STATUS       current
    DESCRIPTION
        "Cisco UCS storage:Enclosure:fsmRmtInvErrCode managed
        object property"
    ::= { cucsStorageEnclosureEntry 28 }

cucsStorageEnclosureFsmRmtInvErrDescr OBJECT-TYPE
    SYNTAX       SnmpAdminString
    MAX-ACCESS   read-only
    STATUS       current
    DESCRIPTION
        "Cisco UCS storage:Enclosure:fsmRmtInvErrDescr
        managed object property"
    ::= { cucsStorageEnclosureEntry 29 }

cucsStorageEnclosureFsmRmtInvRslt OBJECT-TYPE
    SYNTAX       CucsConditionRemoteInvRslt
    MAX-ACCESS   read-only
    STATUS       current
    DESCRIPTION
        "Cisco UCS storage:Enclosure:fsmRmtInvRslt managed
        object property"
    ::= { cucsStorageEnclosureEntry 30 }

cucsStorageEnclosureFsmStageDescr OBJECT-TYPE
    SYNTAX       SnmpAdminString
    MAX-ACCESS   read-only
    STATUS       current
    DESCRIPTION
        "Cisco UCS storage:Enclosure:fsmStageDescr managed
        object property"
    ::= { cucsStorageEnclosureEntry 31 }

cucsStorageEnclosureFsmStamp OBJECT-TYPE
    SYNTAX       DateAndTime
    MAX-ACCESS   read-only
    STATUS       current
    DESCRIPTION
        "Cisco UCS storage:Enclosure:fsmStamp managed object property"
    ::= { cucsStorageEnclosureEntry 32 }

cucsStorageEnclosureFsmStatus OBJECT-TYPE
    SYNTAX       SnmpAdminString
    MAX-ACCESS   read-only
    STATUS       current
    DESCRIPTION
        "Cisco UCS storage:Enclosure:fsmStatus managed object property"
    ::= { cucsStorageEnclosureEntry 33 }

cucsStorageEnclosureFsmTry OBJECT-TYPE
    SYNTAX       Gauge32
    MAX-ACCESS   read-only
    STATUS       current
    DESCRIPTION
        "Cisco UCS storage:Enclosure:fsmTry managed object property"
    ::= { cucsStorageEnclosureEntry 34 }

cucsStorageEnclosureCapTable OBJECT-TYPE
    SYNTAX           SEQUENCE OF CucsStorageEnclosureCapEntry
    MAX-ACCESS       not-accessible
    STATUS           current
    DESCRIPTION
        "Cisco UCS storage:EnclosureCap managed object table"
    ::= { cucsStorageObjects 94 }

cucsStorageEnclosureCapEntry OBJECT-TYPE
    SYNTAX           CucsStorageEnclosureCapEntry
    MAX-ACCESS       not-accessible
    STATUS           current
    DESCRIPTION
        "Entry for the cucsStorageEnclosureCapTable table."
    INDEX { cucsStorageEnclosureCapInstanceId }
    ::= { cucsStorageEnclosureCapTable 1 }

CucsStorageEnclosureCapEntry ::= SEQUENCE {
    cucsStorageEnclosureCapInstanceId                                CucsManagedObjectId,
    cucsStorageEnclosureCapDn                                        CucsManagedObjectDn,
    cucsStorageEnclosureCapRn                                        SnmpAdminString,
    cucsStorageEnclosureCapDescr                                     SnmpAdminString,
    cucsStorageEnclosureCapId                                        Gauge32,
    cucsStorageEnclosureCapNumSlots                                  Gauge32,
    cucsStorageEnclosureCapType                                      CucsStoragePhysicalHolder,
    cucsStorageEnclosureCapDiskVariant                               SnmpAdminString,
    cucsStorageEnclosureCapRemovable                                 TruthValue
}

cucsStorageEnclosureCapInstanceId OBJECT-TYPE
    SYNTAX       CucsManagedObjectId
    MAX-ACCESS   not-accessible
    STATUS       current
    DESCRIPTION
        "Instance identifier of the managed object."
    ::= { cucsStorageEnclosureCapEntry 1 }

cucsStorageEnclosureCapDn OBJECT-TYPE
    SYNTAX       CucsManagedObjectDn
    MAX-ACCESS   read-only
    STATUS       current
    DESCRIPTION
        "Cisco UCS storage:EnclosureCap:dn managed object property"
    ::= { cucsStorageEnclosureCapEntry 2 }

cucsStorageEnclosureCapRn OBJECT-TYPE
    SYNTAX       SnmpAdminString
    MAX-ACCESS   read-only
    STATUS       current
    DESCRIPTION
        "Cisco UCS storage:EnclosureCap:rn managed object property"
    ::= { cucsStorageEnclosureCapEntry 3 }

cucsStorageEnclosureCapDescr OBJECT-TYPE
    SYNTAX       SnmpAdminString
    MAX-ACCESS   read-only
    STATUS       current
    DESCRIPTION
        "Cisco UCS storage:EnclosureCap:descr managed object property"
    ::= { cucsStorageEnclosureCapEntry 4 }

cucsStorageEnclosureCapId OBJECT-TYPE
    SYNTAX       Gauge32
    MAX-ACCESS   read-only
    STATUS       current
    DESCRIPTION
        "Cisco UCS storage:EnclosureCap:id managed object property"
    ::= { cucsStorageEnclosureCapEntry 5 }

cucsStorageEnclosureCapNumSlots OBJECT-TYPE
    SYNTAX       Gauge32
    MAX-ACCESS   read-only
    STATUS       current
    DESCRIPTION
        "Cisco UCS storage:EnclosureCap:numSlots managed object property"
    ::= { cucsStorageEnclosureCapEntry 6 }

cucsStorageEnclosureCapType OBJECT-TYPE
    SYNTAX       CucsStoragePhysicalHolder
    MAX-ACCESS   read-only
    STATUS       current
    DESCRIPTION
        "Cisco UCS storage:EnclosureCap:type managed object property"
    ::= { cucsStorageEnclosureCapEntry 7 }

cucsStorageEnclosureCapDiskVariant OBJECT-TYPE
    SYNTAX       SnmpAdminString
    MAX-ACCESS   read-only
    STATUS       current
    DESCRIPTION
        "Cisco UCS storage:EnclosureCap:diskVariant managed
        object property"
    ::= { cucsStorageEnclosureCapEntry 8 }

cucsStorageEnclosureCapRemovable OBJECT-TYPE
    SYNTAX       TruthValue
    MAX-ACCESS   read-only
    STATUS       current
    DESCRIPTION
        "Cisco UCS storage:EnclosureCap:removable managed object property"
    ::= { cucsStorageEnclosureCapEntry 9 }

cucsStorageEnclosureDiskSlotEpTable OBJECT-TYPE
    SYNTAX           SEQUENCE OF CucsStorageEnclosureDiskSlotEpEntry
    MAX-ACCESS       not-accessible
    STATUS           current
    DESCRIPTION
        "Cisco UCS storage:EnclosureDiskSlotEp managed object table"
    ::= { cucsStorageObjects 54 }

cucsStorageEnclosureDiskSlotEpEntry OBJECT-TYPE
    SYNTAX           CucsStorageEnclosureDiskSlotEpEntry
    MAX-ACCESS       not-accessible
    STATUS           current
    DESCRIPTION
        "Entry for the cucsStorageEnclosureDiskSlotEpTable table."
    INDEX { cucsStorageEnclosureDiskSlotEpInstanceId }
    ::= { cucsStorageEnclosureDiskSlotEpTable 1 }

CucsStorageEnclosureDiskSlotEpEntry ::= SEQUENCE {
    cucsStorageEnclosureDiskSlotEpInstanceId                         CucsManagedObjectId,
    cucsStorageEnclosureDiskSlotEpDn                                 CucsManagedObjectDn,
    cucsStorageEnclosureDiskSlotEpRn                                 SnmpAdminString,
    cucsStorageEnclosureDiskSlotEpConfiguration                      CucsStorageConfiguration,
    cucsStorageEnclosureDiskSlotEpId                                 Gauge32,
    cucsStorageEnclosureDiskSlotEpOperQualifierReason                SnmpAdminString,
    cucsStorageEnclosureDiskSlotEpOperability                        CucsEquipmentOperability,
    cucsStorageEnclosureDiskSlotEpPeerDn                             SnmpAdminString,
    cucsStorageEnclosureDiskSlotEpPresence                           CucsEquipmentPresence,
    cucsStorageEnclosureDiskSlotEpOwnership                          CucsStorageEnclosureDiskSlotEpOwnership,
    cucsStorageEnclosureDiskSlotEpAutoZoneCause                      CucsStorageEnclosureDiskSlotEpAutoZoneCause,
    cucsStorageEnclosureDiskSlotEpLc                                 CucsFsmLifecycle
}

cucsStorageEnclosureDiskSlotEpInstanceId OBJECT-TYPE
    SYNTAX       CucsManagedObjectId
    MAX-ACCESS   not-accessible
    STATUS       current
    DESCRIPTION
        "Instance identifier of the managed object."
    ::= { cucsStorageEnclosureDiskSlotEpEntry 1 }

cucsStorageEnclosureDiskSlotEpDn OBJECT-TYPE
    SYNTAX       CucsManagedObjectDn
    MAX-ACCESS   read-only
    STATUS       current
    DESCRIPTION
        "Cisco UCS storage:EnclosureDiskSlotEp:dn managed object property"
    ::= { cucsStorageEnclosureDiskSlotEpEntry 2 }

cucsStorageEnclosureDiskSlotEpRn OBJECT-TYPE
    SYNTAX       SnmpAdminString
    MAX-ACCESS   read-only
    STATUS       current
    DESCRIPTION
        "Cisco UCS storage:EnclosureDiskSlotEp:rn managed object property"
    ::= { cucsStorageEnclosureDiskSlotEpEntry 3 }

cucsStorageEnclosureDiskSlotEpConfiguration OBJECT-TYPE
    SYNTAX       CucsStorageConfiguration
    MAX-ACCESS   read-only
    STATUS       current
    DESCRIPTION
        "Cisco UCS storage:EnclosureDiskSlotEp:configuration
        managed object property"
    ::= { cucsStorageEnclosureDiskSlotEpEntry 4 }

cucsStorageEnclosureDiskSlotEpId OBJECT-TYPE
    SYNTAX       Gauge32
    MAX-ACCESS   read-only
    STATUS       current
    DESCRIPTION
        "Cisco UCS storage:EnclosureDiskSlotEp:id managed object property"
    ::= { cucsStorageEnclosureDiskSlotEpEntry 5 }

cucsStorageEnclosureDiskSlotEpOperQualifierReason OBJECT-TYPE
    SYNTAX       SnmpAdminString
    MAX-ACCESS   read-only
    STATUS       current
    DESCRIPTION
        "Cisco UCS storage:EnclosureDiskSlotEp:operQualifierReason
        managed object property"
    ::= { cucsStorageEnclosureDiskSlotEpEntry 6 }

cucsStorageEnclosureDiskSlotEpOperability OBJECT-TYPE
    SYNTAX       CucsEquipmentOperability
    MAX-ACCESS   read-only
    STATUS       current
    DESCRIPTION
        "Cisco UCS storage:EnclosureDiskSlotEp:operability
        managed object property"
    ::= { cucsStorageEnclosureDiskSlotEpEntry 7 }

cucsStorageEnclosureDiskSlotEpPeerDn OBJECT-TYPE
    SYNTAX       SnmpAdminString
    MAX-ACCESS   read-only
    STATUS       current
    DESCRIPTION
        "Cisco UCS storage:EnclosureDiskSlotEp:peerDn managed
        object property"
    ::= { cucsStorageEnclosureDiskSlotEpEntry 8 }

cucsStorageEnclosureDiskSlotEpPresence OBJECT-TYPE
    SYNTAX       CucsEquipmentPresence
    MAX-ACCESS   read-only
    STATUS       current
    DESCRIPTION
        "Cisco UCS storage:EnclosureDiskSlotEp:presence
        managed object property"
    ::= { cucsStorageEnclosureDiskSlotEpEntry 9 }

cucsStorageEnclosureDiskSlotEpOwnership OBJECT-TYPE
    SYNTAX       CucsStorageEnclosureDiskSlotEpOwnership
    MAX-ACCESS   read-only
    STATUS       current
    DESCRIPTION
        "Cisco UCS storage:EnclosureDiskSlotEp:ownership
        managed object property"
    ::= { cucsStorageEnclosureDiskSlotEpEntry 10 }

cucsStorageEnclosureDiskSlotEpAutoZoneCause OBJECT-TYPE
    SYNTAX       CucsStorageEnclosureDiskSlotEpAutoZoneCause
    MAX-ACCESS   read-only
    STATUS       current
    DESCRIPTION
        "Cisco UCS storage:EnclosureDiskSlotEp:autoZoneCause
        managed object property"
    ::= { cucsStorageEnclosureDiskSlotEpEntry 11 }

cucsStorageEnclosureDiskSlotEpLc OBJECT-TYPE
    SYNTAX       CucsFsmLifecycle
    MAX-ACCESS   read-only
    STATUS       current
    DESCRIPTION
        "Cisco UCS storage:EnclosureDiskSlotEp:lc managed object property"
    ::= { cucsStorageEnclosureDiskSlotEpEntry 12 }

cucsStorageEnclosureFsmTable OBJECT-TYPE
    SYNTAX           SEQUENCE OF CucsStorageEnclosureFsmEntry
    MAX-ACCESS       not-accessible
    STATUS           current
    DESCRIPTION
        "Cisco UCS storage:EnclosureFsm managed object table"
    ::= { cucsStorageObjects 116 }

cucsStorageEnclosureFsmEntry OBJECT-TYPE
    SYNTAX           CucsStorageEnclosureFsmEntry
    MAX-ACCESS       not-accessible
    STATUS           current
    DESCRIPTION
        "Entry for the cucsStorageEnclosureFsmTable table."
    INDEX { cucsStorageEnclosureFsmInstanceId }
    ::= { cucsStorageEnclosureFsmTable 1 }

CucsStorageEnclosureFsmEntry ::= SEQUENCE {
    cucsStorageEnclosureFsmInstanceId                                CucsManagedObjectId,
    cucsStorageEnclosureFsmDn                                        CucsManagedObjectDn,
    cucsStorageEnclosureFsmRn                                        SnmpAdminString,
    cucsStorageEnclosureFsmCompletionTime                            DateAndTime,
    cucsStorageEnclosureFsmCurrentFsm                                CucsStorageEnclosureFsmCurrentFsm,
    cucsStorageEnclosureFsmDescrData                                 SnmpAdminString,
    cucsStorageEnclosureFsmFsmStatus                                 CucsFsmFsmStageStatus,
    cucsStorageEnclosureFsmProgress                                  Gauge32,
    cucsStorageEnclosureFsmRmtErrCode                                Gauge32,
    cucsStorageEnclosureFsmRmtErrDescr                               SnmpAdminString,
    cucsStorageEnclosureFsmRmtRslt                                   CucsConditionRemoteInvRslt
}

cucsStorageEnclosureFsmInstanceId OBJECT-TYPE
    SYNTAX       CucsManagedObjectId
    MAX-ACCESS   not-accessible
    STATUS       current
    DESCRIPTION
        "Instance identifier of the managed object."
    ::= { cucsStorageEnclosureFsmEntry 1 }

cucsStorageEnclosureFsmDn OBJECT-TYPE
    SYNTAX       CucsManagedObjectDn
    MAX-ACCESS   read-only
    STATUS       current
    DESCRIPTION
        "Cisco UCS storage:EnclosureFsm:dn managed object property"
    ::= { cucsStorageEnclosureFsmEntry 2 }

cucsStorageEnclosureFsmRn OBJECT-TYPE
    SYNTAX       SnmpAdminString
    MAX-ACCESS   read-only
    STATUS       current
    DESCRIPTION
        "Cisco UCS storage:EnclosureFsm:rn managed object property"
    ::= { cucsStorageEnclosureFsmEntry 3 }

cucsStorageEnclosureFsmCompletionTime OBJECT-TYPE
    SYNTAX       DateAndTime
    MAX-ACCESS   read-only
    STATUS       current
    DESCRIPTION
        "Cisco UCS storage:EnclosureFsm:completionTime
        managed object property"
    ::= { cucsStorageEnclosureFsmEntry 4 }

cucsStorageEnclosureFsmCurrentFsm OBJECT-TYPE
    SYNTAX       CucsStorageEnclosureFsmCurrentFsm
    MAX-ACCESS   read-only
    STATUS       current
    DESCRIPTION
        "Cisco UCS storage:EnclosureFsm:currentFsm managed
        object property"
    ::= { cucsStorageEnclosureFsmEntry 5 }

cucsStorageEnclosureFsmDescrData OBJECT-TYPE
    SYNTAX       SnmpAdminString
    MAX-ACCESS   read-only
    STATUS       current
    DESCRIPTION
        "Cisco UCS storage:EnclosureFsm:descr managed object property"
    ::= { cucsStorageEnclosureFsmEntry 6 }

cucsStorageEnclosureFsmFsmStatus OBJECT-TYPE
    SYNTAX       CucsFsmFsmStageStatus
    MAX-ACCESS   read-only
    STATUS       current
    DESCRIPTION
        "Cisco UCS storage:EnclosureFsm:fsmStatus managed object property"
    ::= { cucsStorageEnclosureFsmEntry 7 }

cucsStorageEnclosureFsmProgress OBJECT-TYPE
    SYNTAX       Gauge32
    MAX-ACCESS   read-only
    STATUS       current
    DESCRIPTION
        "Cisco UCS storage:EnclosureFsm:progress managed object property"
    ::= { cucsStorageEnclosureFsmEntry 8 }

cucsStorageEnclosureFsmRmtErrCode OBJECT-TYPE
    SYNTAX       Gauge32
    MAX-ACCESS   read-only
    STATUS       current
    DESCRIPTION
        "Cisco UCS storage:EnclosureFsm:rmtErrCode managed
        object property"
    ::= { cucsStorageEnclosureFsmEntry 9 }

cucsStorageEnclosureFsmRmtErrDescr OBJECT-TYPE
    SYNTAX       SnmpAdminString
    MAX-ACCESS   read-only
    STATUS       current
    DESCRIPTION
        "Cisco UCS storage:EnclosureFsm:rmtErrDescr managed
        object property"
    ::= { cucsStorageEnclosureFsmEntry 10 }

cucsStorageEnclosureFsmRmtRslt OBJECT-TYPE
    SYNTAX       CucsConditionRemoteInvRslt
    MAX-ACCESS   read-only
    STATUS       current
    DESCRIPTION
        "Cisco UCS storage:EnclosureFsm:rmtRslt managed object property"
    ::= { cucsStorageEnclosureFsmEntry 11 }

cucsStorageEnclosureFsmStageTable OBJECT-TYPE
    SYNTAX           SEQUENCE OF CucsStorageEnclosureFsmStageEntry
    MAX-ACCESS       not-accessible
    STATUS           current
    DESCRIPTION
        "Cisco UCS storage:EnclosureFsmStage managed object table"
    ::= { cucsStorageObjects 117 }

cucsStorageEnclosureFsmStageEntry OBJECT-TYPE
    SYNTAX           CucsStorageEnclosureFsmStageEntry
    MAX-ACCESS       not-accessible
    STATUS           current
    DESCRIPTION
        "Entry for the cucsStorageEnclosureFsmStageTable table."
    INDEX { cucsStorageEnclosureFsmStageInstanceId }
    ::= { cucsStorageEnclosureFsmStageTable 1 }

CucsStorageEnclosureFsmStageEntry ::= SEQUENCE {
    cucsStorageEnclosureFsmStageInstanceId                           CucsManagedObjectId,
    cucsStorageEnclosureFsmStageDn                                   CucsManagedObjectDn,
    cucsStorageEnclosureFsmStageRn                                   SnmpAdminString,
    cucsStorageEnclosureFsmStageDescrData                            SnmpAdminString,
    cucsStorageEnclosureFsmStageLastUpdateTime                       DateAndTime,
    cucsStorageEnclosureFsmStageName                                 CucsStorageEnclosureFsmStageName,
    cucsStorageEnclosureFsmStageOrder                                Gauge32,
    cucsStorageEnclosureFsmStageRetry                                Gauge32,
    cucsStorageEnclosureFsmStageStageStatus                          CucsFsmFsmStageStatus
}

cucsStorageEnclosureFsmStageInstanceId OBJECT-TYPE
    SYNTAX       CucsManagedObjectId
    MAX-ACCESS   not-accessible
    STATUS       current
    DESCRIPTION
        "Instance identifier of the managed object."
    ::= { cucsStorageEnclosureFsmStageEntry 1 }

cucsStorageEnclosureFsmStageDn OBJECT-TYPE
    SYNTAX       CucsManagedObjectDn
    MAX-ACCESS   read-only
    STATUS       current
    DESCRIPTION
        "Cisco UCS storage:EnclosureFsmStage:dn managed object property"
    ::= { cucsStorageEnclosureFsmStageEntry 2 }

cucsStorageEnclosureFsmStageRn OBJECT-TYPE
    SYNTAX       SnmpAdminString
    MAX-ACCESS   read-only
    STATUS       current
    DESCRIPTION
        "Cisco UCS storage:EnclosureFsmStage:rn managed object property"
    ::= { cucsStorageEnclosureFsmStageEntry 3 }

cucsStorageEnclosureFsmStageDescrData OBJECT-TYPE
    SYNTAX       SnmpAdminString
    MAX-ACCESS   read-only
    STATUS       current
    DESCRIPTION
        "Cisco UCS storage:EnclosureFsmStage:descr managed
        object property"
    ::= { cucsStorageEnclosureFsmStageEntry 4 }

cucsStorageEnclosureFsmStageLastUpdateTime OBJECT-TYPE
    SYNTAX       DateAndTime
    MAX-ACCESS   read-only
    STATUS       current
    DESCRIPTION
        "Cisco UCS storage:EnclosureFsmStage:lastUpdateTime
        managed object property"
    ::= { cucsStorageEnclosureFsmStageEntry 5 }

cucsStorageEnclosureFsmStageName OBJECT-TYPE
    SYNTAX       CucsStorageEnclosureFsmStageName
    MAX-ACCESS   read-only
    STATUS       current
    DESCRIPTION
        "Cisco UCS storage:EnclosureFsmStage:name managed object property"
    ::= { cucsStorageEnclosureFsmStageEntry 6 }

cucsStorageEnclosureFsmStageOrder OBJECT-TYPE
    SYNTAX       Gauge32
    MAX-ACCESS   read-only
    STATUS       current
    DESCRIPTION
        "Cisco UCS storage:EnclosureFsmStage:order managed
        object property"
    ::= { cucsStorageEnclosureFsmStageEntry 7 }

cucsStorageEnclosureFsmStageRetry OBJECT-TYPE
    SYNTAX       Gauge32
    MAX-ACCESS   read-only
    STATUS       current
    DESCRIPTION
        "Cisco UCS storage:EnclosureFsmStage:retry managed
        object property"
    ::= { cucsStorageEnclosureFsmStageEntry 8 }

cucsStorageEnclosureFsmStageStageStatus OBJECT-TYPE
    SYNTAX       CucsFsmFsmStageStatus
    MAX-ACCESS   read-only
    STATUS       current
    DESCRIPTION
        "Cisco UCS storage:EnclosureFsmStage:stageStatus
        managed object property"
    ::= { cucsStorageEnclosureFsmStageEntry 9 }

cucsStorageEnclosureFsmTaskTable OBJECT-TYPE
    SYNTAX           SEQUENCE OF CucsStorageEnclosureFsmTaskEntry
    MAX-ACCESS       not-accessible
    STATUS           current
    DESCRIPTION
        "Cisco UCS storage:EnclosureFsmTask managed object table"
    ::= { cucsStorageObjects 118 }

cucsStorageEnclosureFsmTaskEntry OBJECT-TYPE
    SYNTAX           CucsStorageEnclosureFsmTaskEntry
    MAX-ACCESS       not-accessible
    STATUS           current
    DESCRIPTION
        "Entry for the cucsStorageEnclosureFsmTaskTable table."
    INDEX { cucsStorageEnclosureFsmTaskInstanceId }
    ::= { cucsStorageEnclosureFsmTaskTable 1 }

CucsStorageEnclosureFsmTaskEntry ::= SEQUENCE {
    cucsStorageEnclosureFsmTaskInstanceId                            CucsManagedObjectId,
    cucsStorageEnclosureFsmTaskDn                                    CucsManagedObjectDn,
    cucsStorageEnclosureFsmTaskRn                                    SnmpAdminString,
    cucsStorageEnclosureFsmTaskCompletion                            CucsFsmCompletion,
    cucsStorageEnclosureFsmTaskFlags                                 CucsFsmFlags,
    cucsStorageEnclosureFsmTaskItem                                  CucsStorageEnclosureFsmTaskItem,
    cucsStorageEnclosureFsmTaskSeqId                                 Gauge32
}

cucsStorageEnclosureFsmTaskInstanceId OBJECT-TYPE
    SYNTAX       CucsManagedObjectId
    MAX-ACCESS   not-accessible
    STATUS       current
    DESCRIPTION
        "Instance identifier of the managed object."
    ::= { cucsStorageEnclosureFsmTaskEntry 1 }

cucsStorageEnclosureFsmTaskDn OBJECT-TYPE
    SYNTAX       CucsManagedObjectDn
    MAX-ACCESS   read-only
    STATUS       current
    DESCRIPTION
        "Cisco UCS storage:EnclosureFsmTask:dn managed object property"
    ::= { cucsStorageEnclosureFsmTaskEntry 2 }

cucsStorageEnclosureFsmTaskRn OBJECT-TYPE
    SYNTAX       SnmpAdminString
    MAX-ACCESS   read-only
    STATUS       current
    DESCRIPTION
        "Cisco UCS storage:EnclosureFsmTask:rn managed object property"
    ::= { cucsStorageEnclosureFsmTaskEntry 3 }

cucsStorageEnclosureFsmTaskCompletion OBJECT-TYPE
    SYNTAX       CucsFsmCompletion
    MAX-ACCESS   read-only
    STATUS       current
    DESCRIPTION
        "Cisco UCS storage:EnclosureFsmTask:completion
        managed object property"
    ::= { cucsStorageEnclosureFsmTaskEntry 4 }

cucsStorageEnclosureFsmTaskFlags OBJECT-TYPE
    SYNTAX       CucsFsmFlags
    MAX-ACCESS   read-only
    STATUS       current
    DESCRIPTION
        "Cisco UCS storage:EnclosureFsmTask:flags managed object property"
    ::= { cucsStorageEnclosureFsmTaskEntry 5 }

cucsStorageEnclosureFsmTaskItem OBJECT-TYPE
    SYNTAX       CucsStorageEnclosureFsmTaskItem
    MAX-ACCESS   read-only
    STATUS       current
    DESCRIPTION
        "Cisco UCS storage:EnclosureFsmTask:item managed object property"
    ::= { cucsStorageEnclosureFsmTaskEntry 6 }

cucsStorageEnclosureFsmTaskSeqId OBJECT-TYPE
    SYNTAX       Gauge32
    MAX-ACCESS   read-only
    STATUS       current
    DESCRIPTION
        "Cisco UCS storage:EnclosureFsmTask:seqId managed object property"
    ::= { cucsStorageEnclosureFsmTaskEntry 7 }

cucsStorageEnclosureLocalDiskConfigTable OBJECT-TYPE
    SYNTAX           SEQUENCE OF CucsStorageEnclosureLocalDiskConfigEntry
    MAX-ACCESS       not-accessible
    STATUS           current
    DESCRIPTION
        "Cisco UCS storage:EnclosureLocalDiskConfig managed object table"
    ::= { cucsStorageObjects 111 }

cucsStorageEnclosureLocalDiskConfigEntry OBJECT-TYPE
    SYNTAX           CucsStorageEnclosureLocalDiskConfigEntry
    MAX-ACCESS       not-accessible
    STATUS           current
    DESCRIPTION
        "Entry for the cucsStorageEnclosureLocalDiskConfigTable table."
    INDEX { cucsStorageEnclosureLocalDiskConfigInstanceId }
    ::= { cucsStorageEnclosureLocalDiskConfigTable 1 }

CucsStorageEnclosureLocalDiskConfigEntry ::= SEQUENCE {
    cucsStorageEnclosureLocalDiskConfigInstanceId                    CucsManagedObjectId,
    cucsStorageEnclosureLocalDiskConfigDn                            CucsManagedObjectDn,
    cucsStorageEnclosureLocalDiskConfigRn                            SnmpAdminString,
    cucsStorageEnclosureLocalDiskConfigBlockSize                     Gauge32,
    cucsStorageEnclosureLocalDiskConfigConnectionProtocol            CucsStorageConnectionProtocol,
    cucsStorageEnclosureLocalDiskConfigDeviceType                    CucsStorageTechnology,
    cucsStorageEnclosureLocalDiskConfigFirmwareVersion               SnmpAdminString,
    cucsStorageEnclosureLocalDiskConfigId                            Gauge32,
    cucsStorageEnclosureLocalDiskConfigLinkSpeed                     CucsStorageLinkSpeed,
    cucsStorageEnclosureLocalDiskConfigLinkState                     CucsStorageEpLinkState,
    cucsStorageEnclosureLocalDiskConfigLinkStateReason               SnmpAdminString,
    cucsStorageEnclosureLocalDiskConfigModel                         SnmpAdminString,
    cucsStorageEnclosureLocalDiskConfigNumberOfBlocks                Unsigned64,
    cucsStorageEnclosureLocalDiskConfigOperQualifierReason           SnmpAdminString,
    cucsStorageEnclosureLocalDiskConfigOperability                   CucsEquipmentOperability,
    cucsStorageEnclosureLocalDiskConfigPhysicalBlockSize             Gauge32,
    cucsStorageEnclosureLocalDiskConfigPowerState                    CucsStoragePowerState,
    cucsStorageEnclosureLocalDiskConfigPresence                      CucsEquipmentPresence,
    cucsStorageEnclosureLocalDiskConfigRevision                      SnmpAdminString,
    cucsStorageEnclosureLocalDiskConfigScsiDiskState                 CucsSesScsiDriveStatus,
    cucsStorageEnclosureLocalDiskConfigSerial                        SnmpAdminString,
    cucsStorageEnclosureLocalDiskConfigSize                          Unsigned64,
    cucsStorageEnclosureLocalDiskConfigVendor                        SnmpAdminString
}

cucsStorageEnclosureLocalDiskConfigInstanceId OBJECT-TYPE
    SYNTAX       CucsManagedObjectId
    MAX-ACCESS   not-accessible
    STATUS       current
    DESCRIPTION
        "Instance identifier of the managed object."
    ::= { cucsStorageEnclosureLocalDiskConfigEntry 1 }

cucsStorageEnclosureLocalDiskConfigDn OBJECT-TYPE
    SYNTAX       CucsManagedObjectDn
    MAX-ACCESS   read-only
    STATUS       current
    DESCRIPTION
        "Cisco UCS storage:EnclosureLocalDiskConfig:dn
        managed object property"
    ::= { cucsStorageEnclosureLocalDiskConfigEntry 2 }

cucsStorageEnclosureLocalDiskConfigRn OBJECT-TYPE
    SYNTAX       SnmpAdminString
    MAX-ACCESS   read-only
    STATUS       current
    DESCRIPTION
        "Cisco UCS storage:EnclosureLocalDiskConfig:rn
        managed object property"
    ::= { cucsStorageEnclosureLocalDiskConfigEntry 3 }

cucsStorageEnclosureLocalDiskConfigBlockSize OBJECT-TYPE
    SYNTAX       Gauge32
    MAX-ACCESS   read-only
    STATUS       current
    DESCRIPTION
        "Cisco UCS storage:EnclosureLocalDiskConfig:blockSize
        managed object property"
    ::= { cucsStorageEnclosureLocalDiskConfigEntry 4 }

cucsStorageEnclosureLocalDiskConfigConnectionProtocol OBJECT-TYPE
    SYNTAX       CucsStorageConnectionProtocol
    MAX-ACCESS   read-only
    STATUS       current
    DESCRIPTION
        "Cisco UCS storage:EnclosureLocalDiskConfig:connectionProtocol
        managed object property"
    ::= { cucsStorageEnclosureLocalDiskConfigEntry 5 }

cucsStorageEnclosureLocalDiskConfigDeviceType OBJECT-TYPE
    SYNTAX       CucsStorageTechnology
    MAX-ACCESS   read-only
    STATUS       current
    DESCRIPTION
        "Cisco UCS storage:EnclosureLocalDiskConfig:deviceType
        managed object property"
    ::= { cucsStorageEnclosureLocalDiskConfigEntry 6 }

cucsStorageEnclosureLocalDiskConfigFirmwareVersion OBJECT-TYPE
    SYNTAX       SnmpAdminString
    MAX-ACCESS   read-only
    STATUS       current
    DESCRIPTION
        "Cisco UCS storage:EnclosureLocalDiskConfig:firmwareVersion
        managed object property"
    ::= { cucsStorageEnclosureLocalDiskConfigEntry 7 }

cucsStorageEnclosureLocalDiskConfigId OBJECT-TYPE
    SYNTAX       Gauge32
    MAX-ACCESS   read-only
    STATUS       current
    DESCRIPTION
        "Cisco UCS storage:EnclosureLocalDiskConfig:id
        managed object property"
    ::= { cucsStorageEnclosureLocalDiskConfigEntry 8 }

cucsStorageEnclosureLocalDiskConfigLinkSpeed OBJECT-TYPE
    SYNTAX       CucsStorageLinkSpeed
    MAX-ACCESS   read-only
    STATUS       current
    DESCRIPTION
        "Cisco UCS storage:EnclosureLocalDiskConfig:linkSpeed
        managed object property"
    ::= { cucsStorageEnclosureLocalDiskConfigEntry 9 }

cucsStorageEnclosureLocalDiskConfigLinkState OBJECT-TYPE
    SYNTAX       CucsStorageEpLinkState
    MAX-ACCESS   read-only
    STATUS       current
    DESCRIPTION
        "Cisco UCS storage:EnclosureLocalDiskConfig:linkState
        managed object property"
    ::= { cucsStorageEnclosureLocalDiskConfigEntry 10 }

cucsStorageEnclosureLocalDiskConfigLinkStateReason OBJECT-TYPE
    SYNTAX       SnmpAdminString
    MAX-ACCESS   read-only
    STATUS       current
    DESCRIPTION
        "Cisco UCS storage:EnclosureLocalDiskConfig:linkStateReason
        managed object property"
    ::= { cucsStorageEnclosureLocalDiskConfigEntry 11 }

cucsStorageEnclosureLocalDiskConfigModel OBJECT-TYPE
    SYNTAX       SnmpAdminString
    MAX-ACCESS   read-only
    STATUS       current
    DESCRIPTION
        "Cisco UCS storage:EnclosureLocalDiskConfig:model
        managed object property"
    ::= { cucsStorageEnclosureLocalDiskConfigEntry 12 }

cucsStorageEnclosureLocalDiskConfigNumberOfBlocks OBJECT-TYPE
    SYNTAX       Unsigned64
    MAX-ACCESS   read-only
    STATUS       current
    DESCRIPTION
        "Cisco UCS storage:EnclosureLocalDiskConfig:numberOfBlocks
        managed object property"
    ::= { cucsStorageEnclosureLocalDiskConfigEntry 13 }

cucsStorageEnclosureLocalDiskConfigOperQualifierReason OBJECT-TYPE
    SYNTAX       SnmpAdminString
    MAX-ACCESS   read-only
    STATUS       current
    DESCRIPTION
        "Cisco UCS storage:EnclosureLocalDiskConfig:operQualifierReason
        managed object property"
    ::= { cucsStorageEnclosureLocalDiskConfigEntry 14 }

cucsStorageEnclosureLocalDiskConfigOperability OBJECT-TYPE
    SYNTAX       CucsEquipmentOperability
    MAX-ACCESS   read-only
    STATUS       current
    DESCRIPTION
        "Cisco UCS storage:EnclosureLocalDiskConfig:operability
        managed object property"
    ::= { cucsStorageEnclosureLocalDiskConfigEntry 15 }

cucsStorageEnclosureLocalDiskConfigPhysicalBlockSize OBJECT-TYPE
    SYNTAX       Gauge32
    MAX-ACCESS   read-only
    STATUS       current
    DESCRIPTION
        "Cisco UCS storage:EnclosureLocalDiskConfig:physicalBlockSize
        managed object property"
    ::= { cucsStorageEnclosureLocalDiskConfigEntry 16 }

cucsStorageEnclosureLocalDiskConfigPowerState OBJECT-TYPE
    SYNTAX       CucsStoragePowerState
    MAX-ACCESS   read-only
    STATUS       current
    DESCRIPTION
        "Cisco UCS storage:EnclosureLocalDiskConfig:powerState
        managed object property"
    ::= { cucsStorageEnclosureLocalDiskConfigEntry 17 }

cucsStorageEnclosureLocalDiskConfigPresence OBJECT-TYPE
    SYNTAX       CucsEquipmentPresence
    MAX-ACCESS   read-only
    STATUS       current
    DESCRIPTION
        "Cisco UCS storage:EnclosureLocalDiskConfig:presence
        managed object property"
    ::= { cucsStorageEnclosureLocalDiskConfigEntry 18 }

cucsStorageEnclosureLocalDiskConfigRevision OBJECT-TYPE
    SYNTAX       SnmpAdminString
    MAX-ACCESS   read-only
    STATUS       current
    DESCRIPTION
        "Cisco UCS storage:EnclosureLocalDiskConfig:revision
        managed object property"
    ::= { cucsStorageEnclosureLocalDiskConfigEntry 19 }

cucsStorageEnclosureLocalDiskConfigScsiDiskState OBJECT-TYPE
    SYNTAX       CucsSesScsiDriveStatus
    MAX-ACCESS   read-only
    STATUS       current
    DESCRIPTION
        "Cisco UCS storage:EnclosureLocalDiskConfig:scsiDiskState
        managed object property"
    ::= { cucsStorageEnclosureLocalDiskConfigEntry 20 }

cucsStorageEnclosureLocalDiskConfigSerial OBJECT-TYPE
    SYNTAX       SnmpAdminString
    MAX-ACCESS   read-only
    STATUS       current
    DESCRIPTION
        "Cisco UCS storage:EnclosureLocalDiskConfig:serial
        managed object property"
    ::= { cucsStorageEnclosureLocalDiskConfigEntry 21 }

cucsStorageEnclosureLocalDiskConfigSize OBJECT-TYPE
    SYNTAX       Unsigned64
    MAX-ACCESS   read-only
    STATUS       current
    DESCRIPTION
        "Cisco UCS storage:EnclosureLocalDiskConfig:size
        managed object property"
    ::= { cucsStorageEnclosureLocalDiskConfigEntry 22 }

cucsStorageEnclosureLocalDiskConfigVendor OBJECT-TYPE
    SYNTAX       SnmpAdminString
    MAX-ACCESS   read-only
    STATUS       current
    DESCRIPTION
        "Cisco UCS storage:EnclosureLocalDiskConfig:vendor
        managed object property"
    ::= { cucsStorageEnclosureLocalDiskConfigEntry 23 }

cucsStorageEpUserTable OBJECT-TYPE
    SYNTAX           SEQUENCE OF CucsStorageEpUserEntry
    MAX-ACCESS       not-accessible
    STATUS           current
    DESCRIPTION
        "Cisco UCS storage:EpUser managed object table"
    ::= { cucsStorageObjects 18 }

cucsStorageEpUserEntry OBJECT-TYPE
    SYNTAX           CucsStorageEpUserEntry
    MAX-ACCESS       not-accessible
    STATUS           current
    DESCRIPTION
        "Entry for the cucsStorageEpUserTable table."
    INDEX { cucsStorageEpUserInstanceId }
    ::= { cucsStorageEpUserTable 1 }

CucsStorageEpUserEntry ::= SEQUENCE {
    cucsStorageEpUserInstanceId                                      CucsManagedObjectId,
    cucsStorageEpUserDn                                              CucsManagedObjectDn,
    cucsStorageEpUserRn                                              SnmpAdminString,
    cucsStorageEpUserConfigState                                     CucsAaaConfigState,
    cucsStorageEpUserConfigStatusMessage                             SnmpAdminString,
    cucsStorageEpUserDescr                                           SnmpAdminString,
    cucsStorageEpUserDomain                                          SnmpAdminString,
    cucsStorageEpUserName                                            SnmpAdminString,
    cucsStorageEpUserPriv                                            CucsStorageEpAccess,
    cucsStorageEpUserPwd                                             SnmpAdminString,
    cucsStorageEpUserPwdSet                                          TruthValue
}

cucsStorageEpUserInstanceId OBJECT-TYPE
    SYNTAX       CucsManagedObjectId
    MAX-ACCESS   not-accessible
    STATUS       current
    DESCRIPTION
        "Instance identifier of the managed object."
    ::= { cucsStorageEpUserEntry 1 }

cucsStorageEpUserDn OBJECT-TYPE
    SYNTAX       CucsManagedObjectDn
    MAX-ACCESS   read-only
    STATUS       current
    DESCRIPTION
        "Cisco UCS storage:EpUser:dn managed object property"
    ::= { cucsStorageEpUserEntry 2 }

cucsStorageEpUserRn OBJECT-TYPE
    SYNTAX       SnmpAdminString
    MAX-ACCESS   read-only
    STATUS       current
    DESCRIPTION
        "Cisco UCS storage:EpUser:rn managed object property"
    ::= { cucsStorageEpUserEntry 3 }

cucsStorageEpUserConfigState OBJECT-TYPE
    SYNTAX       CucsAaaConfigState
    MAX-ACCESS   read-only
    STATUS       current
    DESCRIPTION
        "Cisco UCS storage:EpUser:configState managed object property"
    ::= { cucsStorageEpUserEntry 4 }

cucsStorageEpUserConfigStatusMessage OBJECT-TYPE
    SYNTAX       SnmpAdminString
    MAX-ACCESS   read-only
    STATUS       current
    DESCRIPTION
        "Cisco UCS storage:EpUser:configStatusMessage managed
        object property"
    ::= { cucsStorageEpUserEntry 5 }

cucsStorageEpUserDescr OBJECT-TYPE
    SYNTAX       SnmpAdminString
    MAX-ACCESS   read-only
    STATUS       current
    DESCRIPTION
        "Cisco UCS storage:EpUser:descr managed object property"
    ::= { cucsStorageEpUserEntry 6 }

cucsStorageEpUserDomain OBJECT-TYPE
    SYNTAX       SnmpAdminString
    MAX-ACCESS   read-only
    STATUS       current
    DESCRIPTION
        "Cisco UCS storage:EpUser:domain managed object property"
    ::= { cucsStorageEpUserEntry 7 }

cucsStorageEpUserName OBJECT-TYPE
    SYNTAX       SnmpAdminString
    MAX-ACCESS   read-only
    STATUS       current
    DESCRIPTION
        "Cisco UCS storage:EpUser:name managed object property"
    ::= { cucsStorageEpUserEntry 8 }

cucsStorageEpUserPriv OBJECT-TYPE
    SYNTAX       CucsStorageEpAccess
    MAX-ACCESS   read-only
    STATUS       current
    DESCRIPTION
        "Cisco UCS storage:EpUser:priv managed object property"
    ::= { cucsStorageEpUserEntry 9 }

cucsStorageEpUserPwd OBJECT-TYPE
    SYNTAX       SnmpAdminString
    MAX-ACCESS   read-only
    STATUS       current
    DESCRIPTION
        "Cisco UCS storage:EpUser:pwd managed object property"
    ::= { cucsStorageEpUserEntry 10 }

cucsStorageEpUserPwdSet OBJECT-TYPE
    SYNTAX       TruthValue
    MAX-ACCESS   read-only
    STATUS       current
    DESCRIPTION
        "Cisco UCS storage:EpUser:pwdSet managed object property"
    ::= { cucsStorageEpUserEntry 11 }

cucsStorageEtherIfTable OBJECT-TYPE
    SYNTAX           SEQUENCE OF CucsStorageEtherIfEntry
    MAX-ACCESS       not-accessible
    STATUS           current
    DESCRIPTION
        "Cisco UCS storage:EtherIf managed object table"
    ::= { cucsStorageObjects 19 }

cucsStorageEtherIfEntry OBJECT-TYPE
    SYNTAX           CucsStorageEtherIfEntry
    MAX-ACCESS       not-accessible
    STATUS           current
    DESCRIPTION
        "Entry for the cucsStorageEtherIfTable table."
    INDEX { cucsStorageEtherIfInstanceId }
    ::= { cucsStorageEtherIfTable 1 }

CucsStorageEtherIfEntry ::= SEQUENCE {
    cucsStorageEtherIfInstanceId                                     CucsManagedObjectId,
    cucsStorageEtherIfDn                                             CucsManagedObjectDn,
    cucsStorageEtherIfRn                                             SnmpAdminString,
    cucsStorageEtherIfName                                           SnmpAdminString,
    cucsStorageEtherIfVlanType                                       CucsStorageEtherIfVlanType
}

cucsStorageEtherIfInstanceId OBJECT-TYPE
    SYNTAX       CucsManagedObjectId
    MAX-ACCESS   not-accessible
    STATUS       current
    DESCRIPTION
        "Instance identifier of the managed object."
    ::= { cucsStorageEtherIfEntry 1 }

cucsStorageEtherIfDn OBJECT-TYPE
    SYNTAX       CucsManagedObjectDn
    MAX-ACCESS   read-only
    STATUS       current
    DESCRIPTION
        "Cisco UCS storage:EtherIf:dn managed object property"
    ::= { cucsStorageEtherIfEntry 2 }

cucsStorageEtherIfRn OBJECT-TYPE
    SYNTAX       SnmpAdminString
    MAX-ACCESS   read-only
    STATUS       current
    DESCRIPTION
        "Cisco UCS storage:EtherIf:rn managed object property"
    ::= { cucsStorageEtherIfEntry 3 }

cucsStorageEtherIfName OBJECT-TYPE
    SYNTAX       SnmpAdminString
    MAX-ACCESS   read-only
    STATUS       current
    DESCRIPTION
        "Cisco UCS storage:EtherIf:name managed object property"
    ::= { cucsStorageEtherIfEntry 4 }

cucsStorageEtherIfVlanType OBJECT-TYPE
    SYNTAX       CucsStorageEtherIfVlanType
    MAX-ACCESS   read-only
    STATUS       current
    DESCRIPTION
        "Cisco UCS storage:EtherIf:vlanType managed object property"
    ::= { cucsStorageEtherIfEntry 5 }

cucsStorageFcIfTable OBJECT-TYPE
    SYNTAX           SEQUENCE OF CucsStorageFcIfEntry
    MAX-ACCESS       not-accessible
    STATUS           current
    DESCRIPTION
        "Cisco UCS storage:FcIf managed object table"
    ::= { cucsStorageObjects 20 }

cucsStorageFcIfEntry OBJECT-TYPE
    SYNTAX           CucsStorageFcIfEntry
    MAX-ACCESS       not-accessible
    STATUS           current
    DESCRIPTION
        "Entry for the cucsStorageFcIfTable table."
    INDEX { cucsStorageFcIfInstanceId }
    ::= { cucsStorageFcIfTable 1 }

CucsStorageFcIfEntry ::= SEQUENCE {
    cucsStorageFcIfInstanceId                                        CucsManagedObjectId,
    cucsStorageFcIfDn                                                CucsManagedObjectDn,
    cucsStorageFcIfRn                                                SnmpAdminString,
    cucsStorageFcIfName                                              SnmpAdminString
}

cucsStorageFcIfInstanceId OBJECT-TYPE
    SYNTAX       CucsManagedObjectId
    MAX-ACCESS   not-accessible
    STATUS       current
    DESCRIPTION
        "Instance identifier of the managed object."
    ::= { cucsStorageFcIfEntry 1 }

cucsStorageFcIfDn OBJECT-TYPE
    SYNTAX       CucsManagedObjectDn
    MAX-ACCESS   read-only
    STATUS       current
    DESCRIPTION
        "Cisco UCS storage:FcIf:dn managed object property"
    ::= { cucsStorageFcIfEntry 2 }

cucsStorageFcIfRn OBJECT-TYPE
    SYNTAX       SnmpAdminString
    MAX-ACCESS   read-only
    STATUS       current
    DESCRIPTION
        "Cisco UCS storage:FcIf:rn managed object property"
    ::= { cucsStorageFcIfEntry 3 }

cucsStorageFcIfName OBJECT-TYPE
    SYNTAX       SnmpAdminString
    MAX-ACCESS   read-only
    STATUS       current
    DESCRIPTION
        "Cisco UCS storage:FcIf:name managed object property"
    ::= { cucsStorageFcIfEntry 4 }

cucsStorageFcTargetEpTable OBJECT-TYPE
    SYNTAX           SEQUENCE OF CucsStorageFcTargetEpEntry
    MAX-ACCESS       not-accessible
    STATUS           current
    DESCRIPTION
        "Cisco UCS storage:FcTargetEp managed object table"
    ::= { cucsStorageObjects 21 }

cucsStorageFcTargetEpEntry OBJECT-TYPE
    SYNTAX           CucsStorageFcTargetEpEntry
    MAX-ACCESS       not-accessible
    STATUS           current
    DESCRIPTION
        "Entry for the cucsStorageFcTargetEpTable table."
    INDEX { cucsStorageFcTargetEpInstanceId }
    ::= { cucsStorageFcTargetEpTable 1 }

CucsStorageFcTargetEpEntry ::= SEQUENCE {
    cucsStorageFcTargetEpInstanceId                                  CucsManagedObjectId,
    cucsStorageFcTargetEpDn                                          CucsManagedObjectDn,
    cucsStorageFcTargetEpRn                                          SnmpAdminString,
    cucsStorageFcTargetEpDescr                                       SnmpAdminString,
    cucsStorageFcTargetEpPath                                        CucsStorageTargetPath,
    cucsStorageFcTargetEpTargetwwpn                                  SnmpAdminString
}

cucsStorageFcTargetEpInstanceId OBJECT-TYPE
    SYNTAX       CucsManagedObjectId
    MAX-ACCESS   not-accessible
    STATUS       current
    DESCRIPTION
        "Instance identifier of the managed object."
    ::= { cucsStorageFcTargetEpEntry 1 }

cucsStorageFcTargetEpDn OBJECT-TYPE
    SYNTAX       CucsManagedObjectDn
    MAX-ACCESS   read-only
    STATUS       current
    DESCRIPTION
        "Cisco UCS storage:FcTargetEp:dn managed object property"
    ::= { cucsStorageFcTargetEpEntry 2 }

cucsStorageFcTargetEpRn OBJECT-TYPE
    SYNTAX       SnmpAdminString
    MAX-ACCESS   read-only
    STATUS       current
    DESCRIPTION
        "Cisco UCS storage:FcTargetEp:rn managed object property"
    ::= { cucsStorageFcTargetEpEntry 3 }

cucsStorageFcTargetEpDescr OBJECT-TYPE
    SYNTAX       SnmpAdminString
    MAX-ACCESS   read-only
    STATUS       current
    DESCRIPTION
        "Cisco UCS storage:FcTargetEp:descr managed object property"
    ::= { cucsStorageFcTargetEpEntry 4 }

cucsStorageFcTargetEpPath OBJECT-TYPE
    SYNTAX       CucsStorageTargetPath
    MAX-ACCESS   read-only
    STATUS       current
    DESCRIPTION
        "Cisco UCS storage:FcTargetEp:path managed object property"
    ::= { cucsStorageFcTargetEpEntry 5 }

cucsStorageFcTargetEpTargetwwpn OBJECT-TYPE
    SYNTAX       SnmpAdminString
    MAX-ACCESS   read-only
    STATUS       current
    DESCRIPTION
        "Cisco UCS storage:FcTargetEp:targetwwpn managed object property"
    ::= { cucsStorageFcTargetEpEntry 6 }

cucsStorageFcTargetIfTable OBJECT-TYPE
    SYNTAX           SEQUENCE OF CucsStorageFcTargetIfEntry
    MAX-ACCESS       not-accessible
    STATUS           current
    DESCRIPTION
        "Cisco UCS storage:FcTargetIf managed object table"
    ::= { cucsStorageObjects 22 }

cucsStorageFcTargetIfEntry OBJECT-TYPE
    SYNTAX           CucsStorageFcTargetIfEntry
    MAX-ACCESS       not-accessible
    STATUS           current
    DESCRIPTION
        "Entry for the cucsStorageFcTargetIfTable table."
    INDEX { cucsStorageFcTargetIfInstanceId }
    ::= { cucsStorageFcTargetIfTable 1 }

CucsStorageFcTargetIfEntry ::= SEQUENCE {
    cucsStorageFcTargetIfInstanceId                                  CucsManagedObjectId,
    cucsStorageFcTargetIfDn                                          CucsManagedObjectDn,
    cucsStorageFcTargetIfRn                                          SnmpAdminString,
    cucsStorageFcTargetIfId                                          Unsigned64,
    cucsStorageFcTargetIfProt                                        CucsStorageProtocol
}

cucsStorageFcTargetIfInstanceId OBJECT-TYPE
    SYNTAX       CucsManagedObjectId
    MAX-ACCESS   not-accessible
    STATUS       current
    DESCRIPTION
        "Instance identifier of the managed object."
    ::= { cucsStorageFcTargetIfEntry 1 }

cucsStorageFcTargetIfDn OBJECT-TYPE
    SYNTAX       CucsManagedObjectDn
    MAX-ACCESS   read-only
    STATUS       current
    DESCRIPTION
        "Cisco UCS storage:FcTargetIf:dn managed object property"
    ::= { cucsStorageFcTargetIfEntry 2 }

cucsStorageFcTargetIfRn OBJECT-TYPE
    SYNTAX       SnmpAdminString
    MAX-ACCESS   read-only
    STATUS       current
    DESCRIPTION
        "Cisco UCS storage:FcTargetIf:rn managed object property"
    ::= { cucsStorageFcTargetIfEntry 3 }

cucsStorageFcTargetIfId OBJECT-TYPE
    SYNTAX       Unsigned64
    MAX-ACCESS   read-only
    STATUS       current
    DESCRIPTION
        "Cisco UCS storage:FcTargetIf:id managed object property"
    ::= { cucsStorageFcTargetIfEntry 4 }

cucsStorageFcTargetIfProt OBJECT-TYPE
    SYNTAX       CucsStorageProtocol
    MAX-ACCESS   read-only
    STATUS       current
    DESCRIPTION
        "Cisco UCS storage:FcTargetIf:prot managed object property"
    ::= { cucsStorageFcTargetIfEntry 5 }

cucsStorageFlexFlashCardTable OBJECT-TYPE
    SYNTAX           SEQUENCE OF CucsStorageFlexFlashCardEntry
    MAX-ACCESS       not-accessible
    STATUS           current
    DESCRIPTION
        "Cisco UCS storage:FlexFlashCard managed object table"
    ::= { cucsStorageObjects 34 }

cucsStorageFlexFlashCardEntry OBJECT-TYPE
    SYNTAX           CucsStorageFlexFlashCardEntry
    MAX-ACCESS       not-accessible
    STATUS           current
    DESCRIPTION
        "Entry for the cucsStorageFlexFlashCardTable table."
    INDEX { cucsStorageFlexFlashCardInstanceId }
    ::= { cucsStorageFlexFlashCardTable 1 }

CucsStorageFlexFlashCardEntry ::= SEQUENCE {
    cucsStorageFlexFlashCardInstanceId                               CucsManagedObjectId,
    cucsStorageFlexFlashCardDn                                       CucsManagedObjectDn,
    cucsStorageFlexFlashCardRn                                       SnmpAdminString,
    cucsStorageFlexFlashCardBlockSize                                Gauge32,
    cucsStorageFlexFlashCardCardHealth                               CucsStorageFFCardHealth,
    cucsStorageFlexFlashCardCardMode                                 CucsStorageFFCardMode,
    cucsStorageFlexFlashCardCardType                                 SnmpAdminString,
    cucsStorageFlexFlashCardConnectionProtocol                       CucsStorageConnectionProtocol,
    cucsStorageFlexFlashCardControllerIndex                          Gauge32,
    cucsStorageFlexFlashCardId                                       Gauge32,
    cucsStorageFlexFlashCardMfgDate                                  SnmpAdminString,
    cucsStorageFlexFlashCardMfgId                                    SnmpAdminString,
    cucsStorageFlexFlashCardModel                                    SnmpAdminString,
    cucsStorageFlexFlashCardNumberOfBlocks                           Unsigned64,
    cucsStorageFlexFlashCardOemId                                    SnmpAdminString,
    cucsStorageFlexFlashCardOperQualifierReason                      SnmpAdminString,
    cucsStorageFlexFlashCardOperability                              CucsEquipmentOperability,
    cucsStorageFlexFlashCardPresence                                 CucsEquipmentPresence,
    cucsStorageFlexFlashCardReadIOErrorCount                         Gauge32,
    cucsStorageFlexFlashCardRevision                                 SnmpAdminString,
    cucsStorageFlexFlashCardSerial                                   SnmpAdminString,
    cucsStorageFlexFlashCardSize                                     Unsigned64,
    cucsStorageFlexFlashCardSlotNumber                               Gauge32,
    cucsStorageFlexFlashCardVendor                                   SnmpAdminString,
    cucsStorageFlexFlashCardWriteEnable                              CucsStorageFFCardWriteEnable,
    cucsStorageFlexFlashCardWriteIOErrorCount                        Gauge32,
    cucsStorageFlexFlashCardCardState                                CucsStorageFFCardState,
    cucsStorageFlexFlashCardCardSync                                 CucsStorageFFCardSync,
    cucsStorageFlexFlashCardDrivesEnabled                            SnmpAdminString,
    cucsStorageFlexFlashCardPartitionCount                           Gauge32,
    cucsStorageFlexFlashCardReadErrorThreshold                       Gauge32,
    cucsStorageFlexFlashCardSignature                                SnmpAdminString,
    cucsStorageFlexFlashCardWriteErrorThreshold                      Gauge32,
    cucsStorageFlexFlashCardPhysicalBlockSize                        Gauge32
}

cucsStorageFlexFlashCardInstanceId OBJECT-TYPE
    SYNTAX       CucsManagedObjectId
    MAX-ACCESS   not-accessible
    STATUS       current
    DESCRIPTION
        "Instance identifier of the managed object."
    ::= { cucsStorageFlexFlashCardEntry 1 }

cucsStorageFlexFlashCardDn OBJECT-TYPE
    SYNTAX       CucsManagedObjectDn
    MAX-ACCESS   read-only
    STATUS       current
    DESCRIPTION
        "Cisco UCS storage:FlexFlashCard:dn managed object property"
    ::= { cucsStorageFlexFlashCardEntry 2 }

cucsStorageFlexFlashCardRn OBJECT-TYPE
    SYNTAX       SnmpAdminString
    MAX-ACCESS   read-only
    STATUS       current
    DESCRIPTION
        "Cisco UCS storage:FlexFlashCard:rn managed object property"
    ::= { cucsStorageFlexFlashCardEntry 3 }

cucsStorageFlexFlashCardBlockSize OBJECT-TYPE
    SYNTAX       Gauge32
    MAX-ACCESS   read-only
    STATUS       current
    DESCRIPTION
        "Cisco UCS storage:FlexFlashCard:blockSize managed
        object property"
    ::= { cucsStorageFlexFlashCardEntry 4 }

cucsStorageFlexFlashCardCardHealth OBJECT-TYPE
    SYNTAX       CucsStorageFFCardHealth
    MAX-ACCESS   read-only
    STATUS       current
    DESCRIPTION
        "Cisco UCS storage:FlexFlashCard:cardHealth managed
        object property"
    ::= { cucsStorageFlexFlashCardEntry 5 }

cucsStorageFlexFlashCardCardMode OBJECT-TYPE
    SYNTAX       CucsStorageFFCardMode
    MAX-ACCESS   read-only
    STATUS       current
    DESCRIPTION
        "Cisco UCS storage:FlexFlashCard:cardMode managed object property"
    ::= { cucsStorageFlexFlashCardEntry 6 }

cucsStorageFlexFlashCardCardType OBJECT-TYPE
    SYNTAX       SnmpAdminString
    MAX-ACCESS   read-only
    STATUS       current
    DESCRIPTION
        "Cisco UCS storage:FlexFlashCard:cardType managed object property"
    ::= { cucsStorageFlexFlashCardEntry 7 }

cucsStorageFlexFlashCardConnectionProtocol OBJECT-TYPE
    SYNTAX       CucsStorageConnectionProtocol
    MAX-ACCESS   read-only
    STATUS       current
    DESCRIPTION
        "Cisco UCS storage:FlexFlashCard:connectionProtocol
        managed object property"
    ::= { cucsStorageFlexFlashCardEntry 8 }

cucsStorageFlexFlashCardControllerIndex OBJECT-TYPE
    SYNTAX       Gauge32
    MAX-ACCESS   read-only
    STATUS       current
    DESCRIPTION
        "Cisco UCS storage:FlexFlashCard:controllerIndex
        managed object property"
    ::= { cucsStorageFlexFlashCardEntry 9 }

cucsStorageFlexFlashCardId OBJECT-TYPE
    SYNTAX       Gauge32
    MAX-ACCESS   read-only
    STATUS       current
    DESCRIPTION
        "Cisco UCS storage:FlexFlashCard:id managed object property"
    ::= { cucsStorageFlexFlashCardEntry 10 }

cucsStorageFlexFlashCardMfgDate OBJECT-TYPE
    SYNTAX       SnmpAdminString
    MAX-ACCESS   read-only
    STATUS       current
    DESCRIPTION
        "Cisco UCS storage:FlexFlashCard:mfgDate managed object property"
    ::= { cucsStorageFlexFlashCardEntry 11 }

cucsStorageFlexFlashCardMfgId OBJECT-TYPE
    SYNTAX       SnmpAdminString
    MAX-ACCESS   read-only
    STATUS       current
    DESCRIPTION
        "Cisco UCS storage:FlexFlashCard:mfgId managed object property"
    ::= { cucsStorageFlexFlashCardEntry 12 }

cucsStorageFlexFlashCardModel OBJECT-TYPE
    SYNTAX       SnmpAdminString
    MAX-ACCESS   read-only
    STATUS       current
    DESCRIPTION
        "Cisco UCS storage:FlexFlashCard:model managed object property"
    ::= { cucsStorageFlexFlashCardEntry 13 }

cucsStorageFlexFlashCardNumberOfBlocks OBJECT-TYPE
    SYNTAX       Unsigned64
    MAX-ACCESS   read-only
    STATUS       current
    DESCRIPTION
        "Cisco UCS storage:FlexFlashCard:numberOfBlocks
        managed object property"
    ::= { cucsStorageFlexFlashCardEntry 14 }

cucsStorageFlexFlashCardOemId OBJECT-TYPE
    SYNTAX       SnmpAdminString
    MAX-ACCESS   read-only
    STATUS       current
    DESCRIPTION
        "Cisco UCS storage:FlexFlashCard:oemId managed object property"
    ::= { cucsStorageFlexFlashCardEntry 15 }

cucsStorageFlexFlashCardOperQualifierReason OBJECT-TYPE
    SYNTAX       SnmpAdminString
    MAX-ACCESS   read-only
    STATUS       current
    DESCRIPTION
        "Cisco UCS storage:FlexFlashCard:operQualifierReason
        managed object property"
    ::= { cucsStorageFlexFlashCardEntry 16 }

cucsStorageFlexFlashCardOperability OBJECT-TYPE
    SYNTAX       CucsEquipmentOperability
    MAX-ACCESS   read-only
    STATUS       current
    DESCRIPTION
        "Cisco UCS storage:FlexFlashCard:operability managed
        object property"
    ::= { cucsStorageFlexFlashCardEntry 17 }

cucsStorageFlexFlashCardPresence OBJECT-TYPE
    SYNTAX       CucsEquipmentPresence
    MAX-ACCESS   read-only
    STATUS       current
    DESCRIPTION
        "Cisco UCS storage:FlexFlashCard:presence managed object property"
    ::= { cucsStorageFlexFlashCardEntry 18 }

cucsStorageFlexFlashCardReadIOErrorCount OBJECT-TYPE
    SYNTAX       Gauge32
    MAX-ACCESS   read-only
    STATUS       current
    DESCRIPTION
        "Cisco UCS storage:FlexFlashCard:readIOErrorCount
        managed object property"
    ::= { cucsStorageFlexFlashCardEntry 19 }

cucsStorageFlexFlashCardRevision OBJECT-TYPE
    SYNTAX       SnmpAdminString
    MAX-ACCESS   read-only
    STATUS       current
    DESCRIPTION
        "Cisco UCS storage:FlexFlashCard:revision managed object property"
    ::= { cucsStorageFlexFlashCardEntry 20 }

cucsStorageFlexFlashCardSerial OBJECT-TYPE
    SYNTAX       SnmpAdminString
    MAX-ACCESS   read-only
    STATUS       current
    DESCRIPTION
        "Cisco UCS storage:FlexFlashCard:serial managed object property"
    ::= { cucsStorageFlexFlashCardEntry 21 }

cucsStorageFlexFlashCardSize OBJECT-TYPE
    SYNTAX       Unsigned64
    MAX-ACCESS   read-only
    STATUS       current
    DESCRIPTION
        "Cisco UCS storage:FlexFlashCard:size managed object property"
    ::= { cucsStorageFlexFlashCardEntry 22 }

cucsStorageFlexFlashCardSlotNumber OBJECT-TYPE
    SYNTAX       Gauge32
    MAX-ACCESS   read-only
    STATUS       current
    DESCRIPTION
        "Cisco UCS storage:FlexFlashCard:slotNumber managed
        object property"
    ::= { cucsStorageFlexFlashCardEntry 23 }

cucsStorageFlexFlashCardVendor OBJECT-TYPE
    SYNTAX       SnmpAdminString
    MAX-ACCESS   read-only
    STATUS       current
    DESCRIPTION
        "Cisco UCS storage:FlexFlashCard:vendor managed object property"
    ::= { cucsStorageFlexFlashCardEntry 24 }

cucsStorageFlexFlashCardWriteEnable OBJECT-TYPE
    SYNTAX       CucsStorageFFCardWriteEnable
    MAX-ACCESS   read-only
    STATUS       current
    DESCRIPTION
        "Cisco UCS storage:FlexFlashCard:writeEnable managed
        object property"
    ::= { cucsStorageFlexFlashCardEntry 25 }

cucsStorageFlexFlashCardWriteIOErrorCount OBJECT-TYPE
    SYNTAX       Gauge32
    MAX-ACCESS   read-only
    STATUS       current
    DESCRIPTION
        "Cisco UCS storage:FlexFlashCard:writeIOErrorCount
        managed object property"
    ::= { cucsStorageFlexFlashCardEntry 26 }

cucsStorageFlexFlashCardCardState OBJECT-TYPE
    SYNTAX       CucsStorageFFCardState
    MAX-ACCESS   read-only
    STATUS       current
    DESCRIPTION
        "Cisco UCS storage:FlexFlashCard:cardState managed
        object property"
    ::= { cucsStorageFlexFlashCardEntry 27 }

cucsStorageFlexFlashCardCardSync OBJECT-TYPE
    SYNTAX       CucsStorageFFCardSync
    MAX-ACCESS   read-only
    STATUS       current
    DESCRIPTION
        "Cisco UCS storage:FlexFlashCard:cardSync managed object property"
    ::= { cucsStorageFlexFlashCardEntry 28 }

cucsStorageFlexFlashCardDrivesEnabled OBJECT-TYPE
    SYNTAX       SnmpAdminString
    MAX-ACCESS   read-only
    STATUS       current
    DESCRIPTION
        "Cisco UCS storage:FlexFlashCard:drivesEnabled
        managed object property"
    ::= { cucsStorageFlexFlashCardEntry 29 }

cucsStorageFlexFlashCardPartitionCount OBJECT-TYPE
    SYNTAX       Gauge32
    MAX-ACCESS   read-only
    STATUS       current
    DESCRIPTION
        "Cisco UCS storage:FlexFlashCard:partitionCount
        managed object property"
    ::= { cucsStorageFlexFlashCardEntry 30 }

cucsStorageFlexFlashCardReadErrorThreshold OBJECT-TYPE
    SYNTAX       Gauge32
    MAX-ACCESS   read-only
    STATUS       current
    DESCRIPTION
        "Cisco UCS storage:FlexFlashCard:readErrorThreshold
        managed object property"
    ::= { cucsStorageFlexFlashCardEntry 31 }

cucsStorageFlexFlashCardSignature OBJECT-TYPE
    SYNTAX       SnmpAdminString
    MAX-ACCESS   read-only
    STATUS       current
    DESCRIPTION
        "Cisco UCS storage:FlexFlashCard:signature managed
        object property"
    ::= { cucsStorageFlexFlashCardEntry 32 }

cucsStorageFlexFlashCardWriteErrorThreshold OBJECT-TYPE
    SYNTAX       Gauge32
    MAX-ACCESS   read-only
    STATUS       current
    DESCRIPTION
        "Cisco UCS storage:FlexFlashCard:writeErrorThreshold
        managed object property"
    ::= { cucsStorageFlexFlashCardEntry 33 }

cucsStorageFlexFlashCardPhysicalBlockSize OBJECT-TYPE
    SYNTAX       Gauge32
    MAX-ACCESS   read-only
    STATUS       current
    DESCRIPTION
        "Cisco UCS storage:FlexFlashCard:physicalBlockSize
        managed object property"
    ::= { cucsStorageFlexFlashCardEntry 34 }

cucsStorageFlexFlashControllerTable OBJECT-TYPE
    SYNTAX           SEQUENCE OF CucsStorageFlexFlashControllerEntry
    MAX-ACCESS       not-accessible
    STATUS           current
    DESCRIPTION
        "Cisco UCS storage:FlexFlashController managed object table"
    ::= { cucsStorageObjects 35 }

cucsStorageFlexFlashControllerEntry OBJECT-TYPE
    SYNTAX           CucsStorageFlexFlashControllerEntry
    MAX-ACCESS       not-accessible
    STATUS           current
    DESCRIPTION
        "Entry for the cucsStorageFlexFlashControllerTable table."
    INDEX { cucsStorageFlexFlashControllerInstanceId }
    ::= { cucsStorageFlexFlashControllerTable 1 }

CucsStorageFlexFlashControllerEntry ::= SEQUENCE {
    cucsStorageFlexFlashControllerInstanceId                         CucsManagedObjectId,
    cucsStorageFlexFlashControllerDn                                 CucsManagedObjectDn,
    cucsStorageFlexFlashControllerRn                                 SnmpAdminString,
    cucsStorageFlexFlashControllerControllerHealth                   CucsStorageFFControllerHealth,
    cucsStorageFlexFlashControllerControllerState                    CucsStorageFFControllerState,
    cucsStorageFlexFlashControllerFlexFlashType                      CucsStorageFFType,
    cucsStorageFlexFlashControllerId                                 CucsStorageFlexFlashControllerId,
    cucsStorageFlexFlashControllerModel                              SnmpAdminString,
    cucsStorageFlexFlashControllerOperQualifierReason                SnmpAdminString,
    cucsStorageFlexFlashControllerOperState                          CucsEquipmentOperability,
    cucsStorageFlexFlashControllerOperability                        CucsEquipmentOperability,
    cucsStorageFlexFlashControllerPciAddr                            SnmpAdminString,
    cucsStorageFlexFlashControllerPciSlot                            SnmpAdminString,
    cucsStorageFlexFlashControllerPerf                               CucsEquipmentSensorThresholdStatus,
    cucsStorageFlexFlashControllerPhysicalDriveCount                 Gauge32,
    cucsStorageFlexFlashControllerPower                              CucsEquipmentPowerState,
    cucsStorageFlexFlashControllerPresence                           CucsEquipmentPresence,
    cucsStorageFlexFlashControllerPrimarySlotNumber                  Gauge32,
    cucsStorageFlexFlashControllerRaidSyncSupport                    CucsStorageFFRaidSyncSupport,
    cucsStorageFlexFlashControllerReadErrorThreshold                 Gauge32,
    cucsStorageFlexFlashControllerRevision                           SnmpAdminString,
    cucsStorageFlexFlashControllerSerial                             SnmpAdminString,
    cucsStorageFlexFlashControllerThermal                            CucsEquipmentSensorThresholdStatus,
    cucsStorageFlexFlashControllerType                               CucsStorageControllerType,
    cucsStorageFlexFlashControllerVendor                             SnmpAdminString,
    cucsStorageFlexFlashControllerVirtualDriveCount                  Gauge32,
    cucsStorageFlexFlashControllerVoltage                            CucsEquipmentSensorThresholdStatus,
    cucsStorageFlexFlashControllerWriteErrorThreshold                Gauge32,
    cucsStorageFlexFlashControllerLocationDn                         SnmpAdminString,
    cucsStorageFlexFlashControllerAdminSlotNumber                    CucsStorageFFSlotENUM,
    cucsStorageFlexFlashControllerConfiguredMode                     CucsStorageOperatingModeType,
    cucsStorageFlexFlashControllerFirmwareVersion                    SnmpAdminString,
    cucsStorageFlexFlashControllerFsmDescr                           SnmpAdminString,
    cucsStorageFlexFlashControllerFsmPrev                            SnmpAdminString,
    cucsStorageFlexFlashControllerFsmProgr                           Gauge32,
    cucsStorageFlexFlashControllerFsmRmtInvErrCode                   Gauge32,
    cucsStorageFlexFlashControllerFsmRmtInvErrDescr                  SnmpAdminString,
    cucsStorageFlexFlashControllerFsmRmtInvRslt                      CucsConditionRemoteInvRslt,
    cucsStorageFlexFlashControllerFsmStageDescr                      SnmpAdminString,
    cucsStorageFlexFlashControllerFsmStamp                           DateAndTime,
    cucsStorageFlexFlashControllerFsmStatus                          SnmpAdminString,
    cucsStorageFlexFlashControllerFsmTry                             Gauge32,
    cucsStorageFlexFlashControllerHasError                           CucsStorageFFHasError,
    cucsStorageFlexFlashControllerIsCardMismatch                     CucsStorageFFCardSizeMismatch,
    cucsStorageFlexFlashControllerIsFormatFSMRunning                 CucsStorageFFFormatRunning,
    cucsStorageFlexFlashControllerOperatingMode                      CucsStorageOperatingModeType,
    cucsStorageFlexFlashControllerOperationRequest                   CucsStorageOperationRequestType,
    cucsStorageFlexFlashControllerSubType                            CucsStorageControllerSubType
}

cucsStorageFlexFlashControllerInstanceId OBJECT-TYPE
    SYNTAX       CucsManagedObjectId
    MAX-ACCESS   not-accessible
    STATUS       current
    DESCRIPTION
        "Instance identifier of the managed object."
    ::= { cucsStorageFlexFlashControllerEntry 1 }

cucsStorageFlexFlashControllerDn OBJECT-TYPE
    SYNTAX       CucsManagedObjectDn
    MAX-ACCESS   read-only
    STATUS       current
    DESCRIPTION
        "Cisco UCS storage:FlexFlashController:dn managed object property"
    ::= { cucsStorageFlexFlashControllerEntry 2 }

cucsStorageFlexFlashControllerRn OBJECT-TYPE
    SYNTAX       SnmpAdminString
    MAX-ACCESS   read-only
    STATUS       current
    DESCRIPTION
        "Cisco UCS storage:FlexFlashController:rn managed object property"
    ::= { cucsStorageFlexFlashControllerEntry 3 }

cucsStorageFlexFlashControllerControllerHealth OBJECT-TYPE
    SYNTAX       CucsStorageFFControllerHealth
    MAX-ACCESS   read-only
    STATUS       current
    DESCRIPTION
        "Cisco UCS storage:FlexFlashController:controllerHealth
        managed object property"
    ::= { cucsStorageFlexFlashControllerEntry 4 }

cucsStorageFlexFlashControllerControllerState OBJECT-TYPE
    SYNTAX       CucsStorageFFControllerState
    MAX-ACCESS   read-only
    STATUS       current
    DESCRIPTION
        "Cisco UCS storage:FlexFlashController:controllerState
        managed object property"
    ::= { cucsStorageFlexFlashControllerEntry 5 }

cucsStorageFlexFlashControllerFlexFlashType OBJECT-TYPE
    SYNTAX       CucsStorageFFType
    MAX-ACCESS   read-only
    STATUS       current
    DESCRIPTION
        "Cisco UCS storage:FlexFlashController:flexFlashType
        managed object property"
    ::= { cucsStorageFlexFlashControllerEntry 6 }

cucsStorageFlexFlashControllerId OBJECT-TYPE
    SYNTAX       CucsStorageFlexFlashControllerId
    MAX-ACCESS   read-only
    STATUS       current
    DESCRIPTION
        "Cisco UCS storage:FlexFlashController:id managed object property"
    ::= { cucsStorageFlexFlashControllerEntry 7 }

cucsStorageFlexFlashControllerModel OBJECT-TYPE
    SYNTAX       SnmpAdminString
    MAX-ACCESS   read-only
    STATUS       current
    DESCRIPTION
        "Cisco UCS storage:FlexFlashController:model managed
        object property"
    ::= { cucsStorageFlexFlashControllerEntry 8 }

cucsStorageFlexFlashControllerOperQualifierReason OBJECT-TYPE
    SYNTAX       SnmpAdminString
    MAX-ACCESS   read-only
    STATUS       current
    DESCRIPTION
        "Cisco UCS storage:FlexFlashController:operQualifierReason
        managed object property"
    ::= { cucsStorageFlexFlashControllerEntry 9 }

cucsStorageFlexFlashControllerOperState OBJECT-TYPE
    SYNTAX       CucsEquipmentOperability
    MAX-ACCESS   read-only
    STATUS       current
    DESCRIPTION
        "Cisco UCS storage:FlexFlashController:operState
        managed object property"
    ::= { cucsStorageFlexFlashControllerEntry 10 }

cucsStorageFlexFlashControllerOperability OBJECT-TYPE
    SYNTAX       CucsEquipmentOperability
    MAX-ACCESS   read-only
    STATUS       current
    DESCRIPTION
        "Cisco UCS storage:FlexFlashController:operability
        managed object property"
    ::= { cucsStorageFlexFlashControllerEntry 11 }

cucsStorageFlexFlashControllerPciAddr OBJECT-TYPE
    SYNTAX       SnmpAdminString
    MAX-ACCESS   read-only
    STATUS       current
    DESCRIPTION
        "Cisco UCS storage:FlexFlashController:pciAddr
        managed object property"
    ::= { cucsStorageFlexFlashControllerEntry 12 }

cucsStorageFlexFlashControllerPciSlot OBJECT-TYPE
    SYNTAX       SnmpAdminString
    MAX-ACCESS   read-only
    STATUS       current
    DESCRIPTION
        "Cisco UCS storage:FlexFlashController:pciSlot
        managed object property"
    ::= { cucsStorageFlexFlashControllerEntry 13 }

cucsStorageFlexFlashControllerPerf OBJECT-TYPE
    SYNTAX       CucsEquipmentSensorThresholdStatus
    MAX-ACCESS   read-only
    STATUS       current
    DESCRIPTION
        "Cisco UCS storage:FlexFlashController:perf managed
        object property"
    ::= { cucsStorageFlexFlashControllerEntry 14 }

cucsStorageFlexFlashControllerPhysicalDriveCount OBJECT-TYPE
    SYNTAX       Gauge32
    MAX-ACCESS   read-only
    STATUS       current
    DESCRIPTION
        "Cisco UCS storage:FlexFlashController:physicalDriveCount
        managed object property"
    ::= { cucsStorageFlexFlashControllerEntry 15 }

cucsStorageFlexFlashControllerPower OBJECT-TYPE
    SYNTAX       CucsEquipmentPowerState
    MAX-ACCESS   read-only
    STATUS       current
    DESCRIPTION
        "Cisco UCS storage:FlexFlashController:power managed
        object property"
    ::= { cucsStorageFlexFlashControllerEntry 16 }

cucsStorageFlexFlashControllerPresence OBJECT-TYPE
    SYNTAX       CucsEquipmentPresence
    MAX-ACCESS   read-only
    STATUS       current
    DESCRIPTION
        "Cisco UCS storage:FlexFlashController:presence
        managed object property"
    ::= { cucsStorageFlexFlashControllerEntry 17 }

cucsStorageFlexFlashControllerPrimarySlotNumber OBJECT-TYPE
    SYNTAX       Gauge32
    MAX-ACCESS   read-only
    STATUS       current
    DESCRIPTION
        "Cisco UCS storage:FlexFlashController:primarySlotNumber
        managed object property"
    ::= { cucsStorageFlexFlashControllerEntry 18 }

cucsStorageFlexFlashControllerRaidSyncSupport OBJECT-TYPE
    SYNTAX       CucsStorageFFRaidSyncSupport
    MAX-ACCESS   read-only
    STATUS       current
    DESCRIPTION
        "Cisco UCS storage:FlexFlashController:raidSyncSupport
        managed object property"
    ::= { cucsStorageFlexFlashControllerEntry 19 }

cucsStorageFlexFlashControllerReadErrorThreshold OBJECT-TYPE
    SYNTAX       Gauge32
    MAX-ACCESS   read-only
    STATUS       current
    DESCRIPTION
        "Cisco UCS storage:FlexFlashController:readErrorThreshold
        managed object property"
    ::= { cucsStorageFlexFlashControllerEntry 20 }

cucsStorageFlexFlashControllerRevision OBJECT-TYPE
    SYNTAX       SnmpAdminString
    MAX-ACCESS   read-only
    STATUS       current
    DESCRIPTION
        "Cisco UCS storage:FlexFlashController:revision
        managed object property"
    ::= { cucsStorageFlexFlashControllerEntry 21 }

cucsStorageFlexFlashControllerSerial OBJECT-TYPE
    SYNTAX       SnmpAdminString
    MAX-ACCESS   read-only
    STATUS       current
    DESCRIPTION
        "Cisco UCS storage:FlexFlashController:serial managed
        object property"
    ::= { cucsStorageFlexFlashControllerEntry 22 }

cucsStorageFlexFlashControllerThermal OBJECT-TYPE
    SYNTAX       CucsEquipmentSensorThresholdStatus
    MAX-ACCESS   read-only
    STATUS       current
    DESCRIPTION
        "Cisco UCS storage:FlexFlashController:thermal
        managed object property"
    ::= { cucsStorageFlexFlashControllerEntry 23 }

cucsStorageFlexFlashControllerType OBJECT-TYPE
    SYNTAX       CucsStorageControllerType
    MAX-ACCESS   read-only
    STATUS       current
    DESCRIPTION
        "Cisco UCS storage:FlexFlashController:type managed
        object property"
    ::= { cucsStorageFlexFlashControllerEntry 24 }

cucsStorageFlexFlashControllerVendor OBJECT-TYPE
    SYNTAX       SnmpAdminString
    MAX-ACCESS   read-only
    STATUS       current
    DESCRIPTION
        "Cisco UCS storage:FlexFlashController:vendor managed
        object property"
    ::= { cucsStorageFlexFlashControllerEntry 25 }

cucsStorageFlexFlashControllerVirtualDriveCount OBJECT-TYPE
    SYNTAX       Gauge32
    MAX-ACCESS   read-only
    STATUS       current
    DESCRIPTION
        "Cisco UCS storage:FlexFlashController:virtualDriveCount
        managed object property"
    ::= { cucsStorageFlexFlashControllerEntry 26 }

cucsStorageFlexFlashControllerVoltage OBJECT-TYPE
    SYNTAX       CucsEquipmentSensorThresholdStatus
    MAX-ACCESS   read-only
    STATUS       current
    DESCRIPTION
        "Cisco UCS storage:FlexFlashController:voltage
        managed object property"
    ::= { cucsStorageFlexFlashControllerEntry 27 }

cucsStorageFlexFlashControllerWriteErrorThreshold OBJECT-TYPE
    SYNTAX       Gauge32
    MAX-ACCESS   read-only
    STATUS       current
    DESCRIPTION
        "Cisco UCS storage:FlexFlashController:writeErrorThreshold
        managed object property"
    ::= { cucsStorageFlexFlashControllerEntry 28 }

cucsStorageFlexFlashControllerLocationDn OBJECT-TYPE
    SYNTAX       SnmpAdminString
    MAX-ACCESS   read-only
    STATUS       current
    DESCRIPTION
        "Cisco UCS storage:FlexFlashController:locationDn
        managed object property"
    ::= { cucsStorageFlexFlashControllerEntry 29 }

cucsStorageFlexFlashControllerAdminSlotNumber OBJECT-TYPE
    SYNTAX       CucsStorageFFSlotENUM
    MAX-ACCESS   read-only
    STATUS       current
    DESCRIPTION
        "Cisco UCS storage:FlexFlashController:adminSlotNumber
        managed object property"
    ::= { cucsStorageFlexFlashControllerEntry 30 }

cucsStorageFlexFlashControllerConfiguredMode OBJECT-TYPE
    SYNTAX       CucsStorageOperatingModeType
    MAX-ACCESS   read-only
    STATUS       current
    DESCRIPTION
        "Cisco UCS storage:FlexFlashController:configuredMode
        managed object property"
    ::= { cucsStorageFlexFlashControllerEntry 31 }

cucsStorageFlexFlashControllerFirmwareVersion OBJECT-TYPE
    SYNTAX       SnmpAdminString
    MAX-ACCESS   read-only
    STATUS       current
    DESCRIPTION
        "Cisco UCS storage:FlexFlashController:firmwareVersion
        managed object property"
    ::= { cucsStorageFlexFlashControllerEntry 32 }

cucsStorageFlexFlashControllerFsmDescr OBJECT-TYPE
    SYNTAX       SnmpAdminString
    MAX-ACCESS   read-only
    STATUS       current
    DESCRIPTION
        "Cisco UCS storage:FlexFlashController:fsmDescr
        managed object property"
    ::= { cucsStorageFlexFlashControllerEntry 33 }

cucsStorageFlexFlashControllerFsmPrev OBJECT-TYPE
    SYNTAX       SnmpAdminString
    MAX-ACCESS   read-only
    STATUS       current
    DESCRIPTION
        "Cisco UCS storage:FlexFlashController:fsmPrev
        managed object property"
    ::= { cucsStorageFlexFlashControllerEntry 34 }

cucsStorageFlexFlashControllerFsmProgr OBJECT-TYPE
    SYNTAX       Gauge32
    MAX-ACCESS   read-only
    STATUS       current
    DESCRIPTION
        "Cisco UCS storage:FlexFlashController:fsmProgr
        managed object property"
    ::= { cucsStorageFlexFlashControllerEntry 35 }

cucsStorageFlexFlashControllerFsmRmtInvErrCode OBJECT-TYPE
    SYNTAX       Gauge32
    MAX-ACCESS   read-only
    STATUS       current
    DESCRIPTION
        "Cisco UCS storage:FlexFlashController:fsmRmtInvErrCode
        managed object property"
    ::= { cucsStorageFlexFlashControllerEntry 36 }

cucsStorageFlexFlashControllerFsmRmtInvErrDescr OBJECT-TYPE
    SYNTAX       SnmpAdminString
    MAX-ACCESS   read-only
    STATUS       current
    DESCRIPTION
        "Cisco UCS storage:FlexFlashController:fsmRmtInvErrDescr
        managed object property"
    ::= { cucsStorageFlexFlashControllerEntry 37 }

cucsStorageFlexFlashControllerFsmRmtInvRslt OBJECT-TYPE
    SYNTAX       CucsConditionRemoteInvRslt
    MAX-ACCESS   read-only
    STATUS       current
    DESCRIPTION
        "Cisco UCS storage:FlexFlashController:fsmRmtInvRslt
        managed object property"
    ::= { cucsStorageFlexFlashControllerEntry 38 }

cucsStorageFlexFlashControllerFsmStageDescr OBJECT-TYPE
    SYNTAX       SnmpAdminString
    MAX-ACCESS   read-only
    STATUS       current
    DESCRIPTION
        "Cisco UCS storage:FlexFlashController:fsmStageDescr
        managed object property"
    ::= { cucsStorageFlexFlashControllerEntry 39 }

cucsStorageFlexFlashControllerFsmStamp OBJECT-TYPE
    SYNTAX       DateAndTime
    MAX-ACCESS   read-only
    STATUS       current
    DESCRIPTION
        "Cisco UCS storage:FlexFlashController:fsmStamp
        managed object property"
    ::= { cucsStorageFlexFlashControllerEntry 40 }

cucsStorageFlexFlashControllerFsmStatus OBJECT-TYPE
    SYNTAX       SnmpAdminString
    MAX-ACCESS   read-only
    STATUS       current
    DESCRIPTION
        "Cisco UCS storage:FlexFlashController:fsmStatus
        managed object property"
    ::= { cucsStorageFlexFlashControllerEntry 41 }

cucsStorageFlexFlashControllerFsmTry OBJECT-TYPE
    SYNTAX       Gauge32
    MAX-ACCESS   read-only
    STATUS       current
    DESCRIPTION
        "Cisco UCS storage:FlexFlashController:fsmTry managed
        object property"
    ::= { cucsStorageFlexFlashControllerEntry 42 }

cucsStorageFlexFlashControllerHasError OBJECT-TYPE
    SYNTAX       CucsStorageFFHasError
    MAX-ACCESS   read-only
    STATUS       current
    DESCRIPTION
        "Cisco UCS storage:FlexFlashController:hasError
        managed object property"
    ::= { cucsStorageFlexFlashControllerEntry 43 }

cucsStorageFlexFlashControllerIsCardMismatch OBJECT-TYPE
    SYNTAX       CucsStorageFFCardSizeMismatch
    MAX-ACCESS   read-only
    STATUS       current
    DESCRIPTION
        "Cisco UCS storage:FlexFlashController:isCardMismatch
        managed object property"
    ::= { cucsStorageFlexFlashControllerEntry 44 }

cucsStorageFlexFlashControllerIsFormatFSMRunning OBJECT-TYPE
    SYNTAX       CucsStorageFFFormatRunning
    MAX-ACCESS   read-only
    STATUS       current
    DESCRIPTION
        "Cisco UCS storage:FlexFlashController:isFormatFSMRunning
        managed object property"
    ::= { cucsStorageFlexFlashControllerEntry 45 }

cucsStorageFlexFlashControllerOperatingMode OBJECT-TYPE
    SYNTAX       CucsStorageOperatingModeType
    MAX-ACCESS   read-only
    STATUS       current
    DESCRIPTION
        "Cisco UCS storage:FlexFlashController:operatingMode
        managed object property"
    ::= { cucsStorageFlexFlashControllerEntry 46 }

cucsStorageFlexFlashControllerOperationRequest OBJECT-TYPE
    SYNTAX       CucsStorageOperationRequestType
    MAX-ACCESS   read-only
    STATUS       current
    DESCRIPTION
        "Cisco UCS storage:FlexFlashController:operationRequest
        managed object property"
    ::= { cucsStorageFlexFlashControllerEntry 47 }

cucsStorageFlexFlashControllerSubType OBJECT-TYPE
    SYNTAX       CucsStorageControllerSubType
    MAX-ACCESS   read-only
    STATUS       current
    DESCRIPTION
        "Cisco UCS storage:FlexFlashController:subType
        managed object property"
    ::= { cucsStorageFlexFlashControllerEntry 48 }

cucsStorageFlexFlashControllerFsmTable OBJECT-TYPE
    SYNTAX           SEQUENCE OF CucsStorageFlexFlashControllerFsmEntry
    MAX-ACCESS       not-accessible
    STATUS           current
    DESCRIPTION
        "Cisco UCS storage:FlexFlashControllerFsm managed object table"
    ::= { cucsStorageObjects 40 }

cucsStorageFlexFlashControllerFsmEntry OBJECT-TYPE
    SYNTAX           CucsStorageFlexFlashControllerFsmEntry
    MAX-ACCESS       not-accessible
    STATUS           current
    DESCRIPTION
        "Entry for the cucsStorageFlexFlashControllerFsmTable table."
    INDEX { cucsStorageFlexFlashControllerFsmInstanceId }
    ::= { cucsStorageFlexFlashControllerFsmTable 1 }

CucsStorageFlexFlashControllerFsmEntry ::= SEQUENCE {
    cucsStorageFlexFlashControllerFsmInstanceId                      CucsManagedObjectId,
    cucsStorageFlexFlashControllerFsmDn                              CucsManagedObjectDn,
    cucsStorageFlexFlashControllerFsmRn                              SnmpAdminString,
    cucsStorageFlexFlashControllerFsmCompletionTime                  DateAndTime,
    cucsStorageFlexFlashControllerFsmCurrentFsm                      CucsStorageFlexFlashControllerFsmCurrentFsm,
    cucsStorageFlexFlashControllerFsmDescrData                       SnmpAdminString,
    cucsStorageFlexFlashControllerFsmFsmStatus                       CucsFsmFsmStageStatus,
    cucsStorageFlexFlashControllerFsmProgress                        Gauge32,
    cucsStorageFlexFlashControllerFsmRmtErrCode                      Gauge32,
    cucsStorageFlexFlashControllerFsmRmtErrDescr                     SnmpAdminString,
    cucsStorageFlexFlashControllerFsmRmtRslt                         CucsConditionRemoteInvRslt
}

cucsStorageFlexFlashControllerFsmInstanceId OBJECT-TYPE
    SYNTAX       CucsManagedObjectId
    MAX-ACCESS   not-accessible
    STATUS       current
    DESCRIPTION
        "Instance identifier of the managed object."
    ::= { cucsStorageFlexFlashControllerFsmEntry 1 }

cucsStorageFlexFlashControllerFsmDn OBJECT-TYPE
    SYNTAX       CucsManagedObjectDn
    MAX-ACCESS   read-only
    STATUS       current
    DESCRIPTION
        "Cisco UCS storage:FlexFlashControllerFsm:dn managed
        object property"
    ::= { cucsStorageFlexFlashControllerFsmEntry 2 }

cucsStorageFlexFlashControllerFsmRn OBJECT-TYPE
    SYNTAX       SnmpAdminString
    MAX-ACCESS   read-only
    STATUS       current
    DESCRIPTION
        "Cisco UCS storage:FlexFlashControllerFsm:rn managed
        object property"
    ::= { cucsStorageFlexFlashControllerFsmEntry 3 }

cucsStorageFlexFlashControllerFsmCompletionTime OBJECT-TYPE
    SYNTAX       DateAndTime
    MAX-ACCESS   read-only
    STATUS       current
    DESCRIPTION
        "Cisco UCS storage:FlexFlashControllerFsm:completionTime
        managed object property"
    ::= { cucsStorageFlexFlashControllerFsmEntry 4 }

cucsStorageFlexFlashControllerFsmCurrentFsm OBJECT-TYPE
    SYNTAX       CucsStorageFlexFlashControllerFsmCurrentFsm
    MAX-ACCESS   read-only
    STATUS       current
    DESCRIPTION
        "Cisco UCS storage:FlexFlashControllerFsm:currentFsm
        managed object property"
    ::= { cucsStorageFlexFlashControllerFsmEntry 5 }

cucsStorageFlexFlashControllerFsmDescrData OBJECT-TYPE
    SYNTAX       SnmpAdminString
    MAX-ACCESS   read-only
    STATUS       current
    DESCRIPTION
        "Cisco UCS storage:FlexFlashControllerFsm:descr
        managed object property"
    ::= { cucsStorageFlexFlashControllerFsmEntry 6 }

cucsStorageFlexFlashControllerFsmFsmStatus OBJECT-TYPE
    SYNTAX       CucsFsmFsmStageStatus
    MAX-ACCESS   read-only
    STATUS       current
    DESCRIPTION
        "Cisco UCS storage:FlexFlashControllerFsm:fsmStatus
        managed object property"
    ::= { cucsStorageFlexFlashControllerFsmEntry 7 }

cucsStorageFlexFlashControllerFsmProgress OBJECT-TYPE
    SYNTAX       Gauge32
    MAX-ACCESS   read-only
    STATUS       current
    DESCRIPTION
        "Cisco UCS storage:FlexFlashControllerFsm:progress
        managed object property"
    ::= { cucsStorageFlexFlashControllerFsmEntry 8 }

cucsStorageFlexFlashControllerFsmRmtErrCode OBJECT-TYPE
    SYNTAX       Gauge32
    MAX-ACCESS   read-only
    STATUS       current
    DESCRIPTION
        "Cisco UCS storage:FlexFlashControllerFsm:rmtErrCode
        managed object property"
    ::= { cucsStorageFlexFlashControllerFsmEntry 9 }

cucsStorageFlexFlashControllerFsmRmtErrDescr OBJECT-TYPE
    SYNTAX       SnmpAdminString
    MAX-ACCESS   read-only
    STATUS       current
    DESCRIPTION
        "Cisco UCS storage:FlexFlashControllerFsm:rmtErrDescr
        managed object property"
    ::= { cucsStorageFlexFlashControllerFsmEntry 10 }

cucsStorageFlexFlashControllerFsmRmtRslt OBJECT-TYPE
    SYNTAX       CucsConditionRemoteInvRslt
    MAX-ACCESS   read-only
    STATUS       current
    DESCRIPTION
        "Cisco UCS storage:FlexFlashControllerFsm:rmtRslt
        managed object property"
    ::= { cucsStorageFlexFlashControllerFsmEntry 11 }

cucsStorageFlexFlashControllerFsmStageTable OBJECT-TYPE
    SYNTAX           SEQUENCE OF CucsStorageFlexFlashControllerFsmStageEntry
    MAX-ACCESS       not-accessible
    STATUS           current
    DESCRIPTION
        "Cisco UCS storage:FlexFlashControllerFsmStage
        managed object table"
    ::= { cucsStorageObjects 41 }

cucsStorageFlexFlashControllerFsmStageEntry OBJECT-TYPE
    SYNTAX           CucsStorageFlexFlashControllerFsmStageEntry
    MAX-ACCESS       not-accessible
    STATUS           current
    DESCRIPTION
        "Entry for the cucsStorageFlexFlashControllerFsmStageTable table."
    INDEX { cucsStorageFlexFlashControllerFsmStageInstanceId }
    ::= { cucsStorageFlexFlashControllerFsmStageTable 1 }

CucsStorageFlexFlashControllerFsmStageEntry ::= SEQUENCE {
    cucsStorageFlexFlashControllerFsmStageInstanceId                 CucsManagedObjectId,
    cucsStorageFlexFlashControllerFsmStageDn                         CucsManagedObjectDn,
    cucsStorageFlexFlashControllerFsmStageRn                         SnmpAdminString,
    cucsStorageFlexFlashControllerFsmStageDescrData                  SnmpAdminString,
    cucsStorageFlexFlashControllerFsmStageLastUpdateTime             DateAndTime,
    cucsStorageFlexFlashControllerFsmStageName                       CucsStorageFlexFlashControllerFsmStageName,
    cucsStorageFlexFlashControllerFsmStageOrder                      Gauge32,
    cucsStorageFlexFlashControllerFsmStageRetry                      Gauge32,
    cucsStorageFlexFlashControllerFsmStageStageStatus                CucsFsmFsmStageStatus
}

cucsStorageFlexFlashControllerFsmStageInstanceId OBJECT-TYPE
    SYNTAX       CucsManagedObjectId
    MAX-ACCESS   not-accessible
    STATUS       current
    DESCRIPTION
        "Instance identifier of the managed object."
    ::= { cucsStorageFlexFlashControllerFsmStageEntry 1 }

cucsStorageFlexFlashControllerFsmStageDn OBJECT-TYPE
    SYNTAX       CucsManagedObjectDn
    MAX-ACCESS   read-only
    STATUS       current
    DESCRIPTION
        "Cisco UCS storage:FlexFlashControllerFsmStage:dn
        managed object property"
    ::= { cucsStorageFlexFlashControllerFsmStageEntry 2 }

cucsStorageFlexFlashControllerFsmStageRn OBJECT-TYPE
    SYNTAX       SnmpAdminString
    MAX-ACCESS   read-only
    STATUS       current
    DESCRIPTION
        "Cisco UCS storage:FlexFlashControllerFsmStage:rn
        managed object property"
    ::= { cucsStorageFlexFlashControllerFsmStageEntry 3 }

cucsStorageFlexFlashControllerFsmStageDescrData OBJECT-TYPE
    SYNTAX       SnmpAdminString
    MAX-ACCESS   read-only
    STATUS       current
    DESCRIPTION
        "Cisco UCS storage:FlexFlashControllerFsmStage:descr
        managed object property"
    ::= { cucsStorageFlexFlashControllerFsmStageEntry 4 }

cucsStorageFlexFlashControllerFsmStageLastUpdateTime OBJECT-TYPE
    SYNTAX       DateAndTime
    MAX-ACCESS   read-only
    STATUS       current
    DESCRIPTION
        "Cisco UCS storage:FlexFlashControllerFsmStage:lastUpdateTime
        managed object property"
    ::= { cucsStorageFlexFlashControllerFsmStageEntry 5 }

cucsStorageFlexFlashControllerFsmStageName OBJECT-TYPE
    SYNTAX       CucsStorageFlexFlashControllerFsmStageName
    MAX-ACCESS   read-only
    STATUS       current
    DESCRIPTION
        "Cisco UCS storage:FlexFlashControllerFsmStage:name
        managed object property"
    ::= { cucsStorageFlexFlashControllerFsmStageEntry 6 }

cucsStorageFlexFlashControllerFsmStageOrder OBJECT-TYPE
    SYNTAX       Gauge32
    MAX-ACCESS   read-only
    STATUS       current
    DESCRIPTION
        "Cisco UCS storage:FlexFlashControllerFsmStage:order
        managed object property"
    ::= { cucsStorageFlexFlashControllerFsmStageEntry 7 }

cucsStorageFlexFlashControllerFsmStageRetry OBJECT-TYPE
    SYNTAX       Gauge32
    MAX-ACCESS   read-only
    STATUS       current
    DESCRIPTION
        "Cisco UCS storage:FlexFlashControllerFsmStage:retry
        managed object property"
    ::= { cucsStorageFlexFlashControllerFsmStageEntry 8 }

cucsStorageFlexFlashControllerFsmStageStageStatus OBJECT-TYPE
    SYNTAX       CucsFsmFsmStageStatus
    MAX-ACCESS   read-only
    STATUS       current
    DESCRIPTION
        "Cisco UCS storage:FlexFlashControllerFsmStage:stageStatus
        managed object property"
    ::= { cucsStorageFlexFlashControllerFsmStageEntry 9 }

cucsStorageFlexFlashControllerFsmTaskTable OBJECT-TYPE
    SYNTAX           SEQUENCE OF CucsStorageFlexFlashControllerFsmTaskEntry
    MAX-ACCESS       not-accessible
    STATUS           current
    DESCRIPTION
        "Cisco UCS storage:FlexFlashControllerFsmTask managed
        object table"
    ::= { cucsStorageObjects 42 }

cucsStorageFlexFlashControllerFsmTaskEntry OBJECT-TYPE
    SYNTAX           CucsStorageFlexFlashControllerFsmTaskEntry
    MAX-ACCESS       not-accessible
    STATUS           current
    DESCRIPTION
        "Entry for the cucsStorageFlexFlashControllerFsmTaskTable table."
    INDEX { cucsStorageFlexFlashControllerFsmTaskInstanceId }
    ::= { cucsStorageFlexFlashControllerFsmTaskTable 1 }

CucsStorageFlexFlashControllerFsmTaskEntry ::= SEQUENCE {
    cucsStorageFlexFlashControllerFsmTaskInstanceId                  CucsManagedObjectId,
    cucsStorageFlexFlashControllerFsmTaskDn                          CucsManagedObjectDn,
    cucsStorageFlexFlashControllerFsmTaskRn                          SnmpAdminString,
    cucsStorageFlexFlashControllerFsmTaskCompletion                  CucsFsmCompletion,
    cucsStorageFlexFlashControllerFsmTaskFlags                       CucsFsmFlags,
    cucsStorageFlexFlashControllerFsmTaskItem                        CucsStorageFlexFlashControllerFsmTaskItem,
    cucsStorageFlexFlashControllerFsmTaskSeqId                       Gauge32
}

cucsStorageFlexFlashControllerFsmTaskInstanceId OBJECT-TYPE
    SYNTAX       CucsManagedObjectId
    MAX-ACCESS   not-accessible
    STATUS       current
    DESCRIPTION
        "Instance identifier of the managed object."
    ::= { cucsStorageFlexFlashControllerFsmTaskEntry 1 }

cucsStorageFlexFlashControllerFsmTaskDn OBJECT-TYPE
    SYNTAX       CucsManagedObjectDn
    MAX-ACCESS   read-only
    STATUS       current
    DESCRIPTION
        "Cisco UCS storage:FlexFlashControllerFsmTask:dn
        managed object property"
    ::= { cucsStorageFlexFlashControllerFsmTaskEntry 2 }

cucsStorageFlexFlashControllerFsmTaskRn OBJECT-TYPE
    SYNTAX       SnmpAdminString
    MAX-ACCESS   read-only
    STATUS       current
    DESCRIPTION
        "Cisco UCS storage:FlexFlashControllerFsmTask:rn
        managed object property"
    ::= { cucsStorageFlexFlashControllerFsmTaskEntry 3 }

cucsStorageFlexFlashControllerFsmTaskCompletion OBJECT-TYPE
    SYNTAX       CucsFsmCompletion
    MAX-ACCESS   read-only
    STATUS       current
    DESCRIPTION
        "Cisco UCS storage:FlexFlashControllerFsmTask:completion
        managed object property"
    ::= { cucsStorageFlexFlashControllerFsmTaskEntry 4 }

cucsStorageFlexFlashControllerFsmTaskFlags OBJECT-TYPE
    SYNTAX       CucsFsmFlags
    MAX-ACCESS   read-only
    STATUS       current
    DESCRIPTION
        "Cisco UCS storage:FlexFlashControllerFsmTask:flags
        managed object property"
    ::= { cucsStorageFlexFlashControllerFsmTaskEntry 5 }

cucsStorageFlexFlashControllerFsmTaskItem OBJECT-TYPE
    SYNTAX       CucsStorageFlexFlashControllerFsmTaskItem
    MAX-ACCESS   read-only
    STATUS       current
    DESCRIPTION
        "Cisco UCS storage:FlexFlashControllerFsmTask:item
        managed object property"
    ::= { cucsStorageFlexFlashControllerFsmTaskEntry 6 }

cucsStorageFlexFlashControllerFsmTaskSeqId OBJECT-TYPE
    SYNTAX       Gauge32
    MAX-ACCESS   read-only
    STATUS       current
    DESCRIPTION
        "Cisco UCS storage:FlexFlashControllerFsmTask:seqId
        managed object property"
    ::= { cucsStorageFlexFlashControllerFsmTaskEntry 7 }

cucsStorageFlexFlashDriveTable OBJECT-TYPE
    SYNTAX           SEQUENCE OF CucsStorageFlexFlashDriveEntry
    MAX-ACCESS       not-accessible
    STATUS           current
    DESCRIPTION
        "Cisco UCS storage:FlexFlashDrive managed object table"
    ::= { cucsStorageObjects 36 }

cucsStorageFlexFlashDriveEntry OBJECT-TYPE
    SYNTAX           CucsStorageFlexFlashDriveEntry
    MAX-ACCESS       not-accessible
    STATUS           current
    DESCRIPTION
        "Entry for the cucsStorageFlexFlashDriveTable table."
    INDEX { cucsStorageFlexFlashDriveInstanceId }
    ::= { cucsStorageFlexFlashDriveTable 1 }

CucsStorageFlexFlashDriveEntry ::= SEQUENCE {
    cucsStorageFlexFlashDriveInstanceId                              CucsManagedObjectId,
    cucsStorageFlexFlashDriveDn                                      CucsManagedObjectDn,
    cucsStorageFlexFlashDriveRn                                      SnmpAdminString,
    cucsStorageFlexFlashDriveBlockSize                               Gauge32,
    cucsStorageFlexFlashDriveConnectionProtocol                      CucsStorageConnectionProtocol,
    cucsStorageFlexFlashDriveControllerIndex                         Gauge32,
    cucsStorageFlexFlashDriveDriveState                              CucsStorageFFDriveState,
    cucsStorageFlexFlashDriveDriveType                               CucsStorageFFDriveType,
    cucsStorageFlexFlashDriveId                                      Gauge32,
    cucsStorageFlexFlashDriveModel                                   SnmpAdminString,
    cucsStorageFlexFlashDriveName                                    SnmpAdminString,
    cucsStorageFlexFlashDriveNumberOfBlocks                          Unsigned64,
    cucsStorageFlexFlashDriveOperQualifierReason                     SnmpAdminString,
    cucsStorageFlexFlashDriveOperability                             CucsEquipmentOperability,
    cucsStorageFlexFlashDrivePresence                                CucsEquipmentPresence,
    cucsStorageFlexFlashDriveRevision                                SnmpAdminString,
    cucsStorageFlexFlashDriveSerial                                  SnmpAdminString,
    cucsStorageFlexFlashDriveSize                                    Unsigned64,
    cucsStorageFlexFlashDriveSlotNumber                              Gauge32,
    cucsStorageFlexFlashDriveVendor                                  SnmpAdminString,
    cucsStorageFlexFlashDriveVisible                                 CucsStorageFFDriveVisible,
    cucsStorageFlexFlashDriveRemovable                               CucsStorageFFDriveRemovable,
    cucsStorageFlexFlashDriveRWType                                  CucsStorageFFRWType,
    cucsStorageFlexFlashDriveLastOperation                           CucsStorageOperationStateType,
    cucsStorageFlexFlashDriveOperationState                          CucsStorageOperationStateType,
    cucsStorageFlexFlashDrivePhysicalBlockSize                       Gauge32
}

cucsStorageFlexFlashDriveInstanceId OBJECT-TYPE
    SYNTAX       CucsManagedObjectId
    MAX-ACCESS   not-accessible
    STATUS       current
    DESCRIPTION
        "Instance identifier of the managed object."
    ::= { cucsStorageFlexFlashDriveEntry 1 }

cucsStorageFlexFlashDriveDn OBJECT-TYPE
    SYNTAX       CucsManagedObjectDn
    MAX-ACCESS   read-only
    STATUS       current
    DESCRIPTION
        "Cisco UCS storage:FlexFlashDrive:dn managed object property"
    ::= { cucsStorageFlexFlashDriveEntry 2 }

cucsStorageFlexFlashDriveRn OBJECT-TYPE
    SYNTAX       SnmpAdminString
    MAX-ACCESS   read-only
    STATUS       current
    DESCRIPTION
        "Cisco UCS storage:FlexFlashDrive:rn managed object property"
    ::= { cucsStorageFlexFlashDriveEntry 3 }

cucsStorageFlexFlashDriveBlockSize OBJECT-TYPE
    SYNTAX       Gauge32
    MAX-ACCESS   read-only
    STATUS       current
    DESCRIPTION
        "Cisco UCS storage:FlexFlashDrive:blockSize managed
        object property"
    ::= { cucsStorageFlexFlashDriveEntry 4 }

cucsStorageFlexFlashDriveConnectionProtocol OBJECT-TYPE
    SYNTAX       CucsStorageConnectionProtocol
    MAX-ACCESS   read-only
    STATUS       current
    DESCRIPTION
        "Cisco UCS storage:FlexFlashDrive:connectionProtocol
        managed object property"
    ::= { cucsStorageFlexFlashDriveEntry 5 }

cucsStorageFlexFlashDriveControllerIndex OBJECT-TYPE
    SYNTAX       Gauge32
    MAX-ACCESS   read-only
    STATUS       current
    DESCRIPTION
        "Cisco UCS storage:FlexFlashDrive:controllerIndex
        managed object property"
    ::= { cucsStorageFlexFlashDriveEntry 6 }

cucsStorageFlexFlashDriveDriveState OBJECT-TYPE
    SYNTAX       CucsStorageFFDriveState
    MAX-ACCESS   read-only
    STATUS       current
    DESCRIPTION
        "Cisco UCS storage:FlexFlashDrive:driveState managed
        object property"
    ::= { cucsStorageFlexFlashDriveEntry 7 }

cucsStorageFlexFlashDriveDriveType OBJECT-TYPE
    SYNTAX       CucsStorageFFDriveType
    MAX-ACCESS   read-only
    STATUS       current
    DESCRIPTION
        "Cisco UCS storage:FlexFlashDrive:driveType managed
        object property"
    ::= { cucsStorageFlexFlashDriveEntry 8 }

cucsStorageFlexFlashDriveId OBJECT-TYPE
    SYNTAX       Gauge32
    MAX-ACCESS   read-only
    STATUS       current
    DESCRIPTION
        "Cisco UCS storage:FlexFlashDrive:id managed object property"
    ::= { cucsStorageFlexFlashDriveEntry 9 }

cucsStorageFlexFlashDriveModel OBJECT-TYPE
    SYNTAX       SnmpAdminString
    MAX-ACCESS   read-only
    STATUS       current
    DESCRIPTION
        "Cisco UCS storage:FlexFlashDrive:model managed object property"
    ::= { cucsStorageFlexFlashDriveEntry 10 }

cucsStorageFlexFlashDriveName OBJECT-TYPE
    SYNTAX       SnmpAdminString
    MAX-ACCESS   read-only
    STATUS       current
    DESCRIPTION
        "Cisco UCS storage:FlexFlashDrive:name managed object property"
    ::= { cucsStorageFlexFlashDriveEntry 11 }

cucsStorageFlexFlashDriveNumberOfBlocks OBJECT-TYPE
    SYNTAX       Unsigned64
    MAX-ACCESS   read-only
    STATUS       current
    DESCRIPTION
        "Cisco UCS storage:FlexFlashDrive:numberOfBlocks
        managed object property"
    ::= { cucsStorageFlexFlashDriveEntry 12 }

cucsStorageFlexFlashDriveOperQualifierReason OBJECT-TYPE
    SYNTAX       SnmpAdminString
    MAX-ACCESS   read-only
    STATUS       current
    DESCRIPTION
        "Cisco UCS storage:FlexFlashDrive:operQualifierReason
        managed object property"
    ::= { cucsStorageFlexFlashDriveEntry 13 }

cucsStorageFlexFlashDriveOperability OBJECT-TYPE
    SYNTAX       CucsEquipmentOperability
    MAX-ACCESS   read-only
    STATUS       current
    DESCRIPTION
        "Cisco UCS storage:FlexFlashDrive:operability managed
        object property"
    ::= { cucsStorageFlexFlashDriveEntry 14 }

cucsStorageFlexFlashDrivePresence OBJECT-TYPE
    SYNTAX       CucsEquipmentPresence
    MAX-ACCESS   read-only
    STATUS       current
    DESCRIPTION
        "Cisco UCS storage:FlexFlashDrive:presence managed
        object property"
    ::= { cucsStorageFlexFlashDriveEntry 15 }

cucsStorageFlexFlashDriveRevision OBJECT-TYPE
    SYNTAX       SnmpAdminString
    MAX-ACCESS   read-only
    STATUS       current
    DESCRIPTION
        "Cisco UCS storage:FlexFlashDrive:revision managed
        object property"
    ::= { cucsStorageFlexFlashDriveEntry 16 }

cucsStorageFlexFlashDriveSerial OBJECT-TYPE
    SYNTAX       SnmpAdminString
    MAX-ACCESS   read-only
    STATUS       current
    DESCRIPTION
        "Cisco UCS storage:FlexFlashDrive:serial managed object property"
    ::= { cucsStorageFlexFlashDriveEntry 17 }

cucsStorageFlexFlashDriveSize OBJECT-TYPE
    SYNTAX       Unsigned64
    MAX-ACCESS   read-only
    STATUS       current
    DESCRIPTION
        "Cisco UCS storage:FlexFlashDrive:size managed object property"
    ::= { cucsStorageFlexFlashDriveEntry 18 }

cucsStorageFlexFlashDriveSlotNumber OBJECT-TYPE
    SYNTAX       Gauge32
    MAX-ACCESS   read-only
    STATUS       current
    DESCRIPTION
        "Cisco UCS storage:FlexFlashDrive:slotNumber managed
        object property"
    ::= { cucsStorageFlexFlashDriveEntry 19 }

cucsStorageFlexFlashDriveVendor OBJECT-TYPE
    SYNTAX       SnmpAdminString
    MAX-ACCESS   read-only
    STATUS       current
    DESCRIPTION
        "Cisco UCS storage:FlexFlashDrive:vendor managed object property"
    ::= { cucsStorageFlexFlashDriveEntry 20 }

cucsStorageFlexFlashDriveVisible OBJECT-TYPE
    SYNTAX       CucsStorageFFDriveVisible
    MAX-ACCESS   read-only
    STATUS       current
    DESCRIPTION
        "Cisco UCS storage:FlexFlashDrive:visible managed object property"
    ::= { cucsStorageFlexFlashDriveEntry 21 }

cucsStorageFlexFlashDriveRemovable OBJECT-TYPE
    SYNTAX       CucsStorageFFDriveRemovable
    MAX-ACCESS   read-only
    STATUS       current
    DESCRIPTION
        "Cisco UCS storage:FlexFlashDrive:removable managed
        object property"
    ::= { cucsStorageFlexFlashDriveEntry 22 }

cucsStorageFlexFlashDriveRWType OBJECT-TYPE
    SYNTAX       CucsStorageFFRWType
    MAX-ACCESS   read-only
    STATUS       current
    DESCRIPTION
        "Cisco UCS storage:FlexFlashDrive:RWType managed object property"
    ::= { cucsStorageFlexFlashDriveEntry 23 }

cucsStorageFlexFlashDriveLastOperation OBJECT-TYPE
    SYNTAX       CucsStorageOperationStateType
    MAX-ACCESS   read-only
    STATUS       current
    DESCRIPTION
        "Cisco UCS storage:FlexFlashDrive:lastOperation
        managed object property"
    ::= { cucsStorageFlexFlashDriveEntry 24 }

cucsStorageFlexFlashDriveOperationState OBJECT-TYPE
    SYNTAX       CucsStorageOperationStateType
    MAX-ACCESS   read-only
    STATUS       current
    DESCRIPTION
        "Cisco UCS storage:FlexFlashDrive:operationState
        managed object property"
    ::= { cucsStorageFlexFlashDriveEntry 25 }

cucsStorageFlexFlashDrivePhysicalBlockSize OBJECT-TYPE
    SYNTAX       Gauge32
    MAX-ACCESS   read-only
    STATUS       current
    DESCRIPTION
        "Cisco UCS storage:FlexFlashDrive:physicalBlockSize
        managed object property"
    ::= { cucsStorageFlexFlashDriveEntry 26 }

cucsStorageFlexFlashVirtualDriveTable OBJECT-TYPE
    SYNTAX           SEQUENCE OF CucsStorageFlexFlashVirtualDriveEntry
    MAX-ACCESS       not-accessible
    STATUS           current
    DESCRIPTION
        "Cisco UCS storage:FlexFlashVirtualDrive managed object table"
    ::= { cucsStorageObjects 37 }

cucsStorageFlexFlashVirtualDriveEntry OBJECT-TYPE
    SYNTAX           CucsStorageFlexFlashVirtualDriveEntry
    MAX-ACCESS       not-accessible
    STATUS           current
    DESCRIPTION
        "Entry for the cucsStorageFlexFlashVirtualDriveTable table."
    INDEX { cucsStorageFlexFlashVirtualDriveInstanceId }
    ::= { cucsStorageFlexFlashVirtualDriveTable 1 }

CucsStorageFlexFlashVirtualDriveEntry ::= SEQUENCE {
    cucsStorageFlexFlashVirtualDriveInstanceId                       CucsManagedObjectId,
    cucsStorageFlexFlashVirtualDriveDn                               CucsManagedObjectDn,
    cucsStorageFlexFlashVirtualDriveRn                               SnmpAdminString,
    cucsStorageFlexFlashVirtualDriveBlockSize                        Gauge32,
    cucsStorageFlexFlashVirtualDriveConnectionProtocol               CucsStorageConnectionProtocol,
    cucsStorageFlexFlashVirtualDriveId                               Gauge32,
    cucsStorageFlexFlashVirtualDriveModel                            SnmpAdminString,
    cucsStorageFlexFlashVirtualDriveNumberOfBlocks                   Unsigned64,
    cucsStorageFlexFlashVirtualDriveOperQualifierReason              SnmpAdminString,
    cucsStorageFlexFlashVirtualDriveOperability                      CucsEquipmentOperability,
    cucsStorageFlexFlashVirtualDrivePresence                         CucsEquipmentPresence,
    cucsStorageFlexFlashVirtualDriveRaidHealth                       CucsStorageFFRAIDHealth,
    cucsStorageFlexFlashVirtualDriveRaidState                        CucsStorageFFRAIDState,
    cucsStorageFlexFlashVirtualDriveRevision                         SnmpAdminString,
    cucsStorageFlexFlashVirtualDriveSerial                           SnmpAdminString,
    cucsStorageFlexFlashVirtualDriveSize                             Unsigned64,
    cucsStorageFlexFlashVirtualDriveType                             CucsStorageLunType,
    cucsStorageFlexFlashVirtualDriveVendor                           SnmpAdminString,
    cucsStorageFlexFlashVirtualDrivePhysicalBlockSize                Gauge32
}

cucsStorageFlexFlashVirtualDriveInstanceId OBJECT-TYPE
    SYNTAX       CucsManagedObjectId
    MAX-ACCESS   not-accessible
    STATUS       current
    DESCRIPTION
        "Instance identifier of the managed object."
    ::= { cucsStorageFlexFlashVirtualDriveEntry 1 }

cucsStorageFlexFlashVirtualDriveDn OBJECT-TYPE
    SYNTAX       CucsManagedObjectDn
    MAX-ACCESS   read-only
    STATUS       current
    DESCRIPTION
        "Cisco UCS storage:FlexFlashVirtualDrive:dn managed
        object property"
    ::= { cucsStorageFlexFlashVirtualDriveEntry 2 }

cucsStorageFlexFlashVirtualDriveRn OBJECT-TYPE
    SYNTAX       SnmpAdminString
    MAX-ACCESS   read-only
    STATUS       current
    DESCRIPTION
        "Cisco UCS storage:FlexFlashVirtualDrive:rn managed
        object property"
    ::= { cucsStorageFlexFlashVirtualDriveEntry 3 }

cucsStorageFlexFlashVirtualDriveBlockSize OBJECT-TYPE
    SYNTAX       Gauge32
    MAX-ACCESS   read-only
    STATUS       current
    DESCRIPTION
        "Cisco UCS storage:FlexFlashVirtualDrive:blockSize
        managed object property"
    ::= { cucsStorageFlexFlashVirtualDriveEntry 4 }

cucsStorageFlexFlashVirtualDriveConnectionProtocol OBJECT-TYPE
    SYNTAX       CucsStorageConnectionProtocol
    MAX-ACCESS   read-only
    STATUS       current
    DESCRIPTION
        "Cisco UCS storage:FlexFlashVirtualDrive:connectionProtocol
        managed object property"
    ::= { cucsStorageFlexFlashVirtualDriveEntry 5 }

cucsStorageFlexFlashVirtualDriveId OBJECT-TYPE
    SYNTAX       Gauge32
    MAX-ACCESS   read-only
    STATUS       current
    DESCRIPTION
        "Cisco UCS storage:FlexFlashVirtualDrive:id managed
        object property"
    ::= { cucsStorageFlexFlashVirtualDriveEntry 6 }

cucsStorageFlexFlashVirtualDriveModel OBJECT-TYPE
    SYNTAX       SnmpAdminString
    MAX-ACCESS   read-only
    STATUS       current
    DESCRIPTION
        "Cisco UCS storage:FlexFlashVirtualDrive:model
        managed object property"
    ::= { cucsStorageFlexFlashVirtualDriveEntry 7 }

cucsStorageFlexFlashVirtualDriveNumberOfBlocks OBJECT-TYPE
    SYNTAX       Unsigned64
    MAX-ACCESS   read-only
    STATUS       current
    DESCRIPTION
        "Cisco UCS storage:FlexFlashVirtualDrive:numberOfBlocks
        managed object property"
    ::= { cucsStorageFlexFlashVirtualDriveEntry 8 }

cucsStorageFlexFlashVirtualDriveOperQualifierReason OBJECT-TYPE
    SYNTAX       SnmpAdminString
    MAX-ACCESS   read-only
    STATUS       current
    DESCRIPTION
        "Cisco UCS storage:FlexFlashVirtualDrive:operQualifierReason
        managed object property"
    ::= { cucsStorageFlexFlashVirtualDriveEntry 9 }

cucsStorageFlexFlashVirtualDriveOperability OBJECT-TYPE
    SYNTAX       CucsEquipmentOperability
    MAX-ACCESS   read-only
    STATUS       current
    DESCRIPTION
        "Cisco UCS storage:FlexFlashVirtualDrive:operability
        managed object property"
    ::= { cucsStorageFlexFlashVirtualDriveEntry 10 }

cucsStorageFlexFlashVirtualDrivePresence OBJECT-TYPE
    SYNTAX       CucsEquipmentPresence
    MAX-ACCESS   read-only
    STATUS       current
    DESCRIPTION
        "Cisco UCS storage:FlexFlashVirtualDrive:presence
        managed object property"
    ::= { cucsStorageFlexFlashVirtualDriveEntry 11 }

cucsStorageFlexFlashVirtualDriveRaidHealth OBJECT-TYPE
    SYNTAX       CucsStorageFFRAIDHealth
    MAX-ACCESS   read-only
    STATUS       current
    DESCRIPTION
        "Cisco UCS storage:FlexFlashVirtualDrive:raidHealth
        managed object property"
    ::= { cucsStorageFlexFlashVirtualDriveEntry 12 }

cucsStorageFlexFlashVirtualDriveRaidState OBJECT-TYPE
    SYNTAX       CucsStorageFFRAIDState
    MAX-ACCESS   read-only
    STATUS       current
    DESCRIPTION
        "Cisco UCS storage:FlexFlashVirtualDrive:raidState
        managed object property"
    ::= { cucsStorageFlexFlashVirtualDriveEntry 13 }

cucsStorageFlexFlashVirtualDriveRevision OBJECT-TYPE
    SYNTAX       SnmpAdminString
    MAX-ACCESS   read-only
    STATUS       current
    DESCRIPTION
        "Cisco UCS storage:FlexFlashVirtualDrive:revision
        managed object property"
    ::= { cucsStorageFlexFlashVirtualDriveEntry 14 }

cucsStorageFlexFlashVirtualDriveSerial OBJECT-TYPE
    SYNTAX       SnmpAdminString
    MAX-ACCESS   read-only
    STATUS       current
    DESCRIPTION
        "Cisco UCS storage:FlexFlashVirtualDrive:serial
        managed object property"
    ::= { cucsStorageFlexFlashVirtualDriveEntry 15 }

cucsStorageFlexFlashVirtualDriveSize OBJECT-TYPE
    SYNTAX       Unsigned64
    MAX-ACCESS   read-only
    STATUS       current
    DESCRIPTION
        "Cisco UCS storage:FlexFlashVirtualDrive:size managed
        object property"
    ::= { cucsStorageFlexFlashVirtualDriveEntry 16 }

cucsStorageFlexFlashVirtualDriveType OBJECT-TYPE
    SYNTAX       CucsStorageLunType
    MAX-ACCESS   read-only
    STATUS       current
    DESCRIPTION
        "Cisco UCS storage:FlexFlashVirtualDrive:type managed
        object property"
    ::= { cucsStorageFlexFlashVirtualDriveEntry 17 }

cucsStorageFlexFlashVirtualDriveVendor OBJECT-TYPE
    SYNTAX       SnmpAdminString
    MAX-ACCESS   read-only
    STATUS       current
    DESCRIPTION
        "Cisco UCS storage:FlexFlashVirtualDrive:vendor
        managed object property"
    ::= { cucsStorageFlexFlashVirtualDriveEntry 18 }

cucsStorageFlexFlashVirtualDrivePhysicalBlockSize OBJECT-TYPE
    SYNTAX       Gauge32
    MAX-ACCESS   read-only
    STATUS       current
    DESCRIPTION
        "Cisco UCS storage:FlexFlashVirtualDrive:physicalBlockSize
        managed object property"
    ::= { cucsStorageFlexFlashVirtualDriveEntry 19 }

cucsStorageHddMotherBoardTempStatsTable OBJECT-TYPE
    SYNTAX           SEQUENCE OF CucsStorageHddMotherBoardTempStatsEntry
    MAX-ACCESS       not-accessible
    STATUS           current
    DESCRIPTION
        "Cisco UCS storage:HddMotherBoardTempStats managed object table"
    ::= { cucsStorageObjects 112 }

cucsStorageHddMotherBoardTempStatsEntry OBJECT-TYPE
    SYNTAX           CucsStorageHddMotherBoardTempStatsEntry
    MAX-ACCESS       not-accessible
    STATUS           current
    DESCRIPTION
        "Entry for the cucsStorageHddMotherBoardTempStatsTable table."
    INDEX { cucsStorageHddMotherBoardTempStatsInstanceId }
    ::= { cucsStorageHddMotherBoardTempStatsTable 1 }

CucsStorageHddMotherBoardTempStatsEntry ::= SEQUENCE {
    cucsStorageHddMotherBoardTempStatsInstanceId                     CucsManagedObjectId,
    cucsStorageHddMotherBoardTempStatsDn                             CucsManagedObjectDn,
    cucsStorageHddMotherBoardTempStatsRn                             SnmpAdminString,
    cucsStorageHddMotherBoardTempStatsIntervals                      Gauge32,
    cucsStorageHddMotherBoardTempStatsLeftInletTemp                  SnmpAdminString,
    cucsStorageHddMotherBoardTempStatsLeftInletTempAvg               SnmpAdminString,
    cucsStorageHddMotherBoardTempStatsLeftInletTempMax               SnmpAdminString,
    cucsStorageHddMotherBoardTempStatsLeftInletTempMin               SnmpAdminString,
    cucsStorageHddMotherBoardTempStatsLeftOutletTemp                 SnmpAdminString,
    cucsStorageHddMotherBoardTempStatsLeftOutletTempAvg              SnmpAdminString,
    cucsStorageHddMotherBoardTempStatsLeftOutletTempMax              SnmpAdminString,
    cucsStorageHddMotherBoardTempStatsLeftOutletTempMin              SnmpAdminString,
    cucsStorageHddMotherBoardTempStatsRightInletTemp                 SnmpAdminString,
    cucsStorageHddMotherBoardTempStatsRightInletTempAvg              SnmpAdminString,
    cucsStorageHddMotherBoardTempStatsRightInletTempMax              SnmpAdminString,
    cucsStorageHddMotherBoardTempStatsRightInletTempMin              SnmpAdminString,
    cucsStorageHddMotherBoardTempStatsRightOutletTemp                SnmpAdminString,
    cucsStorageHddMotherBoardTempStatsRightOutletTempAvg             SnmpAdminString,
    cucsStorageHddMotherBoardTempStatsRightOutletTempMax             SnmpAdminString,
    cucsStorageHddMotherBoardTempStatsRightOutletTempMin             SnmpAdminString,
    cucsStorageHddMotherBoardTempStatsSuspect                        TruthValue,
    cucsStorageHddMotherBoardTempStatsThresholded                    CucsStorageHddMotherBoardTempStatsThresholded,
    cucsStorageHddMotherBoardTempStatsTimeCollected                  DateAndTime,
    cucsStorageHddMotherBoardTempStatsUpdate                         Gauge32
}

cucsStorageHddMotherBoardTempStatsInstanceId OBJECT-TYPE
    SYNTAX       CucsManagedObjectId
    MAX-ACCESS   not-accessible
    STATUS       current
    DESCRIPTION
        "Instance identifier of the managed object."
    ::= { cucsStorageHddMotherBoardTempStatsEntry 1 }

cucsStorageHddMotherBoardTempStatsDn OBJECT-TYPE
    SYNTAX       CucsManagedObjectDn
    MAX-ACCESS   read-only
    STATUS       current
    DESCRIPTION
        "Cisco UCS storage:HddMotherBoardTempStats:dn managed
        object property"
    ::= { cucsStorageHddMotherBoardTempStatsEntry 2 }

cucsStorageHddMotherBoardTempStatsRn OBJECT-TYPE
    SYNTAX       SnmpAdminString
    MAX-ACCESS   read-only
    STATUS       current
    DESCRIPTION
        "Cisco UCS storage:HddMotherBoardTempStats:rn managed
        object property"
    ::= { cucsStorageHddMotherBoardTempStatsEntry 3 }

cucsStorageHddMotherBoardTempStatsIntervals OBJECT-TYPE
    SYNTAX       Gauge32
    MAX-ACCESS   read-only
    STATUS       current
    DESCRIPTION
        "Cisco UCS storage:HddMotherBoardTempStats:intervals
        managed object property"
    ::= { cucsStorageHddMotherBoardTempStatsEntry 4 }

cucsStorageHddMotherBoardTempStatsLeftInletTemp OBJECT-TYPE
    SYNTAX       SnmpAdminString
    MAX-ACCESS   read-only
    STATUS       current
    DESCRIPTION
        "Cisco UCS storage:HddMotherBoardTempStats:leftInletTemp
        managed object property"
    ::= { cucsStorageHddMotherBoardTempStatsEntry 5 }

cucsStorageHddMotherBoardTempStatsLeftInletTempAvg OBJECT-TYPE
    SYNTAX       SnmpAdminString
    MAX-ACCESS   read-only
    STATUS       current
    DESCRIPTION
        "Cisco UCS storage:HddMotherBoardTempStats:leftInletTempAvg
        managed object property"
    ::= { cucsStorageHddMotherBoardTempStatsEntry 6 }

cucsStorageHddMotherBoardTempStatsLeftInletTempMax OBJECT-TYPE
    SYNTAX       SnmpAdminString
    MAX-ACCESS   read-only
    STATUS       current
    DESCRIPTION
        "Cisco UCS storage:HddMotherBoardTempStats:leftInletTempMax
        managed object property"
    ::= { cucsStorageHddMotherBoardTempStatsEntry 7 }

cucsStorageHddMotherBoardTempStatsLeftInletTempMin OBJECT-TYPE
    SYNTAX       SnmpAdminString
    MAX-ACCESS   read-only
    STATUS       current
    DESCRIPTION
        "Cisco UCS storage:HddMotherBoardTempStats:leftInletTempMin
        managed object property"
    ::= { cucsStorageHddMotherBoardTempStatsEntry 8 }

cucsStorageHddMotherBoardTempStatsLeftOutletTemp OBJECT-TYPE
    SYNTAX       SnmpAdminString
    MAX-ACCESS   read-only
    STATUS       current
    DESCRIPTION
        "Cisco UCS storage:HddMotherBoardTempStats:leftOutletTemp
        managed object property"
    ::= { cucsStorageHddMotherBoardTempStatsEntry 9 }

cucsStorageHddMotherBoardTempStatsLeftOutletTempAvg OBJECT-TYPE
    SYNTAX       SnmpAdminString
    MAX-ACCESS   read-only
    STATUS       current
    DESCRIPTION
        "Cisco UCS storage:HddMotherBoardTempStats:leftOutletTempAvg
        managed object property"
    ::= { cucsStorageHddMotherBoardTempStatsEntry 10 }

cucsStorageHddMotherBoardTempStatsLeftOutletTempMax OBJECT-TYPE
    SYNTAX       SnmpAdminString
    MAX-ACCESS   read-only
    STATUS       current
    DESCRIPTION
        "Cisco UCS storage:HddMotherBoardTempStats:leftOutletTempMax
        managed object property"
    ::= { cucsStorageHddMotherBoardTempStatsEntry 11 }

cucsStorageHddMotherBoardTempStatsLeftOutletTempMin OBJECT-TYPE
    SYNTAX       SnmpAdminString
    MAX-ACCESS   read-only
    STATUS       current
    DESCRIPTION
        "Cisco UCS storage:HddMotherBoardTempStats:leftOutletTempMin
        managed object property"
    ::= { cucsStorageHddMotherBoardTempStatsEntry 12 }

cucsStorageHddMotherBoardTempStatsRightInletTemp OBJECT-TYPE
    SYNTAX       SnmpAdminString
    MAX-ACCESS   read-only
    STATUS       current
    DESCRIPTION
        "Cisco UCS storage:HddMotherBoardTempStats:rightInletTemp
        managed object property"
    ::= { cucsStorageHddMotherBoardTempStatsEntry 14 }

cucsStorageHddMotherBoardTempStatsRightInletTempAvg OBJECT-TYPE
    SYNTAX       SnmpAdminString
    MAX-ACCESS   read-only
    STATUS       current
    DESCRIPTION
        "Cisco UCS storage:HddMotherBoardTempStats:rightInletTempAvg
        managed object property"
    ::= { cucsStorageHddMotherBoardTempStatsEntry 15 }

cucsStorageHddMotherBoardTempStatsRightInletTempMax OBJECT-TYPE
    SYNTAX       SnmpAdminString
    MAX-ACCESS   read-only
    STATUS       current
    DESCRIPTION
        "Cisco UCS storage:HddMotherBoardTempStats:rightInletTempMax
        managed object property"
    ::= { cucsStorageHddMotherBoardTempStatsEntry 16 }

cucsStorageHddMotherBoardTempStatsRightInletTempMin OBJECT-TYPE
    SYNTAX       SnmpAdminString
    MAX-ACCESS   read-only
    STATUS       current
    DESCRIPTION
        "Cisco UCS storage:HddMotherBoardTempStats:rightInletTempMin
        managed object property"
    ::= { cucsStorageHddMotherBoardTempStatsEntry 17 }

cucsStorageHddMotherBoardTempStatsRightOutletTemp OBJECT-TYPE
    SYNTAX       SnmpAdminString
    MAX-ACCESS   read-only
    STATUS       current
    DESCRIPTION
        "Cisco UCS storage:HddMotherBoardTempStats:rightOutletTemp
        managed object property"
    ::= { cucsStorageHddMotherBoardTempStatsEntry 18 }

cucsStorageHddMotherBoardTempStatsRightOutletTempAvg OBJECT-TYPE
    SYNTAX       SnmpAdminString
    MAX-ACCESS   read-only
    STATUS       current
    DESCRIPTION
        "Cisco UCS storage:HddMotherBoardTempStats:rightOutletTempAvg
        managed object property"
    ::= { cucsStorageHddMotherBoardTempStatsEntry 19 }

cucsStorageHddMotherBoardTempStatsRightOutletTempMax OBJECT-TYPE
    SYNTAX       SnmpAdminString
    MAX-ACCESS   read-only
    STATUS       current
    DESCRIPTION
        "Cisco UCS storage:HddMotherBoardTempStats:rightOutletTempMax
        managed object property"
    ::= { cucsStorageHddMotherBoardTempStatsEntry 20 }

cucsStorageHddMotherBoardTempStatsRightOutletTempMin OBJECT-TYPE
    SYNTAX       SnmpAdminString
    MAX-ACCESS   read-only
    STATUS       current
    DESCRIPTION
        "Cisco UCS storage:HddMotherBoardTempStats:rightOutletTempMin
        managed object property"
    ::= { cucsStorageHddMotherBoardTempStatsEntry 21 }

cucsStorageHddMotherBoardTempStatsSuspect OBJECT-TYPE
    SYNTAX       TruthValue
    MAX-ACCESS   read-only
    STATUS       current
    DESCRIPTION
        "Cisco UCS storage:HddMotherBoardTempStats:suspect
        managed object property"
    ::= { cucsStorageHddMotherBoardTempStatsEntry 23 }

cucsStorageHddMotherBoardTempStatsThresholded OBJECT-TYPE
    SYNTAX       CucsStorageHddMotherBoardTempStatsThresholded
    MAX-ACCESS   read-only
    STATUS       current
    DESCRIPTION
        "Cisco UCS storage:HddMotherBoardTempStats:thresholded
        managed object property"
    ::= { cucsStorageHddMotherBoardTempStatsEntry 24 }

cucsStorageHddMotherBoardTempStatsTimeCollected OBJECT-TYPE
    SYNTAX       DateAndTime
    MAX-ACCESS   read-only
    STATUS       current
    DESCRIPTION
        "Cisco UCS storage:HddMotherBoardTempStats:timeCollected
        managed object property"
    ::= { cucsStorageHddMotherBoardTempStatsEntry 25 }

cucsStorageHddMotherBoardTempStatsUpdate OBJECT-TYPE
    SYNTAX       Gauge32
    MAX-ACCESS   read-only
    STATUS       current
    DESCRIPTION
        "Cisco UCS storage:HddMotherBoardTempStats:update
        managed object property"
    ::= { cucsStorageHddMotherBoardTempStatsEntry 26 }

cucsStorageHddMotherBoardTempStatsHistTable OBJECT-TYPE
    SYNTAX           SEQUENCE OF CucsStorageHddMotherBoardTempStatsHistEntry
    MAX-ACCESS       not-accessible
    STATUS           current
    DESCRIPTION
        "Cisco UCS storage:HddMotherBoardTempStatsHist
        managed object table"
    ::= { cucsStorageObjects 113 }

cucsStorageHddMotherBoardTempStatsHistEntry OBJECT-TYPE
    SYNTAX           CucsStorageHddMotherBoardTempStatsHistEntry
    MAX-ACCESS       not-accessible
    STATUS           current
    DESCRIPTION
        "Entry for the cucsStorageHddMotherBoardTempStatsHistTable table."
    INDEX { cucsStorageHddMotherBoardTempStatsHistInstanceId }
    ::= { cucsStorageHddMotherBoardTempStatsHistTable 1 }

CucsStorageHddMotherBoardTempStatsHistEntry ::= SEQUENCE {
    cucsStorageHddMotherBoardTempStatsHistInstanceId                 CucsManagedObjectId,
    cucsStorageHddMotherBoardTempStatsHistDn                         CucsManagedObjectDn,
    cucsStorageHddMotherBoardTempStatsHistRn                         SnmpAdminString,
    cucsStorageHddMotherBoardTempStatsHistId                         Unsigned64,
    cucsStorageHddMotherBoardTempStatsHistLeftInletTemp              SnmpAdminString,
    cucsStorageHddMotherBoardTempStatsHistLeftInletTempAvg           SnmpAdminString,
    cucsStorageHddMotherBoardTempStatsHistLeftInletTempMax           SnmpAdminString,
    cucsStorageHddMotherBoardTempStatsHistLeftInletTempMin           SnmpAdminString,
    cucsStorageHddMotherBoardTempStatsHistLeftOutletTemp             SnmpAdminString,
    cucsStorageHddMotherBoardTempStatsHistLeftOutletTempAvg          SnmpAdminString,
    cucsStorageHddMotherBoardTempStatsHistLeftOutletTempMax          SnmpAdminString,
    cucsStorageHddMotherBoardTempStatsHistLeftOutletTempMin          SnmpAdminString,
    cucsStorageHddMotherBoardTempStatsHistMostRecent                 TruthValue,
    cucsStorageHddMotherBoardTempStatsHistRightInletTemp             SnmpAdminString,
    cucsStorageHddMotherBoardTempStatsHistRightInletTempAvg          SnmpAdminString,
    cucsStorageHddMotherBoardTempStatsHistRightInletTempMax          SnmpAdminString,
    cucsStorageHddMotherBoardTempStatsHistRightInletTempMin          SnmpAdminString,
    cucsStorageHddMotherBoardTempStatsHistRightOutletTemp            SnmpAdminString,
    cucsStorageHddMotherBoardTempStatsHistRightOutletTempAvg         SnmpAdminString,
    cucsStorageHddMotherBoardTempStatsHistRightOutletTempMax         SnmpAdminString,
    cucsStorageHddMotherBoardTempStatsHistRightOutletTempMin         SnmpAdminString,
    cucsStorageHddMotherBoardTempStatsHistSuspect                    TruthValue,
    cucsStorageHddMotherBoardTempStatsHistThresholded                CucsStorageHddMotherBoardTempStatsHistThresholded,
    cucsStorageHddMotherBoardTempStatsHistTimeCollected              DateAndTime
}

cucsStorageHddMotherBoardTempStatsHistInstanceId OBJECT-TYPE
    SYNTAX       CucsManagedObjectId
    MAX-ACCESS   not-accessible
    STATUS       current
    DESCRIPTION
        "Instance identifier of the managed object."
    ::= { cucsStorageHddMotherBoardTempStatsHistEntry 1 }

cucsStorageHddMotherBoardTempStatsHistDn OBJECT-TYPE
    SYNTAX       CucsManagedObjectDn
    MAX-ACCESS   read-only
    STATUS       current
    DESCRIPTION
        "Cisco UCS storage:HddMotherBoardTempStatsHist:dn
        managed object property"
    ::= { cucsStorageHddMotherBoardTempStatsHistEntry 2 }

cucsStorageHddMotherBoardTempStatsHistRn OBJECT-TYPE
    SYNTAX       SnmpAdminString
    MAX-ACCESS   read-only
    STATUS       current
    DESCRIPTION
        "Cisco UCS storage:HddMotherBoardTempStatsHist:rn
        managed object property"
    ::= { cucsStorageHddMotherBoardTempStatsHistEntry 3 }

cucsStorageHddMotherBoardTempStatsHistId OBJECT-TYPE
    SYNTAX       Unsigned64
    MAX-ACCESS   read-only
    STATUS       current
    DESCRIPTION
        "Cisco UCS storage:HddMotherBoardTempStatsHist:id
        managed object property"
    ::= { cucsStorageHddMotherBoardTempStatsHistEntry 4 }

cucsStorageHddMotherBoardTempStatsHistLeftInletTemp OBJECT-TYPE
    SYNTAX       SnmpAdminString
    MAX-ACCESS   read-only
    STATUS       current
    DESCRIPTION
        "Cisco UCS storage:HddMotherBoardTempStatsHist:leftInletTemp
        managed object property"
    ::= { cucsStorageHddMotherBoardTempStatsHistEntry 5 }

cucsStorageHddMotherBoardTempStatsHistLeftInletTempAvg OBJECT-TYPE
    SYNTAX       SnmpAdminString
    MAX-ACCESS   read-only
    STATUS       current
    DESCRIPTION
        "Cisco UCS storage:HddMotherBoardTempStatsHist:leftInletTempAvg
        managed object property"
    ::= { cucsStorageHddMotherBoardTempStatsHistEntry 6 }

cucsStorageHddMotherBoardTempStatsHistLeftInletTempMax OBJECT-TYPE
    SYNTAX       SnmpAdminString
    MAX-ACCESS   read-only
    STATUS       current
    DESCRIPTION
        "Cisco UCS storage:HddMotherBoardTempStatsHist:leftInletTempMax
        managed object property"
    ::= { cucsStorageHddMotherBoardTempStatsHistEntry 7 }

cucsStorageHddMotherBoardTempStatsHistLeftInletTempMin OBJECT-TYPE
    SYNTAX       SnmpAdminString
    MAX-ACCESS   read-only
    STATUS       current
    DESCRIPTION
        "Cisco UCS storage:HddMotherBoardTempStatsHist:leftInletTempMin
        managed object property"
    ::= { cucsStorageHddMotherBoardTempStatsHistEntry 8 }

cucsStorageHddMotherBoardTempStatsHistLeftOutletTemp OBJECT-TYPE
    SYNTAX       SnmpAdminString
    MAX-ACCESS   read-only
    STATUS       current
    DESCRIPTION
        "Cisco UCS storage:HddMotherBoardTempStatsHist:leftOutletTemp
        managed object property"
    ::= { cucsStorageHddMotherBoardTempStatsHistEntry 9 }

cucsStorageHddMotherBoardTempStatsHistLeftOutletTempAvg OBJECT-TYPE
    SYNTAX       SnmpAdminString
    MAX-ACCESS   read-only
    STATUS       current
    DESCRIPTION
        "Cisco UCS storage:HddMotherBoardTempStatsHist:leftOutletTempAvg
        managed object property"
    ::= { cucsStorageHddMotherBoardTempStatsHistEntry 10 }

cucsStorageHddMotherBoardTempStatsHistLeftOutletTempMax OBJECT-TYPE
    SYNTAX       SnmpAdminString
    MAX-ACCESS   read-only
    STATUS       current
    DESCRIPTION
        "Cisco UCS storage:HddMotherBoardTempStatsHist:leftOutletTempMax
        managed object property"
    ::= { cucsStorageHddMotherBoardTempStatsHistEntry 11 }

cucsStorageHddMotherBoardTempStatsHistLeftOutletTempMin OBJECT-TYPE
    SYNTAX       SnmpAdminString
    MAX-ACCESS   read-only
    STATUS       current
    DESCRIPTION
        "Cisco UCS storage:HddMotherBoardTempStatsHist:leftOutletTempMin
        managed object property"
    ::= { cucsStorageHddMotherBoardTempStatsHistEntry 12 }

cucsStorageHddMotherBoardTempStatsHistMostRecent OBJECT-TYPE
    SYNTAX       TruthValue
    MAX-ACCESS   read-only
    STATUS       current
    DESCRIPTION
        "Cisco UCS storage:HddMotherBoardTempStatsHist:mostRecent
        managed object property"
    ::= { cucsStorageHddMotherBoardTempStatsHistEntry 13 }

cucsStorageHddMotherBoardTempStatsHistRightInletTemp OBJECT-TYPE
    SYNTAX       SnmpAdminString
    MAX-ACCESS   read-only
    STATUS       current
    DESCRIPTION
        "Cisco UCS storage:HddMotherBoardTempStatsHist:rightInletTemp
        managed object property"
    ::= { cucsStorageHddMotherBoardTempStatsHistEntry 14 }

cucsStorageHddMotherBoardTempStatsHistRightInletTempAvg OBJECT-TYPE
    SYNTAX       SnmpAdminString
    MAX-ACCESS   read-only
    STATUS       current
    DESCRIPTION
        "Cisco UCS storage:HddMotherBoardTempStatsHist:rightInletTempAvg
        managed object property"
    ::= { cucsStorageHddMotherBoardTempStatsHistEntry 15 }

cucsStorageHddMotherBoardTempStatsHistRightInletTempMax OBJECT-TYPE
    SYNTAX       SnmpAdminString
    MAX-ACCESS   read-only
    STATUS       current
    DESCRIPTION
        "Cisco UCS storage:HddMotherBoardTempStatsHist:rightInletTempMax
        managed object property"
    ::= { cucsStorageHddMotherBoardTempStatsHistEntry 16 }

cucsStorageHddMotherBoardTempStatsHistRightInletTempMin OBJECT-TYPE
    SYNTAX       SnmpAdminString
    MAX-ACCESS   read-only
    STATUS       current
    DESCRIPTION
        "Cisco UCS storage:HddMotherBoardTempStatsHist:rightInletTempMin
        managed object property"
    ::= { cucsStorageHddMotherBoardTempStatsHistEntry 17 }

cucsStorageHddMotherBoardTempStatsHistRightOutletTemp OBJECT-TYPE
    SYNTAX       SnmpAdminString
    MAX-ACCESS   read-only
    STATUS       current
    DESCRIPTION
        "Cisco UCS storage:HddMotherBoardTempStatsHist:rightOutletTemp
        managed object property"
    ::= { cucsStorageHddMotherBoardTempStatsHistEntry 18 }

cucsStorageHddMotherBoardTempStatsHistRightOutletTempAvg OBJECT-TYPE
    SYNTAX       SnmpAdminString
    MAX-ACCESS   read-only
    STATUS       current
    DESCRIPTION
        "Cisco UCS storage:HddMotherBoardTempStatsHist:rightOutletTempAvg
        managed object property"
    ::= { cucsStorageHddMotherBoardTempStatsHistEntry 19 }

cucsStorageHddMotherBoardTempStatsHistRightOutletTempMax OBJECT-TYPE
    SYNTAX       SnmpAdminString
    MAX-ACCESS   read-only
    STATUS       current
    DESCRIPTION
        "Cisco UCS storage:HddMotherBoardTempStatsHist:rightOutletTempMax
        managed object property"
    ::= { cucsStorageHddMotherBoardTempStatsHistEntry 20 }

cucsStorageHddMotherBoardTempStatsHistRightOutletTempMin OBJECT-TYPE
    SYNTAX       SnmpAdminString
    MAX-ACCESS   read-only
    STATUS       current
    DESCRIPTION
        "Cisco UCS storage:HddMotherBoardTempStatsHist:rightOutletTempMin
        managed object property"
    ::= { cucsStorageHddMotherBoardTempStatsHistEntry 21 }

cucsStorageHddMotherBoardTempStatsHistSuspect OBJECT-TYPE
    SYNTAX       TruthValue
    MAX-ACCESS   read-only
    STATUS       current
    DESCRIPTION
        "Cisco UCS storage:HddMotherBoardTempStatsHist:suspect
        managed object property"
    ::= { cucsStorageHddMotherBoardTempStatsHistEntry 22 }

cucsStorageHddMotherBoardTempStatsHistThresholded OBJECT-TYPE
    SYNTAX       CucsStorageHddMotherBoardTempStatsHistThresholded
    MAX-ACCESS   read-only
    STATUS       current
    DESCRIPTION
        "Cisco UCS storage:HddMotherBoardTempStatsHist:thresholded
        managed object property"
    ::= { cucsStorageHddMotherBoardTempStatsHistEntry 23 }

cucsStorageHddMotherBoardTempStatsHistTimeCollected OBJECT-TYPE
    SYNTAX       DateAndTime
    MAX-ACCESS   read-only
    STATUS       current
    DESCRIPTION
        "Cisco UCS storage:HddMotherBoardTempStatsHist:timeCollected
        managed object property"
    ::= { cucsStorageHddMotherBoardTempStatsHistEntry 24 }

cucsStorageIScsiTargetIfTable OBJECT-TYPE
    SYNTAX           SEQUENCE OF CucsStorageIScsiTargetIfEntry
    MAX-ACCESS       not-accessible
    STATUS           current
    DESCRIPTION
        "Cisco UCS storage:IScsiTargetIf managed object table"
    ::= { cucsStorageObjects 23 }

cucsStorageIScsiTargetIfEntry OBJECT-TYPE
    SYNTAX           CucsStorageIScsiTargetIfEntry
    MAX-ACCESS       not-accessible
    STATUS           current
    DESCRIPTION
        "Entry for the cucsStorageIScsiTargetIfTable table."
    INDEX { cucsStorageIScsiTargetIfInstanceId }
    ::= { cucsStorageIScsiTargetIfTable 1 }

CucsStorageIScsiTargetIfEntry ::= SEQUENCE {
    cucsStorageIScsiTargetIfInstanceId                               CucsManagedObjectId,
    cucsStorageIScsiTargetIfDn                                       CucsManagedObjectDn,
    cucsStorageIScsiTargetIfRn                                       SnmpAdminString,
    cucsStorageIScsiTargetIfName                                     SnmpAdminString,
    cucsStorageIScsiTargetIfProt                                     CucsStorageProtocol
}

cucsStorageIScsiTargetIfInstanceId OBJECT-TYPE
    SYNTAX       CucsManagedObjectId
    MAX-ACCESS   not-accessible
    STATUS       current
    DESCRIPTION
        "Instance identifier of the managed object."
    ::= { cucsStorageIScsiTargetIfEntry 1 }

cucsStorageIScsiTargetIfDn OBJECT-TYPE
    SYNTAX       CucsManagedObjectDn
    MAX-ACCESS   read-only
    STATUS       current
    DESCRIPTION
        "Cisco UCS storage:IScsiTargetIf:dn managed object property"
    ::= { cucsStorageIScsiTargetIfEntry 2 }

cucsStorageIScsiTargetIfRn OBJECT-TYPE
    SYNTAX       SnmpAdminString
    MAX-ACCESS   read-only
    STATUS       current
    DESCRIPTION
        "Cisco UCS storage:IScsiTargetIf:rn managed object property"
    ::= { cucsStorageIScsiTargetIfEntry 3 }

cucsStorageIScsiTargetIfName OBJECT-TYPE
    SYNTAX       SnmpAdminString
    MAX-ACCESS   read-only
    STATUS       current
    DESCRIPTION
        "Cisco UCS storage:IScsiTargetIf:name managed object property"
    ::= { cucsStorageIScsiTargetIfEntry 4 }

cucsStorageIScsiTargetIfProt OBJECT-TYPE
    SYNTAX       CucsStorageProtocol
    MAX-ACCESS   read-only
    STATUS       current
    DESCRIPTION
        "Cisco UCS storage:IScsiTargetIf:prot managed object property"
    ::= { cucsStorageIScsiTargetIfEntry 5 }

cucsStorageIniGroupTable OBJECT-TYPE
    SYNTAX           SEQUENCE OF CucsStorageIniGroupEntry
    MAX-ACCESS       not-accessible
    STATUS           current
    DESCRIPTION
        "Cisco UCS storage:IniGroup managed object table"
    ::= { cucsStorageObjects 24 }

cucsStorageIniGroupEntry OBJECT-TYPE
    SYNTAX           CucsStorageIniGroupEntry
    MAX-ACCESS       not-accessible
    STATUS           current
    DESCRIPTION
        "Entry for the cucsStorageIniGroupTable table."
    INDEX { cucsStorageIniGroupInstanceId }
    ::= { cucsStorageIniGroupTable 1 }

CucsStorageIniGroupEntry ::= SEQUENCE {
    cucsStorageIniGroupInstanceId                                    CucsManagedObjectId,
    cucsStorageIniGroupDn                                            CucsManagedObjectDn,
    cucsStorageIniGroupRn                                            SnmpAdminString,
    cucsStorageIniGroupDescr                                         SnmpAdminString,
    cucsStorageIniGroupGroupPolicyName                               SnmpAdminString,
    cucsStorageIniGroupIntId                                         SnmpAdminString,
    cucsStorageIniGroupName                                          SnmpAdminString,
    cucsStorageIniGroupOperProtocol                                  CucsStorageIniGroupOperProtocol,
    cucsStorageIniGroupOwner                                         CucsStorageIniGroupOwner,
    cucsStorageIniGroupPolicyLevel                                   Gauge32,
    cucsStorageIniGroupPolicyName                                    SnmpAdminString,
    cucsStorageIniGroupPolicyOwner                                   CucsPolicyPolicyOwner,
    cucsStorageIniGroupProtocol                                      CucsStorageIniGroupProtocol,
    cucsStorageIniGroupRmtDiskCfgName                                SnmpAdminString,
    cucsStorageIniGroupOperState                                     CucsStorageOperState
}

cucsStorageIniGroupInstanceId OBJECT-TYPE
    SYNTAX       CucsManagedObjectId
    MAX-ACCESS   not-accessible
    STATUS       current
    DESCRIPTION
        "Instance identifier of the managed object."
    ::= { cucsStorageIniGroupEntry 1 }

cucsStorageIniGroupDn OBJECT-TYPE
    SYNTAX       CucsManagedObjectDn
    MAX-ACCESS   read-only
    STATUS       current
    DESCRIPTION
        "Cisco UCS storage:IniGroup:dn managed object property"
    ::= { cucsStorageIniGroupEntry 2 }

cucsStorageIniGroupRn OBJECT-TYPE
    SYNTAX       SnmpAdminString
    MAX-ACCESS   read-only
    STATUS       current
    DESCRIPTION
        "Cisco UCS storage:IniGroup:rn managed object property"
    ::= { cucsStorageIniGroupEntry 3 }

cucsStorageIniGroupDescr OBJECT-TYPE
    SYNTAX       SnmpAdminString
    MAX-ACCESS   read-only
    STATUS       current
    DESCRIPTION
        "Cisco UCS storage:IniGroup:descr managed object property"
    ::= { cucsStorageIniGroupEntry 4 }

cucsStorageIniGroupGroupPolicyName OBJECT-TYPE
    SYNTAX       SnmpAdminString
    MAX-ACCESS   read-only
    STATUS       current
    DESCRIPTION
        "Cisco UCS storage:IniGroup:groupPolicyName managed
        object property"
    ::= { cucsStorageIniGroupEntry 5 }

cucsStorageIniGroupIntId OBJECT-TYPE
    SYNTAX       SnmpAdminString
    MAX-ACCESS   read-only
    STATUS       current
    DESCRIPTION
        "Cisco UCS storage:IniGroup:intId managed object property"
    ::= { cucsStorageIniGroupEntry 6 }

cucsStorageIniGroupName OBJECT-TYPE
    SYNTAX       SnmpAdminString
    MAX-ACCESS   read-only
    STATUS       current
    DESCRIPTION
        "Cisco UCS storage:IniGroup:name managed object property"
    ::= { cucsStorageIniGroupEntry 7 }

cucsStorageIniGroupOperProtocol OBJECT-TYPE
    SYNTAX       CucsStorageIniGroupOperProtocol
    MAX-ACCESS   read-only
    STATUS       current
    DESCRIPTION
        "Cisco UCS storage:IniGroup:operProtocol managed object property"
    ::= { cucsStorageIniGroupEntry 8 }

cucsStorageIniGroupOwner OBJECT-TYPE
    SYNTAX       CucsStorageIniGroupOwner
    MAX-ACCESS   read-only
    STATUS       current
    DESCRIPTION
        "Cisco UCS storage:IniGroup:owner managed object property"
    ::= { cucsStorageIniGroupEntry 9 }

cucsStorageIniGroupPolicyLevel OBJECT-TYPE
    SYNTAX       Gauge32
    MAX-ACCESS   read-only
    STATUS       current
    DESCRIPTION
        "Cisco UCS storage:IniGroup:policyLevel managed object property"
    ::= { cucsStorageIniGroupEntry 10 }

cucsStorageIniGroupPolicyName OBJECT-TYPE
    SYNTAX       SnmpAdminString
    MAX-ACCESS   read-only
    STATUS       current
    DESCRIPTION
        "Cisco UCS storage:IniGroup:policyName managed object property"
    ::= { cucsStorageIniGroupEntry 11 }

cucsStorageIniGroupPolicyOwner OBJECT-TYPE
    SYNTAX       CucsPolicyPolicyOwner
    MAX-ACCESS   read-only
    STATUS       current
    DESCRIPTION
        "Cisco UCS storage:IniGroup:policyOwner managed object property"
    ::= { cucsStorageIniGroupEntry 12 }

cucsStorageIniGroupProtocol OBJECT-TYPE
    SYNTAX       CucsStorageIniGroupProtocol
    MAX-ACCESS   read-only
    STATUS       current
    DESCRIPTION
        "Cisco UCS storage:IniGroup:protocol managed object property"
    ::= { cucsStorageIniGroupEntry 13 }

cucsStorageIniGroupRmtDiskCfgName OBJECT-TYPE
    SYNTAX       SnmpAdminString
    MAX-ACCESS   read-only
    STATUS       current
    DESCRIPTION
        "Cisco UCS storage:IniGroup:rmtDiskCfgName managed
        object property"
    ::= { cucsStorageIniGroupEntry 14 }

cucsStorageIniGroupOperState OBJECT-TYPE
    SYNTAX       CucsStorageOperState
    MAX-ACCESS   read-only
    STATUS       current
    DESCRIPTION
        "Cisco UCS storage:IniGroup:operState managed object property"
    ::= { cucsStorageIniGroupEntry 15 }

cucsStorageInitiatorTable OBJECT-TYPE
    SYNTAX           SEQUENCE OF CucsStorageInitiatorEntry
    MAX-ACCESS       not-accessible
    STATUS           current
    DESCRIPTION
        "Cisco UCS storage:Initiator managed object table"
    ::= { cucsStorageObjects 25 }

cucsStorageInitiatorEntry OBJECT-TYPE
    SYNTAX           CucsStorageInitiatorEntry
    MAX-ACCESS       not-accessible
    STATUS           current
    DESCRIPTION
        "Entry for the cucsStorageInitiatorTable table."
    INDEX { cucsStorageInitiatorInstanceId }
    ::= { cucsStorageInitiatorTable 1 }

CucsStorageInitiatorEntry ::= SEQUENCE {
    cucsStorageInitiatorInstanceId                                   CucsManagedObjectId,
    cucsStorageInitiatorDn                                           CucsManagedObjectDn,
    cucsStorageInitiatorRn                                           SnmpAdminString,
    cucsStorageInitiatorDescr                                        SnmpAdminString,
    cucsStorageInitiatorIntId                                        SnmpAdminString,
    cucsStorageInitiatorName                                         SnmpAdminString,
    cucsStorageInitiatorOperState                                    CucsStorageOperState,
    cucsStorageInitiatorPolicyLevel                                  Gauge32,
    cucsStorageInitiatorPolicyOwner                                  CucsPolicyPolicyOwner,
    cucsStorageInitiatorDuplicateTarget                              SnmpAdminString
}

cucsStorageInitiatorInstanceId OBJECT-TYPE
    SYNTAX       CucsManagedObjectId
    MAX-ACCESS   not-accessible
    STATUS       current
    DESCRIPTION
        "Instance identifier of the managed object."
    ::= { cucsStorageInitiatorEntry 1 }

cucsStorageInitiatorDn OBJECT-TYPE
    SYNTAX       CucsManagedObjectDn
    MAX-ACCESS   read-only
    STATUS       current
    DESCRIPTION
        "Cisco UCS storage:Initiator:dn managed object property"
    ::= { cucsStorageInitiatorEntry 2 }

cucsStorageInitiatorRn OBJECT-TYPE
    SYNTAX       SnmpAdminString
    MAX-ACCESS   read-only
    STATUS       current
    DESCRIPTION
        "Cisco UCS storage:Initiator:rn managed object property"
    ::= { cucsStorageInitiatorEntry 3 }

cucsStorageInitiatorDescr OBJECT-TYPE
    SYNTAX       SnmpAdminString
    MAX-ACCESS   read-only
    STATUS       current
    DESCRIPTION
        "Cisco UCS storage:Initiator:descr managed object property"
    ::= { cucsStorageInitiatorEntry 4 }

cucsStorageInitiatorIntId OBJECT-TYPE
    SYNTAX       SnmpAdminString
    MAX-ACCESS   read-only
    STATUS       current
    DESCRIPTION
        "Cisco UCS storage:Initiator:intId managed object property"
    ::= { cucsStorageInitiatorEntry 5 }

cucsStorageInitiatorName OBJECT-TYPE
    SYNTAX       SnmpAdminString
    MAX-ACCESS   read-only
    STATUS       current
    DESCRIPTION
        "Cisco UCS storage:Initiator:name managed object property"
    ::= { cucsStorageInitiatorEntry 6 }

cucsStorageInitiatorOperState OBJECT-TYPE
    SYNTAX       CucsStorageOperState
    MAX-ACCESS   read-only
    STATUS       current
    DESCRIPTION
        "Cisco UCS storage:Initiator:operState managed object property"
    ::= { cucsStorageInitiatorEntry 7 }

cucsStorageInitiatorPolicyLevel OBJECT-TYPE
    SYNTAX       Gauge32
    MAX-ACCESS   read-only
    STATUS       current
    DESCRIPTION
        "Cisco UCS storage:Initiator:policyLevel managed object property"
    ::= { cucsStorageInitiatorEntry 8 }

cucsStorageInitiatorPolicyOwner OBJECT-TYPE
    SYNTAX       CucsPolicyPolicyOwner
    MAX-ACCESS   read-only
    STATUS       current
    DESCRIPTION
        "Cisco UCS storage:Initiator:policyOwner managed object property"
    ::= { cucsStorageInitiatorEntry 9 }

cucsStorageInitiatorDuplicateTarget OBJECT-TYPE
    SYNTAX       SnmpAdminString
    MAX-ACCESS   read-only
    STATUS       current
    DESCRIPTION
        "Cisco UCS storage:Initiator:duplicateTarget managed
        object property"
    ::= { cucsStorageInitiatorEntry 10 }

cucsStorageItemTable OBJECT-TYPE
    SYNTAX           SEQUENCE OF CucsStorageItemEntry
    MAX-ACCESS       not-accessible
    STATUS           current
    DESCRIPTION
        "Cisco UCS storage:Item managed object table"
    ::= { cucsStorageObjects 3 }

cucsStorageItemEntry OBJECT-TYPE
    SYNTAX           CucsStorageItemEntry
    MAX-ACCESS       not-accessible
    STATUS           current
    DESCRIPTION
        "Entry for the cucsStorageItemTable table."
    INDEX { cucsStorageItemInstanceId }
    ::= { cucsStorageItemTable 1 }

CucsStorageItemEntry ::= SEQUENCE {
    cucsStorageItemInstanceId                                        CucsManagedObjectId,
    cucsStorageItemDn                                                CucsManagedObjectDn,
    cucsStorageItemRn                                                SnmpAdminString,
    cucsStorageItemName                                              SnmpAdminString,
    cucsStorageItemSize                                              Unsigned64,
    cucsStorageItemUsed                                              Gauge32,
    cucsStorageItemOperState                                         CucsStorageFileSystemStatus,
    cucsStorageItemAlarmType                                         CucsStorageAlarmType
}

cucsStorageItemInstanceId OBJECT-TYPE
    SYNTAX       CucsManagedObjectId
    MAX-ACCESS   not-accessible
    STATUS       current
    DESCRIPTION
        "Instance identifier of the managed object."
    ::= { cucsStorageItemEntry 1 }

cucsStorageItemDn OBJECT-TYPE
    SYNTAX       CucsManagedObjectDn
    MAX-ACCESS   read-only
    STATUS       current
    DESCRIPTION
        "Cisco UCS storage:Item:dn managed object property"
    ::= { cucsStorageItemEntry 2 }

cucsStorageItemRn OBJECT-TYPE
    SYNTAX       SnmpAdminString
    MAX-ACCESS   read-only
    STATUS       current
    DESCRIPTION
        "Cisco UCS storage:Item:rn managed object property"
    ::= { cucsStorageItemEntry 3 }

cucsStorageItemName OBJECT-TYPE
    SYNTAX       SnmpAdminString
    MAX-ACCESS   read-only
    STATUS       current
    DESCRIPTION
        "Cisco UCS storage:Item:name managed object property"
    ::= { cucsStorageItemEntry 4 }

cucsStorageItemSize OBJECT-TYPE
    SYNTAX       Unsigned64
    MAX-ACCESS   read-only
    STATUS       current
    DESCRIPTION
        "Cisco UCS storage:Item:size managed object property"
    ::= { cucsStorageItemEntry 5 }

cucsStorageItemUsed OBJECT-TYPE
    SYNTAX       Gauge32
    MAX-ACCESS   read-only
    STATUS       current
    DESCRIPTION
        "Cisco UCS storage:Item:used managed object property"
    ::= { cucsStorageItemEntry 6 }

cucsStorageItemOperState OBJECT-TYPE
    SYNTAX       CucsStorageFileSystemStatus
    MAX-ACCESS   read-only
    STATUS       current
    DESCRIPTION
        "Cisco UCS storage:Item:operState managed object property"
    ::= { cucsStorageItemEntry 7 }

cucsStorageItemAlarmType OBJECT-TYPE
    SYNTAX       CucsStorageAlarmType
    MAX-ACCESS   read-only
    STATUS       current
    DESCRIPTION
        "Cisco UCS storage:Item:alarmType managed object property"
    ::= { cucsStorageItemEntry 13 }

cucsStorageLocalDiskTable OBJECT-TYPE
    SYNTAX           SEQUENCE OF CucsStorageLocalDiskEntry
    MAX-ACCESS       not-accessible
    STATUS           current
    DESCRIPTION
        "Cisco UCS storage:LocalDisk managed object table"
    ::= { cucsStorageObjects 4 }

cucsStorageLocalDiskEntry OBJECT-TYPE
    SYNTAX           CucsStorageLocalDiskEntry
    MAX-ACCESS       not-accessible
    STATUS           current
    DESCRIPTION
        "Entry for the cucsStorageLocalDiskTable table."
    INDEX { cucsStorageLocalDiskInstanceId }
    ::= { cucsStorageLocalDiskTable 1 }

CucsStorageLocalDiskEntry ::= SEQUENCE {
    cucsStorageLocalDiskInstanceId                                   CucsManagedObjectId,
    cucsStorageLocalDiskDn                                           CucsManagedObjectDn,
    cucsStorageLocalDiskRn                                           SnmpAdminString,
    cucsStorageLocalDiskBlockSize                                    Gauge32,
    cucsStorageLocalDiskConnectionProtocol                           CucsStorageConnectionProtocol,
    cucsStorageLocalDiskId                                           Gauge32,
    cucsStorageLocalDiskModel                                        SnmpAdminString,
    cucsStorageLocalDiskNumberOfBlocks                               Unsigned64,
    cucsStorageLocalDiskOperability                                  CucsEquipmentOperability,
    cucsStorageLocalDiskPresence                                     CucsEquipmentPresence,
    cucsStorageLocalDiskRevision                                     SnmpAdminString,
    cucsStorageLocalDiskSerial                                       SnmpAdminString,
    cucsStorageLocalDiskSize                                         Unsigned64,
    cucsStorageLocalDiskVendor                                       SnmpAdminString,
    cucsStorageLocalDiskLc                                           CucsFsmLifecycle,
    cucsStorageLocalDiskOperQualifierReason                          SnmpAdminString,
    cucsStorageLocalDiskDeviceType                                   CucsStorageTechnology,
    cucsStorageLocalDiskDiskState                                    CucsStoragePDriveStatus,
    cucsStorageLocalDiskLinkSpeed                                    CucsStorageLinkSpeed,
    cucsStorageLocalDiskPowerState                                   CucsStoragePowerState,
    cucsStorageLocalDiskAdminAction                                  CucsStorageAdminActionType,
    cucsStorageLocalDiskAdminActionTrigger                           CucsStorageAdminActionTrigger,
    cucsStorageLocalDiskBootable                                     CucsStorageBootableType,
    cucsStorageLocalDiskConfigState                                  CucsStorageConfigState,
    cucsStorageLocalDiskThermal                                      CucsEquipmentSensorThresholdStatus,
    cucsStorageLocalDiskAdminVirtualDriveId                          Gauge32,
    cucsStorageLocalDiskConfigCheckPoint                             CucsStorageConfigCheckPoint,
    cucsStorageLocalDiskLinkState                                    CucsStorageEpLinkState,
    cucsStorageLocalDiskLinkStateReason                              SnmpAdminString,
    cucsStorageLocalDiskDiscoveredPath                               CucsStorageLocalDiskDiscoveredPath,
    cucsStorageLocalDiskEncAssociation                               CucsStorageEnclosureAssociation,
    cucsStorageLocalDiskPhysicalBlockSize                            Gauge32,
    cucsStorageLocalDiskRawSize                                      Unsigned64,
    cucsStorageLocalDiskDeviceVersion                                SnmpAdminString,
    cucsStorageLocalDiskFsmDescr                                     SnmpAdminString,
    cucsStorageLocalDiskFsmFlags                                     SnmpAdminString,
    cucsStorageLocalDiskFsmPrev                                      SnmpAdminString,
    cucsStorageLocalDiskFsmProgr                                     Gauge32,
    cucsStorageLocalDiskFsmRmtInvErrCode                             Gauge32,
    cucsStorageLocalDiskFsmRmtInvErrDescr                            SnmpAdminString,
    cucsStorageLocalDiskFsmRmtInvRslt                                CucsConditionRemoteInvRslt,
    cucsStorageLocalDiskFsmStageDescr                                SnmpAdminString,
    cucsStorageLocalDiskFsmStamp                                     DateAndTime,
    cucsStorageLocalDiskFsmStatus                                    SnmpAdminString,
    cucsStorageLocalDiskFsmTry                                       Gauge32,
    cucsStorageLocalDiskVariantType                                  SnmpAdminString,
    cucsStorageLocalDiskAdminSecurityKey                             SnmpAdminString,
    cucsStorageLocalDiskDriveState                                   CucsStorageDriveFlags,
    cucsStorageLocalDiskErrDescription                               SnmpAdminString
}

cucsStorageLocalDiskInstanceId OBJECT-TYPE
    SYNTAX       CucsManagedObjectId
    MAX-ACCESS   not-accessible
    STATUS       current
    DESCRIPTION
        "Instance identifier of the managed object."
    ::= { cucsStorageLocalDiskEntry 1 }

cucsStorageLocalDiskDn OBJECT-TYPE
    SYNTAX       CucsManagedObjectDn
    MAX-ACCESS   read-only
    STATUS       current
    DESCRIPTION
        "Cisco UCS storage:LocalDisk:dn managed object property"
    ::= { cucsStorageLocalDiskEntry 2 }

cucsStorageLocalDiskRn OBJECT-TYPE
    SYNTAX       SnmpAdminString
    MAX-ACCESS   read-only
    STATUS       current
    DESCRIPTION
        "Cisco UCS storage:LocalDisk:rn managed object property"
    ::= { cucsStorageLocalDiskEntry 3 }

cucsStorageLocalDiskBlockSize OBJECT-TYPE
    SYNTAX       Gauge32
    MAX-ACCESS   read-only
    STATUS       current
    DESCRIPTION
        "Cisco UCS storage:LocalDisk:blockSize managed object property"
    ::= { cucsStorageLocalDiskEntry 4 }

cucsStorageLocalDiskConnectionProtocol OBJECT-TYPE
    SYNTAX       CucsStorageConnectionProtocol
    MAX-ACCESS   read-only
    STATUS       current
    DESCRIPTION
        "Cisco UCS storage:LocalDisk:connectionProtocol
        managed object property"
    ::= { cucsStorageLocalDiskEntry 5 }

cucsStorageLocalDiskId OBJECT-TYPE
    SYNTAX       Gauge32
    MAX-ACCESS   read-only
    STATUS       current
    DESCRIPTION
        "Cisco UCS storage:LocalDisk:id managed object property"
    ::= { cucsStorageLocalDiskEntry 6 }

cucsStorageLocalDiskModel OBJECT-TYPE
    SYNTAX       SnmpAdminString
    MAX-ACCESS   read-only
    STATUS       current
    DESCRIPTION
        "Cisco UCS storage:LocalDisk:model managed object property"
    ::= { cucsStorageLocalDiskEntry 7 }

cucsStorageLocalDiskNumberOfBlocks OBJECT-TYPE
    SYNTAX       Unsigned64
    MAX-ACCESS   read-only
    STATUS       current
    DESCRIPTION
        "Cisco UCS storage:LocalDisk:numberOfBlocks managed
        object property"
    ::= { cucsStorageLocalDiskEntry 8 }

cucsStorageLocalDiskOperability OBJECT-TYPE
    SYNTAX       CucsEquipmentOperability
    MAX-ACCESS   read-only
    STATUS       current
    DESCRIPTION
        "Cisco UCS storage:LocalDisk:operability managed object property"
    ::= { cucsStorageLocalDiskEntry 9 }

cucsStorageLocalDiskPresence OBJECT-TYPE
    SYNTAX       CucsEquipmentPresence
    MAX-ACCESS   read-only
    STATUS       current
    DESCRIPTION
        "Cisco UCS storage:LocalDisk:presence managed object property"
    ::= { cucsStorageLocalDiskEntry 10 }

cucsStorageLocalDiskRevision OBJECT-TYPE
    SYNTAX       SnmpAdminString
    MAX-ACCESS   read-only
    STATUS       current
    DESCRIPTION
        "Cisco UCS storage:LocalDisk:revision managed object property"
    ::= { cucsStorageLocalDiskEntry 11 }

cucsStorageLocalDiskSerial OBJECT-TYPE
    SYNTAX       SnmpAdminString
    MAX-ACCESS   read-only
    STATUS       current
    DESCRIPTION
        "Cisco UCS storage:LocalDisk:serial managed object property"
    ::= { cucsStorageLocalDiskEntry 12 }

cucsStorageLocalDiskSize OBJECT-TYPE
    SYNTAX       Unsigned64
    MAX-ACCESS   read-only
    STATUS       current
    DESCRIPTION
        "Cisco UCS storage:LocalDisk:size managed object property"
    ::= { cucsStorageLocalDiskEntry 13 }

cucsStorageLocalDiskVendor OBJECT-TYPE
    SYNTAX       SnmpAdminString
    MAX-ACCESS   read-only
    STATUS       current
    DESCRIPTION
        "Cisco UCS storage:LocalDisk:vendor managed object property"
    ::= { cucsStorageLocalDiskEntry 14 }

cucsStorageLocalDiskLc OBJECT-TYPE
    SYNTAX       CucsFsmLifecycle
    MAX-ACCESS   read-only
    STATUS       current
    DESCRIPTION
        "Cisco UCS storage:LocalDisk:lc managed object property"
    ::= { cucsStorageLocalDiskEntry 15 }

cucsStorageLocalDiskOperQualifierReason OBJECT-TYPE
    SYNTAX       SnmpAdminString
    MAX-ACCESS   read-only
    STATUS       current
    DESCRIPTION
        "Cisco UCS storage:LocalDisk:operQualifierReason
        managed object property"
    ::= { cucsStorageLocalDiskEntry 16 }

cucsStorageLocalDiskDeviceType OBJECT-TYPE
    SYNTAX       CucsStorageTechnology
    MAX-ACCESS   read-only
    STATUS       current
    DESCRIPTION
        "Cisco UCS storage:LocalDisk:deviceType managed object property"
    ::= { cucsStorageLocalDiskEntry 17 }

cucsStorageLocalDiskDiskState OBJECT-TYPE
    SYNTAX       CucsStoragePDriveStatus
    MAX-ACCESS   read-only
    STATUS       current
    DESCRIPTION
        "Cisco UCS storage:LocalDisk:diskState managed object property"
    ::= { cucsStorageLocalDiskEntry 18 }

cucsStorageLocalDiskLinkSpeed OBJECT-TYPE
    SYNTAX       CucsStorageLinkSpeed
    MAX-ACCESS   read-only
    STATUS       current
    DESCRIPTION
        "Cisco UCS storage:LocalDisk:linkSpeed managed object property"
    ::= { cucsStorageLocalDiskEntry 19 }

cucsStorageLocalDiskPowerState OBJECT-TYPE
    SYNTAX       CucsStoragePowerState
    MAX-ACCESS   read-only
    STATUS       current
    DESCRIPTION
        "Cisco UCS storage:LocalDisk:powerState managed object property"
    ::= { cucsStorageLocalDiskEntry 20 }

cucsStorageLocalDiskAdminAction OBJECT-TYPE
    SYNTAX       CucsStorageAdminActionType
    MAX-ACCESS   read-only
    STATUS       current
    DESCRIPTION
        "Cisco UCS storage:LocalDisk:adminAction managed object property"
    ::= { cucsStorageLocalDiskEntry 21 }

cucsStorageLocalDiskAdminActionTrigger OBJECT-TYPE
    SYNTAX       CucsStorageAdminActionTrigger
    MAX-ACCESS   read-only
    STATUS       current
    DESCRIPTION
        "Cisco UCS storage:LocalDisk:adminActionTrigger
        managed object property"
    ::= { cucsStorageLocalDiskEntry 22 }

cucsStorageLocalDiskBootable OBJECT-TYPE
    SYNTAX       CucsStorageBootableType
    MAX-ACCESS   read-only
    STATUS       current
    DESCRIPTION
        "Cisco UCS storage:LocalDisk:bootable managed object property"
    ::= { cucsStorageLocalDiskEntry 23 }

cucsStorageLocalDiskConfigState OBJECT-TYPE
    SYNTAX       CucsStorageConfigState
    MAX-ACCESS   read-only
    STATUS       current
    DESCRIPTION
        "Cisco UCS storage:LocalDisk:configState managed object property"
    ::= { cucsStorageLocalDiskEntry 24 }

cucsStorageLocalDiskThermal OBJECT-TYPE
    SYNTAX       CucsEquipmentSensorThresholdStatus
    MAX-ACCESS   read-only
    STATUS       current
    DESCRIPTION
        "Cisco UCS storage:LocalDisk:thermal managed object property"
    ::= { cucsStorageLocalDiskEntry 25 }

cucsStorageLocalDiskAdminVirtualDriveId OBJECT-TYPE
    SYNTAX       Gauge32
    MAX-ACCESS   read-only
    STATUS       current
    DESCRIPTION
        "Cisco UCS storage:LocalDisk:adminVirtualDriveId
        managed object property"
    ::= { cucsStorageLocalDiskEntry 26 }

cucsStorageLocalDiskConfigCheckPoint OBJECT-TYPE
    SYNTAX       CucsStorageConfigCheckPoint
    MAX-ACCESS   read-only
    STATUS       current
    DESCRIPTION
        "Cisco UCS storage:LocalDisk:configCheckPoint managed
        object property"
    ::= { cucsStorageLocalDiskEntry 27 }

cucsStorageLocalDiskLinkState OBJECT-TYPE
    SYNTAX       CucsStorageEpLinkState
    MAX-ACCESS   read-only
    STATUS       current
    DESCRIPTION
        "Cisco UCS storage:LocalDisk:linkState managed object property"
    ::= { cucsStorageLocalDiskEntry 28 }

cucsStorageLocalDiskLinkStateReason OBJECT-TYPE
    SYNTAX       SnmpAdminString
    MAX-ACCESS   read-only
    STATUS       current
    DESCRIPTION
        "Cisco UCS storage:LocalDisk:linkStateReason managed
        object property"
    ::= { cucsStorageLocalDiskEntry 29 }

cucsStorageLocalDiskDiscoveredPath OBJECT-TYPE
    SYNTAX       CucsStorageLocalDiskDiscoveredPath
    MAX-ACCESS   read-only
    STATUS       current
    DESCRIPTION
        "Cisco UCS storage:LocalDisk:discoveredPath managed
        object property"
    ::= { cucsStorageLocalDiskEntry 30 }

cucsStorageLocalDiskEncAssociation OBJECT-TYPE
    SYNTAX       CucsStorageEnclosureAssociation
    MAX-ACCESS   read-only
    STATUS       current
    DESCRIPTION
        "Cisco UCS storage:LocalDisk:encAssociation managed
        object property"
    ::= { cucsStorageLocalDiskEntry 31 }

cucsStorageLocalDiskPhysicalBlockSize OBJECT-TYPE
    SYNTAX       Gauge32
    MAX-ACCESS   read-only
    STATUS       current
    DESCRIPTION
        "Cisco UCS storage:LocalDisk:physicalBlockSize
        managed object property"
    ::= { cucsStorageLocalDiskEntry 32 }

cucsStorageLocalDiskRawSize OBJECT-TYPE
    SYNTAX       Unsigned64
    MAX-ACCESS   read-only
    STATUS       current
    DESCRIPTION
        "Cisco UCS storage:LocalDisk:rawSize managed object property"
    ::= { cucsStorageLocalDiskEntry 33 }

cucsStorageLocalDiskDeviceVersion OBJECT-TYPE
    SYNTAX       SnmpAdminString
    MAX-ACCESS   read-only
    STATUS       current
    DESCRIPTION
        "Cisco UCS storage:LocalDisk:deviceVersion managed
        object property"
    ::= { cucsStorageLocalDiskEntry 34 }

cucsStorageLocalDiskFsmDescr OBJECT-TYPE
    SYNTAX       SnmpAdminString
    MAX-ACCESS   read-only
    STATUS       current
    DESCRIPTION
        "Cisco UCS storage:LocalDisk:fsmDescr managed object property"
    ::= { cucsStorageLocalDiskEntry 35 }

cucsStorageLocalDiskFsmFlags OBJECT-TYPE
    SYNTAX       SnmpAdminString
    MAX-ACCESS   read-only
    STATUS       current
    DESCRIPTION
        "Cisco UCS storage:LocalDisk:fsmFlags managed object property"
    ::= { cucsStorageLocalDiskEntry 36 }

cucsStorageLocalDiskFsmPrev OBJECT-TYPE
    SYNTAX       SnmpAdminString
    MAX-ACCESS   read-only
    STATUS       current
    DESCRIPTION
        "Cisco UCS storage:LocalDisk:fsmPrev managed object property"
    ::= { cucsStorageLocalDiskEntry 37 }

cucsStorageLocalDiskFsmProgr OBJECT-TYPE
    SYNTAX       Gauge32
    MAX-ACCESS   read-only
    STATUS       current
    DESCRIPTION
        "Cisco UCS storage:LocalDisk:fsmProgr managed object property"
    ::= { cucsStorageLocalDiskEntry 38 }

cucsStorageLocalDiskFsmRmtInvErrCode OBJECT-TYPE
    SYNTAX       Gauge32
    MAX-ACCESS   read-only
    STATUS       current
    DESCRIPTION
        "Cisco UCS storage:LocalDisk:fsmRmtInvErrCode managed
        object property"
    ::= { cucsStorageLocalDiskEntry 39 }

cucsStorageLocalDiskFsmRmtInvErrDescr OBJECT-TYPE
    SYNTAX       SnmpAdminString
    MAX-ACCESS   read-only
    STATUS       current
    DESCRIPTION
        "Cisco UCS storage:LocalDisk:fsmRmtInvErrDescr
        managed object property"
    ::= { cucsStorageLocalDiskEntry 40 }

cucsStorageLocalDiskFsmRmtInvRslt OBJECT-TYPE
    SYNTAX       CucsConditionRemoteInvRslt
    MAX-ACCESS   read-only
    STATUS       current
    DESCRIPTION
        "Cisco UCS storage:LocalDisk:fsmRmtInvRslt managed
        object property"
    ::= { cucsStorageLocalDiskEntry 41 }

cucsStorageLocalDiskFsmStageDescr OBJECT-TYPE
    SYNTAX       SnmpAdminString
    MAX-ACCESS   read-only
    STATUS       current
    DESCRIPTION
        "Cisco UCS storage:LocalDisk:fsmStageDescr managed
        object property"
    ::= { cucsStorageLocalDiskEntry 42 }

cucsStorageLocalDiskFsmStamp OBJECT-TYPE
    SYNTAX       DateAndTime
    MAX-ACCESS   read-only
    STATUS       current
    DESCRIPTION
        "Cisco UCS storage:LocalDisk:fsmStamp managed object property"
    ::= { cucsStorageLocalDiskEntry 43 }

cucsStorageLocalDiskFsmStatus OBJECT-TYPE
    SYNTAX       SnmpAdminString
    MAX-ACCESS   read-only
    STATUS       current
    DESCRIPTION
        "Cisco UCS storage:LocalDisk:fsmStatus managed object property"
    ::= { cucsStorageLocalDiskEntry 44 }

cucsStorageLocalDiskFsmTry OBJECT-TYPE
    SYNTAX       Gauge32
    MAX-ACCESS   read-only
    STATUS       current
    DESCRIPTION
        "Cisco UCS storage:LocalDisk:fsmTry managed object property"
    ::= { cucsStorageLocalDiskEntry 45 }

cucsStorageLocalDiskVariantType OBJECT-TYPE
    SYNTAX       SnmpAdminString
    MAX-ACCESS   read-only
    STATUS       current
    DESCRIPTION
        "Cisco UCS storage:LocalDisk:variantType managed object property"
    ::= { cucsStorageLocalDiskEntry 46 }

cucsStorageLocalDiskAdminSecurityKey OBJECT-TYPE
    SYNTAX       SnmpAdminString
    MAX-ACCESS   read-only
    STATUS       current
    DESCRIPTION
        "Cisco UCS storage:LocalDisk:adminSecurityKey managed
        object property"
    ::= { cucsStorageLocalDiskEntry 47 }

cucsStorageLocalDiskDriveState OBJECT-TYPE
    SYNTAX       CucsStorageDriveFlags
    MAX-ACCESS   read-only
    STATUS       current
    DESCRIPTION
        "Cisco UCS storage:LocalDisk:driveState managed object property"
    ::= { cucsStorageLocalDiskEntry 48 }

cucsStorageLocalDiskErrDescription OBJECT-TYPE
    SYNTAX       SnmpAdminString
    MAX-ACCESS   read-only
    STATUS       current
    DESCRIPTION
        "Cisco UCS storage:LocalDisk:errDescription managed
        object property"
    ::= { cucsStorageLocalDiskEntry 49 }

cucsStorageLocalDiskConfigDefTable OBJECT-TYPE
    SYNTAX           SEQUENCE OF CucsStorageLocalDiskConfigDefEntry
    MAX-ACCESS       not-accessible
    STATUS           current
    DESCRIPTION
        "Cisco UCS storage:LocalDiskConfigDef managed object table"
    ::= { cucsStorageObjects 5 }

cucsStorageLocalDiskConfigDefEntry OBJECT-TYPE
    SYNTAX           CucsStorageLocalDiskConfigDefEntry
    MAX-ACCESS       not-accessible
    STATUS           current
    DESCRIPTION
        "Entry for the cucsStorageLocalDiskConfigDefTable table."
    INDEX { cucsStorageLocalDiskConfigDefInstanceId }
    ::= { cucsStorageLocalDiskConfigDefTable 1 }

CucsStorageLocalDiskConfigDefEntry ::= SEQUENCE {
    cucsStorageLocalDiskConfigDefInstanceId                          CucsManagedObjectId,
    cucsStorageLocalDiskConfigDefDn                                  CucsManagedObjectDn,
    cucsStorageLocalDiskConfigDefRn                                  SnmpAdminString,
    cucsStorageLocalDiskConfigDefDescr                               SnmpAdminString,
    cucsStorageLocalDiskConfigDefIntId                               SnmpAdminString,
    cucsStorageLocalDiskConfigDefMode                                CucsStorageLocalDiskMode,
    cucsStorageLocalDiskConfigDefName                                SnmpAdminString,
    cucsStorageLocalDiskConfigDefProtectConfig                       TruthValue,
    cucsStorageLocalDiskConfigDefPolicyLevel                         Gauge32,
    cucsStorageLocalDiskConfigDefPolicyOwner                         CucsPolicyPolicyOwner,
    cucsStorageLocalDiskConfigDefFlexFlashRAIDReportingState         CucsStorageLocalDiskConfigFlexFlashRAIDReportingState,
    cucsStorageLocalDiskConfigDefFlexFlashState                      CucsStorageLocalDiskConfigFlexFlashState
}

cucsStorageLocalDiskConfigDefInstanceId OBJECT-TYPE
    SYNTAX       CucsManagedObjectId
    MAX-ACCESS   not-accessible
    STATUS       current
    DESCRIPTION
        "Instance identifier of the managed object."
    ::= { cucsStorageLocalDiskConfigDefEntry 1 }

cucsStorageLocalDiskConfigDefDn OBJECT-TYPE
    SYNTAX       CucsManagedObjectDn
    MAX-ACCESS   read-only
    STATUS       current
    DESCRIPTION
        "Cisco UCS storage:LocalDiskConfigDef:dn managed object property"
    ::= { cucsStorageLocalDiskConfigDefEntry 2 }

cucsStorageLocalDiskConfigDefRn OBJECT-TYPE
    SYNTAX       SnmpAdminString
    MAX-ACCESS   read-only
    STATUS       current
    DESCRIPTION
        "Cisco UCS storage:LocalDiskConfigDef:rn managed object property"
    ::= { cucsStorageLocalDiskConfigDefEntry 3 }

cucsStorageLocalDiskConfigDefDescr OBJECT-TYPE
    SYNTAX       SnmpAdminString
    MAX-ACCESS   read-only
    STATUS       current
    DESCRIPTION
        "Cisco UCS storage:LocalDiskConfigDef:descr managed
        object property"
    ::= { cucsStorageLocalDiskConfigDefEntry 4 }

cucsStorageLocalDiskConfigDefIntId OBJECT-TYPE
    SYNTAX       SnmpAdminString
    MAX-ACCESS   read-only
    STATUS       current
    DESCRIPTION
        "Cisco UCS storage:LocalDiskConfigDef:intId managed
        object property"
    ::= { cucsStorageLocalDiskConfigDefEntry 5 }

cucsStorageLocalDiskConfigDefMode OBJECT-TYPE
    SYNTAX       CucsStorageLocalDiskMode
    MAX-ACCESS   read-only
    STATUS       current
    DESCRIPTION
        "Cisco UCS storage:LocalDiskConfigDef:mode managed
        object property"
    ::= { cucsStorageLocalDiskConfigDefEntry 6 }

cucsStorageLocalDiskConfigDefName OBJECT-TYPE
    SYNTAX       SnmpAdminString
    MAX-ACCESS   read-only
    STATUS       current
    DESCRIPTION
        "Cisco UCS storage:LocalDiskConfigDef:name managed
        object property"
    ::= { cucsStorageLocalDiskConfigDefEntry 7 }

cucsStorageLocalDiskConfigDefProtectConfig OBJECT-TYPE
    SYNTAX       TruthValue
    MAX-ACCESS   read-only
    STATUS       current
    DESCRIPTION
        "Cisco UCS storage:LocalDiskConfigDef:protectConfig
        managed object property"
    ::= { cucsStorageLocalDiskConfigDefEntry 8 }

cucsStorageLocalDiskConfigDefPolicyLevel OBJECT-TYPE
    SYNTAX       Gauge32
    MAX-ACCESS   read-only
    STATUS       current
    DESCRIPTION
        "Cisco UCS storage:LocalDiskConfigDef:policyLevel
        managed object property"
    ::= { cucsStorageLocalDiskConfigDefEntry 9 }

cucsStorageLocalDiskConfigDefPolicyOwner OBJECT-TYPE
    SYNTAX       CucsPolicyPolicyOwner
    MAX-ACCESS   read-only
    STATUS       current
    DESCRIPTION
        "Cisco UCS storage:LocalDiskConfigDef:policyOwner
        managed object property"
    ::= { cucsStorageLocalDiskConfigDefEntry 10 }

cucsStorageLocalDiskConfigDefFlexFlashRAIDReportingState OBJECT-TYPE
    SYNTAX       CucsStorageLocalDiskConfigFlexFlashRAIDReportingState
    MAX-ACCESS   read-only
    STATUS       current
    DESCRIPTION
        "Cisco UCS storage:LocalDiskConfigDef:flexFlashRAIDReportingState
        managed object property"
    ::= { cucsStorageLocalDiskConfigDefEntry 11 }

cucsStorageLocalDiskConfigDefFlexFlashState OBJECT-TYPE
    SYNTAX       CucsStorageLocalDiskConfigFlexFlashState
    MAX-ACCESS   read-only
    STATUS       current
    DESCRIPTION
        "Cisco UCS storage:LocalDiskConfigDef:flexFlashState
        managed object property"
    ::= { cucsStorageLocalDiskConfigDefEntry 12 }

cucsStorageLocalDiskConfigPolicyTable OBJECT-TYPE
    SYNTAX           SEQUENCE OF CucsStorageLocalDiskConfigPolicyEntry
    MAX-ACCESS       not-accessible
    STATUS           current
    DESCRIPTION
        "Cisco UCS storage:LocalDiskConfigPolicy managed object table"
    ::= { cucsStorageObjects 6 }

cucsStorageLocalDiskConfigPolicyEntry OBJECT-TYPE
    SYNTAX           CucsStorageLocalDiskConfigPolicyEntry
    MAX-ACCESS       not-accessible
    STATUS           current
    DESCRIPTION
        "Entry for the cucsStorageLocalDiskConfigPolicyTable table."
    INDEX { cucsStorageLocalDiskConfigPolicyInstanceId }
    ::= { cucsStorageLocalDiskConfigPolicyTable 1 }

CucsStorageLocalDiskConfigPolicyEntry ::= SEQUENCE {
    cucsStorageLocalDiskConfigPolicyInstanceId                       CucsManagedObjectId,
    cucsStorageLocalDiskConfigPolicyDn                               CucsManagedObjectDn,
    cucsStorageLocalDiskConfigPolicyRn                               SnmpAdminString,
    cucsStorageLocalDiskConfigPolicyDescr                            SnmpAdminString,
    cucsStorageLocalDiskConfigPolicyIntId                            SnmpAdminString,
    cucsStorageLocalDiskConfigPolicyMode                             CucsStorageLocalDiskMode,
    cucsStorageLocalDiskConfigPolicyName                             SnmpAdminString,
    cucsStorageLocalDiskConfigPolicyProtectConfig                    TruthValue,
    cucsStorageLocalDiskConfigPolicyPolicyLevel                      Gauge32,
    cucsStorageLocalDiskConfigPolicyPolicyOwner                      CucsPolicyPolicyOwner,
    cucsStorageLocalDiskConfigPolicyFlexFlashRAIDReportingState      CucsStorageLocalDiskConfigFlexFlashRAIDReportingState,
    cucsStorageLocalDiskConfigPolicyFlexFlashState                   CucsStorageLocalDiskConfigFlexFlashState
}

cucsStorageLocalDiskConfigPolicyInstanceId OBJECT-TYPE
    SYNTAX       CucsManagedObjectId
    MAX-ACCESS   not-accessible
    STATUS       current
    DESCRIPTION
        "Instance identifier of the managed object."
    ::= { cucsStorageLocalDiskConfigPolicyEntry 1 }

cucsStorageLocalDiskConfigPolicyDn OBJECT-TYPE
    SYNTAX       CucsManagedObjectDn
    MAX-ACCESS   read-only
    STATUS       current
    DESCRIPTION
        "Cisco UCS storage:LocalDiskConfigPolicy:dn managed
        object property"
    ::= { cucsStorageLocalDiskConfigPolicyEntry 2 }

cucsStorageLocalDiskConfigPolicyRn OBJECT-TYPE
    SYNTAX       SnmpAdminString
    MAX-ACCESS   read-only
    STATUS       current
    DESCRIPTION
        "Cisco UCS storage:LocalDiskConfigPolicy:rn managed
        object property"
    ::= { cucsStorageLocalDiskConfigPolicyEntry 3 }

cucsStorageLocalDiskConfigPolicyDescr OBJECT-TYPE
    SYNTAX       SnmpAdminString
    MAX-ACCESS   read-only
    STATUS       current
    DESCRIPTION
        "Cisco UCS storage:LocalDiskConfigPolicy:descr
        managed object property"
    ::= { cucsStorageLocalDiskConfigPolicyEntry 4 }

cucsStorageLocalDiskConfigPolicyIntId OBJECT-TYPE
    SYNTAX       SnmpAdminString
    MAX-ACCESS   read-only
    STATUS       current
    DESCRIPTION
        "Cisco UCS storage:LocalDiskConfigPolicy:intId
        managed object property"
    ::= { cucsStorageLocalDiskConfigPolicyEntry 5 }

cucsStorageLocalDiskConfigPolicyMode OBJECT-TYPE
    SYNTAX       CucsStorageLocalDiskMode
    MAX-ACCESS   read-only
    STATUS       current
    DESCRIPTION
        "Cisco UCS storage:LocalDiskConfigPolicy:mode managed
        object property"
    ::= { cucsStorageLocalDiskConfigPolicyEntry 6 }

cucsStorageLocalDiskConfigPolicyName OBJECT-TYPE
    SYNTAX       SnmpAdminString
    MAX-ACCESS   read-only
    STATUS       current
    DESCRIPTION
        "Cisco UCS storage:LocalDiskConfigPolicy:name managed
        object property"
    ::= { cucsStorageLocalDiskConfigPolicyEntry 7 }

cucsStorageLocalDiskConfigPolicyProtectConfig OBJECT-TYPE
    SYNTAX       TruthValue
    MAX-ACCESS   read-only
    STATUS       current
    DESCRIPTION
        "Cisco UCS storage:LocalDiskConfigPolicy:protectConfig
        managed object property"
    ::= { cucsStorageLocalDiskConfigPolicyEntry 8 }

cucsStorageLocalDiskConfigPolicyPolicyLevel OBJECT-TYPE
    SYNTAX       Gauge32
    MAX-ACCESS   read-only
    STATUS       current
    DESCRIPTION
        "Cisco UCS storage:LocalDiskConfigPolicy:policyLevel
        managed object property"
    ::= { cucsStorageLocalDiskConfigPolicyEntry 9 }

cucsStorageLocalDiskConfigPolicyPolicyOwner OBJECT-TYPE
    SYNTAX       CucsPolicyPolicyOwner
    MAX-ACCESS   read-only
    STATUS       current
    DESCRIPTION
        "Cisco UCS storage:LocalDiskConfigPolicy:policyOwner
        managed object property"
    ::= { cucsStorageLocalDiskConfigPolicyEntry 10 }

cucsStorageLocalDiskConfigPolicyFlexFlashRAIDReportingState OBJECT-TYPE
    SYNTAX       CucsStorageLocalDiskConfigFlexFlashRAIDReportingState
    MAX-ACCESS   read-only
    STATUS       current
    DESCRIPTION
        "Cisco UCS storage:LocalDiskConfigPolicy:flexFlashRAIDReportingSta
        te managed object property"
    ::= { cucsStorageLocalDiskConfigPolicyEntry 11 }

cucsStorageLocalDiskConfigPolicyFlexFlashState OBJECT-TYPE
    SYNTAX       CucsStorageLocalDiskConfigFlexFlashState
    MAX-ACCESS   read-only
    STATUS       current
    DESCRIPTION
        "Cisco UCS storage:LocalDiskConfigPolicy:flexFlashState
        managed object property"
    ::= { cucsStorageLocalDiskConfigPolicyEntry 12 }

cucsStorageLocalDiskEpTable OBJECT-TYPE
    SYNTAX           SEQUENCE OF CucsStorageLocalDiskEpEntry
    MAX-ACCESS       not-accessible
    STATUS           current
    DESCRIPTION
        "Cisco UCS storage:LocalDiskEp managed object table"
    ::= { cucsStorageObjects 60 }

cucsStorageLocalDiskEpEntry OBJECT-TYPE
    SYNTAX           CucsStorageLocalDiskEpEntry
    MAX-ACCESS       not-accessible
    STATUS           current
    DESCRIPTION
        "Entry for the cucsStorageLocalDiskEpTable table."
    INDEX { cucsStorageLocalDiskEpInstanceId }
    ::= { cucsStorageLocalDiskEpTable 1 }

CucsStorageLocalDiskEpEntry ::= SEQUENCE {
    cucsStorageLocalDiskEpInstanceId                                 CucsManagedObjectId,
    cucsStorageLocalDiskEpDn                                         CucsManagedObjectDn,
    cucsStorageLocalDiskEpRn                                         SnmpAdminString,
    cucsStorageLocalDiskEpDiskDn                                     SnmpAdminString,
    cucsStorageLocalDiskEpEncId                                      Gauge32,
    cucsStorageLocalDiskEpId                                         Gauge32,
    cucsStorageLocalDiskEpModel                                      SnmpAdminString,
    cucsStorageLocalDiskEpRevision                                   SnmpAdminString,
    cucsStorageLocalDiskEpSerial                                     SnmpAdminString,
    cucsStorageLocalDiskEpVendor                                     SnmpAdminString,
    cucsStorageLocalDiskEpBootable                                   CucsStorageBootableType,
    cucsStorageLocalDiskEpDiskState                                  CucsStoragePDriveStatus,
    cucsStorageLocalDiskEpLc                                         CucsFsmLifecycle
}

cucsStorageLocalDiskEpInstanceId OBJECT-TYPE
    SYNTAX       CucsManagedObjectId
    MAX-ACCESS   not-accessible
    STATUS       current
    DESCRIPTION
        "Instance identifier of the managed object."
    ::= { cucsStorageLocalDiskEpEntry 1 }

cucsStorageLocalDiskEpDn OBJECT-TYPE
    SYNTAX       CucsManagedObjectDn
    MAX-ACCESS   read-only
    STATUS       current
    DESCRIPTION
        "Cisco UCS storage:LocalDiskEp:dn managed object property"
    ::= { cucsStorageLocalDiskEpEntry 2 }

cucsStorageLocalDiskEpRn OBJECT-TYPE
    SYNTAX       SnmpAdminString
    MAX-ACCESS   read-only
    STATUS       current
    DESCRIPTION
        "Cisco UCS storage:LocalDiskEp:rn managed object property"
    ::= { cucsStorageLocalDiskEpEntry 3 }

cucsStorageLocalDiskEpDiskDn OBJECT-TYPE
    SYNTAX       SnmpAdminString
    MAX-ACCESS   read-only
    STATUS       current
    DESCRIPTION
        "Cisco UCS storage:LocalDiskEp:diskDn managed object property"
    ::= { cucsStorageLocalDiskEpEntry 4 }

cucsStorageLocalDiskEpEncId OBJECT-TYPE
    SYNTAX       Gauge32
    MAX-ACCESS   read-only
    STATUS       current
    DESCRIPTION
        "Cisco UCS storage:LocalDiskEp:encId managed object property"
    ::= { cucsStorageLocalDiskEpEntry 5 }

cucsStorageLocalDiskEpId OBJECT-TYPE
    SYNTAX       Gauge32
    MAX-ACCESS   read-only
    STATUS       current
    DESCRIPTION
        "Cisco UCS storage:LocalDiskEp:id managed object property"
    ::= { cucsStorageLocalDiskEpEntry 6 }

cucsStorageLocalDiskEpModel OBJECT-TYPE
    SYNTAX       SnmpAdminString
    MAX-ACCESS   read-only
    STATUS       current
    DESCRIPTION
        "Cisco UCS storage:LocalDiskEp:model managed object property"
    ::= { cucsStorageLocalDiskEpEntry 7 }

cucsStorageLocalDiskEpRevision OBJECT-TYPE
    SYNTAX       SnmpAdminString
    MAX-ACCESS   read-only
    STATUS       current
    DESCRIPTION
        "Cisco UCS storage:LocalDiskEp:revision managed object property"
    ::= { cucsStorageLocalDiskEpEntry 8 }

cucsStorageLocalDiskEpSerial OBJECT-TYPE
    SYNTAX       SnmpAdminString
    MAX-ACCESS   read-only
    STATUS       current
    DESCRIPTION
        "Cisco UCS storage:LocalDiskEp:serial managed object property"
    ::= { cucsStorageLocalDiskEpEntry 9 }

cucsStorageLocalDiskEpVendor OBJECT-TYPE
    SYNTAX       SnmpAdminString
    MAX-ACCESS   read-only
    STATUS       current
    DESCRIPTION
        "Cisco UCS storage:LocalDiskEp:vendor managed object property"
    ::= { cucsStorageLocalDiskEpEntry 10 }

cucsStorageLocalDiskEpBootable OBJECT-TYPE
    SYNTAX       CucsStorageBootableType
    MAX-ACCESS   read-only
    STATUS       current
    DESCRIPTION
        "Cisco UCS storage:LocalDiskEp:bootable managed object property"
    ::= { cucsStorageLocalDiskEpEntry 11 }

cucsStorageLocalDiskEpDiskState OBJECT-TYPE
    SYNTAX       CucsStoragePDriveStatus
    MAX-ACCESS   read-only
    STATUS       current
    DESCRIPTION
        "Cisco UCS storage:LocalDiskEp:diskState managed object property"
    ::= { cucsStorageLocalDiskEpEntry 12 }

cucsStorageLocalDiskEpLc OBJECT-TYPE
    SYNTAX       CucsFsmLifecycle
    MAX-ACCESS   read-only
    STATUS       current
    DESCRIPTION
        "Cisco UCS storage:LocalDiskEp:lc managed object property"
    ::= { cucsStorageLocalDiskEpEntry 13 }

cucsStorageLocalDiskFsmTable OBJECT-TYPE
    SYNTAX           SEQUENCE OF CucsStorageLocalDiskFsmEntry
    MAX-ACCESS       not-accessible
    STATUS           current
    DESCRIPTION
        "Cisco UCS storage:LocalDiskFsm managed object table"
    ::= { cucsStorageObjects 119 }

cucsStorageLocalDiskFsmEntry OBJECT-TYPE
    SYNTAX           CucsStorageLocalDiskFsmEntry
    MAX-ACCESS       not-accessible
    STATUS           current
    DESCRIPTION
        "Entry for the cucsStorageLocalDiskFsmTable table."
    INDEX { cucsStorageLocalDiskFsmInstanceId }
    ::= { cucsStorageLocalDiskFsmTable 1 }

CucsStorageLocalDiskFsmEntry ::= SEQUENCE {
    cucsStorageLocalDiskFsmInstanceId                                CucsManagedObjectId,
    cucsStorageLocalDiskFsmDn                                        CucsManagedObjectDn,
    cucsStorageLocalDiskFsmRn                                        SnmpAdminString,
    cucsStorageLocalDiskFsmCompletionTime                            DateAndTime,
    cucsStorageLocalDiskFsmCurrentFsm                                CucsStorageLocalDiskFsmCurrentFsm,
    cucsStorageLocalDiskFsmDescrData                                 SnmpAdminString,
    cucsStorageLocalDiskFsmFsmStatus                                 CucsFsmFsmStageStatus,
    cucsStorageLocalDiskFsmProgress                                  Gauge32,
    cucsStorageLocalDiskFsmRmtErrCode                                Gauge32,
    cucsStorageLocalDiskFsmRmtErrDescr                               SnmpAdminString,
    cucsStorageLocalDiskFsmRmtRslt                                   CucsConditionRemoteInvRslt
}

cucsStorageLocalDiskFsmInstanceId OBJECT-TYPE
    SYNTAX       CucsManagedObjectId
    MAX-ACCESS   not-accessible
    STATUS       current
    DESCRIPTION
        "Instance identifier of the managed object."
    ::= { cucsStorageLocalDiskFsmEntry 1 }

cucsStorageLocalDiskFsmDn OBJECT-TYPE
    SYNTAX       CucsManagedObjectDn
    MAX-ACCESS   read-only
    STATUS       current
    DESCRIPTION
        "Cisco UCS storage:LocalDiskFsm:dn managed object property"
    ::= { cucsStorageLocalDiskFsmEntry 2 }

cucsStorageLocalDiskFsmRn OBJECT-TYPE
    SYNTAX       SnmpAdminString
    MAX-ACCESS   read-only
    STATUS       current
    DESCRIPTION
        "Cisco UCS storage:LocalDiskFsm:rn managed object property"
    ::= { cucsStorageLocalDiskFsmEntry 3 }

cucsStorageLocalDiskFsmCompletionTime OBJECT-TYPE
    SYNTAX       DateAndTime
    MAX-ACCESS   read-only
    STATUS       current
    DESCRIPTION
        "Cisco UCS storage:LocalDiskFsm:completionTime
        managed object property"
    ::= { cucsStorageLocalDiskFsmEntry 4 }

cucsStorageLocalDiskFsmCurrentFsm OBJECT-TYPE
    SYNTAX       CucsStorageLocalDiskFsmCurrentFsm
    MAX-ACCESS   read-only
    STATUS       current
    DESCRIPTION
        "Cisco UCS storage:LocalDiskFsm:currentFsm managed
        object property"
    ::= { cucsStorageLocalDiskFsmEntry 5 }

cucsStorageLocalDiskFsmDescrData OBJECT-TYPE
    SYNTAX       SnmpAdminString
    MAX-ACCESS   read-only
    STATUS       current
    DESCRIPTION
        "Cisco UCS storage:LocalDiskFsm:descr managed object property"
    ::= { cucsStorageLocalDiskFsmEntry 6 }

cucsStorageLocalDiskFsmFsmStatus OBJECT-TYPE
    SYNTAX       CucsFsmFsmStageStatus
    MAX-ACCESS   read-only
    STATUS       current
    DESCRIPTION
        "Cisco UCS storage:LocalDiskFsm:fsmStatus managed object property"
    ::= { cucsStorageLocalDiskFsmEntry 7 }

cucsStorageLocalDiskFsmProgress OBJECT-TYPE
    SYNTAX       Gauge32
    MAX-ACCESS   read-only
    STATUS       current
    DESCRIPTION
        "Cisco UCS storage:LocalDiskFsm:progress managed object property"
    ::= { cucsStorageLocalDiskFsmEntry 8 }

cucsStorageLocalDiskFsmRmtErrCode OBJECT-TYPE
    SYNTAX       Gauge32
    MAX-ACCESS   read-only
    STATUS       current
    DESCRIPTION
        "Cisco UCS storage:LocalDiskFsm:rmtErrCode managed
        object property"
    ::= { cucsStorageLocalDiskFsmEntry 9 }

cucsStorageLocalDiskFsmRmtErrDescr OBJECT-TYPE
    SYNTAX       SnmpAdminString
    MAX-ACCESS   read-only
    STATUS       current
    DESCRIPTION
        "Cisco UCS storage:LocalDiskFsm:rmtErrDescr managed
        object property"
    ::= { cucsStorageLocalDiskFsmEntry 10 }

cucsStorageLocalDiskFsmRmtRslt OBJECT-TYPE
    SYNTAX       CucsConditionRemoteInvRslt
    MAX-ACCESS   read-only
    STATUS       current
    DESCRIPTION
        "Cisco UCS storage:LocalDiskFsm:rmtRslt managed object property"
    ::= { cucsStorageLocalDiskFsmEntry 11 }

cucsStorageLocalDiskFsmStageTable OBJECT-TYPE
    SYNTAX           SEQUENCE OF CucsStorageLocalDiskFsmStageEntry
    MAX-ACCESS       not-accessible
    STATUS           current
    DESCRIPTION
        "Cisco UCS storage:LocalDiskFsmStage managed object table"
    ::= { cucsStorageObjects 120 }

cucsStorageLocalDiskFsmStageEntry OBJECT-TYPE
    SYNTAX           CucsStorageLocalDiskFsmStageEntry
    MAX-ACCESS       not-accessible
    STATUS           current
    DESCRIPTION
        "Entry for the cucsStorageLocalDiskFsmStageTable table."
    INDEX { cucsStorageLocalDiskFsmStageInstanceId }
    ::= { cucsStorageLocalDiskFsmStageTable 1 }

CucsStorageLocalDiskFsmStageEntry ::= SEQUENCE {
    cucsStorageLocalDiskFsmStageInstanceId                           CucsManagedObjectId,
    cucsStorageLocalDiskFsmStageDn                                   CucsManagedObjectDn,
    cucsStorageLocalDiskFsmStageRn                                   SnmpAdminString,
    cucsStorageLocalDiskFsmStageDescrData                            SnmpAdminString,
    cucsStorageLocalDiskFsmStageLastUpdateTime                       DateAndTime,
    cucsStorageLocalDiskFsmStageName                                 CucsStorageLocalDiskFsmStageName,
    cucsStorageLocalDiskFsmStageOrder                                Gauge32,
    cucsStorageLocalDiskFsmStageRetry                                Gauge32,
    cucsStorageLocalDiskFsmStageStageStatus                          CucsFsmFsmStageStatus
}

cucsStorageLocalDiskFsmStageInstanceId OBJECT-TYPE
    SYNTAX       CucsManagedObjectId
    MAX-ACCESS   not-accessible
    STATUS       current
    DESCRIPTION
        "Instance identifier of the managed object."
    ::= { cucsStorageLocalDiskFsmStageEntry 1 }

cucsStorageLocalDiskFsmStageDn OBJECT-TYPE
    SYNTAX       CucsManagedObjectDn
    MAX-ACCESS   read-only
    STATUS       current
    DESCRIPTION
        "Cisco UCS storage:LocalDiskFsmStage:dn managed object property"
    ::= { cucsStorageLocalDiskFsmStageEntry 2 }

cucsStorageLocalDiskFsmStageRn OBJECT-TYPE
    SYNTAX       SnmpAdminString
    MAX-ACCESS   read-only
    STATUS       current
    DESCRIPTION
        "Cisco UCS storage:LocalDiskFsmStage:rn managed object property"
    ::= { cucsStorageLocalDiskFsmStageEntry 3 }

cucsStorageLocalDiskFsmStageDescrData OBJECT-TYPE
    SYNTAX       SnmpAdminString
    MAX-ACCESS   read-only
    STATUS       current
    DESCRIPTION
        "Cisco UCS storage:LocalDiskFsmStage:descr managed
        object property"
    ::= { cucsStorageLocalDiskFsmStageEntry 4 }

cucsStorageLocalDiskFsmStageLastUpdateTime OBJECT-TYPE
    SYNTAX       DateAndTime
    MAX-ACCESS   read-only
    STATUS       current
    DESCRIPTION
        "Cisco UCS storage:LocalDiskFsmStage:lastUpdateTime
        managed object property"
    ::= { cucsStorageLocalDiskFsmStageEntry 5 }

cucsStorageLocalDiskFsmStageName OBJECT-TYPE
    SYNTAX       CucsStorageLocalDiskFsmStageName
    MAX-ACCESS   read-only
    STATUS       current
    DESCRIPTION
        "Cisco UCS storage:LocalDiskFsmStage:name managed object property"
    ::= { cucsStorageLocalDiskFsmStageEntry 6 }

cucsStorageLocalDiskFsmStageOrder OBJECT-TYPE
    SYNTAX       Gauge32
    MAX-ACCESS   read-only
    STATUS       current
    DESCRIPTION
        "Cisco UCS storage:LocalDiskFsmStage:order managed
        object property"
    ::= { cucsStorageLocalDiskFsmStageEntry 7 }

cucsStorageLocalDiskFsmStageRetry OBJECT-TYPE
    SYNTAX       Gauge32
    MAX-ACCESS   read-only
    STATUS       current
    DESCRIPTION
        "Cisco UCS storage:LocalDiskFsmStage:retry managed
        object property"
    ::= { cucsStorageLocalDiskFsmStageEntry 8 }

cucsStorageLocalDiskFsmStageStageStatus OBJECT-TYPE
    SYNTAX       CucsFsmFsmStageStatus
    MAX-ACCESS   read-only
    STATUS       current
    DESCRIPTION
        "Cisco UCS storage:LocalDiskFsmStage:stageStatus
        managed object property"
    ::= { cucsStorageLocalDiskFsmStageEntry 9 }

cucsStorageLocalDiskFsmTaskTable OBJECT-TYPE
    SYNTAX           SEQUENCE OF CucsStorageLocalDiskFsmTaskEntry
    MAX-ACCESS       not-accessible
    STATUS           current
    DESCRIPTION
        "Cisco UCS storage:LocalDiskFsmTask managed object table"
    ::= { cucsStorageObjects 121 }

cucsStorageLocalDiskFsmTaskEntry OBJECT-TYPE
    SYNTAX           CucsStorageLocalDiskFsmTaskEntry
    MAX-ACCESS       not-accessible
    STATUS           current
    DESCRIPTION
        "Entry for the cucsStorageLocalDiskFsmTaskTable table."
    INDEX { cucsStorageLocalDiskFsmTaskInstanceId }
    ::= { cucsStorageLocalDiskFsmTaskTable 1 }

CucsStorageLocalDiskFsmTaskEntry ::= SEQUENCE {
    cucsStorageLocalDiskFsmTaskInstanceId                            CucsManagedObjectId,
    cucsStorageLocalDiskFsmTaskDn                                    CucsManagedObjectDn,
    cucsStorageLocalDiskFsmTaskRn                                    SnmpAdminString,
    cucsStorageLocalDiskFsmTaskCompletion                            CucsFsmCompletion,
    cucsStorageLocalDiskFsmTaskFlags                                 CucsStorageLocalDiskFsmTaskFlags,
    cucsStorageLocalDiskFsmTaskItem                                  CucsStorageLocalDiskFsmTaskItem,
    cucsStorageLocalDiskFsmTaskSeqId                                 Gauge32
}

cucsStorageLocalDiskFsmTaskInstanceId OBJECT-TYPE
    SYNTAX       CucsManagedObjectId
    MAX-ACCESS   not-accessible
    STATUS       current
    DESCRIPTION
        "Instance identifier of the managed object."
    ::= { cucsStorageLocalDiskFsmTaskEntry 1 }

cucsStorageLocalDiskFsmTaskDn OBJECT-TYPE
    SYNTAX       CucsManagedObjectDn
    MAX-ACCESS   read-only
    STATUS       current
    DESCRIPTION
        "Cisco UCS storage:LocalDiskFsmTask:dn managed object property"
    ::= { cucsStorageLocalDiskFsmTaskEntry 2 }

cucsStorageLocalDiskFsmTaskRn OBJECT-TYPE
    SYNTAX       SnmpAdminString
    MAX-ACCESS   read-only
    STATUS       current
    DESCRIPTION
        "Cisco UCS storage:LocalDiskFsmTask:rn managed object property"
    ::= { cucsStorageLocalDiskFsmTaskEntry 3 }

cucsStorageLocalDiskFsmTaskCompletion OBJECT-TYPE
    SYNTAX       CucsFsmCompletion
    MAX-ACCESS   read-only
    STATUS       current
    DESCRIPTION
        "Cisco UCS storage:LocalDiskFsmTask:completion
        managed object property"
    ::= { cucsStorageLocalDiskFsmTaskEntry 4 }

cucsStorageLocalDiskFsmTaskFlags OBJECT-TYPE
    SYNTAX       CucsStorageLocalDiskFsmTaskFlags
    MAX-ACCESS   read-only
    STATUS       current
    DESCRIPTION
        "Cisco UCS storage:LocalDiskFsmTask:flags managed object property"
    ::= { cucsStorageLocalDiskFsmTaskEntry 5 }

cucsStorageLocalDiskFsmTaskItem OBJECT-TYPE
    SYNTAX       CucsStorageLocalDiskFsmTaskItem
    MAX-ACCESS   read-only
    STATUS       current
    DESCRIPTION
        "Cisco UCS storage:LocalDiskFsmTask:item managed object property"
    ::= { cucsStorageLocalDiskFsmTaskEntry 6 }

cucsStorageLocalDiskFsmTaskSeqId OBJECT-TYPE
    SYNTAX       Gauge32
    MAX-ACCESS   read-only
    STATUS       current
    DESCRIPTION
        "Cisco UCS storage:LocalDiskFsmTask:seqId managed object property"
    ::= { cucsStorageLocalDiskFsmTaskEntry 7 }

cucsStorageLocalDiskPartitionTable OBJECT-TYPE
    SYNTAX           SEQUENCE OF CucsStorageLocalDiskPartitionEntry
    MAX-ACCESS       not-accessible
    STATUS           current
    DESCRIPTION
        "Cisco UCS storage:LocalDiskPartition managed object table"
    ::= { cucsStorageObjects 7 }

cucsStorageLocalDiskPartitionEntry OBJECT-TYPE
    SYNTAX           CucsStorageLocalDiskPartitionEntry
    MAX-ACCESS       not-accessible
    STATUS           current
    DESCRIPTION
        "Entry for the cucsStorageLocalDiskPartitionTable table."
    INDEX { cucsStorageLocalDiskPartitionInstanceId }
    ::= { cucsStorageLocalDiskPartitionTable 1 }

CucsStorageLocalDiskPartitionEntry ::= SEQUENCE {
    cucsStorageLocalDiskPartitionInstanceId                          CucsManagedObjectId,
    cucsStorageLocalDiskPartitionDn                                  CucsManagedObjectDn,
    cucsStorageLocalDiskPartitionRn                                  SnmpAdminString,
    cucsStorageLocalDiskPartitionName                                SnmpAdminString,
    cucsStorageLocalDiskPartitionSize                                Unsigned64,
    cucsStorageLocalDiskPartitionType                                Gauge32,
    cucsStorageLocalDiskPartitionBootable                            CucsStorageBootableType,
    cucsStorageLocalDiskPartitionId                                  Gauge32,
    cucsStorageLocalDiskPartitionPartitionEnd                        Unsigned64,
    cucsStorageLocalDiskPartitionPartitionStart                      Unsigned64,
    cucsStorageLocalDiskPartitionRawTypeDesc                         SnmpAdminString
}

cucsStorageLocalDiskPartitionInstanceId OBJECT-TYPE
    SYNTAX       CucsManagedObjectId
    MAX-ACCESS   not-accessible
    STATUS       current
    DESCRIPTION
        "Instance identifier of the managed object."
    ::= { cucsStorageLocalDiskPartitionEntry 1 }

cucsStorageLocalDiskPartitionDn OBJECT-TYPE
    SYNTAX       CucsManagedObjectDn
    MAX-ACCESS   read-only
    STATUS       current
    DESCRIPTION
        "Cisco UCS storage:LocalDiskPartition:dn managed object property"
    ::= { cucsStorageLocalDiskPartitionEntry 2 }

cucsStorageLocalDiskPartitionRn OBJECT-TYPE
    SYNTAX       SnmpAdminString
    MAX-ACCESS   read-only
    STATUS       current
    DESCRIPTION
        "Cisco UCS storage:LocalDiskPartition:rn managed object property"
    ::= { cucsStorageLocalDiskPartitionEntry 3 }

cucsStorageLocalDiskPartitionName OBJECT-TYPE
    SYNTAX       SnmpAdminString
    MAX-ACCESS   read-only
    STATUS       current
    DESCRIPTION
        "Cisco UCS storage:LocalDiskPartition:name managed
        object property"
    ::= { cucsStorageLocalDiskPartitionEntry 6 }

cucsStorageLocalDiskPartitionSize OBJECT-TYPE
    SYNTAX       Unsigned64
    MAX-ACCESS   read-only
    STATUS       current
    DESCRIPTION
        "Cisco UCS storage:LocalDiskPartition:size managed
        object property"
    ::= { cucsStorageLocalDiskPartitionEntry 8 }

cucsStorageLocalDiskPartitionType OBJECT-TYPE
    SYNTAX       Gauge32
    MAX-ACCESS   read-only
    STATUS       current
    DESCRIPTION
        "Cisco UCS storage:LocalDiskPartition:type managed
        object property"
    ::= { cucsStorageLocalDiskPartitionEntry 9 }

cucsStorageLocalDiskPartitionBootable OBJECT-TYPE
    SYNTAX       CucsStorageBootableType
    MAX-ACCESS   read-only
    STATUS       current
    DESCRIPTION
        "Cisco UCS storage:LocalDiskPartition:bootable
        managed object property"
    ::= { cucsStorageLocalDiskPartitionEntry 12 }

cucsStorageLocalDiskPartitionId OBJECT-TYPE
    SYNTAX       Gauge32
    MAX-ACCESS   read-only
    STATUS       current
    DESCRIPTION
        "Cisco UCS storage:LocalDiskPartition:id managed object property"
    ::= { cucsStorageLocalDiskPartitionEntry 13 }

cucsStorageLocalDiskPartitionPartitionEnd OBJECT-TYPE
    SYNTAX       Unsigned64
    MAX-ACCESS   read-only
    STATUS       current
    DESCRIPTION
        "Cisco UCS storage:LocalDiskPartition:partitionEnd
        managed object property"
    ::= { cucsStorageLocalDiskPartitionEntry 14 }

cucsStorageLocalDiskPartitionPartitionStart OBJECT-TYPE
    SYNTAX       Unsigned64
    MAX-ACCESS   read-only
    STATUS       current
    DESCRIPTION
        "Cisco UCS storage:LocalDiskPartition:partitionStart
        managed object property"
    ::= { cucsStorageLocalDiskPartitionEntry 15 }

cucsStorageLocalDiskPartitionRawTypeDesc OBJECT-TYPE
    SYNTAX       SnmpAdminString
    MAX-ACCESS   read-only
    STATUS       current
    DESCRIPTION
        "Cisco UCS storage:LocalDiskPartition:rawTypeDesc
        managed object property"
    ::= { cucsStorageLocalDiskPartitionEntry 16 }

cucsStorageLocalDiskSlotEpTable OBJECT-TYPE
    SYNTAX           SEQUENCE OF CucsStorageLocalDiskSlotEpEntry
    MAX-ACCESS       not-accessible
    STATUS           current
    DESCRIPTION
        "Cisco UCS storage:LocalDiskSlotEp managed object table"
    ::= { cucsStorageObjects 13 }

cucsStorageLocalDiskSlotEpEntry OBJECT-TYPE
    SYNTAX           CucsStorageLocalDiskSlotEpEntry
    MAX-ACCESS       not-accessible
    STATUS           current
    DESCRIPTION
        "Entry for the cucsStorageLocalDiskSlotEpTable table."
    INDEX { cucsStorageLocalDiskSlotEpInstanceId }
    ::= { cucsStorageLocalDiskSlotEpTable 1 }

CucsStorageLocalDiskSlotEpEntry ::= SEQUENCE {
    cucsStorageLocalDiskSlotEpInstanceId                             CucsManagedObjectId,
    cucsStorageLocalDiskSlotEpDn                                     CucsManagedObjectDn,
    cucsStorageLocalDiskSlotEpRn                                     SnmpAdminString,
    cucsStorageLocalDiskSlotEpConfiguration                          CucsStorageConfiguration,
    cucsStorageLocalDiskSlotEpId                                     Gauge32,
    cucsStorageLocalDiskSlotEpOperability                            CucsEquipmentOperability,
    cucsStorageLocalDiskSlotEpPeerDn                                 SnmpAdminString,
    cucsStorageLocalDiskSlotEpPresence                               CucsEquipmentPresence,
    cucsStorageLocalDiskSlotEpOperQualifierReason                    SnmpAdminString
}

cucsStorageLocalDiskSlotEpInstanceId OBJECT-TYPE
    SYNTAX       CucsManagedObjectId
    MAX-ACCESS   not-accessible
    STATUS       current
    DESCRIPTION
        "Instance identifier of the managed object."
    ::= { cucsStorageLocalDiskSlotEpEntry 1 }

cucsStorageLocalDiskSlotEpDn OBJECT-TYPE
    SYNTAX       CucsManagedObjectDn
    MAX-ACCESS   read-only
    STATUS       current
    DESCRIPTION
        "Cisco UCS storage:LocalDiskSlotEp:dn managed object property"
    ::= { cucsStorageLocalDiskSlotEpEntry 2 }

cucsStorageLocalDiskSlotEpRn OBJECT-TYPE
    SYNTAX       SnmpAdminString
    MAX-ACCESS   read-only
    STATUS       current
    DESCRIPTION
        "Cisco UCS storage:LocalDiskSlotEp:rn managed object property"
    ::= { cucsStorageLocalDiskSlotEpEntry 3 }

cucsStorageLocalDiskSlotEpConfiguration OBJECT-TYPE
    SYNTAX       CucsStorageConfiguration
    MAX-ACCESS   read-only
    STATUS       current
    DESCRIPTION
        "Cisco UCS storage:LocalDiskSlotEp:configuration
        managed object property"
    ::= { cucsStorageLocalDiskSlotEpEntry 4 }

cucsStorageLocalDiskSlotEpId OBJECT-TYPE
    SYNTAX       Gauge32
    MAX-ACCESS   read-only
    STATUS       current
    DESCRIPTION
        "Cisco UCS storage:LocalDiskSlotEp:id managed object property"
    ::= { cucsStorageLocalDiskSlotEpEntry 5 }

cucsStorageLocalDiskSlotEpOperability OBJECT-TYPE
    SYNTAX       CucsEquipmentOperability
    MAX-ACCESS   read-only
    STATUS       current
    DESCRIPTION
        "Cisco UCS storage:LocalDiskSlotEp:operability
        managed object property"
    ::= { cucsStorageLocalDiskSlotEpEntry 6 }

cucsStorageLocalDiskSlotEpPeerDn OBJECT-TYPE
    SYNTAX       SnmpAdminString
    MAX-ACCESS   read-only
    STATUS       current
    DESCRIPTION
        "Cisco UCS storage:LocalDiskSlotEp:peerDn managed object property"
    ::= { cucsStorageLocalDiskSlotEpEntry 7 }

cucsStorageLocalDiskSlotEpPresence OBJECT-TYPE
    SYNTAX       CucsEquipmentPresence
    MAX-ACCESS   read-only
    STATUS       current
    DESCRIPTION
        "Cisco UCS storage:LocalDiskSlotEp:presence managed
        object property"
    ::= { cucsStorageLocalDiskSlotEpEntry 8 }

cucsStorageLocalDiskSlotEpOperQualifierReason OBJECT-TYPE
    SYNTAX       SnmpAdminString
    MAX-ACCESS   read-only
    STATUS       current
    DESCRIPTION
        "Cisco UCS storage:LocalDiskSlotEp:operQualifierReason
        managed object property"
    ::= { cucsStorageLocalDiskSlotEpEntry 9 }

cucsStorageLocalLunTable OBJECT-TYPE
    SYNTAX           SEQUENCE OF CucsStorageLocalLunEntry
    MAX-ACCESS       not-accessible
    STATUS           current
    DESCRIPTION
        "Cisco UCS storage:LocalLun managed object table"
    ::= { cucsStorageObjects 8 }

cucsStorageLocalLunEntry OBJECT-TYPE
    SYNTAX           CucsStorageLocalLunEntry
    MAX-ACCESS       not-accessible
    STATUS           current
    DESCRIPTION
        "Entry for the cucsStorageLocalLunTable table."
    INDEX { cucsStorageLocalLunInstanceId }
    ::= { cucsStorageLocalLunTable 1 }

CucsStorageLocalLunEntry ::= SEQUENCE {
    cucsStorageLocalLunInstanceId                                    CucsManagedObjectId,
    cucsStorageLocalLunDn                                            CucsManagedObjectDn,
    cucsStorageLocalLunRn                                            SnmpAdminString,
    cucsStorageLocalLunBlockSize                                     Gauge32,
    cucsStorageLocalLunConnectionProtocol                            CucsStorageConnectionProtocol,
    cucsStorageLocalLunId                                            Gauge32,
    cucsStorageLocalLunModel                                         SnmpAdminString,
    cucsStorageLocalLunNumberOfBlocks                                Unsigned64,
    cucsStorageLocalLunOperability                                   CucsEquipmentOperability,
    cucsStorageLocalLunPresence                                      CucsEquipmentPresence,
    cucsStorageLocalLunRevision                                      SnmpAdminString,
    cucsStorageLocalLunSerial                                        SnmpAdminString,
    cucsStorageLocalLunSize                                          Unsigned64,
    cucsStorageLocalLunType                                          CucsStorageLunType,
    cucsStorageLocalLunVendor                                        SnmpAdminString,
    cucsStorageLocalLunLc                                            CucsFsmLifecycle,
    cucsStorageLocalLunOperQualifierReason                           SnmpAdminString,
    cucsStorageLocalLunPhysicalBlockSize                             Gauge32
}

cucsStorageLocalLunInstanceId OBJECT-TYPE
    SYNTAX       CucsManagedObjectId
    MAX-ACCESS   not-accessible
    STATUS       current
    DESCRIPTION
        "Instance identifier of the managed object."
    ::= { cucsStorageLocalLunEntry 1 }

cucsStorageLocalLunDn OBJECT-TYPE
    SYNTAX       CucsManagedObjectDn
    MAX-ACCESS   read-only
    STATUS       current
    DESCRIPTION
        "Cisco UCS storage:LocalLun:dn managed object property"
    ::= { cucsStorageLocalLunEntry 2 }

cucsStorageLocalLunRn OBJECT-TYPE
    SYNTAX       SnmpAdminString
    MAX-ACCESS   read-only
    STATUS       current
    DESCRIPTION
        "Cisco UCS storage:LocalLun:rn managed object property"
    ::= { cucsStorageLocalLunEntry 3 }

cucsStorageLocalLunBlockSize OBJECT-TYPE
    SYNTAX       Gauge32
    MAX-ACCESS   read-only
    STATUS       current
    DESCRIPTION
        "Cisco UCS storage:LocalLun:blockSize managed object property"
    ::= { cucsStorageLocalLunEntry 4 }

cucsStorageLocalLunConnectionProtocol OBJECT-TYPE
    SYNTAX       CucsStorageConnectionProtocol
    MAX-ACCESS   read-only
    STATUS       current
    DESCRIPTION
        "Cisco UCS storage:LocalLun:connectionProtocol
        managed object property"
    ::= { cucsStorageLocalLunEntry 5 }

cucsStorageLocalLunId OBJECT-TYPE
    SYNTAX       Gauge32
    MAX-ACCESS   read-only
    STATUS       current
    DESCRIPTION
        "Cisco UCS storage:LocalLun:id managed object property"
    ::= { cucsStorageLocalLunEntry 6 }

cucsStorageLocalLunModel OBJECT-TYPE
    SYNTAX       SnmpAdminString
    MAX-ACCESS   read-only
    STATUS       current
    DESCRIPTION
        "Cisco UCS storage:LocalLun:model managed object property"
    ::= { cucsStorageLocalLunEntry 7 }

cucsStorageLocalLunNumberOfBlocks OBJECT-TYPE
    SYNTAX       Unsigned64
    MAX-ACCESS   read-only
    STATUS       current
    DESCRIPTION
        "Cisco UCS storage:LocalLun:numberOfBlocks managed
        object property"
    ::= { cucsStorageLocalLunEntry 8 }

cucsStorageLocalLunOperability OBJECT-TYPE
    SYNTAX       CucsEquipmentOperability
    MAX-ACCESS   read-only
    STATUS       current
    DESCRIPTION
        "Cisco UCS storage:LocalLun:operability managed object property"
    ::= { cucsStorageLocalLunEntry 9 }

cucsStorageLocalLunPresence OBJECT-TYPE
    SYNTAX       CucsEquipmentPresence
    MAX-ACCESS   read-only
    STATUS       current
    DESCRIPTION
        "Cisco UCS storage:LocalLun:presence managed object property"
    ::= { cucsStorageLocalLunEntry 10 }

cucsStorageLocalLunRevision OBJECT-TYPE
    SYNTAX       SnmpAdminString
    MAX-ACCESS   read-only
    STATUS       current
    DESCRIPTION
        "Cisco UCS storage:LocalLun:revision managed object property"
    ::= { cucsStorageLocalLunEntry 11 }

cucsStorageLocalLunSerial OBJECT-TYPE
    SYNTAX       SnmpAdminString
    MAX-ACCESS   read-only
    STATUS       current
    DESCRIPTION
        "Cisco UCS storage:LocalLun:serial managed object property"
    ::= { cucsStorageLocalLunEntry 12 }

cucsStorageLocalLunSize OBJECT-TYPE
    SYNTAX       Unsigned64
    MAX-ACCESS   read-only
    STATUS       current
    DESCRIPTION
        "Cisco UCS storage:LocalLun:size managed object property"
    ::= { cucsStorageLocalLunEntry 13 }

cucsStorageLocalLunType OBJECT-TYPE
    SYNTAX       CucsStorageLunType
    MAX-ACCESS   read-only
    STATUS       current
    DESCRIPTION
        "Cisco UCS storage:LocalLun:type managed object property"
    ::= { cucsStorageLocalLunEntry 14 }

cucsStorageLocalLunVendor OBJECT-TYPE
    SYNTAX       SnmpAdminString
    MAX-ACCESS   read-only
    STATUS       current
    DESCRIPTION
        "Cisco UCS storage:LocalLun:vendor managed object property"
    ::= { cucsStorageLocalLunEntry 15 }

cucsStorageLocalLunLc OBJECT-TYPE
    SYNTAX       CucsFsmLifecycle
    MAX-ACCESS   read-only
    STATUS       current
    DESCRIPTION
        "Cisco UCS storage:LocalLun:lc managed object property"
    ::= { cucsStorageLocalLunEntry 16 }

cucsStorageLocalLunOperQualifierReason OBJECT-TYPE
    SYNTAX       SnmpAdminString
    MAX-ACCESS   read-only
    STATUS       current
    DESCRIPTION
        "Cisco UCS storage:LocalLun:operQualifierReason
        managed object property"
    ::= { cucsStorageLocalLunEntry 17 }

cucsStorageLocalLunPhysicalBlockSize OBJECT-TYPE
    SYNTAX       Gauge32
    MAX-ACCESS   read-only
    STATUS       current
    DESCRIPTION
        "Cisco UCS storage:LocalLun:physicalBlockSize managed
        object property"
    ::= { cucsStorageLocalLunEntry 18 }

cucsStorageLunDiskTable OBJECT-TYPE
    SYNTAX           SEQUENCE OF CucsStorageLunDiskEntry
    MAX-ACCESS       not-accessible
    STATUS           current
    DESCRIPTION
        "Cisco UCS storage:LunDisk managed object table"
    ::= { cucsStorageObjects 9 }

cucsStorageLunDiskEntry OBJECT-TYPE
    SYNTAX           CucsStorageLunDiskEntry
    MAX-ACCESS       not-accessible
    STATUS           current
    DESCRIPTION
        "Entry for the cucsStorageLunDiskTable table."
    INDEX { cucsStorageLunDiskInstanceId }
    ::= { cucsStorageLunDiskTable 1 }

CucsStorageLunDiskEntry ::= SEQUENCE {
    cucsStorageLunDiskInstanceId                                     CucsManagedObjectId,
    cucsStorageLunDiskDn                                             CucsManagedObjectDn,
    cucsStorageLunDiskRn                                             SnmpAdminString,
    cucsStorageLunDiskId                                             Gauge32
}

cucsStorageLunDiskInstanceId OBJECT-TYPE
    SYNTAX       CucsManagedObjectId
    MAX-ACCESS   not-accessible
    STATUS       current
    DESCRIPTION
        "Instance identifier of the managed object."
    ::= { cucsStorageLunDiskEntry 1 }

cucsStorageLunDiskDn OBJECT-TYPE
    SYNTAX       CucsManagedObjectDn
    MAX-ACCESS   read-only
    STATUS       current
    DESCRIPTION
        "Cisco UCS storage:LunDisk:dn managed object property"
    ::= { cucsStorageLunDiskEntry 2 }

cucsStorageLunDiskRn OBJECT-TYPE
    SYNTAX       SnmpAdminString
    MAX-ACCESS   read-only
    STATUS       current
    DESCRIPTION
        "Cisco UCS storage:LunDisk:rn managed object property"
    ::= { cucsStorageLunDiskEntry 3 }

cucsStorageLunDiskId OBJECT-TYPE
    SYNTAX       Gauge32
    MAX-ACCESS   read-only
    STATUS       current
    DESCRIPTION
        "Cisco UCS storage:LunDisk:id managed object property"
    ::= { cucsStorageLunDiskEntry 4 }

cucsStorageLunResourceSelectionLogTable OBJECT-TYPE
    SYNTAX           SEQUENCE OF CucsStorageLunResourceSelectionLogEntry
    MAX-ACCESS       not-accessible
    STATUS           current
    DESCRIPTION
        "Cisco UCS storage:LunResourceSelectionLog managed object table"
    ::= { cucsStorageObjects 64 }

cucsStorageLunResourceSelectionLogEntry OBJECT-TYPE
    SYNTAX           CucsStorageLunResourceSelectionLogEntry
    MAX-ACCESS       not-accessible
    STATUS           current
    DESCRIPTION
        "Entry for the cucsStorageLunResourceSelectionLogTable table."
    INDEX { cucsStorageLunResourceSelectionLogInstanceId }
    ::= { cucsStorageLunResourceSelectionLogTable 1 }

CucsStorageLunResourceSelectionLogEntry ::= SEQUENCE {
    cucsStorageLunResourceSelectionLogInstanceId                     CucsManagedObjectId,
    cucsStorageLunResourceSelectionLogDn                             CucsManagedObjectDn,
    cucsStorageLunResourceSelectionLogRn                             SnmpAdminString,
    cucsStorageLunResourceSelectionLogDecisionType                   CucsStorageSelectionDecisionType,
    cucsStorageLunResourceSelectionLogDescr                          SnmpAdminString,
    cucsStorageLunResourceSelectionLogOrder                          Gauge32,
    cucsStorageLunResourceSelectionLogResult                         CucsStorageSelectionResultType,
    cucsStorageLunResourceSelectionLogTimeStamp                      DateAndTime
}

cucsStorageLunResourceSelectionLogInstanceId OBJECT-TYPE
    SYNTAX       CucsManagedObjectId
    MAX-ACCESS   not-accessible
    STATUS       current
    DESCRIPTION
        "Instance identifier of the managed object."
    ::= { cucsStorageLunResourceSelectionLogEntry 1 }

cucsStorageLunResourceSelectionLogDn OBJECT-TYPE
    SYNTAX       CucsManagedObjectDn
    MAX-ACCESS   read-only
    STATUS       current
    DESCRIPTION
        "Cisco UCS storage:LunResourceSelectionLog:dn managed
        object property"
    ::= { cucsStorageLunResourceSelectionLogEntry 2 }

cucsStorageLunResourceSelectionLogRn OBJECT-TYPE
    SYNTAX       SnmpAdminString
    MAX-ACCESS   read-only
    STATUS       current
    DESCRIPTION
        "Cisco UCS storage:LunResourceSelectionLog:rn managed
        object property"
    ::= { cucsStorageLunResourceSelectionLogEntry 3 }

cucsStorageLunResourceSelectionLogDecisionType OBJECT-TYPE
    SYNTAX       CucsStorageSelectionDecisionType
    MAX-ACCESS   read-only
    STATUS       current
    DESCRIPTION
        "Cisco UCS storage:LunResourceSelectionLog:decisionType
        managed object property"
    ::= { cucsStorageLunResourceSelectionLogEntry 4 }

cucsStorageLunResourceSelectionLogDescr OBJECT-TYPE
    SYNTAX       SnmpAdminString
    MAX-ACCESS   read-only
    STATUS       current
    DESCRIPTION
        "Cisco UCS storage:LunResourceSelectionLog:descr
        managed object property"
    ::= { cucsStorageLunResourceSelectionLogEntry 5 }

cucsStorageLunResourceSelectionLogOrder OBJECT-TYPE
    SYNTAX       Gauge32
    MAX-ACCESS   read-only
    STATUS       current
    DESCRIPTION
        "Cisco UCS storage:LunResourceSelectionLog:order
        managed object property"
    ::= { cucsStorageLunResourceSelectionLogEntry 6 }

cucsStorageLunResourceSelectionLogResult OBJECT-TYPE
    SYNTAX       CucsStorageSelectionResultType
    MAX-ACCESS   read-only
    STATUS       current
    DESCRIPTION
        "Cisco UCS storage:LunResourceSelectionLog:result
        managed object property"
    ::= { cucsStorageLunResourceSelectionLogEntry 7 }

cucsStorageLunResourceSelectionLogTimeStamp OBJECT-TYPE
    SYNTAX       DateAndTime
    MAX-ACCESS   read-only
    STATUS       current
    DESCRIPTION
        "Cisco UCS storage:LunResourceSelectionLog:timeStamp
        managed object property"
    ::= { cucsStorageLunResourceSelectionLogEntry 8 }

cucsStorageMezzFlashLifeTable OBJECT-TYPE
    SYNTAX           SEQUENCE OF CucsStorageMezzFlashLifeEntry
    MAX-ACCESS       not-accessible
    STATUS           current
    DESCRIPTION
        "Cisco UCS storage:MezzFlashLife managed object table"
    ::= { cucsStorageObjects 39 }

cucsStorageMezzFlashLifeEntry OBJECT-TYPE
    SYNTAX           CucsStorageMezzFlashLifeEntry
    MAX-ACCESS       not-accessible
    STATUS           current
    DESCRIPTION
        "Entry for the cucsStorageMezzFlashLifeTable table."
    INDEX { cucsStorageMezzFlashLifeInstanceId }
    ::= { cucsStorageMezzFlashLifeTable 1 }

CucsStorageMezzFlashLifeEntry ::= SEQUENCE {
    cucsStorageMezzFlashLifeInstanceId                               CucsManagedObjectId,
    cucsStorageMezzFlashLifeDn                                       CucsManagedObjectDn,
    cucsStorageMezzFlashLifeRn                                       SnmpAdminString,
    cucsStorageMezzFlashLifeBlockSize                                Gauge32,
    cucsStorageMezzFlashLifeConnectionProtocol                       CucsStorageConnectionProtocol,
    cucsStorageMezzFlashLifeFlashPercentage                          SnmpAdminString,
    cucsStorageMezzFlashLifeFlashStatus                              SnmpAdminString,
    cucsStorageMezzFlashLifeId                                       Gauge32,
    cucsStorageMezzFlashLifeModel                                    SnmpAdminString,
    cucsStorageMezzFlashLifeNumberOfBlocks                           Unsigned64,
    cucsStorageMezzFlashLifeOperQualifierReason                      SnmpAdminString,
    cucsStorageMezzFlashLifeOperability                              CucsEquipmentOperability,
    cucsStorageMezzFlashLifePresence                                 CucsEquipmentPresence,
    cucsStorageMezzFlashLifeRevision                                 SnmpAdminString,
    cucsStorageMezzFlashLifeSerial                                   SnmpAdminString,
    cucsStorageMezzFlashLifeSize                                     Unsigned64,
    cucsStorageMezzFlashLifeVendor                                   SnmpAdminString,
    cucsStorageMezzFlashLifePhysicalBlockSize                        Gauge32
}

cucsStorageMezzFlashLifeInstanceId OBJECT-TYPE
    SYNTAX       CucsManagedObjectId
    MAX-ACCESS   not-accessible
    STATUS       current
    DESCRIPTION
        "Instance identifier of the managed object."
    ::= { cucsStorageMezzFlashLifeEntry 1 }

cucsStorageMezzFlashLifeDn OBJECT-TYPE
    SYNTAX       CucsManagedObjectDn
    MAX-ACCESS   read-only
    STATUS       current
    DESCRIPTION
        "Cisco UCS storage:MezzFlashLife:dn managed object property"
    ::= { cucsStorageMezzFlashLifeEntry 2 }

cucsStorageMezzFlashLifeRn OBJECT-TYPE
    SYNTAX       SnmpAdminString
    MAX-ACCESS   read-only
    STATUS       current
    DESCRIPTION
        "Cisco UCS storage:MezzFlashLife:rn managed object property"
    ::= { cucsStorageMezzFlashLifeEntry 3 }

cucsStorageMezzFlashLifeBlockSize OBJECT-TYPE
    SYNTAX       Gauge32
    MAX-ACCESS   read-only
    STATUS       current
    DESCRIPTION
        "Cisco UCS storage:MezzFlashLife:blockSize managed
        object property"
    ::= { cucsStorageMezzFlashLifeEntry 4 }

cucsStorageMezzFlashLifeConnectionProtocol OBJECT-TYPE
    SYNTAX       CucsStorageConnectionProtocol
    MAX-ACCESS   read-only
    STATUS       current
    DESCRIPTION
        "Cisco UCS storage:MezzFlashLife:connectionProtocol
        managed object property"
    ::= { cucsStorageMezzFlashLifeEntry 5 }

cucsStorageMezzFlashLifeFlashPercentage OBJECT-TYPE
    SYNTAX       SnmpAdminString
    MAX-ACCESS   read-only
    STATUS       current
    DESCRIPTION
        "Cisco UCS storage:MezzFlashLife:flashPercentage
        managed object property"
    ::= { cucsStorageMezzFlashLifeEntry 6 }

cucsStorageMezzFlashLifeFlashStatus OBJECT-TYPE
    SYNTAX       SnmpAdminString
    MAX-ACCESS   read-only
    STATUS       current
    DESCRIPTION
        "Cisco UCS storage:MezzFlashLife:flashStatus managed
        object property"
    ::= { cucsStorageMezzFlashLifeEntry 7 }

cucsStorageMezzFlashLifeId OBJECT-TYPE
    SYNTAX       Gauge32
    MAX-ACCESS   read-only
    STATUS       current
    DESCRIPTION
        "Cisco UCS storage:MezzFlashLife:id managed object property"
    ::= { cucsStorageMezzFlashLifeEntry 8 }

cucsStorageMezzFlashLifeModel OBJECT-TYPE
    SYNTAX       SnmpAdminString
    MAX-ACCESS   read-only
    STATUS       current
    DESCRIPTION
        "Cisco UCS storage:MezzFlashLife:model managed object property"
    ::= { cucsStorageMezzFlashLifeEntry 9 }

cucsStorageMezzFlashLifeNumberOfBlocks OBJECT-TYPE
    SYNTAX       Unsigned64
    MAX-ACCESS   read-only
    STATUS       current
    DESCRIPTION
        "Cisco UCS storage:MezzFlashLife:numberOfBlocks
        managed object property"
    ::= { cucsStorageMezzFlashLifeEntry 10 }

cucsStorageMezzFlashLifeOperQualifierReason OBJECT-TYPE
    SYNTAX       SnmpAdminString
    MAX-ACCESS   read-only
    STATUS       current
    DESCRIPTION
        "Cisco UCS storage:MezzFlashLife:operQualifierReason
        managed object property"
    ::= { cucsStorageMezzFlashLifeEntry 11 }

cucsStorageMezzFlashLifeOperability OBJECT-TYPE
    SYNTAX       CucsEquipmentOperability
    MAX-ACCESS   read-only
    STATUS       current
    DESCRIPTION
        "Cisco UCS storage:MezzFlashLife:operability managed
        object property"
    ::= { cucsStorageMezzFlashLifeEntry 12 }

cucsStorageMezzFlashLifePresence OBJECT-TYPE
    SYNTAX       CucsEquipmentPresence
    MAX-ACCESS   read-only
    STATUS       current
    DESCRIPTION
        "Cisco UCS storage:MezzFlashLife:presence managed object property"
    ::= { cucsStorageMezzFlashLifeEntry 13 }

cucsStorageMezzFlashLifeRevision OBJECT-TYPE
    SYNTAX       SnmpAdminString
    MAX-ACCESS   read-only
    STATUS       current
    DESCRIPTION
        "Cisco UCS storage:MezzFlashLife:revision managed object property"
    ::= { cucsStorageMezzFlashLifeEntry 14 }

cucsStorageMezzFlashLifeSerial OBJECT-TYPE
    SYNTAX       SnmpAdminString
    MAX-ACCESS   read-only
    STATUS       current
    DESCRIPTION
        "Cisco UCS storage:MezzFlashLife:serial managed object property"
    ::= { cucsStorageMezzFlashLifeEntry 15 }

cucsStorageMezzFlashLifeSize OBJECT-TYPE
    SYNTAX       Unsigned64
    MAX-ACCESS   read-only
    STATUS       current
    DESCRIPTION
        "Cisco UCS storage:MezzFlashLife:size managed object property"
    ::= { cucsStorageMezzFlashLifeEntry 16 }

cucsStorageMezzFlashLifeVendor OBJECT-TYPE
    SYNTAX       SnmpAdminString
    MAX-ACCESS   read-only
    STATUS       current
    DESCRIPTION
        "Cisco UCS storage:MezzFlashLife:vendor managed object property"
    ::= { cucsStorageMezzFlashLifeEntry 17 }

cucsStorageMezzFlashLifePhysicalBlockSize OBJECT-TYPE
    SYNTAX       Gauge32
    MAX-ACCESS   read-only
    STATUS       current
    DESCRIPTION
        "Cisco UCS storage:MezzFlashLife:physicalBlockSize
        managed object property"
    ::= { cucsStorageMezzFlashLifeEntry 18 }

cucsStorageMiniStorageTable OBJECT-TYPE
    SYNTAX           SEQUENCE OF CucsStorageMiniStorageEntry
    MAX-ACCESS       not-accessible
    STATUS           current
    DESCRIPTION
        "Cisco UCS storage:MiniStorage managed object table"
    ::= { cucsStorageObjects 130 }

cucsStorageMiniStorageEntry OBJECT-TYPE
    SYNTAX           CucsStorageMiniStorageEntry
    MAX-ACCESS       not-accessible
    STATUS           current
    DESCRIPTION
        "Entry for the cucsStorageMiniStorageTable table."
    INDEX { cucsStorageMiniStorageInstanceId }
    ::= { cucsStorageMiniStorageTable 1 }

CucsStorageMiniStorageEntry ::= SEQUENCE {
    cucsStorageMiniStorageInstanceId                                 CucsManagedObjectId,
    cucsStorageMiniStorageDn                                         CucsManagedObjectDn,
    cucsStorageMiniStorageRn                                         SnmpAdminString,
    cucsStorageMiniStorageAssetTag                                   SnmpAdminString,
    cucsStorageMiniStorageId                                         CucsStorageMiniStorageId,
    cucsStorageMiniStorageLocationDn                                 SnmpAdminString,
    cucsStorageMiniStorageModel                                      SnmpAdminString,
    cucsStorageMiniStorageOperQualifierReason                        SnmpAdminString,
    cucsStorageMiniStorageOperState                                  CucsEquipmentOperability,
    cucsStorageMiniStorageOperability                                CucsEquipmentOperability,
    cucsStorageMiniStoragePartNumber                                 SnmpAdminString,
    cucsStorageMiniStoragePciAddr                                    SnmpAdminString,
    cucsStorageMiniStoragePciSlot                                    SnmpAdminString,
    cucsStorageMiniStoragePerf                                       CucsEquipmentSensorThresholdStatus,
    cucsStorageMiniStoragePower                                      CucsEquipmentPowerState,
    cucsStorageMiniStoragePresence                                   CucsEquipmentPresence,
    cucsStorageMiniStorageRevision                                   SnmpAdminString,
    cucsStorageMiniStorageSerial                                     SnmpAdminString,
    cucsStorageMiniStorageSubType                                    CucsStorageControllerSubType,
    cucsStorageMiniStorageThermal                                    CucsEquipmentSensorThresholdStatus,
    cucsStorageMiniStorageType                                       CucsStorageControllerType,
    cucsStorageMiniStorageVendor                                     SnmpAdminString,
    cucsStorageMiniStorageVid                                        SnmpAdminString,
    cucsStorageMiniStorageVoltage                                    CucsEquipmentSensorThresholdStatus
}

cucsStorageMiniStorageInstanceId OBJECT-TYPE
    SYNTAX       CucsManagedObjectId
    MAX-ACCESS   not-accessible
    STATUS       current
    DESCRIPTION
        "Instance identifier of the managed object."
    ::= { cucsStorageMiniStorageEntry 1 }

cucsStorageMiniStorageDn OBJECT-TYPE
    SYNTAX       CucsManagedObjectDn
    MAX-ACCESS   read-only
    STATUS       current
    DESCRIPTION
        "Cisco UCS storage:MiniStorage:dn managed object property"
    ::= { cucsStorageMiniStorageEntry 2 }

cucsStorageMiniStorageRn OBJECT-TYPE
    SYNTAX       SnmpAdminString
    MAX-ACCESS   read-only
    STATUS       current
    DESCRIPTION
        "Cisco UCS storage:MiniStorage:rn managed object property"
    ::= { cucsStorageMiniStorageEntry 3 }

cucsStorageMiniStorageAssetTag OBJECT-TYPE
    SYNTAX       SnmpAdminString
    MAX-ACCESS   read-only
    STATUS       current
    DESCRIPTION
        "Cisco UCS storage:MiniStorage:assetTag managed object property"
    ::= { cucsStorageMiniStorageEntry 4 }

cucsStorageMiniStorageId OBJECT-TYPE
    SYNTAX       CucsStorageMiniStorageId
    MAX-ACCESS   read-only
    STATUS       current
    DESCRIPTION
        "Cisco UCS storage:MiniStorage:id managed object property"
    ::= { cucsStorageMiniStorageEntry 5 }

cucsStorageMiniStorageLocationDn OBJECT-TYPE
    SYNTAX       SnmpAdminString
    MAX-ACCESS   read-only
    STATUS       current
    DESCRIPTION
        "Cisco UCS storage:MiniStorage:locationDn managed object property"
    ::= { cucsStorageMiniStorageEntry 6 }

cucsStorageMiniStorageModel OBJECT-TYPE
    SYNTAX       SnmpAdminString
    MAX-ACCESS   read-only
    STATUS       current
    DESCRIPTION
        "Cisco UCS storage:MiniStorage:model managed object property"
    ::= { cucsStorageMiniStorageEntry 7 }

cucsStorageMiniStorageOperQualifierReason OBJECT-TYPE
    SYNTAX       SnmpAdminString
    MAX-ACCESS   read-only
    STATUS       current
    DESCRIPTION
        "Cisco UCS storage:MiniStorage:operQualifierReason
        managed object property"
    ::= { cucsStorageMiniStorageEntry 8 }

cucsStorageMiniStorageOperState OBJECT-TYPE
    SYNTAX       CucsEquipmentOperability
    MAX-ACCESS   read-only
    STATUS       current
    DESCRIPTION
        "Cisco UCS storage:MiniStorage:operState managed object property"
    ::= { cucsStorageMiniStorageEntry 9 }

cucsStorageMiniStorageOperability OBJECT-TYPE
    SYNTAX       CucsEquipmentOperability
    MAX-ACCESS   read-only
    STATUS       current
    DESCRIPTION
        "Cisco UCS storage:MiniStorage:operability managed
        object property"
    ::= { cucsStorageMiniStorageEntry 10 }

cucsStorageMiniStoragePartNumber OBJECT-TYPE
    SYNTAX       SnmpAdminString
    MAX-ACCESS   read-only
    STATUS       current
    DESCRIPTION
        "Cisco UCS storage:MiniStorage:partNumber managed object property"
    ::= { cucsStorageMiniStorageEntry 11 }

cucsStorageMiniStoragePciAddr OBJECT-TYPE
    SYNTAX       SnmpAdminString
    MAX-ACCESS   read-only
    STATUS       current
    DESCRIPTION
        "Cisco UCS storage:MiniStorage:pciAddr managed object property"
    ::= { cucsStorageMiniStorageEntry 12 }

cucsStorageMiniStoragePciSlot OBJECT-TYPE
    SYNTAX       SnmpAdminString
    MAX-ACCESS   read-only
    STATUS       current
    DESCRIPTION
        "Cisco UCS storage:MiniStorage:pciSlot managed object property"
    ::= { cucsStorageMiniStorageEntry 13 }

cucsStorageMiniStoragePerf OBJECT-TYPE
    SYNTAX       CucsEquipmentSensorThresholdStatus
    MAX-ACCESS   read-only
    STATUS       current
    DESCRIPTION
        "Cisco UCS storage:MiniStorage:perf managed object property"
    ::= { cucsStorageMiniStorageEntry 14 }

cucsStorageMiniStoragePower OBJECT-TYPE
    SYNTAX       CucsEquipmentPowerState
    MAX-ACCESS   read-only
    STATUS       current
    DESCRIPTION
        "Cisco UCS storage:MiniStorage:power managed object property"
    ::= { cucsStorageMiniStorageEntry 15 }

cucsStorageMiniStoragePresence OBJECT-TYPE
    SYNTAX       CucsEquipmentPresence
    MAX-ACCESS   read-only
    STATUS       current
    DESCRIPTION
        "Cisco UCS storage:MiniStorage:presence managed object property"
    ::= { cucsStorageMiniStorageEntry 16 }

cucsStorageMiniStorageRevision OBJECT-TYPE
    SYNTAX       SnmpAdminString
    MAX-ACCESS   read-only
    STATUS       current
    DESCRIPTION
        "Cisco UCS storage:MiniStorage:revision managed object property"
    ::= { cucsStorageMiniStorageEntry 17 }

cucsStorageMiniStorageSerial OBJECT-TYPE
    SYNTAX       SnmpAdminString
    MAX-ACCESS   read-only
    STATUS       current
    DESCRIPTION
        "Cisco UCS storage:MiniStorage:serial managed object property"
    ::= { cucsStorageMiniStorageEntry 18 }

cucsStorageMiniStorageSubType OBJECT-TYPE
    SYNTAX       CucsStorageControllerSubType
    MAX-ACCESS   read-only
    STATUS       current
    DESCRIPTION
        "Cisco UCS storage:MiniStorage:subType managed object property"
    ::= { cucsStorageMiniStorageEntry 19 }

cucsStorageMiniStorageThermal OBJECT-TYPE
    SYNTAX       CucsEquipmentSensorThresholdStatus
    MAX-ACCESS   read-only
    STATUS       current
    DESCRIPTION
        "Cisco UCS storage:MiniStorage:thermal managed object property"
    ::= { cucsStorageMiniStorageEntry 20 }

cucsStorageMiniStorageType OBJECT-TYPE
    SYNTAX       CucsStorageControllerType
    MAX-ACCESS   read-only
    STATUS       current
    DESCRIPTION
        "Cisco UCS storage:MiniStorage:type managed object property"
    ::= { cucsStorageMiniStorageEntry 21 }

cucsStorageMiniStorageVendor OBJECT-TYPE
    SYNTAX       SnmpAdminString
    MAX-ACCESS   read-only
    STATUS       current
    DESCRIPTION
        "Cisco UCS storage:MiniStorage:vendor managed object property"
    ::= { cucsStorageMiniStorageEntry 22 }

cucsStorageMiniStorageVid OBJECT-TYPE
    SYNTAX       SnmpAdminString
    MAX-ACCESS   read-only
    STATUS       current
    DESCRIPTION
        "Cisco UCS storage:MiniStorage:vid managed object property"
    ::= { cucsStorageMiniStorageEntry 23 }

cucsStorageMiniStorageVoltage OBJECT-TYPE
    SYNTAX       CucsEquipmentSensorThresholdStatus
    MAX-ACCESS   read-only
    STATUS       current
    DESCRIPTION
        "Cisco UCS storage:MiniStorage:voltage managed object property"
    ::= { cucsStorageMiniStorageEntry 24 }

cucsStorageNodeEpTable OBJECT-TYPE
    SYNTAX           SEQUENCE OF CucsStorageNodeEpEntry
    MAX-ACCESS       not-accessible
    STATUS           current
    DESCRIPTION
        "Cisco UCS storage:NodeEp managed object table"
    ::= { cucsStorageObjects 26 }

cucsStorageNodeEpEntry OBJECT-TYPE
    SYNTAX           CucsStorageNodeEpEntry
    MAX-ACCESS       not-accessible
    STATUS           current
    DESCRIPTION
        "Entry for the cucsStorageNodeEpTable table."
    INDEX { cucsStorageNodeEpInstanceId }
    ::= { cucsStorageNodeEpTable 1 }

CucsStorageNodeEpEntry ::= SEQUENCE {
    cucsStorageNodeEpInstanceId                                      CucsManagedObjectId,
    cucsStorageNodeEpDn                                              CucsManagedObjectDn,
    cucsStorageNodeEpRn                                              SnmpAdminString,
    cucsStorageNodeEpEpDn                                            SnmpAdminString,
    cucsStorageNodeEpId                                              Gauge32
}

cucsStorageNodeEpInstanceId OBJECT-TYPE
    SYNTAX       CucsManagedObjectId
    MAX-ACCESS   not-accessible
    STATUS       current
    DESCRIPTION
        "Instance identifier of the managed object."
    ::= { cucsStorageNodeEpEntry 1 }

cucsStorageNodeEpDn OBJECT-TYPE
    SYNTAX       CucsManagedObjectDn
    MAX-ACCESS   read-only
    STATUS       current
    DESCRIPTION
        "Cisco UCS storage:NodeEp:dn managed object property"
    ::= { cucsStorageNodeEpEntry 2 }

cucsStorageNodeEpRn OBJECT-TYPE
    SYNTAX       SnmpAdminString
    MAX-ACCESS   read-only
    STATUS       current
    DESCRIPTION
        "Cisco UCS storage:NodeEp:rn managed object property"
    ::= { cucsStorageNodeEpEntry 3 }

cucsStorageNodeEpEpDn OBJECT-TYPE
    SYNTAX       SnmpAdminString
    MAX-ACCESS   read-only
    STATUS       current
    DESCRIPTION
        "Cisco UCS storage:NodeEp:epDn managed object property"
    ::= { cucsStorageNodeEpEntry 4 }

cucsStorageNodeEpId OBJECT-TYPE
    SYNTAX       Gauge32
    MAX-ACCESS   read-only
    STATUS       current
    DESCRIPTION
        "Cisco UCS storage:NodeEp:id managed object property"
    ::= { cucsStorageNodeEpEntry 5 }

cucsStorageNvmeStatsTable OBJECT-TYPE
    SYNTAX           SEQUENCE OF CucsStorageNvmeStatsEntry
    MAX-ACCESS       not-accessible
    STATUS           current
    DESCRIPTION
        "Cisco UCS storage:NvmeStats managed object table"
    ::= { cucsStorageObjects 122 }

cucsStorageNvmeStatsEntry OBJECT-TYPE
    SYNTAX           CucsStorageNvmeStatsEntry
    MAX-ACCESS       not-accessible
    STATUS           current
    DESCRIPTION
        "Entry for the cucsStorageNvmeStatsTable table."
    INDEX { cucsStorageNvmeStatsInstanceId }
    ::= { cucsStorageNvmeStatsTable 1 }

CucsStorageNvmeStatsEntry ::= SEQUENCE {
    cucsStorageNvmeStatsInstanceId                                   CucsManagedObjectId,
    cucsStorageNvmeStatsDn                                           CucsManagedObjectDn,
    cucsStorageNvmeStatsRn                                           SnmpAdminString,
    cucsStorageNvmeStatsDriveLifeUsedPercentage                      Gauge32,
    cucsStorageNvmeStatsDriveLifeUsedPercentageAvg                   Gauge32,
    cucsStorageNvmeStatsDriveLifeUsedPercentageMax                   Gauge32,
    cucsStorageNvmeStatsDriveLifeUsedPercentageMin                   Gauge32,
    cucsStorageNvmeStatsIntervals                                    Gauge32,
    cucsStorageNvmeStatsSuspect                                      TruthValue,
    cucsStorageNvmeStatsTemperature                                  SnmpAdminString,
    cucsStorageNvmeStatsTemperatureAvg                               SnmpAdminString,
    cucsStorageNvmeStatsTemperatureMax                               SnmpAdminString,
    cucsStorageNvmeStatsTemperatureMin                               SnmpAdminString,
    cucsStorageNvmeStatsThresholded                                  CucsStorageNvmeStatsThresholded,
    cucsStorageNvmeStatsTimeCollected                                DateAndTime,
    cucsStorageNvmeStatsUpdate                                       Gauge32
}

cucsStorageNvmeStatsInstanceId OBJECT-TYPE
    SYNTAX       CucsManagedObjectId
    MAX-ACCESS   not-accessible
    STATUS       current
    DESCRIPTION
        "Instance identifier of the managed object."
    ::= { cucsStorageNvmeStatsEntry 1 }

cucsStorageNvmeStatsDn OBJECT-TYPE
    SYNTAX       CucsManagedObjectDn
    MAX-ACCESS   read-only
    STATUS       current
    DESCRIPTION
        "Cisco UCS storage:NvmeStats:dn managed object property"
    ::= { cucsStorageNvmeStatsEntry 2 }

cucsStorageNvmeStatsRn OBJECT-TYPE
    SYNTAX       SnmpAdminString
    MAX-ACCESS   read-only
    STATUS       current
    DESCRIPTION
        "Cisco UCS storage:NvmeStats:rn managed object property"
    ::= { cucsStorageNvmeStatsEntry 3 }

cucsStorageNvmeStatsDriveLifeUsedPercentage OBJECT-TYPE
    SYNTAX       Gauge32
    MAX-ACCESS   read-only
    STATUS       current
    DESCRIPTION
        "Cisco UCS storage:NvmeStats:driveLifeUsedPercentage
        managed object property"
    ::= { cucsStorageNvmeStatsEntry 4 }

cucsStorageNvmeStatsDriveLifeUsedPercentageAvg OBJECT-TYPE
    SYNTAX       Gauge32
    MAX-ACCESS   read-only
    STATUS       current
    DESCRIPTION
        "Cisco UCS storage:NvmeStats:driveLifeUsedPercentageAvg
        managed object property"
    ::= { cucsStorageNvmeStatsEntry 5 }

cucsStorageNvmeStatsDriveLifeUsedPercentageMax OBJECT-TYPE
    SYNTAX       Gauge32
    MAX-ACCESS   read-only
    STATUS       current
    DESCRIPTION
        "Cisco UCS storage:NvmeStats:driveLifeUsedPercentageMax
        managed object property"
    ::= { cucsStorageNvmeStatsEntry 6 }

cucsStorageNvmeStatsDriveLifeUsedPercentageMin OBJECT-TYPE
    SYNTAX       Gauge32
    MAX-ACCESS   read-only
    STATUS       current
    DESCRIPTION
        "Cisco UCS storage:NvmeStats:driveLifeUsedPercentageMin
        managed object property"
    ::= { cucsStorageNvmeStatsEntry 7 }

cucsStorageNvmeStatsIntervals OBJECT-TYPE
    SYNTAX       Gauge32
    MAX-ACCESS   read-only
    STATUS       current
    DESCRIPTION
        "Cisco UCS storage:NvmeStats:intervals managed object property"
    ::= { cucsStorageNvmeStatsEntry 8 }

cucsStorageNvmeStatsSuspect OBJECT-TYPE
    SYNTAX       TruthValue
    MAX-ACCESS   read-only
    STATUS       current
    DESCRIPTION
        "Cisco UCS storage:NvmeStats:suspect managed object property"
    ::= { cucsStorageNvmeStatsEntry 9 }

cucsStorageNvmeStatsTemperature OBJECT-TYPE
    SYNTAX       SnmpAdminString
    MAX-ACCESS   read-only
    STATUS       current
    DESCRIPTION
        "Cisco UCS storage:NvmeStats:temperature managed object property"
    ::= { cucsStorageNvmeStatsEntry 10 }

cucsStorageNvmeStatsTemperatureAvg OBJECT-TYPE
    SYNTAX       SnmpAdminString
    MAX-ACCESS   read-only
    STATUS       current
    DESCRIPTION
        "Cisco UCS storage:NvmeStats:temperatureAvg managed
        object property"
    ::= { cucsStorageNvmeStatsEntry 11 }

cucsStorageNvmeStatsTemperatureMax OBJECT-TYPE
    SYNTAX       SnmpAdminString
    MAX-ACCESS   read-only
    STATUS       current
    DESCRIPTION
        "Cisco UCS storage:NvmeStats:temperatureMax managed
        object property"
    ::= { cucsStorageNvmeStatsEntry 12 }

cucsStorageNvmeStatsTemperatureMin OBJECT-TYPE
    SYNTAX       SnmpAdminString
    MAX-ACCESS   read-only
    STATUS       current
    DESCRIPTION
        "Cisco UCS storage:NvmeStats:temperatureMin managed
        object property"
    ::= { cucsStorageNvmeStatsEntry 13 }

cucsStorageNvmeStatsThresholded OBJECT-TYPE
    SYNTAX       CucsStorageNvmeStatsThresholded
    MAX-ACCESS   read-only
    STATUS       current
    DESCRIPTION
        "Cisco UCS storage:NvmeStats:thresholded managed object property"
    ::= { cucsStorageNvmeStatsEntry 14 }

cucsStorageNvmeStatsTimeCollected OBJECT-TYPE
    SYNTAX       DateAndTime
    MAX-ACCESS   read-only
    STATUS       current
    DESCRIPTION
        "Cisco UCS storage:NvmeStats:timeCollected managed
        object property"
    ::= { cucsStorageNvmeStatsEntry 15 }

cucsStorageNvmeStatsUpdate OBJECT-TYPE
    SYNTAX       Gauge32
    MAX-ACCESS   read-only
    STATUS       current
    DESCRIPTION
        "Cisco UCS storage:NvmeStats:update managed object property"
    ::= { cucsStorageNvmeStatsEntry 16 }

cucsStorageNvmeStatsHistTable OBJECT-TYPE
    SYNTAX           SEQUENCE OF CucsStorageNvmeStatsHistEntry
    MAX-ACCESS       not-accessible
    STATUS           current
    DESCRIPTION
        "Cisco UCS storage:NvmeStatsHist managed object table"
    ::= { cucsStorageObjects 123 }

cucsStorageNvmeStatsHistEntry OBJECT-TYPE
    SYNTAX           CucsStorageNvmeStatsHistEntry
    MAX-ACCESS       not-accessible
    STATUS           current
    DESCRIPTION
        "Entry for the cucsStorageNvmeStatsHistTable table."
    INDEX { cucsStorageNvmeStatsHistInstanceId }
    ::= { cucsStorageNvmeStatsHistTable 1 }

CucsStorageNvmeStatsHistEntry ::= SEQUENCE {
    cucsStorageNvmeStatsHistInstanceId                               CucsManagedObjectId,
    cucsStorageNvmeStatsHistDn                                       CucsManagedObjectDn,
    cucsStorageNvmeStatsHistRn                                       SnmpAdminString,
    cucsStorageNvmeStatsHistDriveLifeUsedPercentage                  Gauge32,
    cucsStorageNvmeStatsHistDriveLifeUsedPercentageAvg               Gauge32,
    cucsStorageNvmeStatsHistDriveLifeUsedPercentageMax               Gauge32,
    cucsStorageNvmeStatsHistDriveLifeUsedPercentageMin               Gauge32,
    cucsStorageNvmeStatsHistId                                       Unsigned64,
    cucsStorageNvmeStatsHistMostRecent                               TruthValue,
    cucsStorageNvmeStatsHistSuspect                                  TruthValue,
    cucsStorageNvmeStatsHistTemperature                              SnmpAdminString,
    cucsStorageNvmeStatsHistTemperatureAvg                           SnmpAdminString,
    cucsStorageNvmeStatsHistTemperatureMax                           SnmpAdminString,
    cucsStorageNvmeStatsHistTemperatureMin                           SnmpAdminString,
    cucsStorageNvmeStatsHistThresholded                              CucsStorageNvmeStatsHistThresholded,
    cucsStorageNvmeStatsHistTimeCollected                            DateAndTime
}

cucsStorageNvmeStatsHistInstanceId OBJECT-TYPE
    SYNTAX       CucsManagedObjectId
    MAX-ACCESS   not-accessible
    STATUS       current
    DESCRIPTION
        "Instance identifier of the managed object."
    ::= { cucsStorageNvmeStatsHistEntry 1 }

cucsStorageNvmeStatsHistDn OBJECT-TYPE
    SYNTAX       CucsManagedObjectDn
    MAX-ACCESS   read-only
    STATUS       current
    DESCRIPTION
        "Cisco UCS storage:NvmeStatsHist:dn managed object property"
    ::= { cucsStorageNvmeStatsHistEntry 2 }

cucsStorageNvmeStatsHistRn OBJECT-TYPE
    SYNTAX       SnmpAdminString
    MAX-ACCESS   read-only
    STATUS       current
    DESCRIPTION
        "Cisco UCS storage:NvmeStatsHist:rn managed object property"
    ::= { cucsStorageNvmeStatsHistEntry 3 }

cucsStorageNvmeStatsHistDriveLifeUsedPercentage OBJECT-TYPE
    SYNTAX       Gauge32
    MAX-ACCESS   read-only
    STATUS       current
    DESCRIPTION
        "Cisco UCS storage:NvmeStatsHist:driveLifeUsedPercentage
        managed object property"
    ::= { cucsStorageNvmeStatsHistEntry 4 }

cucsStorageNvmeStatsHistDriveLifeUsedPercentageAvg OBJECT-TYPE
    SYNTAX       Gauge32
    MAX-ACCESS   read-only
    STATUS       current
    DESCRIPTION
        "Cisco UCS storage:NvmeStatsHist:driveLifeUsedPercentageAvg
        managed object property"
    ::= { cucsStorageNvmeStatsHistEntry 5 }

cucsStorageNvmeStatsHistDriveLifeUsedPercentageMax OBJECT-TYPE
    SYNTAX       Gauge32
    MAX-ACCESS   read-only
    STATUS       current
    DESCRIPTION
        "Cisco UCS storage:NvmeStatsHist:driveLifeUsedPercentageMax
        managed object property"
    ::= { cucsStorageNvmeStatsHistEntry 6 }

cucsStorageNvmeStatsHistDriveLifeUsedPercentageMin OBJECT-TYPE
    SYNTAX       Gauge32
    MAX-ACCESS   read-only
    STATUS       current
    DESCRIPTION
        "Cisco UCS storage:NvmeStatsHist:driveLifeUsedPercentageMin
        managed object property"
    ::= { cucsStorageNvmeStatsHistEntry 7 }

cucsStorageNvmeStatsHistId OBJECT-TYPE
    SYNTAX       Unsigned64
    MAX-ACCESS   read-only
    STATUS       current
    DESCRIPTION
        "Cisco UCS storage:NvmeStatsHist:id managed object property"
    ::= { cucsStorageNvmeStatsHistEntry 8 }

cucsStorageNvmeStatsHistMostRecent OBJECT-TYPE
    SYNTAX       TruthValue
    MAX-ACCESS   read-only
    STATUS       current
    DESCRIPTION
        "Cisco UCS storage:NvmeStatsHist:mostRecent managed
        object property"
    ::= { cucsStorageNvmeStatsHistEntry 9 }

cucsStorageNvmeStatsHistSuspect OBJECT-TYPE
    SYNTAX       TruthValue
    MAX-ACCESS   read-only
    STATUS       current
    DESCRIPTION
        "Cisco UCS storage:NvmeStatsHist:suspect managed object property"
    ::= { cucsStorageNvmeStatsHistEntry 10 }

cucsStorageNvmeStatsHistTemperature OBJECT-TYPE
    SYNTAX       SnmpAdminString
    MAX-ACCESS   read-only
    STATUS       current
    DESCRIPTION
        "Cisco UCS storage:NvmeStatsHist:temperature managed
        object property"
    ::= { cucsStorageNvmeStatsHistEntry 11 }

cucsStorageNvmeStatsHistTemperatureAvg OBJECT-TYPE
    SYNTAX       SnmpAdminString
    MAX-ACCESS   read-only
    STATUS       current
    DESCRIPTION
        "Cisco UCS storage:NvmeStatsHist:temperatureAvg
        managed object property"
    ::= { cucsStorageNvmeStatsHistEntry 12 }

cucsStorageNvmeStatsHistTemperatureMax OBJECT-TYPE
    SYNTAX       SnmpAdminString
    MAX-ACCESS   read-only
    STATUS       current
    DESCRIPTION
        "Cisco UCS storage:NvmeStatsHist:temperatureMax
        managed object property"
    ::= { cucsStorageNvmeStatsHistEntry 13 }

cucsStorageNvmeStatsHistTemperatureMin OBJECT-TYPE
    SYNTAX       SnmpAdminString
    MAX-ACCESS   read-only
    STATUS       current
    DESCRIPTION
        "Cisco UCS storage:NvmeStatsHist:temperatureMin
        managed object property"
    ::= { cucsStorageNvmeStatsHistEntry 14 }

cucsStorageNvmeStatsHistThresholded OBJECT-TYPE
    SYNTAX       CucsStorageNvmeStatsHistThresholded
    MAX-ACCESS   read-only
    STATUS       current
    DESCRIPTION
        "Cisco UCS storage:NvmeStatsHist:thresholded managed
        object property"
    ::= { cucsStorageNvmeStatsHistEntry 15 }

cucsStorageNvmeStatsHistTimeCollected OBJECT-TYPE
    SYNTAX       DateAndTime
    MAX-ACCESS   read-only
    STATUS       current
    DESCRIPTION
        "Cisco UCS storage:NvmeStatsHist:timeCollected
        managed object property"
    ::= { cucsStorageNvmeStatsHistEntry 16 }

cucsStorageNvmeStorageTable OBJECT-TYPE
    SYNTAX           SEQUENCE OF CucsStorageNvmeStorageEntry
    MAX-ACCESS       not-accessible
    STATUS           current
    DESCRIPTION
        "Cisco UCS storage:NvmeStorage managed object table"
    ::= { cucsStorageObjects 124 }

cucsStorageNvmeStorageEntry OBJECT-TYPE
    SYNTAX           CucsStorageNvmeStorageEntry
    MAX-ACCESS       not-accessible
    STATUS           current
    DESCRIPTION
        "Entry for the cucsStorageNvmeStorageTable table."
    INDEX { cucsStorageNvmeStorageInstanceId }
    ::= { cucsStorageNvmeStorageTable 1 }

CucsStorageNvmeStorageEntry ::= SEQUENCE {
    cucsStorageNvmeStorageInstanceId                                 CucsManagedObjectId,
    cucsStorageNvmeStorageDn                                         CucsManagedObjectDn,
    cucsStorageNvmeStorageRn                                         SnmpAdminString,
    cucsStorageNvmeStoragePerformanceLevel                           Gauge32
}

cucsStorageNvmeStorageInstanceId OBJECT-TYPE
    SYNTAX       CucsManagedObjectId
    MAX-ACCESS   not-accessible
    STATUS       current
    DESCRIPTION
        "Instance identifier of the managed object."
    ::= { cucsStorageNvmeStorageEntry 1 }

cucsStorageNvmeStorageDn OBJECT-TYPE
    SYNTAX       CucsManagedObjectDn
    MAX-ACCESS   read-only
    STATUS       current
    DESCRIPTION
        "Cisco UCS storage:NvmeStorage:dn managed object property"
    ::= { cucsStorageNvmeStorageEntry 2 }

cucsStorageNvmeStorageRn OBJECT-TYPE
    SYNTAX       SnmpAdminString
    MAX-ACCESS   read-only
    STATUS       current
    DESCRIPTION
        "Cisco UCS storage:NvmeStorage:rn managed object property"
    ::= { cucsStorageNvmeStorageEntry 3 }

cucsStorageNvmeStoragePerformanceLevel OBJECT-TYPE
    SYNTAX       Gauge32
    MAX-ACCESS   read-only
    STATUS       current
    DESCRIPTION
        "Cisco UCS storage:NvmeStorage:performanceLevel
        managed object property"
    ::= { cucsStorageNvmeStorageEntry 4 }

cucsStorageOnboardDeviceTable OBJECT-TYPE
    SYNTAX           SEQUENCE OF CucsStorageOnboardDeviceEntry
    MAX-ACCESS       not-accessible
    STATUS           current
    DESCRIPTION
        "Cisco UCS storage:OnboardDevice managed object table"
    ::= { cucsStorageObjects 108 }

cucsStorageOnboardDeviceEntry OBJECT-TYPE
    SYNTAX           CucsStorageOnboardDeviceEntry
    MAX-ACCESS       not-accessible
    STATUS           current
    DESCRIPTION
        "Entry for the cucsStorageOnboardDeviceTable table."
    INDEX { cucsStorageOnboardDeviceInstanceId }
    ::= { cucsStorageOnboardDeviceTable 1 }

CucsStorageOnboardDeviceEntry ::= SEQUENCE {
    cucsStorageOnboardDeviceInstanceId                               CucsManagedObjectId,
    cucsStorageOnboardDeviceDn                                       CucsManagedObjectDn,
    cucsStorageOnboardDeviceRn                                       SnmpAdminString,
    cucsStorageOnboardDeviceBlockSize                                Gauge32,
    cucsStorageOnboardDeviceConfigCheckPoint                         CucsStorageConfigCheckPoint,
    cucsStorageOnboardDeviceConnectionProtocol                       CucsStorageConnectionProtocol,
    cucsStorageOnboardDeviceDescription                              SnmpAdminString,
    cucsStorageOnboardDeviceDeviceType                               CucsStorageOnboardDeviceType,
    cucsStorageOnboardDeviceId                                       Gauge32,
    cucsStorageOnboardDeviceModel                                    SnmpAdminString,
    cucsStorageOnboardDeviceNumberOfBlocks                           Unsigned64,
    cucsStorageOnboardDeviceOperQualifierReason                      SnmpAdminString,
    cucsStorageOnboardDeviceOperability                              CucsEquipmentOperability,
    cucsStorageOnboardDevicePresence                                 CucsEquipmentPresence,
    cucsStorageOnboardDeviceRevision                                 SnmpAdminString,
    cucsStorageOnboardDeviceSerial                                   SnmpAdminString,
    cucsStorageOnboardDeviceSize                                     Unsigned64,
    cucsStorageOnboardDeviceVendor                                   SnmpAdminString,
    cucsStorageOnboardDevicePhysicalBlockSize                        Gauge32
}

cucsStorageOnboardDeviceInstanceId OBJECT-TYPE
    SYNTAX       CucsManagedObjectId
    MAX-ACCESS   not-accessible
    STATUS       current
    DESCRIPTION
        "Instance identifier of the managed object."
    ::= { cucsStorageOnboardDeviceEntry 1 }

cucsStorageOnboardDeviceDn OBJECT-TYPE
    SYNTAX       CucsManagedObjectDn
    MAX-ACCESS   read-only
    STATUS       current
    DESCRIPTION
        "Cisco UCS storage:OnboardDevice:dn managed object property"
    ::= { cucsStorageOnboardDeviceEntry 2 }

cucsStorageOnboardDeviceRn OBJECT-TYPE
    SYNTAX       SnmpAdminString
    MAX-ACCESS   read-only
    STATUS       current
    DESCRIPTION
        "Cisco UCS storage:OnboardDevice:rn managed object property"
    ::= { cucsStorageOnboardDeviceEntry 3 }

cucsStorageOnboardDeviceBlockSize OBJECT-TYPE
    SYNTAX       Gauge32
    MAX-ACCESS   read-only
    STATUS       current
    DESCRIPTION
        "Cisco UCS storage:OnboardDevice:blockSize managed
        object property"
    ::= { cucsStorageOnboardDeviceEntry 4 }

cucsStorageOnboardDeviceConfigCheckPoint OBJECT-TYPE
    SYNTAX       CucsStorageConfigCheckPoint
    MAX-ACCESS   read-only
    STATUS       current
    DESCRIPTION
        "Cisco UCS storage:OnboardDevice:configCheckPoint
        managed object property"
    ::= { cucsStorageOnboardDeviceEntry 5 }

cucsStorageOnboardDeviceConnectionProtocol OBJECT-TYPE
    SYNTAX       CucsStorageConnectionProtocol
    MAX-ACCESS   read-only
    STATUS       current
    DESCRIPTION
        "Cisco UCS storage:OnboardDevice:connectionProtocol
        managed object property"
    ::= { cucsStorageOnboardDeviceEntry 6 }

cucsStorageOnboardDeviceDescription OBJECT-TYPE
    SYNTAX       SnmpAdminString
    MAX-ACCESS   read-only
    STATUS       current
    DESCRIPTION
        "Cisco UCS storage:OnboardDevice:description managed
        object property"
    ::= { cucsStorageOnboardDeviceEntry 7 }

cucsStorageOnboardDeviceDeviceType OBJECT-TYPE
    SYNTAX       CucsStorageOnboardDeviceType
    MAX-ACCESS   read-only
    STATUS       current
    DESCRIPTION
        "Cisco UCS storage:OnboardDevice:deviceType managed
        object property"
    ::= { cucsStorageOnboardDeviceEntry 8 }

cucsStorageOnboardDeviceId OBJECT-TYPE
    SYNTAX       Gauge32
    MAX-ACCESS   read-only
    STATUS       current
    DESCRIPTION
        "Cisco UCS storage:OnboardDevice:id managed object property"
    ::= { cucsStorageOnboardDeviceEntry 9 }

cucsStorageOnboardDeviceModel OBJECT-TYPE
    SYNTAX       SnmpAdminString
    MAX-ACCESS   read-only
    STATUS       current
    DESCRIPTION
        "Cisco UCS storage:OnboardDevice:model managed object property"
    ::= { cucsStorageOnboardDeviceEntry 10 }

cucsStorageOnboardDeviceNumberOfBlocks OBJECT-TYPE
    SYNTAX       Unsigned64
    MAX-ACCESS   read-only
    STATUS       current
    DESCRIPTION
        "Cisco UCS storage:OnboardDevice:numberOfBlocks
        managed object property"
    ::= { cucsStorageOnboardDeviceEntry 11 }

cucsStorageOnboardDeviceOperQualifierReason OBJECT-TYPE
    SYNTAX       SnmpAdminString
    MAX-ACCESS   read-only
    STATUS       current
    DESCRIPTION
        "Cisco UCS storage:OnboardDevice:operQualifierReason
        managed object property"
    ::= { cucsStorageOnboardDeviceEntry 12 }

cucsStorageOnboardDeviceOperability OBJECT-TYPE
    SYNTAX       CucsEquipmentOperability
    MAX-ACCESS   read-only
    STATUS       current
    DESCRIPTION
        "Cisco UCS storage:OnboardDevice:operability managed
        object property"
    ::= { cucsStorageOnboardDeviceEntry 13 }

cucsStorageOnboardDevicePresence OBJECT-TYPE
    SYNTAX       CucsEquipmentPresence
    MAX-ACCESS   read-only
    STATUS       current
    DESCRIPTION
        "Cisco UCS storage:OnboardDevice:presence managed object property"
    ::= { cucsStorageOnboardDeviceEntry 14 }

cucsStorageOnboardDeviceRevision OBJECT-TYPE
    SYNTAX       SnmpAdminString
    MAX-ACCESS   read-only
    STATUS       current
    DESCRIPTION
        "Cisco UCS storage:OnboardDevice:revision managed object property"
    ::= { cucsStorageOnboardDeviceEntry 15 }

cucsStorageOnboardDeviceSerial OBJECT-TYPE
    SYNTAX       SnmpAdminString
    MAX-ACCESS   read-only
    STATUS       current
    DESCRIPTION
        "Cisco UCS storage:OnboardDevice:serial managed object property"
    ::= { cucsStorageOnboardDeviceEntry 16 }

cucsStorageOnboardDeviceSize OBJECT-TYPE
    SYNTAX       Unsigned64
    MAX-ACCESS   read-only
    STATUS       current
    DESCRIPTION
        "Cisco UCS storage:OnboardDevice:size managed object property"
    ::= { cucsStorageOnboardDeviceEntry 17 }

cucsStorageOnboardDeviceVendor OBJECT-TYPE
    SYNTAX       SnmpAdminString
    MAX-ACCESS   read-only
    STATUS       current
    DESCRIPTION
        "Cisco UCS storage:OnboardDevice:vendor managed object property"
    ::= { cucsStorageOnboardDeviceEntry 18 }

cucsStorageOnboardDevicePhysicalBlockSize OBJECT-TYPE
    SYNTAX       Gauge32
    MAX-ACCESS   read-only
    STATUS       current
    DESCRIPTION
        "Cisco UCS storage:OnboardDevice:physicalBlockSize
        managed object property"
    ::= { cucsStorageOnboardDeviceEntry 19 }

cucsStorageOperationTable OBJECT-TYPE
    SYNTAX           SEQUENCE OF CucsStorageOperationEntry
    MAX-ACCESS       not-accessible
    STATUS           current
    DESCRIPTION
        "Cisco UCS storage:Operation managed object table"
    ::= { cucsStorageObjects 38 }

cucsStorageOperationEntry OBJECT-TYPE
    SYNTAX           CucsStorageOperationEntry
    MAX-ACCESS       not-accessible
    STATUS           current
    DESCRIPTION
        "Entry for the cucsStorageOperationTable table."
    INDEX { cucsStorageOperationInstanceId }
    ::= { cucsStorageOperationTable 1 }

CucsStorageOperationEntry ::= SEQUENCE {
    cucsStorageOperationInstanceId                                   CucsManagedObjectId,
    cucsStorageOperationDn                                           CucsManagedObjectDn,
    cucsStorageOperationRn                                           SnmpAdminString,
    cucsStorageOperationEndTime                                      DateAndTime,
    cucsStorageOperationName                                         CucsStorageOperationType,
    cucsStorageOperationOperState                                    CucsStorageOperationState,
    cucsStorageOperationProgress                                     Gauge32,
    cucsStorageOperationStartTime                                    DateAndTime,
    cucsStorageOperationStatusDescr                                  SnmpAdminString
}

cucsStorageOperationInstanceId OBJECT-TYPE
    SYNTAX       CucsManagedObjectId
    MAX-ACCESS   not-accessible
    STATUS       current
    DESCRIPTION
        "Instance identifier of the managed object."
    ::= { cucsStorageOperationEntry 1 }

cucsStorageOperationDn OBJECT-TYPE
    SYNTAX       CucsManagedObjectDn
    MAX-ACCESS   read-only
    STATUS       current
    DESCRIPTION
        "Cisco UCS storage:Operation:dn managed object property"
    ::= { cucsStorageOperationEntry 2 }

cucsStorageOperationRn OBJECT-TYPE
    SYNTAX       SnmpAdminString
    MAX-ACCESS   read-only
    STATUS       current
    DESCRIPTION
        "Cisco UCS storage:Operation:rn managed object property"
    ::= { cucsStorageOperationEntry 3 }

cucsStorageOperationEndTime OBJECT-TYPE
    SYNTAX       DateAndTime
    MAX-ACCESS   read-only
    STATUS       current
    DESCRIPTION
        "Cisco UCS storage:Operation:endTime managed object property"
    ::= { cucsStorageOperationEntry 4 }

cucsStorageOperationName OBJECT-TYPE
    SYNTAX       CucsStorageOperationType
    MAX-ACCESS   read-only
    STATUS       current
    DESCRIPTION
        "Cisco UCS storage:Operation:name managed object property"
    ::= { cucsStorageOperationEntry 5 }

cucsStorageOperationOperState OBJECT-TYPE
    SYNTAX       CucsStorageOperationState
    MAX-ACCESS   read-only
    STATUS       current
    DESCRIPTION
        "Cisco UCS storage:Operation:operState managed object property"
    ::= { cucsStorageOperationEntry 6 }

cucsStorageOperationProgress OBJECT-TYPE
    SYNTAX       Gauge32
    MAX-ACCESS   read-only
    STATUS       current
    DESCRIPTION
        "Cisco UCS storage:Operation:progress managed object property"
    ::= { cucsStorageOperationEntry 7 }

cucsStorageOperationStartTime OBJECT-TYPE
    SYNTAX       DateAndTime
    MAX-ACCESS   read-only
    STATUS       current
    DESCRIPTION
        "Cisco UCS storage:Operation:startTime managed object property"
    ::= { cucsStorageOperationEntry 8 }

cucsStorageOperationStatusDescr OBJECT-TYPE
    SYNTAX       SnmpAdminString
    MAX-ACCESS   read-only
    STATUS       current
    DESCRIPTION
        "Cisco UCS storage:Operation:statusDescr managed object property"
    ::= { cucsStorageOperationEntry 9 }

cucsStorageQualTable OBJECT-TYPE
    SYNTAX           SEQUENCE OF CucsStorageQualEntry
    MAX-ACCESS       not-accessible
    STATUS           current
    DESCRIPTION
        "Cisco UCS storage:Qual managed object table"
    ::= { cucsStorageObjects 10 }

cucsStorageQualEntry OBJECT-TYPE
    SYNTAX           CucsStorageQualEntry
    MAX-ACCESS       not-accessible
    STATUS           current
    DESCRIPTION
        "Entry for the cucsStorageQualTable table."
    INDEX { cucsStorageQualInstanceId }
    ::= { cucsStorageQualTable 1 }

CucsStorageQualEntry ::= SEQUENCE {
    cucsStorageQualInstanceId                                        CucsManagedObjectId,
    cucsStorageQualDn                                                CucsManagedObjectDn,
    cucsStorageQualRn                                                SnmpAdminString,
    cucsStorageQualBlockSize                                         Gauge32,
    cucsStorageQualMaxCap                                            Unsigned64,
    cucsStorageQualMinCap                                            Unsigned64,
    cucsStorageQualNumberOfBlocks                                    Unsigned64,
    cucsStorageQualPerDiskCap                                        Unsigned64,
    cucsStorageQualUnits                                             Gauge32,
    cucsStorageQualDiskless                                          CucsStorageDisklessAction,
    cucsStorageQualNumberOfFlexFlashCards                            INTEGER,
    cucsStorageQualDiskType                                          CucsStorageTechnology
}

cucsStorageQualInstanceId OBJECT-TYPE
    SYNTAX       CucsManagedObjectId
    MAX-ACCESS   not-accessible
    STATUS       current
    DESCRIPTION
        "Instance identifier of the managed object."
    ::= { cucsStorageQualEntry 1 }

cucsStorageQualDn OBJECT-TYPE
    SYNTAX       CucsManagedObjectDn
    MAX-ACCESS   read-only
    STATUS       current
    DESCRIPTION
        "Cisco UCS storage:Qual:dn managed object property"
    ::= { cucsStorageQualEntry 2 }

cucsStorageQualRn OBJECT-TYPE
    SYNTAX       SnmpAdminString
    MAX-ACCESS   read-only
    STATUS       current
    DESCRIPTION
        "Cisco UCS storage:Qual:rn managed object property"
    ::= { cucsStorageQualEntry 3 }

cucsStorageQualBlockSize OBJECT-TYPE
    SYNTAX       Gauge32
    MAX-ACCESS   read-only
    STATUS       current
    DESCRIPTION
        "Cisco UCS storage:Qual:blockSize managed object property"
    ::= { cucsStorageQualEntry 4 }

cucsStorageQualMaxCap OBJECT-TYPE
    SYNTAX       Unsigned64
    MAX-ACCESS   read-only
    STATUS       current
    DESCRIPTION
        "Cisco UCS storage:Qual:maxCap managed object property"
    ::= { cucsStorageQualEntry 5 }

cucsStorageQualMinCap OBJECT-TYPE
    SYNTAX       Unsigned64
    MAX-ACCESS   read-only
    STATUS       current
    DESCRIPTION
        "Cisco UCS storage:Qual:minCap managed object property"
    ::= { cucsStorageQualEntry 6 }

cucsStorageQualNumberOfBlocks OBJECT-TYPE
    SYNTAX       Unsigned64
    MAX-ACCESS   read-only
    STATUS       current
    DESCRIPTION
        "Cisco UCS storage:Qual:numberOfBlocks managed object property"
    ::= { cucsStorageQualEntry 7 }

cucsStorageQualPerDiskCap OBJECT-TYPE
    SYNTAX       Unsigned64
    MAX-ACCESS   read-only
    STATUS       current
    DESCRIPTION
        "Cisco UCS storage:Qual:perDiskCap managed object property"
    ::= { cucsStorageQualEntry 8 }

cucsStorageQualUnits OBJECT-TYPE
    SYNTAX       Gauge32
    MAX-ACCESS   read-only
    STATUS       current
    DESCRIPTION
        "Cisco UCS storage:Qual:units managed object property"
    ::= { cucsStorageQualEntry 9 }

cucsStorageQualDiskless OBJECT-TYPE
    SYNTAX       CucsStorageDisklessAction
    MAX-ACCESS   read-only
    STATUS       current
    DESCRIPTION
        "Cisco UCS storage:Qual:diskless managed object property"
    ::= { cucsStorageQualEntry 10 }

cucsStorageQualNumberOfFlexFlashCards OBJECT-TYPE
    SYNTAX       INTEGER
    MAX-ACCESS   read-only
    STATUS       current
    DESCRIPTION
        "Cisco UCS storage:Qual:numberOfFlexFlashCards
        managed object property"
    ::= { cucsStorageQualEntry 11 }

cucsStorageQualDiskType OBJECT-TYPE
    SYNTAX       CucsStorageTechnology
    MAX-ACCESS   read-only
    STATUS       current
    DESCRIPTION
        "Cisco UCS storage:Qual:diskType managed object property"
    ::= { cucsStorageQualEntry 12 }

cucsStorageRaidBatteryTable OBJECT-TYPE
    SYNTAX           SEQUENCE OF CucsStorageRaidBatteryEntry
    MAX-ACCESS       not-accessible
    STATUS           current
    DESCRIPTION
        "Cisco UCS storage:RaidBattery managed object table"
    ::= { cucsStorageObjects 11 }

cucsStorageRaidBatteryEntry OBJECT-TYPE
    SYNTAX           CucsStorageRaidBatteryEntry
    MAX-ACCESS       not-accessible
    STATUS           current
    DESCRIPTION
        "Entry for the cucsStorageRaidBatteryTable table."
    INDEX { cucsStorageRaidBatteryInstanceId }
    ::= { cucsStorageRaidBatteryTable 1 }

CucsStorageRaidBatteryEntry ::= SEQUENCE {
    cucsStorageRaidBatteryInstanceId                                 CucsManagedObjectId,
    cucsStorageRaidBatteryDn                                         CucsManagedObjectDn,
    cucsStorageRaidBatteryRn                                         SnmpAdminString,
    cucsStorageRaidBatteryBlockSize                                  Gauge32,
    cucsStorageRaidBatteryConnectionProtocol                         CucsStorageConnectionProtocol,
    cucsStorageRaidBatteryId                                         Gauge32,
    cucsStorageRaidBatteryModel                                      SnmpAdminString,
    cucsStorageRaidBatteryNumberOfBlocks                             Unsigned64,
    cucsStorageRaidBatteryOperability                                CucsEquipmentOperability,
    cucsStorageRaidBatteryPresence                                   CucsEquipmentPresence,
    cucsStorageRaidBatteryRevision                                   SnmpAdminString,
    cucsStorageRaidBatterySerial                                     SnmpAdminString,
    cucsStorageRaidBatterySize                                       Unsigned64,
    cucsStorageRaidBatteryVendor                                     SnmpAdminString,
    cucsStorageRaidBatteryOperQualifierReason                        SnmpAdminString,
    cucsStorageRaidBatteryBatteryType                                CucsStorageBatteryType,
    cucsStorageRaidBatteryCapacityPercentage                         Gauge32,
    cucsStorageRaidBatteryOperabilityQualifier                       CucsStorageRaidBatteryOperabilityQualifier,
    cucsStorageRaidBatteryOperabilityQualifierReason                 SnmpAdminString,
    cucsStorageRaidBatteryTemperature                                SnmpAdminString,
    cucsStorageRaidBatteryBbuStatus                                  CucsStorageBbuStatus,
    cucsStorageRaidBatteryLc                                         CucsFsmLifecycle,
    cucsStorageRaidBatteryLearnCycleRequested                        CucsStorageLearnCycleRequested,
    cucsStorageRaidBatteryLearnMode                                  CucsStorageLearnMode,
    cucsStorageRaidBatteryNextLearnCycleTs                           DateAndTime,
    cucsStorageRaidBatteryPhysicalBlockSize                          Gauge32
}

cucsStorageRaidBatteryInstanceId OBJECT-TYPE
    SYNTAX       CucsManagedObjectId
    MAX-ACCESS   not-accessible
    STATUS       current
    DESCRIPTION
        "Instance identifier of the managed object."
    ::= { cucsStorageRaidBatteryEntry 1 }

cucsStorageRaidBatteryDn OBJECT-TYPE
    SYNTAX       CucsManagedObjectDn
    MAX-ACCESS   read-only
    STATUS       current
    DESCRIPTION
        "Cisco UCS storage:RaidBattery:dn managed object property"
    ::= { cucsStorageRaidBatteryEntry 2 }

cucsStorageRaidBatteryRn OBJECT-TYPE
    SYNTAX       SnmpAdminString
    MAX-ACCESS   read-only
    STATUS       current
    DESCRIPTION
        "Cisco UCS storage:RaidBattery:rn managed object property"
    ::= { cucsStorageRaidBatteryEntry 3 }

cucsStorageRaidBatteryBlockSize OBJECT-TYPE
    SYNTAX       Gauge32
    MAX-ACCESS   read-only
    STATUS       current
    DESCRIPTION
        "Cisco UCS storage:RaidBattery:blockSize managed object property"
    ::= { cucsStorageRaidBatteryEntry 4 }

cucsStorageRaidBatteryConnectionProtocol OBJECT-TYPE
    SYNTAX       CucsStorageConnectionProtocol
    MAX-ACCESS   read-only
    STATUS       current
    DESCRIPTION
        "Cisco UCS storage:RaidBattery:connectionProtocol
        managed object property"
    ::= { cucsStorageRaidBatteryEntry 5 }

cucsStorageRaidBatteryId OBJECT-TYPE
    SYNTAX       Gauge32
    MAX-ACCESS   read-only
    STATUS       current
    DESCRIPTION
        "Cisco UCS storage:RaidBattery:id managed object property"
    ::= { cucsStorageRaidBatteryEntry 6 }

cucsStorageRaidBatteryModel OBJECT-TYPE
    SYNTAX       SnmpAdminString
    MAX-ACCESS   read-only
    STATUS       current
    DESCRIPTION
        "Cisco UCS storage:RaidBattery:model managed object property"
    ::= { cucsStorageRaidBatteryEntry 7 }

cucsStorageRaidBatteryNumberOfBlocks OBJECT-TYPE
    SYNTAX       Unsigned64
    MAX-ACCESS   read-only
    STATUS       current
    DESCRIPTION
        "Cisco UCS storage:RaidBattery:numberOfBlocks managed
        object property"
    ::= { cucsStorageRaidBatteryEntry 8 }

cucsStorageRaidBatteryOperability OBJECT-TYPE
    SYNTAX       CucsEquipmentOperability
    MAX-ACCESS   read-only
    STATUS       current
    DESCRIPTION
        "Cisco UCS storage:RaidBattery:operability managed
        object property"
    ::= { cucsStorageRaidBatteryEntry 9 }

cucsStorageRaidBatteryPresence OBJECT-TYPE
    SYNTAX       CucsEquipmentPresence
    MAX-ACCESS   read-only
    STATUS       current
    DESCRIPTION
        "Cisco UCS storage:RaidBattery:presence managed object property"
    ::= { cucsStorageRaidBatteryEntry 10 }

cucsStorageRaidBatteryRevision OBJECT-TYPE
    SYNTAX       SnmpAdminString
    MAX-ACCESS   read-only
    STATUS       current
    DESCRIPTION
        "Cisco UCS storage:RaidBattery:revision managed object property"
    ::= { cucsStorageRaidBatteryEntry 11 }

cucsStorageRaidBatterySerial OBJECT-TYPE
    SYNTAX       SnmpAdminString
    MAX-ACCESS   read-only
    STATUS       current
    DESCRIPTION
        "Cisco UCS storage:RaidBattery:serial managed object property"
    ::= { cucsStorageRaidBatteryEntry 12 }

cucsStorageRaidBatterySize OBJECT-TYPE
    SYNTAX       Unsigned64
    MAX-ACCESS   read-only
    STATUS       current
    DESCRIPTION
        "Cisco UCS storage:RaidBattery:size managed object property"
    ::= { cucsStorageRaidBatteryEntry 13 }

cucsStorageRaidBatteryVendor OBJECT-TYPE
    SYNTAX       SnmpAdminString
    MAX-ACCESS   read-only
    STATUS       current
    DESCRIPTION
        "Cisco UCS storage:RaidBattery:vendor managed object property"
    ::= { cucsStorageRaidBatteryEntry 14 }

cucsStorageRaidBatteryOperQualifierReason OBJECT-TYPE
    SYNTAX       SnmpAdminString
    MAX-ACCESS   read-only
    STATUS       current
    DESCRIPTION
        "Cisco UCS storage:RaidBattery:operQualifierReason
        managed object property"
    ::= { cucsStorageRaidBatteryEntry 15 }

cucsStorageRaidBatteryBatteryType OBJECT-TYPE
    SYNTAX       CucsStorageBatteryType
    MAX-ACCESS   read-only
    STATUS       current
    DESCRIPTION
        "Cisco UCS storage:RaidBattery:batteryType managed
        object property"
    ::= { cucsStorageRaidBatteryEntry 16 }

cucsStorageRaidBatteryCapacityPercentage OBJECT-TYPE
    SYNTAX       Gauge32
    MAX-ACCESS   read-only
    STATUS       current
    DESCRIPTION
        "Cisco UCS storage:RaidBattery:capacityPercentage
        managed object property"
    ::= { cucsStorageRaidBatteryEntry 17 }

cucsStorageRaidBatteryOperabilityQualifier OBJECT-TYPE
    SYNTAX       CucsStorageRaidBatteryOperabilityQualifier
    MAX-ACCESS   read-only
    STATUS       current
    DESCRIPTION
        "Cisco UCS storage:RaidBattery:operabilityQualifier
        managed object property"
    ::= { cucsStorageRaidBatteryEntry 18 }

cucsStorageRaidBatteryOperabilityQualifierReason OBJECT-TYPE
    SYNTAX       SnmpAdminString
    MAX-ACCESS   read-only
    STATUS       current
    DESCRIPTION
        "Cisco UCS storage:RaidBattery:operabilityQualifierReason
        managed object property"
    ::= { cucsStorageRaidBatteryEntry 19 }

cucsStorageRaidBatteryTemperature OBJECT-TYPE
    SYNTAX       SnmpAdminString
    MAX-ACCESS   read-only
    STATUS       current
    DESCRIPTION
        "Cisco UCS storage:RaidBattery:temperature managed
        object property"
    ::= { cucsStorageRaidBatteryEntry 20 }

cucsStorageRaidBatteryBbuStatus OBJECT-TYPE
    SYNTAX       CucsStorageBbuStatus
    MAX-ACCESS   read-only
    STATUS       current
    DESCRIPTION
        "Cisco UCS storage:RaidBattery:bbuStatus managed object property"
    ::= { cucsStorageRaidBatteryEntry 21 }

cucsStorageRaidBatteryLc OBJECT-TYPE
    SYNTAX       CucsFsmLifecycle
    MAX-ACCESS   read-only
    STATUS       current
    DESCRIPTION
        "Cisco UCS storage:RaidBattery:lc managed object property"
    ::= { cucsStorageRaidBatteryEntry 22 }

cucsStorageRaidBatteryLearnCycleRequested OBJECT-TYPE
    SYNTAX       CucsStorageLearnCycleRequested
    MAX-ACCESS   read-only
    STATUS       current
    DESCRIPTION
        "Cisco UCS storage:RaidBattery:learnCycleRequested
        managed object property"
    ::= { cucsStorageRaidBatteryEntry 23 }

cucsStorageRaidBatteryLearnMode OBJECT-TYPE
    SYNTAX       CucsStorageLearnMode
    MAX-ACCESS   read-only
    STATUS       current
    DESCRIPTION
        "Cisco UCS storage:RaidBattery:learnMode managed object property"
    ::= { cucsStorageRaidBatteryEntry 24 }

cucsStorageRaidBatteryNextLearnCycleTs OBJECT-TYPE
    SYNTAX       DateAndTime
    MAX-ACCESS   read-only
    STATUS       current
    DESCRIPTION
        "Cisco UCS storage:RaidBattery:nextLearnCycleTs
        managed object property"
    ::= { cucsStorageRaidBatteryEntry 25 }

cucsStorageRaidBatteryPhysicalBlockSize OBJECT-TYPE
    SYNTAX       Gauge32
    MAX-ACCESS   read-only
    STATUS       current
    DESCRIPTION
        "Cisco UCS storage:RaidBattery:physicalBlockSize
        managed object property"
    ::= { cucsStorageRaidBatteryEntry 26 }

cucsStorageSasExpanderTable OBJECT-TYPE
    SYNTAX           SEQUENCE OF CucsStorageSasExpanderEntry
    MAX-ACCESS       not-accessible
    STATUS           current
    DESCRIPTION
        "Cisco UCS storage:SasExpander managed object table"
    ::= { cucsStorageObjects 78 }

cucsStorageSasExpanderEntry OBJECT-TYPE
    SYNTAX           CucsStorageSasExpanderEntry
    MAX-ACCESS       not-accessible
    STATUS           current
    DESCRIPTION
        "Entry for the cucsStorageSasExpanderTable table."
    INDEX { cucsStorageSasExpanderInstanceId }
    ::= { cucsStorageSasExpanderTable 1 }

CucsStorageSasExpanderEntry ::= SEQUENCE {
    cucsStorageSasExpanderInstanceId                                 CucsManagedObjectId,
    cucsStorageSasExpanderDn                                         CucsManagedObjectDn,
    cucsStorageSasExpanderRn                                         SnmpAdminString,
    cucsStorageSasExpanderId                                         Gauge32,
    cucsStorageSasExpanderLocationDn                                 SnmpAdminString,
    cucsStorageSasExpanderModel                                      SnmpAdminString,
    cucsStorageSasExpanderOperQualifierReason                        SnmpAdminString,
    cucsStorageSasExpanderOperState                                  CucsEquipmentOperability,
    cucsStorageSasExpanderOperability                                CucsEquipmentOperability,
    cucsStorageSasExpanderPerf                                       CucsEquipmentSensorThresholdStatus,
    cucsStorageSasExpanderPower                                      CucsEquipmentPowerState,
    cucsStorageSasExpanderPresence                                   CucsEquipmentPresence,
    cucsStorageSasExpanderRevision                                   SnmpAdminString,
    cucsStorageSasExpanderSerial                                     SnmpAdminString,
    cucsStorageSasExpanderThermal                                    CucsEquipmentSensorThresholdStatus,
    cucsStorageSasExpanderVendor                                     SnmpAdminString,
    cucsStorageSasExpanderVoltage                                    CucsEquipmentSensorThresholdStatus,
    cucsStorageSasExpanderExpanderState                              CucsStorageExpanderState,
    cucsStorageSasExpanderLc                                         CucsFsmLifecycle,
    cucsStorageSasExpanderUplinkState                                CucsStorageEpLinkState,
    cucsStorageSasExpanderUplinkStateReason                          SnmpAdminString,
    cucsStorageSasExpanderFwRegionOne                                SnmpAdminString,
    cucsStorageSasExpanderFwRegionTwo                                SnmpAdminString,
    cucsStorageSasExpanderFwRunningRegion                            SnmpAdminString,
    cucsStorageSasExpanderSasAddress                                 SnmpAdminString,
    cucsStorageSasExpanderCurrentEPFB                                SnmpAdminString,
    cucsStorageSasExpanderElid                                       SnmpAdminString,
    cucsStorageSasExpanderMfgMajorRev                                SnmpAdminString,
    cucsStorageSasExpanderMfgMinorRev                                SnmpAdminString,
    cucsStorageSasExpanderMfgPlatformId                              SnmpAdminString,
    cucsStorageSasExpanderPersistedEPFB                              SnmpAdminString,
    cucsStorageSasExpanderStartSlotNum                               SnmpAdminString,
    cucsStorageSasExpanderTemperature                                SnmpAdminString,
    cucsStorageSasExpanderTotalSlots                                 SnmpAdminString,
    cucsStorageSasExpanderConfigCheckPoint                           CucsStorageConfigCheckPoint
}

cucsStorageSasExpanderInstanceId OBJECT-TYPE
    SYNTAX       CucsManagedObjectId
    MAX-ACCESS   not-accessible
    STATUS       current
    DESCRIPTION
        "Instance identifier of the managed object."
    ::= { cucsStorageSasExpanderEntry 1 }

cucsStorageSasExpanderDn OBJECT-TYPE
    SYNTAX       CucsManagedObjectDn
    MAX-ACCESS   read-only
    STATUS       current
    DESCRIPTION
        "Cisco UCS storage:SasExpander:dn managed object property"
    ::= { cucsStorageSasExpanderEntry 2 }

cucsStorageSasExpanderRn OBJECT-TYPE
    SYNTAX       SnmpAdminString
    MAX-ACCESS   read-only
    STATUS       current
    DESCRIPTION
        "Cisco UCS storage:SasExpander:rn managed object property"
    ::= { cucsStorageSasExpanderEntry 3 }

cucsStorageSasExpanderId OBJECT-TYPE
    SYNTAX       Gauge32
    MAX-ACCESS   read-only
    STATUS       current
    DESCRIPTION
        "Cisco UCS storage:SasExpander:id managed object property"
    ::= { cucsStorageSasExpanderEntry 4 }

cucsStorageSasExpanderLocationDn OBJECT-TYPE
    SYNTAX       SnmpAdminString
    MAX-ACCESS   read-only
    STATUS       current
    DESCRIPTION
        "Cisco UCS storage:SasExpander:locationDn managed object property"
    ::= { cucsStorageSasExpanderEntry 5 }

cucsStorageSasExpanderModel OBJECT-TYPE
    SYNTAX       SnmpAdminString
    MAX-ACCESS   read-only
    STATUS       current
    DESCRIPTION
        "Cisco UCS storage:SasExpander:model managed object property"
    ::= { cucsStorageSasExpanderEntry 6 }

cucsStorageSasExpanderOperQualifierReason OBJECT-TYPE
    SYNTAX       SnmpAdminString
    MAX-ACCESS   read-only
    STATUS       current
    DESCRIPTION
        "Cisco UCS storage:SasExpander:operQualifierReason
        managed object property"
    ::= { cucsStorageSasExpanderEntry 7 }

cucsStorageSasExpanderOperState OBJECT-TYPE
    SYNTAX       CucsEquipmentOperability
    MAX-ACCESS   read-only
    STATUS       current
    DESCRIPTION
        "Cisco UCS storage:SasExpander:operState managed object property"
    ::= { cucsStorageSasExpanderEntry 8 }

cucsStorageSasExpanderOperability OBJECT-TYPE
    SYNTAX       CucsEquipmentOperability
    MAX-ACCESS   read-only
    STATUS       current
    DESCRIPTION
        "Cisco UCS storage:SasExpander:operability managed
        object property"
    ::= { cucsStorageSasExpanderEntry 9 }

cucsStorageSasExpanderPerf OBJECT-TYPE
    SYNTAX       CucsEquipmentSensorThresholdStatus
    MAX-ACCESS   read-only
    STATUS       current
    DESCRIPTION
        "Cisco UCS storage:SasExpander:perf managed object property"
    ::= { cucsStorageSasExpanderEntry 10 }

cucsStorageSasExpanderPower OBJECT-TYPE
    SYNTAX       CucsEquipmentPowerState
    MAX-ACCESS   read-only
    STATUS       current
    DESCRIPTION
        "Cisco UCS storage:SasExpander:power managed object property"
    ::= { cucsStorageSasExpanderEntry 11 }

cucsStorageSasExpanderPresence OBJECT-TYPE
    SYNTAX       CucsEquipmentPresence
    MAX-ACCESS   read-only
    STATUS       current
    DESCRIPTION
        "Cisco UCS storage:SasExpander:presence managed object property"
    ::= { cucsStorageSasExpanderEntry 12 }

cucsStorageSasExpanderRevision OBJECT-TYPE
    SYNTAX       SnmpAdminString
    MAX-ACCESS   read-only
    STATUS       current
    DESCRIPTION
        "Cisco UCS storage:SasExpander:revision managed object property"
    ::= { cucsStorageSasExpanderEntry 13 }

cucsStorageSasExpanderSerial OBJECT-TYPE
    SYNTAX       SnmpAdminString
    MAX-ACCESS   read-only
    STATUS       current
    DESCRIPTION
        "Cisco UCS storage:SasExpander:serial managed object property"
    ::= { cucsStorageSasExpanderEntry 14 }

cucsStorageSasExpanderThermal OBJECT-TYPE
    SYNTAX       CucsEquipmentSensorThresholdStatus
    MAX-ACCESS   read-only
    STATUS       current
    DESCRIPTION
        "Cisco UCS storage:SasExpander:thermal managed object property"
    ::= { cucsStorageSasExpanderEntry 15 }

cucsStorageSasExpanderVendor OBJECT-TYPE
    SYNTAX       SnmpAdminString
    MAX-ACCESS   read-only
    STATUS       current
    DESCRIPTION
        "Cisco UCS storage:SasExpander:vendor managed object property"
    ::= { cucsStorageSasExpanderEntry 16 }

cucsStorageSasExpanderVoltage OBJECT-TYPE
    SYNTAX       CucsEquipmentSensorThresholdStatus
    MAX-ACCESS   read-only
    STATUS       current
    DESCRIPTION
        "Cisco UCS storage:SasExpander:voltage managed object property"
    ::= { cucsStorageSasExpanderEntry 17 }

cucsStorageSasExpanderExpanderState OBJECT-TYPE
    SYNTAX       CucsStorageExpanderState
    MAX-ACCESS   read-only
    STATUS       current
    DESCRIPTION
        "Cisco UCS storage:SasExpander:expanderState managed
        object property"
    ::= { cucsStorageSasExpanderEntry 19 }

cucsStorageSasExpanderLc OBJECT-TYPE
    SYNTAX       CucsFsmLifecycle
    MAX-ACCESS   read-only
    STATUS       current
    DESCRIPTION
        "Cisco UCS storage:SasExpander:lc managed object property"
    ::= { cucsStorageSasExpanderEntry 20 }

cucsStorageSasExpanderUplinkState OBJECT-TYPE
    SYNTAX       CucsStorageEpLinkState
    MAX-ACCESS   read-only
    STATUS       current
    DESCRIPTION
        "Cisco UCS storage:SasExpander:uplinkState managed
        object property"
    ::= { cucsStorageSasExpanderEntry 21 }

cucsStorageSasExpanderUplinkStateReason OBJECT-TYPE
    SYNTAX       SnmpAdminString
    MAX-ACCESS   read-only
    STATUS       current
    DESCRIPTION
        "Cisco UCS storage:SasExpander:uplinkStateReason
        managed object property"
    ::= { cucsStorageSasExpanderEntry 22 }

cucsStorageSasExpanderFwRegionOne OBJECT-TYPE
    SYNTAX       SnmpAdminString
    MAX-ACCESS   read-only
    STATUS       current
    DESCRIPTION
        "Cisco UCS storage:SasExpander:fwRegionOne managed
        object property"
    ::= { cucsStorageSasExpanderEntry 23 }

cucsStorageSasExpanderFwRegionTwo OBJECT-TYPE
    SYNTAX       SnmpAdminString
    MAX-ACCESS   read-only
    STATUS       current
    DESCRIPTION
        "Cisco UCS storage:SasExpander:fwRegionTwo managed
        object property"
    ::= { cucsStorageSasExpanderEntry 24 }

cucsStorageSasExpanderFwRunningRegion OBJECT-TYPE
    SYNTAX       SnmpAdminString
    MAX-ACCESS   read-only
    STATUS       current
    DESCRIPTION
        "Cisco UCS storage:SasExpander:fwRunningRegion
        managed object property"
    ::= { cucsStorageSasExpanderEntry 25 }

cucsStorageSasExpanderSasAddress OBJECT-TYPE
    SYNTAX       SnmpAdminString
    MAX-ACCESS   read-only
    STATUS       current
    DESCRIPTION
        "Cisco UCS storage:SasExpander:sasAddress managed object property"
    ::= { cucsStorageSasExpanderEntry 26 }

cucsStorageSasExpanderCurrentEPFB OBJECT-TYPE
    SYNTAX       SnmpAdminString
    MAX-ACCESS   read-only
    STATUS       current
    DESCRIPTION
        "Cisco UCS storage:SasExpander:currentEPFB managed
        object property"
    ::= { cucsStorageSasExpanderEntry 27 }

cucsStorageSasExpanderElid OBJECT-TYPE
    SYNTAX       SnmpAdminString
    MAX-ACCESS   read-only
    STATUS       current
    DESCRIPTION
        "Cisco UCS storage:SasExpander:elid managed object property"
    ::= { cucsStorageSasExpanderEntry 28 }

cucsStorageSasExpanderMfgMajorRev OBJECT-TYPE
    SYNTAX       SnmpAdminString
    MAX-ACCESS   read-only
    STATUS       current
    DESCRIPTION
        "Cisco UCS storage:SasExpander:mfgMajorRev managed
        object property"
    ::= { cucsStorageSasExpanderEntry 29 }

cucsStorageSasExpanderMfgMinorRev OBJECT-TYPE
    SYNTAX       SnmpAdminString
    MAX-ACCESS   read-only
    STATUS       current
    DESCRIPTION
        "Cisco UCS storage:SasExpander:mfgMinorRev managed
        object property"
    ::= { cucsStorageSasExpanderEntry 30 }

cucsStorageSasExpanderMfgPlatformId OBJECT-TYPE
    SYNTAX       SnmpAdminString
    MAX-ACCESS   read-only
    STATUS       current
    DESCRIPTION
        "Cisco UCS storage:SasExpander:mfgPlatformId managed
        object property"
    ::= { cucsStorageSasExpanderEntry 31 }

cucsStorageSasExpanderPersistedEPFB OBJECT-TYPE
    SYNTAX       SnmpAdminString
    MAX-ACCESS   read-only
    STATUS       current
    DESCRIPTION
        "Cisco UCS storage:SasExpander:persistedEPFB managed
        object property"
    ::= { cucsStorageSasExpanderEntry 32 }

cucsStorageSasExpanderStartSlotNum OBJECT-TYPE
    SYNTAX       SnmpAdminString
    MAX-ACCESS   read-only
    STATUS       current
    DESCRIPTION
        "Cisco UCS storage:SasExpander:startSlotNum managed
        object property"
    ::= { cucsStorageSasExpanderEntry 33 }

cucsStorageSasExpanderTemperature OBJECT-TYPE
    SYNTAX       SnmpAdminString
    MAX-ACCESS   read-only
    STATUS       current
    DESCRIPTION
        "Cisco UCS storage:SasExpander:temperature managed
        object property"
    ::= { cucsStorageSasExpanderEntry 34 }

cucsStorageSasExpanderTotalSlots OBJECT-TYPE
    SYNTAX       SnmpAdminString
    MAX-ACCESS   read-only
    STATUS       current
    DESCRIPTION
        "Cisco UCS storage:SasExpander:totalSlots managed object property"
    ::= { cucsStorageSasExpanderEntry 35 }

cucsStorageSasExpanderConfigCheckPoint OBJECT-TYPE
    SYNTAX       CucsStorageConfigCheckPoint
    MAX-ACCESS   read-only
    STATUS       current
    DESCRIPTION
        "Cisco UCS storage:SasExpander:configCheckPoint
        managed object property"
    ::= { cucsStorageSasExpanderEntry 36 }

cucsStorageSasLinkDescriptorTable OBJECT-TYPE
    SYNTAX           SEQUENCE OF CucsStorageSasLinkDescriptorEntry
    MAX-ACCESS       not-accessible
    STATUS           current
    DESCRIPTION
        "Cisco UCS storage:SasLinkDescriptor managed object table"
    ::= { cucsStorageObjects 95 }

cucsStorageSasLinkDescriptorEntry OBJECT-TYPE
    SYNTAX           CucsStorageSasLinkDescriptorEntry
    MAX-ACCESS       not-accessible
    STATUS           current
    DESCRIPTION
        "Entry for the cucsStorageSasLinkDescriptorTable table."
    INDEX { cucsStorageSasLinkDescriptorInstanceId }
    ::= { cucsStorageSasLinkDescriptorTable 1 }

CucsStorageSasLinkDescriptorEntry ::= SEQUENCE {
    cucsStorageSasLinkDescriptorInstanceId                           CucsManagedObjectId,
    cucsStorageSasLinkDescriptorDn                                   CucsManagedObjectDn,
    cucsStorageSasLinkDescriptorRn                                   SnmpAdminString,
    cucsStorageSasLinkDescriptorControllerId                         Gauge32,
    cucsStorageSasLinkDescriptorId                                   Gauge32,
    cucsStorageSasLinkDescriptorLinkDescr                            SnmpAdminString,
    cucsStorageSasLinkDescriptorServerId                             Gauge32,
    cucsStorageSasLinkDescriptorControllerType                       CucsStorageSasLinkDescriptorControllerType
}

cucsStorageSasLinkDescriptorInstanceId OBJECT-TYPE
    SYNTAX       CucsManagedObjectId
    MAX-ACCESS   not-accessible
    STATUS       current
    DESCRIPTION
        "Instance identifier of the managed object."
    ::= { cucsStorageSasLinkDescriptorEntry 1 }

cucsStorageSasLinkDescriptorDn OBJECT-TYPE
    SYNTAX       CucsManagedObjectDn
    MAX-ACCESS   read-only
    STATUS       current
    DESCRIPTION
        "Cisco UCS storage:SasLinkDescriptor:dn managed object property"
    ::= { cucsStorageSasLinkDescriptorEntry 2 }

cucsStorageSasLinkDescriptorRn OBJECT-TYPE
    SYNTAX       SnmpAdminString
    MAX-ACCESS   read-only
    STATUS       current
    DESCRIPTION
        "Cisco UCS storage:SasLinkDescriptor:rn managed object property"
    ::= { cucsStorageSasLinkDescriptorEntry 3 }

cucsStorageSasLinkDescriptorControllerId OBJECT-TYPE
    SYNTAX       Gauge32
    MAX-ACCESS   read-only
    STATUS       current
    DESCRIPTION
        "Cisco UCS storage:SasLinkDescriptor:controllerId
        managed object property"
    ::= { cucsStorageSasLinkDescriptorEntry 4 }

cucsStorageSasLinkDescriptorId OBJECT-TYPE
    SYNTAX       Gauge32
    MAX-ACCESS   read-only
    STATUS       current
    DESCRIPTION
        "Cisco UCS storage:SasLinkDescriptor:id managed object property"
    ::= { cucsStorageSasLinkDescriptorEntry 5 }

cucsStorageSasLinkDescriptorLinkDescr OBJECT-TYPE
    SYNTAX       SnmpAdminString
    MAX-ACCESS   read-only
    STATUS       current
    DESCRIPTION
        "Cisco UCS storage:SasLinkDescriptor:linkDescr
        managed object property"
    ::= { cucsStorageSasLinkDescriptorEntry 6 }

cucsStorageSasLinkDescriptorServerId OBJECT-TYPE
    SYNTAX       Gauge32
    MAX-ACCESS   read-only
    STATUS       current
    DESCRIPTION
        "Cisco UCS storage:SasLinkDescriptor:serverId managed
        object property"
    ::= { cucsStorageSasLinkDescriptorEntry 7 }

cucsStorageSasLinkDescriptorControllerType OBJECT-TYPE
    SYNTAX       CucsStorageSasLinkDescriptorControllerType
    MAX-ACCESS   read-only
    STATUS       current
    DESCRIPTION
        "Cisco UCS storage:SasLinkDescriptor:controllerType
        managed object property"
    ::= { cucsStorageSasLinkDescriptorEntry 8 }

cucsStorageSasPortTable OBJECT-TYPE
    SYNTAX           SEQUENCE OF CucsStorageSasPortEntry
    MAX-ACCESS       not-accessible
    STATUS           current
    DESCRIPTION
        "Cisco UCS storage:SasPort managed object table"
    ::= { cucsStorageObjects 96 }

cucsStorageSasPortEntry OBJECT-TYPE
    SYNTAX           CucsStorageSasPortEntry
    MAX-ACCESS       not-accessible
    STATUS           current
    DESCRIPTION
        "Entry for the cucsStorageSasPortTable table."
    INDEX { cucsStorageSasPortInstanceId }
    ::= { cucsStorageSasPortTable 1 }

CucsStorageSasPortEntry ::= SEQUENCE {
    cucsStorageSasPortInstanceId                                     CucsManagedObjectId,
    cucsStorageSasPortDn                                             CucsManagedObjectDn,
    cucsStorageSasPortRn                                             SnmpAdminString,
    cucsStorageSasPortAddress                                        SnmpAdminString,
    cucsStorageSasPortEndpoint                                       Gauge32,
    cucsStorageSasPortId                                             Gauge32,
    cucsStorageSasPortLc                                             CucsFsmLifecycle,
    cucsStorageSasPortLinkDescr                                      SnmpAdminString,
    cucsStorageSasPortLinkSpeed                                      CucsStorageLinkSpeed
}

cucsStorageSasPortInstanceId OBJECT-TYPE
    SYNTAX       CucsManagedObjectId
    MAX-ACCESS   not-accessible
    STATUS       current
    DESCRIPTION
        "Instance identifier of the managed object."
    ::= { cucsStorageSasPortEntry 1 }

cucsStorageSasPortDn OBJECT-TYPE
    SYNTAX       CucsManagedObjectDn
    MAX-ACCESS   read-only
    STATUS       current
    DESCRIPTION
        "Cisco UCS storage:SasPort:dn managed object property"
    ::= { cucsStorageSasPortEntry 2 }

cucsStorageSasPortRn OBJECT-TYPE
    SYNTAX       SnmpAdminString
    MAX-ACCESS   read-only
    STATUS       current
    DESCRIPTION
        "Cisco UCS storage:SasPort:rn managed object property"
    ::= { cucsStorageSasPortEntry 3 }

cucsStorageSasPortAddress OBJECT-TYPE
    SYNTAX       SnmpAdminString
    MAX-ACCESS   read-only
    STATUS       current
    DESCRIPTION
        "Cisco UCS storage:SasPort:address managed object property"
    ::= { cucsStorageSasPortEntry 4 }

cucsStorageSasPortEndpoint OBJECT-TYPE
    SYNTAX       Gauge32
    MAX-ACCESS   read-only
    STATUS       current
    DESCRIPTION
        "Cisco UCS storage:SasPort:endpoint managed object property"
    ::= { cucsStorageSasPortEntry 5 }

cucsStorageSasPortId OBJECT-TYPE
    SYNTAX       Gauge32
    MAX-ACCESS   read-only
    STATUS       current
    DESCRIPTION
        "Cisco UCS storage:SasPort:id managed object property"
    ::= { cucsStorageSasPortEntry 6 }

cucsStorageSasPortLc OBJECT-TYPE
    SYNTAX       CucsFsmLifecycle
    MAX-ACCESS   read-only
    STATUS       current
    DESCRIPTION
        "Cisco UCS storage:SasPort:lc managed object property"
    ::= { cucsStorageSasPortEntry 7 }

cucsStorageSasPortLinkDescr OBJECT-TYPE
    SYNTAX       SnmpAdminString
    MAX-ACCESS   read-only
    STATUS       current
    DESCRIPTION
        "Cisco UCS storage:SasPort:linkDescr managed object property"
    ::= { cucsStorageSasPortEntry 8 }

cucsStorageSasPortLinkSpeed OBJECT-TYPE
    SYNTAX       CucsStorageLinkSpeed
    MAX-ACCESS   read-only
    STATUS       current
    DESCRIPTION
        "Cisco UCS storage:SasPort:linkSpeed managed object property"
    ::= { cucsStorageSasPortEntry 9 }

cucsStorageSasPortDescriptorTable OBJECT-TYPE
    SYNTAX           SEQUENCE OF CucsStorageSasPortDescriptorEntry
    MAX-ACCESS       not-accessible
    STATUS           current
    DESCRIPTION
        "Cisco UCS storage:SasPortDescriptor managed object table"
    ::= { cucsStorageObjects 97 }

cucsStorageSasPortDescriptorEntry OBJECT-TYPE
    SYNTAX           CucsStorageSasPortDescriptorEntry
    MAX-ACCESS       not-accessible
    STATUS           current
    DESCRIPTION
        "Entry for the cucsStorageSasPortDescriptorTable table."
    INDEX { cucsStorageSasPortDescriptorInstanceId }
    ::= { cucsStorageSasPortDescriptorTable 1 }

CucsStorageSasPortDescriptorEntry ::= SEQUENCE {
    cucsStorageSasPortDescriptorInstanceId                           CucsManagedObjectId,
    cucsStorageSasPortDescriptorDn                                   CucsManagedObjectDn,
    cucsStorageSasPortDescriptorRn                                   SnmpAdminString,
    cucsStorageSasPortDescriptorId                                   Gauge32,
    cucsStorageSasPortDescriptorLinkDescr                            SnmpAdminString
}

cucsStorageSasPortDescriptorInstanceId OBJECT-TYPE
    SYNTAX       CucsManagedObjectId
    MAX-ACCESS   not-accessible
    STATUS       current
    DESCRIPTION
        "Instance identifier of the managed object."
    ::= { cucsStorageSasPortDescriptorEntry 1 }

cucsStorageSasPortDescriptorDn OBJECT-TYPE
    SYNTAX       CucsManagedObjectDn
    MAX-ACCESS   read-only
    STATUS       current
    DESCRIPTION
        "Cisco UCS storage:SasPortDescriptor:dn managed object property"
    ::= { cucsStorageSasPortDescriptorEntry 2 }

cucsStorageSasPortDescriptorRn OBJECT-TYPE
    SYNTAX       SnmpAdminString
    MAX-ACCESS   read-only
    STATUS       current
    DESCRIPTION
        "Cisco UCS storage:SasPortDescriptor:rn managed object property"
    ::= { cucsStorageSasPortDescriptorEntry 3 }

cucsStorageSasPortDescriptorId OBJECT-TYPE
    SYNTAX       Gauge32
    MAX-ACCESS   read-only
    STATUS       current
    DESCRIPTION
        "Cisco UCS storage:SasPortDescriptor:id managed object property"
    ::= { cucsStorageSasPortDescriptorEntry 4 }

cucsStorageSasPortDescriptorLinkDescr OBJECT-TYPE
    SYNTAX       SnmpAdminString
    MAX-ACCESS   read-only
    STATUS       current
    DESCRIPTION
        "Cisco UCS storage:SasPortDescriptor:linkDescr
        managed object property"
    ::= { cucsStorageSasPortDescriptorEntry 5 }

cucsStorageSasUpLinkTable OBJECT-TYPE
    SYNTAX           SEQUENCE OF CucsStorageSasUpLinkEntry
    MAX-ACCESS       not-accessible
    STATUS           current
    DESCRIPTION
        "Cisco UCS storage:SasUpLink managed object table"
    ::= { cucsStorageObjects 98 }

cucsStorageSasUpLinkEntry OBJECT-TYPE
    SYNTAX           CucsStorageSasUpLinkEntry
    MAX-ACCESS       not-accessible
    STATUS           current
    DESCRIPTION
        "Entry for the cucsStorageSasUpLinkTable table."
    INDEX { cucsStorageSasUpLinkInstanceId }
    ::= { cucsStorageSasUpLinkTable 1 }

CucsStorageSasUpLinkEntry ::= SEQUENCE {
    cucsStorageSasUpLinkInstanceId                                   CucsManagedObjectId,
    cucsStorageSasUpLinkDn                                           CucsManagedObjectDn,
    cucsStorageSasUpLinkRn                                           SnmpAdminString,
    cucsStorageSasUpLinkControllerId                                 Gauge32,
    cucsStorageSasUpLinkId                                           Gauge32,
    cucsStorageSasUpLinkLc                                           CucsFsmLifecycle,
    cucsStorageSasUpLinkLinkDescr                                    SnmpAdminString,
    cucsStorageSasUpLinkLinkSpeed                                    CucsStorageLinkSpeed,
    cucsStorageSasUpLinkServerId                                     Gauge32,
    cucsStorageSasUpLinkControllerType                               CucsStorageSasUpLinkControllerType
}

cucsStorageSasUpLinkInstanceId OBJECT-TYPE
    SYNTAX       CucsManagedObjectId
    MAX-ACCESS   not-accessible
    STATUS       current
    DESCRIPTION
        "Instance identifier of the managed object."
    ::= { cucsStorageSasUpLinkEntry 1 }

cucsStorageSasUpLinkDn OBJECT-TYPE
    SYNTAX       CucsManagedObjectDn
    MAX-ACCESS   read-only
    STATUS       current
    DESCRIPTION
        "Cisco UCS storage:SasUpLink:dn managed object property"
    ::= { cucsStorageSasUpLinkEntry 2 }

cucsStorageSasUpLinkRn OBJECT-TYPE
    SYNTAX       SnmpAdminString
    MAX-ACCESS   read-only
    STATUS       current
    DESCRIPTION
        "Cisco UCS storage:SasUpLink:rn managed object property"
    ::= { cucsStorageSasUpLinkEntry 3 }

cucsStorageSasUpLinkControllerId OBJECT-TYPE
    SYNTAX       Gauge32
    MAX-ACCESS   read-only
    STATUS       current
    DESCRIPTION
        "Cisco UCS storage:SasUpLink:controllerId managed object property"
    ::= { cucsStorageSasUpLinkEntry 4 }

cucsStorageSasUpLinkId OBJECT-TYPE
    SYNTAX       Gauge32
    MAX-ACCESS   read-only
    STATUS       current
    DESCRIPTION
        "Cisco UCS storage:SasUpLink:id managed object property"
    ::= { cucsStorageSasUpLinkEntry 5 }

cucsStorageSasUpLinkLc OBJECT-TYPE
    SYNTAX       CucsFsmLifecycle
    MAX-ACCESS   read-only
    STATUS       current
    DESCRIPTION
        "Cisco UCS storage:SasUpLink:lc managed object property"
    ::= { cucsStorageSasUpLinkEntry 6 }

cucsStorageSasUpLinkLinkDescr OBJECT-TYPE
    SYNTAX       SnmpAdminString
    MAX-ACCESS   read-only
    STATUS       current
    DESCRIPTION
        "Cisco UCS storage:SasUpLink:linkDescr managed object property"
    ::= { cucsStorageSasUpLinkEntry 7 }

cucsStorageSasUpLinkLinkSpeed OBJECT-TYPE
    SYNTAX       CucsStorageLinkSpeed
    MAX-ACCESS   read-only
    STATUS       current
    DESCRIPTION
        "Cisco UCS storage:SasUpLink:linkSpeed managed object property"
    ::= { cucsStorageSasUpLinkEntry 8 }

cucsStorageSasUpLinkServerId OBJECT-TYPE
    SYNTAX       Gauge32
    MAX-ACCESS   read-only
    STATUS       current
    DESCRIPTION
        "Cisco UCS storage:SasUpLink:serverId managed object property"
    ::= { cucsStorageSasUpLinkEntry 9 }

cucsStorageSasUpLinkControllerType OBJECT-TYPE
    SYNTAX       CucsStorageSasUpLinkControllerType
    MAX-ACCESS   read-only
    STATUS       current
    DESCRIPTION
        "Cisco UCS storage:SasUpLink:controllerType managed
        object property"
    ::= { cucsStorageSasUpLinkEntry 10 }

cucsStorageScsiLunRefTable OBJECT-TYPE
    SYNTAX           SEQUENCE OF CucsStorageScsiLunRefEntry
    MAX-ACCESS       not-accessible
    STATUS           current
    DESCRIPTION
        "Cisco UCS storage:ScsiLunRef managed object table"
    ::= { cucsStorageObjects 83 }

cucsStorageScsiLunRefEntry OBJECT-TYPE
    SYNTAX           CucsStorageScsiLunRefEntry
    MAX-ACCESS       not-accessible
    STATUS           current
    DESCRIPTION
        "Entry for the cucsStorageScsiLunRefTable table."
    INDEX { cucsStorageScsiLunRefInstanceId }
    ::= { cucsStorageScsiLunRefTable 1 }

CucsStorageScsiLunRefEntry ::= SEQUENCE {
    cucsStorageScsiLunRefInstanceId                                  CucsManagedObjectId,
    cucsStorageScsiLunRefDn                                          CucsManagedObjectDn,
    cucsStorageScsiLunRefRn                                          SnmpAdminString,
    cucsStorageScsiLunRefId                                          Gauge32,
    cucsStorageScsiLunRefLsDn                                        SnmpAdminString,
    cucsStorageScsiLunRefLunName                                     SnmpAdminString,
    cucsStorageScsiLunRefProfileDn                                   SnmpAdminString,
    cucsStorageScsiLunRefPnDn                                        SnmpAdminString
}

cucsStorageScsiLunRefInstanceId OBJECT-TYPE
    SYNTAX       CucsManagedObjectId
    MAX-ACCESS   not-accessible
    STATUS       current
    DESCRIPTION
        "Instance identifier of the managed object."
    ::= { cucsStorageScsiLunRefEntry 1 }

cucsStorageScsiLunRefDn OBJECT-TYPE
    SYNTAX       CucsManagedObjectDn
    MAX-ACCESS   read-only
    STATUS       current
    DESCRIPTION
        "Cisco UCS storage:ScsiLunRef:dn managed object property"
    ::= { cucsStorageScsiLunRefEntry 2 }

cucsStorageScsiLunRefRn OBJECT-TYPE
    SYNTAX       SnmpAdminString
    MAX-ACCESS   read-only
    STATUS       current
    DESCRIPTION
        "Cisco UCS storage:ScsiLunRef:rn managed object property"
    ::= { cucsStorageScsiLunRefEntry 3 }

cucsStorageScsiLunRefId OBJECT-TYPE
    SYNTAX       Gauge32
    MAX-ACCESS   read-only
    STATUS       current
    DESCRIPTION
        "Cisco UCS storage:ScsiLunRef:id managed object property"
    ::= { cucsStorageScsiLunRefEntry 4 }

cucsStorageScsiLunRefLsDn OBJECT-TYPE
    SYNTAX       SnmpAdminString
    MAX-ACCESS   read-only
    STATUS       current
    DESCRIPTION
        "Cisco UCS storage:ScsiLunRef:lsDn managed object property"
    ::= { cucsStorageScsiLunRefEntry 5 }

cucsStorageScsiLunRefLunName OBJECT-TYPE
    SYNTAX       SnmpAdminString
    MAX-ACCESS   read-only
    STATUS       current
    DESCRIPTION
        "Cisco UCS storage:ScsiLunRef:lunName managed object property"
    ::= { cucsStorageScsiLunRefEntry 6 }

cucsStorageScsiLunRefProfileDn OBJECT-TYPE
    SYNTAX       SnmpAdminString
    MAX-ACCESS   read-only
    STATUS       current
    DESCRIPTION
        "Cisco UCS storage:ScsiLunRef:profileDn managed object property"
    ::= { cucsStorageScsiLunRefEntry 7 }

cucsStorageScsiLunRefPnDn OBJECT-TYPE
    SYNTAX       SnmpAdminString
    MAX-ACCESS   read-only
    STATUS       current
    DESCRIPTION
        "Cisco UCS storage:ScsiLunRef:pnDn managed object property"
    ::= { cucsStorageScsiLunRefEntry 8 }

cucsStorageSsdHealthStatsTable OBJECT-TYPE
    SYNTAX           SEQUENCE OF CucsStorageSsdHealthStatsEntry
    MAX-ACCESS       not-accessible
    STATUS           current
    DESCRIPTION
        "Cisco UCS storage:SsdHealthStats managed object table"
    ::= { cucsStorageObjects 125 }

cucsStorageSsdHealthStatsEntry OBJECT-TYPE
    SYNTAX           CucsStorageSsdHealthStatsEntry
    MAX-ACCESS       not-accessible
    STATUS           current
    DESCRIPTION
        "Entry for the cucsStorageSsdHealthStatsTable table."
    INDEX { cucsStorageSsdHealthStatsInstanceId }
    ::= { cucsStorageSsdHealthStatsTable 1 }

CucsStorageSsdHealthStatsEntry ::= SEQUENCE {
    cucsStorageSsdHealthStatsInstanceId                              CucsManagedObjectId,
    cucsStorageSsdHealthStatsDn                                      CucsManagedObjectDn,
    cucsStorageSsdHealthStatsRn                                      SnmpAdminString,
    cucsStorageSsdHealthStatsId                                      Gauge32,
    cucsStorageSsdHealthStatsIntervals                               Gauge32,
    cucsStorageSsdHealthStatsPercentageLifeLeft                      Gauge32,
    cucsStorageSsdHealthStatsPercentageLifeLeftAvg                   Gauge32,
    cucsStorageSsdHealthStatsPercentageLifeLeftMax                   Gauge32,
    cucsStorageSsdHealthStatsPercentageLifeLeftMin                   Gauge32,
    cucsStorageSsdHealthStatsPowerCycleCount                         Unsigned64,
    cucsStorageSsdHealthStatsPowerCycleCountAvg                      Unsigned64,
    cucsStorageSsdHealthStatsPowerCycleCountMax                      Unsigned64,
    cucsStorageSsdHealthStatsPowerCycleCountMin                      Unsigned64,
    cucsStorageSsdHealthStatsPowerOnHours                            Unsigned64,
    cucsStorageSsdHealthStatsPowerOnHoursAvg                         Unsigned64,
    cucsStorageSsdHealthStatsPowerOnHoursMax                         Unsigned64,
    cucsStorageSsdHealthStatsPowerOnHoursMin                         Unsigned64,
    cucsStorageSsdHealthStatsSuspect                                 TruthValue,
    cucsStorageSsdHealthStatsThresholded                             CucsStorageSsdHealthStatsThresholded,
    cucsStorageSsdHealthStatsTimeCollected                           DateAndTime,
    cucsStorageSsdHealthStatsUpdate                                  Gauge32,
    cucsStorageSsdHealthStatsWearStatusInDays                        Unsigned64,
    cucsStorageSsdHealthStatsWearStatusInDaysAvg                     Unsigned64,
    cucsStorageSsdHealthStatsWearStatusInDaysMax                     Unsigned64,
    cucsStorageSsdHealthStatsWearStatusInDaysMin                     Unsigned64
}

cucsStorageSsdHealthStatsInstanceId OBJECT-TYPE
    SYNTAX       CucsManagedObjectId
    MAX-ACCESS   not-accessible
    STATUS       current
    DESCRIPTION
        "Instance identifier of the managed object."
    ::= { cucsStorageSsdHealthStatsEntry 1 }

cucsStorageSsdHealthStatsDn OBJECT-TYPE
    SYNTAX       CucsManagedObjectDn
    MAX-ACCESS   read-only
    STATUS       current
    DESCRIPTION
        "Cisco UCS storage:SsdHealthStats:dn managed object property"
    ::= { cucsStorageSsdHealthStatsEntry 2 }

cucsStorageSsdHealthStatsRn OBJECT-TYPE
    SYNTAX       SnmpAdminString
    MAX-ACCESS   read-only
    STATUS       current
    DESCRIPTION
        "Cisco UCS storage:SsdHealthStats:rn managed object property"
    ::= { cucsStorageSsdHealthStatsEntry 3 }

cucsStorageSsdHealthStatsId OBJECT-TYPE
    SYNTAX       Gauge32
    MAX-ACCESS   read-only
    STATUS       current
    DESCRIPTION
        "Cisco UCS storage:SsdHealthStats:id managed object property"
    ::= { cucsStorageSsdHealthStatsEntry 4 }

cucsStorageSsdHealthStatsIntervals OBJECT-TYPE
    SYNTAX       Gauge32
    MAX-ACCESS   read-only
    STATUS       current
    DESCRIPTION
        "Cisco UCS storage:SsdHealthStats:intervals managed
        object property"
    ::= { cucsStorageSsdHealthStatsEntry 5 }

cucsStorageSsdHealthStatsPercentageLifeLeft OBJECT-TYPE
    SYNTAX       Gauge32
    MAX-ACCESS   read-only
    STATUS       current
    DESCRIPTION
        "Cisco UCS storage:SsdHealthStats:percentageLifeLeft
        managed object property"
    ::= { cucsStorageSsdHealthStatsEntry 6 }

cucsStorageSsdHealthStatsPercentageLifeLeftAvg OBJECT-TYPE
    SYNTAX       Gauge32
    MAX-ACCESS   read-only
    STATUS       current
    DESCRIPTION
        "Cisco UCS storage:SsdHealthStats:percentageLifeLeftAvg
        managed object property"
    ::= { cucsStorageSsdHealthStatsEntry 7 }

cucsStorageSsdHealthStatsPercentageLifeLeftMax OBJECT-TYPE
    SYNTAX       Gauge32
    MAX-ACCESS   read-only
    STATUS       current
    DESCRIPTION
        "Cisco UCS storage:SsdHealthStats:percentageLifeLeftMax
        managed object property"
    ::= { cucsStorageSsdHealthStatsEntry 8 }

cucsStorageSsdHealthStatsPercentageLifeLeftMin OBJECT-TYPE
    SYNTAX       Gauge32
    MAX-ACCESS   read-only
    STATUS       current
    DESCRIPTION
        "Cisco UCS storage:SsdHealthStats:percentageLifeLeftMin
        managed object property"
    ::= { cucsStorageSsdHealthStatsEntry 9 }

cucsStorageSsdHealthStatsPowerCycleCount OBJECT-TYPE
    SYNTAX       Unsigned64
    MAX-ACCESS   read-only
    STATUS       current
    DESCRIPTION
        "Cisco UCS storage:SsdHealthStats:powerCycleCount
        managed object property"
    ::= { cucsStorageSsdHealthStatsEntry 10 }

cucsStorageSsdHealthStatsPowerCycleCountAvg OBJECT-TYPE
    SYNTAX       Unsigned64
    MAX-ACCESS   read-only
    STATUS       current
    DESCRIPTION
        "Cisco UCS storage:SsdHealthStats:powerCycleCountAvg
        managed object property"
    ::= { cucsStorageSsdHealthStatsEntry 11 }

cucsStorageSsdHealthStatsPowerCycleCountMax OBJECT-TYPE
    SYNTAX       Unsigned64
    MAX-ACCESS   read-only
    STATUS       current
    DESCRIPTION
        "Cisco UCS storage:SsdHealthStats:powerCycleCountMax
        managed object property"
    ::= { cucsStorageSsdHealthStatsEntry 12 }

cucsStorageSsdHealthStatsPowerCycleCountMin OBJECT-TYPE
    SYNTAX       Unsigned64
    MAX-ACCESS   read-only
    STATUS       current
    DESCRIPTION
        "Cisco UCS storage:SsdHealthStats:powerCycleCountMin
        managed object property"
    ::= { cucsStorageSsdHealthStatsEntry 13 }

cucsStorageSsdHealthStatsPowerOnHours OBJECT-TYPE
    SYNTAX       Unsigned64
    MAX-ACCESS   read-only
    STATUS       current
    DESCRIPTION
        "Cisco UCS storage:SsdHealthStats:powerOnHours
        managed object property"
    ::= { cucsStorageSsdHealthStatsEntry 14 }

cucsStorageSsdHealthStatsPowerOnHoursAvg OBJECT-TYPE
    SYNTAX       Unsigned64
    MAX-ACCESS   read-only
    STATUS       current
    DESCRIPTION
        "Cisco UCS storage:SsdHealthStats:powerOnHoursAvg
        managed object property"
    ::= { cucsStorageSsdHealthStatsEntry 15 }

cucsStorageSsdHealthStatsPowerOnHoursMax OBJECT-TYPE
    SYNTAX       Unsigned64
    MAX-ACCESS   read-only
    STATUS       current
    DESCRIPTION
        "Cisco UCS storage:SsdHealthStats:powerOnHoursMax
        managed object property"
    ::= { cucsStorageSsdHealthStatsEntry 16 }

cucsStorageSsdHealthStatsPowerOnHoursMin OBJECT-TYPE
    SYNTAX       Unsigned64
    MAX-ACCESS   read-only
    STATUS       current
    DESCRIPTION
        "Cisco UCS storage:SsdHealthStats:powerOnHoursMin
        managed object property"
    ::= { cucsStorageSsdHealthStatsEntry 17 }

cucsStorageSsdHealthStatsSuspect OBJECT-TYPE
    SYNTAX       TruthValue
    MAX-ACCESS   read-only
    STATUS       current
    DESCRIPTION
        "Cisco UCS storage:SsdHealthStats:suspect managed object property"
    ::= { cucsStorageSsdHealthStatsEntry 18 }

cucsStorageSsdHealthStatsThresholded OBJECT-TYPE
    SYNTAX       CucsStorageSsdHealthStatsThresholded
    MAX-ACCESS   read-only
    STATUS       current
    DESCRIPTION
        "Cisco UCS storage:SsdHealthStats:thresholded managed
        object property"
    ::= { cucsStorageSsdHealthStatsEntry 19 }

cucsStorageSsdHealthStatsTimeCollected OBJECT-TYPE
    SYNTAX       DateAndTime
    MAX-ACCESS   read-only
    STATUS       current
    DESCRIPTION
        "Cisco UCS storage:SsdHealthStats:timeCollected
        managed object property"
    ::= { cucsStorageSsdHealthStatsEntry 20 }

cucsStorageSsdHealthStatsUpdate OBJECT-TYPE
    SYNTAX       Gauge32
    MAX-ACCESS   read-only
    STATUS       current
    DESCRIPTION
        "Cisco UCS storage:SsdHealthStats:update managed object property"
    ::= { cucsStorageSsdHealthStatsEntry 21 }

cucsStorageSsdHealthStatsWearStatusInDays OBJECT-TYPE
    SYNTAX       Unsigned64
    MAX-ACCESS   read-only
    STATUS       current
    DESCRIPTION
        "Cisco UCS storage:SsdHealthStats:wearStatusInDays
        managed object property"
    ::= { cucsStorageSsdHealthStatsEntry 22 }

cucsStorageSsdHealthStatsWearStatusInDaysAvg OBJECT-TYPE
    SYNTAX       Unsigned64
    MAX-ACCESS   read-only
    STATUS       current
    DESCRIPTION
        "Cisco UCS storage:SsdHealthStats:wearStatusInDaysAvg
        managed object property"
    ::= { cucsStorageSsdHealthStatsEntry 23 }

cucsStorageSsdHealthStatsWearStatusInDaysMax OBJECT-TYPE
    SYNTAX       Unsigned64
    MAX-ACCESS   read-only
    STATUS       current
    DESCRIPTION
        "Cisco UCS storage:SsdHealthStats:wearStatusInDaysMax
        managed object property"
    ::= { cucsStorageSsdHealthStatsEntry 24 }

cucsStorageSsdHealthStatsWearStatusInDaysMin OBJECT-TYPE
    SYNTAX       Unsigned64
    MAX-ACCESS   read-only
    STATUS       current
    DESCRIPTION
        "Cisco UCS storage:SsdHealthStats:wearStatusInDaysMin
        managed object property"
    ::= { cucsStorageSsdHealthStatsEntry 25 }

cucsStorageSsdHealthStatsHistTable OBJECT-TYPE
    SYNTAX           SEQUENCE OF CucsStorageSsdHealthStatsHistEntry
    MAX-ACCESS       not-accessible
    STATUS           current
    DESCRIPTION
        "Cisco UCS storage:SsdHealthStatsHist managed object table"
    ::= { cucsStorageObjects 126 }

cucsStorageSsdHealthStatsHistEntry OBJECT-TYPE
    SYNTAX           CucsStorageSsdHealthStatsHistEntry
    MAX-ACCESS       not-accessible
    STATUS           current
    DESCRIPTION
        "Entry for the cucsStorageSsdHealthStatsHistTable table."
    INDEX { cucsStorageSsdHealthStatsHistInstanceId }
    ::= { cucsStorageSsdHealthStatsHistTable 1 }

CucsStorageSsdHealthStatsHistEntry ::= SEQUENCE {
    cucsStorageSsdHealthStatsHistInstanceId                          CucsManagedObjectId,
    cucsStorageSsdHealthStatsHistDn                                  CucsManagedObjectDn,
    cucsStorageSsdHealthStatsHistRn                                  SnmpAdminString,
    cucsStorageSsdHealthStatsHistId                                  Unsigned64,
    cucsStorageSsdHealthStatsHistMostRecent                          TruthValue,
    cucsStorageSsdHealthStatsHistPercentageLifeLeft                  Gauge32,
    cucsStorageSsdHealthStatsHistPercentageLifeLeftAvg               Gauge32,
    cucsStorageSsdHealthStatsHistPercentageLifeLeftMax               Gauge32,
    cucsStorageSsdHealthStatsHistPercentageLifeLeftMin               Gauge32,
    cucsStorageSsdHealthStatsHistPowerCycleCount                     Unsigned64,
    cucsStorageSsdHealthStatsHistPowerCycleCountAvg                  Unsigned64,
    cucsStorageSsdHealthStatsHistPowerCycleCountMax                  Unsigned64,
    cucsStorageSsdHealthStatsHistPowerCycleCountMin                  Unsigned64,
    cucsStorageSsdHealthStatsHistPowerOnHours                        Unsigned64,
    cucsStorageSsdHealthStatsHistPowerOnHoursAvg                     Unsigned64,
    cucsStorageSsdHealthStatsHistPowerOnHoursMax                     Unsigned64,
    cucsStorageSsdHealthStatsHistPowerOnHoursMin                     Unsigned64,
    cucsStorageSsdHealthStatsHistSuspect                             TruthValue,
    cucsStorageSsdHealthStatsHistThresholded                         CucsStorageSsdHealthStatsHistThresholded,
    cucsStorageSsdHealthStatsHistTimeCollected                       DateAndTime,
    cucsStorageSsdHealthStatsHistWearStatusInDays                    Unsigned64,
    cucsStorageSsdHealthStatsHistWearStatusInDaysAvg                 Unsigned64,
    cucsStorageSsdHealthStatsHistWearStatusInDaysMax                 Unsigned64,
    cucsStorageSsdHealthStatsHistWearStatusInDaysMin                 Unsigned64
}

cucsStorageSsdHealthStatsHistInstanceId OBJECT-TYPE
    SYNTAX       CucsManagedObjectId
    MAX-ACCESS   not-accessible
    STATUS       current
    DESCRIPTION
        "Instance identifier of the managed object."
    ::= { cucsStorageSsdHealthStatsHistEntry 1 }

cucsStorageSsdHealthStatsHistDn OBJECT-TYPE
    SYNTAX       CucsManagedObjectDn
    MAX-ACCESS   read-only
    STATUS       current
    DESCRIPTION
        "Cisco UCS storage:SsdHealthStatsHist:dn managed object property"
    ::= { cucsStorageSsdHealthStatsHistEntry 2 }

cucsStorageSsdHealthStatsHistRn OBJECT-TYPE
    SYNTAX       SnmpAdminString
    MAX-ACCESS   read-only
    STATUS       current
    DESCRIPTION
        "Cisco UCS storage:SsdHealthStatsHist:rn managed object property"
    ::= { cucsStorageSsdHealthStatsHistEntry 3 }

cucsStorageSsdHealthStatsHistId OBJECT-TYPE
    SYNTAX       Unsigned64
    MAX-ACCESS   read-only
    STATUS       current
    DESCRIPTION
        "Cisco UCS storage:SsdHealthStatsHist:id managed object property"
    ::= { cucsStorageSsdHealthStatsHistEntry 4 }

cucsStorageSsdHealthStatsHistMostRecent OBJECT-TYPE
    SYNTAX       TruthValue
    MAX-ACCESS   read-only
    STATUS       current
    DESCRIPTION
        "Cisco UCS storage:SsdHealthStatsHist:mostRecent
        managed object property"
    ::= { cucsStorageSsdHealthStatsHistEntry 5 }

cucsStorageSsdHealthStatsHistPercentageLifeLeft OBJECT-TYPE
    SYNTAX       Gauge32
    MAX-ACCESS   read-only
    STATUS       current
    DESCRIPTION
        "Cisco UCS storage:SsdHealthStatsHist:percentageLifeLeft
        managed object property"
    ::= { cucsStorageSsdHealthStatsHistEntry 6 }

cucsStorageSsdHealthStatsHistPercentageLifeLeftAvg OBJECT-TYPE
    SYNTAX       Gauge32
    MAX-ACCESS   read-only
    STATUS       current
    DESCRIPTION
        "Cisco UCS storage:SsdHealthStatsHist:percentageLifeLeftAvg
        managed object property"
    ::= { cucsStorageSsdHealthStatsHistEntry 7 }

cucsStorageSsdHealthStatsHistPercentageLifeLeftMax OBJECT-TYPE
    SYNTAX       Gauge32
    MAX-ACCESS   read-only
    STATUS       current
    DESCRIPTION
        "Cisco UCS storage:SsdHealthStatsHist:percentageLifeLeftMax
        managed object property"
    ::= { cucsStorageSsdHealthStatsHistEntry 8 }

cucsStorageSsdHealthStatsHistPercentageLifeLeftMin OBJECT-TYPE
    SYNTAX       Gauge32
    MAX-ACCESS   read-only
    STATUS       current
    DESCRIPTION
        "Cisco UCS storage:SsdHealthStatsHist:percentageLifeLeftMin
        managed object property"
    ::= { cucsStorageSsdHealthStatsHistEntry 9 }

cucsStorageSsdHealthStatsHistPowerCycleCount OBJECT-TYPE
    SYNTAX       Unsigned64
    MAX-ACCESS   read-only
    STATUS       current
    DESCRIPTION
        "Cisco UCS storage:SsdHealthStatsHist:powerCycleCount
        managed object property"
    ::= { cucsStorageSsdHealthStatsHistEntry 10 }

cucsStorageSsdHealthStatsHistPowerCycleCountAvg OBJECT-TYPE
    SYNTAX       Unsigned64
    MAX-ACCESS   read-only
    STATUS       current
    DESCRIPTION
        "Cisco UCS storage:SsdHealthStatsHist:powerCycleCountAvg
        managed object property"
    ::= { cucsStorageSsdHealthStatsHistEntry 11 }

cucsStorageSsdHealthStatsHistPowerCycleCountMax OBJECT-TYPE
    SYNTAX       Unsigned64
    MAX-ACCESS   read-only
    STATUS       current
    DESCRIPTION
        "Cisco UCS storage:SsdHealthStatsHist:powerCycleCountMax
        managed object property"
    ::= { cucsStorageSsdHealthStatsHistEntry 12 }

cucsStorageSsdHealthStatsHistPowerCycleCountMin OBJECT-TYPE
    SYNTAX       Unsigned64
    MAX-ACCESS   read-only
    STATUS       current
    DESCRIPTION
        "Cisco UCS storage:SsdHealthStatsHist:powerCycleCountMin
        managed object property"
    ::= { cucsStorageSsdHealthStatsHistEntry 13 }

cucsStorageSsdHealthStatsHistPowerOnHours OBJECT-TYPE
    SYNTAX       Unsigned64
    MAX-ACCESS   read-only
    STATUS       current
    DESCRIPTION
        "Cisco UCS storage:SsdHealthStatsHist:powerOnHours
        managed object property"
    ::= { cucsStorageSsdHealthStatsHistEntry 14 }

cucsStorageSsdHealthStatsHistPowerOnHoursAvg OBJECT-TYPE
    SYNTAX       Unsigned64
    MAX-ACCESS   read-only
    STATUS       current
    DESCRIPTION
        "Cisco UCS storage:SsdHealthStatsHist:powerOnHoursAvg
        managed object property"
    ::= { cucsStorageSsdHealthStatsHistEntry 15 }

cucsStorageSsdHealthStatsHistPowerOnHoursMax OBJECT-TYPE
    SYNTAX       Unsigned64
    MAX-ACCESS   read-only
    STATUS       current
    DESCRIPTION
        "Cisco UCS storage:SsdHealthStatsHist:powerOnHoursMax
        managed object property"
    ::= { cucsStorageSsdHealthStatsHistEntry 16 }

cucsStorageSsdHealthStatsHistPowerOnHoursMin OBJECT-TYPE
    SYNTAX       Unsigned64
    MAX-ACCESS   read-only
    STATUS       current
    DESCRIPTION
        "Cisco UCS storage:SsdHealthStatsHist:powerOnHoursMin
        managed object property"
    ::= { cucsStorageSsdHealthStatsHistEntry 17 }

cucsStorageSsdHealthStatsHistSuspect OBJECT-TYPE
    SYNTAX       TruthValue
    MAX-ACCESS   read-only
    STATUS       current
    DESCRIPTION
        "Cisco UCS storage:SsdHealthStatsHist:suspect managed
        object property"
    ::= { cucsStorageSsdHealthStatsHistEntry 18 }

cucsStorageSsdHealthStatsHistThresholded OBJECT-TYPE
    SYNTAX       CucsStorageSsdHealthStatsHistThresholded
    MAX-ACCESS   read-only
    STATUS       current
    DESCRIPTION
        "Cisco UCS storage:SsdHealthStatsHist:thresholded
        managed object property"
    ::= { cucsStorageSsdHealthStatsHistEntry 19 }

cucsStorageSsdHealthStatsHistTimeCollected OBJECT-TYPE
    SYNTAX       DateAndTime
    MAX-ACCESS   read-only
    STATUS       current
    DESCRIPTION
        "Cisco UCS storage:SsdHealthStatsHist:timeCollected
        managed object property"
    ::= { cucsStorageSsdHealthStatsHistEntry 20 }

cucsStorageSsdHealthStatsHistWearStatusInDays OBJECT-TYPE
    SYNTAX       Unsigned64
    MAX-ACCESS   read-only
    STATUS       current
    DESCRIPTION
        "Cisco UCS storage:SsdHealthStatsHist:wearStatusInDays
        managed object property"
    ::= { cucsStorageSsdHealthStatsHistEntry 21 }

cucsStorageSsdHealthStatsHistWearStatusInDaysAvg OBJECT-TYPE
    SYNTAX       Unsigned64
    MAX-ACCESS   read-only
    STATUS       current
    DESCRIPTION
        "Cisco UCS storage:SsdHealthStatsHist:wearStatusInDaysAvg
        managed object property"
    ::= { cucsStorageSsdHealthStatsHistEntry 22 }

cucsStorageSsdHealthStatsHistWearStatusInDaysMax OBJECT-TYPE
    SYNTAX       Unsigned64
    MAX-ACCESS   read-only
    STATUS       current
    DESCRIPTION
        "Cisco UCS storage:SsdHealthStatsHist:wearStatusInDaysMax
        managed object property"
    ::= { cucsStorageSsdHealthStatsHistEntry 23 }

cucsStorageSsdHealthStatsHistWearStatusInDaysMin OBJECT-TYPE
    SYNTAX       Unsigned64
    MAX-ACCESS   read-only
    STATUS       current
    DESCRIPTION
        "Cisco UCS storage:SsdHealthStatsHist:wearStatusInDaysMin
        managed object property"
    ::= { cucsStorageSsdHealthStatsHistEntry 24 }

cucsStorageSystemTable OBJECT-TYPE
    SYNTAX           SEQUENCE OF CucsStorageSystemEntry
    MAX-ACCESS       not-accessible
    STATUS           current
    DESCRIPTION
        "Cisco UCS storage:System managed object table"
    ::= { cucsStorageObjects 27 }

cucsStorageSystemEntry OBJECT-TYPE
    SYNTAX           CucsStorageSystemEntry
    MAX-ACCESS       not-accessible
    STATUS           current
    DESCRIPTION
        "Entry for the cucsStorageSystemTable table."
    INDEX { cucsStorageSystemInstanceId }
    ::= { cucsStorageSystemTable 1 }

CucsStorageSystemEntry ::= SEQUENCE {
    cucsStorageSystemInstanceId                                      CucsManagedObjectId,
    cucsStorageSystemDn                                              CucsManagedObjectDn,
    cucsStorageSystemRn                                              SnmpAdminString,
    cucsStorageSystemFsmDescr                                        SnmpAdminString,
    cucsStorageSystemFsmPrev                                         SnmpAdminString,
    cucsStorageSystemFsmProgr                                        Gauge32,
    cucsStorageSystemFsmRmtInvErrCode                                Gauge32,
    cucsStorageSystemFsmRmtInvErrDescr                               SnmpAdminString,
    cucsStorageSystemFsmRmtInvRslt                                   CucsConditionRemoteInvRslt,
    cucsStorageSystemFsmStageDescr                                   SnmpAdminString,
    cucsStorageSystemFsmStamp                                        DateAndTime,
    cucsStorageSystemFsmStatus                                       SnmpAdminString,
    cucsStorageSystemFsmTry                                          Gauge32,
    cucsStorageSystemId                                              SnmpAdminString,
    cucsStorageSystemName                                            SnmpAdminString
}

cucsStorageSystemInstanceId OBJECT-TYPE
    SYNTAX       CucsManagedObjectId
    MAX-ACCESS   not-accessible
    STATUS       current
    DESCRIPTION
        "Instance identifier of the managed object."
    ::= { cucsStorageSystemEntry 1 }

cucsStorageSystemDn OBJECT-TYPE
    SYNTAX       CucsManagedObjectDn
    MAX-ACCESS   read-only
    STATUS       current
    DESCRIPTION
        "Cisco UCS storage:System:dn managed object property"
    ::= { cucsStorageSystemEntry 2 }

cucsStorageSystemRn OBJECT-TYPE
    SYNTAX       SnmpAdminString
    MAX-ACCESS   read-only
    STATUS       current
    DESCRIPTION
        "Cisco UCS storage:System:rn managed object property"
    ::= { cucsStorageSystemEntry 3 }

cucsStorageSystemFsmDescr OBJECT-TYPE
    SYNTAX       SnmpAdminString
    MAX-ACCESS   read-only
    STATUS       current
    DESCRIPTION
        "Cisco UCS storage:System:fsmDescr managed object property"
    ::= { cucsStorageSystemEntry 4 }

cucsStorageSystemFsmPrev OBJECT-TYPE
    SYNTAX       SnmpAdminString
    MAX-ACCESS   read-only
    STATUS       current
    DESCRIPTION
        "Cisco UCS storage:System:fsmPrev managed object property"
    ::= { cucsStorageSystemEntry 5 }

cucsStorageSystemFsmProgr OBJECT-TYPE
    SYNTAX       Gauge32
    MAX-ACCESS   read-only
    STATUS       current
    DESCRIPTION
        "Cisco UCS storage:System:fsmProgr managed object property"
    ::= { cucsStorageSystemEntry 6 }

cucsStorageSystemFsmRmtInvErrCode OBJECT-TYPE
    SYNTAX       Gauge32
    MAX-ACCESS   read-only
    STATUS       current
    DESCRIPTION
        "Cisco UCS storage:System:fsmRmtInvErrCode managed
        object property"
    ::= { cucsStorageSystemEntry 7 }

cucsStorageSystemFsmRmtInvErrDescr OBJECT-TYPE
    SYNTAX       SnmpAdminString
    MAX-ACCESS   read-only
    STATUS       current
    DESCRIPTION
        "Cisco UCS storage:System:fsmRmtInvErrDescr managed
        object property"
    ::= { cucsStorageSystemEntry 8 }

cucsStorageSystemFsmRmtInvRslt OBJECT-TYPE
    SYNTAX       CucsConditionRemoteInvRslt
    MAX-ACCESS   read-only
    STATUS       current
    DESCRIPTION
        "Cisco UCS storage:System:fsmRmtInvRslt managed object property"
    ::= { cucsStorageSystemEntry 9 }

cucsStorageSystemFsmStageDescr OBJECT-TYPE
    SYNTAX       SnmpAdminString
    MAX-ACCESS   read-only
    STATUS       current
    DESCRIPTION
        "Cisco UCS storage:System:fsmStageDescr managed object property"
    ::= { cucsStorageSystemEntry 10 }

cucsStorageSystemFsmStamp OBJECT-TYPE
    SYNTAX       DateAndTime
    MAX-ACCESS   read-only
    STATUS       current
    DESCRIPTION
        "Cisco UCS storage:System:fsmStamp managed object property"
    ::= { cucsStorageSystemEntry 11 }

cucsStorageSystemFsmStatus OBJECT-TYPE
    SYNTAX       SnmpAdminString
    MAX-ACCESS   read-only
    STATUS       current
    DESCRIPTION
        "Cisco UCS storage:System:fsmStatus managed object property"
    ::= { cucsStorageSystemEntry 12 }

cucsStorageSystemFsmTry OBJECT-TYPE
    SYNTAX       Gauge32
    MAX-ACCESS   read-only
    STATUS       current
    DESCRIPTION
        "Cisco UCS storage:System:fsmTry managed object property"
    ::= { cucsStorageSystemEntry 13 }

cucsStorageSystemId OBJECT-TYPE
    SYNTAX       SnmpAdminString
    MAX-ACCESS   read-only
    STATUS       current
    DESCRIPTION
        "Cisco UCS storage:System:id managed object property"
    ::= { cucsStorageSystemEntry 14 }

cucsStorageSystemName OBJECT-TYPE
    SYNTAX       SnmpAdminString
    MAX-ACCESS   read-only
    STATUS       current
    DESCRIPTION
        "Cisco UCS storage:System:name managed object property"
    ::= { cucsStorageSystemEntry 15 }

cucsStorageSystemFsmTable OBJECT-TYPE
    SYNTAX           SEQUENCE OF CucsStorageSystemFsmEntry
    MAX-ACCESS       not-accessible
    STATUS           current
    DESCRIPTION
        "Cisco UCS storage:SystemFsm managed object table"
    ::= { cucsStorageObjects 28 }

cucsStorageSystemFsmEntry OBJECT-TYPE
    SYNTAX           CucsStorageSystemFsmEntry
    MAX-ACCESS       not-accessible
    STATUS           current
    DESCRIPTION
        "Entry for the cucsStorageSystemFsmTable table."
    INDEX { cucsStorageSystemFsmInstanceId }
    ::= { cucsStorageSystemFsmTable 1 }

CucsStorageSystemFsmEntry ::= SEQUENCE {
    cucsStorageSystemFsmInstanceId                                   CucsManagedObjectId,
    cucsStorageSystemFsmDn                                           CucsManagedObjectDn,
    cucsStorageSystemFsmRn                                           SnmpAdminString,
    cucsStorageSystemFsmCompletionTime                               DateAndTime,
    cucsStorageSystemFsmCurrentFsm                                   CucsStorageSystemFsmCurrentFsm,
    cucsStorageSystemFsmDescrData                                    SnmpAdminString,
    cucsStorageSystemFsmFsmStatus                                    CucsFsmFsmStageStatus,
    cucsStorageSystemFsmProgress                                     Gauge32,
    cucsStorageSystemFsmRmtErrCode                                   Gauge32,
    cucsStorageSystemFsmRmtErrDescr                                  SnmpAdminString,
    cucsStorageSystemFsmRmtRslt                                      CucsConditionRemoteInvRslt
}

cucsStorageSystemFsmInstanceId OBJECT-TYPE
    SYNTAX       CucsManagedObjectId
    MAX-ACCESS   not-accessible
    STATUS       current
    DESCRIPTION
        "Instance identifier of the managed object."
    ::= { cucsStorageSystemFsmEntry 1 }

cucsStorageSystemFsmDn OBJECT-TYPE
    SYNTAX       CucsManagedObjectDn
    MAX-ACCESS   read-only
    STATUS       current
    DESCRIPTION
        "Cisco UCS storage:SystemFsm:dn managed object property"
    ::= { cucsStorageSystemFsmEntry 2 }

cucsStorageSystemFsmRn OBJECT-TYPE
    SYNTAX       SnmpAdminString
    MAX-ACCESS   read-only
    STATUS       current
    DESCRIPTION
        "Cisco UCS storage:SystemFsm:rn managed object property"
    ::= { cucsStorageSystemFsmEntry 3 }

cucsStorageSystemFsmCompletionTime OBJECT-TYPE
    SYNTAX       DateAndTime
    MAX-ACCESS   read-only
    STATUS       current
    DESCRIPTION
        "Cisco UCS storage:SystemFsm:completionTime managed
        object property"
    ::= { cucsStorageSystemFsmEntry 4 }

cucsStorageSystemFsmCurrentFsm OBJECT-TYPE
    SYNTAX       CucsStorageSystemFsmCurrentFsm
    MAX-ACCESS   read-only
    STATUS       current
    DESCRIPTION
        "Cisco UCS storage:SystemFsm:currentFsm managed object property"
    ::= { cucsStorageSystemFsmEntry 5 }

cucsStorageSystemFsmDescrData OBJECT-TYPE
    SYNTAX       SnmpAdminString
    MAX-ACCESS   read-only
    STATUS       current
    DESCRIPTION
        "Cisco UCS storage:SystemFsm:descr managed object property"
    ::= { cucsStorageSystemFsmEntry 6 }

cucsStorageSystemFsmFsmStatus OBJECT-TYPE
    SYNTAX       CucsFsmFsmStageStatus
    MAX-ACCESS   read-only
    STATUS       current
    DESCRIPTION
        "Cisco UCS storage:SystemFsm:fsmStatus managed object property"
    ::= { cucsStorageSystemFsmEntry 7 }

cucsStorageSystemFsmProgress OBJECT-TYPE
    SYNTAX       Gauge32
    MAX-ACCESS   read-only
    STATUS       current
    DESCRIPTION
        "Cisco UCS storage:SystemFsm:progress managed object property"
    ::= { cucsStorageSystemFsmEntry 8 }

cucsStorageSystemFsmRmtErrCode OBJECT-TYPE
    SYNTAX       Gauge32
    MAX-ACCESS   read-only
    STATUS       current
    DESCRIPTION
        "Cisco UCS storage:SystemFsm:rmtErrCode managed object property"
    ::= { cucsStorageSystemFsmEntry 9 }

cucsStorageSystemFsmRmtErrDescr OBJECT-TYPE
    SYNTAX       SnmpAdminString
    MAX-ACCESS   read-only
    STATUS       current
    DESCRIPTION
        "Cisco UCS storage:SystemFsm:rmtErrDescr managed object property"
    ::= { cucsStorageSystemFsmEntry 10 }

cucsStorageSystemFsmRmtRslt OBJECT-TYPE
    SYNTAX       CucsConditionRemoteInvRslt
    MAX-ACCESS   read-only
    STATUS       current
    DESCRIPTION
        "Cisco UCS storage:SystemFsm:rmtRslt managed object property"
    ::= { cucsStorageSystemFsmEntry 11 }

cucsStorageSystemFsmStageTable OBJECT-TYPE
    SYNTAX           SEQUENCE OF CucsStorageSystemFsmStageEntry
    MAX-ACCESS       not-accessible
    STATUS           current
    DESCRIPTION
        "Cisco UCS storage:SystemFsmStage managed object table"
    ::= { cucsStorageObjects 29 }

cucsStorageSystemFsmStageEntry OBJECT-TYPE
    SYNTAX           CucsStorageSystemFsmStageEntry
    MAX-ACCESS       not-accessible
    STATUS           current
    DESCRIPTION
        "Entry for the cucsStorageSystemFsmStageTable table."
    INDEX { cucsStorageSystemFsmStageInstanceId }
    ::= { cucsStorageSystemFsmStageTable 1 }

CucsStorageSystemFsmStageEntry ::= SEQUENCE {
    cucsStorageSystemFsmStageInstanceId                              CucsManagedObjectId,
    cucsStorageSystemFsmStageDn                                      CucsManagedObjectDn,
    cucsStorageSystemFsmStageRn                                      SnmpAdminString,
    cucsStorageSystemFsmStageDescrData                               SnmpAdminString,
    cucsStorageSystemFsmStageLastUpdateTime                          DateAndTime,
    cucsStorageSystemFsmStageName                                    CucsStorageSystemFsmStageName,
    cucsStorageSystemFsmStageOrder                                   Gauge32,
    cucsStorageSystemFsmStageRetry                                   Gauge32,
    cucsStorageSystemFsmStageStageStatus                             CucsFsmFsmStageStatus
}

cucsStorageSystemFsmStageInstanceId OBJECT-TYPE
    SYNTAX       CucsManagedObjectId
    MAX-ACCESS   not-accessible
    STATUS       current
    DESCRIPTION
        "Instance identifier of the managed object."
    ::= { cucsStorageSystemFsmStageEntry 1 }

cucsStorageSystemFsmStageDn OBJECT-TYPE
    SYNTAX       CucsManagedObjectDn
    MAX-ACCESS   read-only
    STATUS       current
    DESCRIPTION
        "Cisco UCS storage:SystemFsmStage:dn managed object property"
    ::= { cucsStorageSystemFsmStageEntry 2 }

cucsStorageSystemFsmStageRn OBJECT-TYPE
    SYNTAX       SnmpAdminString
    MAX-ACCESS   read-only
    STATUS       current
    DESCRIPTION
        "Cisco UCS storage:SystemFsmStage:rn managed object property"
    ::= { cucsStorageSystemFsmStageEntry 3 }

cucsStorageSystemFsmStageDescrData OBJECT-TYPE
    SYNTAX       SnmpAdminString
    MAX-ACCESS   read-only
    STATUS       current
    DESCRIPTION
        "Cisco UCS storage:SystemFsmStage:descr managed object property"
    ::= { cucsStorageSystemFsmStageEntry 4 }

cucsStorageSystemFsmStageLastUpdateTime OBJECT-TYPE
    SYNTAX       DateAndTime
    MAX-ACCESS   read-only
    STATUS       current
    DESCRIPTION
        "Cisco UCS storage:SystemFsmStage:lastUpdateTime
        managed object property"
    ::= { cucsStorageSystemFsmStageEntry 5 }

cucsStorageSystemFsmStageName OBJECT-TYPE
    SYNTAX       CucsStorageSystemFsmStageName
    MAX-ACCESS   read-only
    STATUS       current
    DESCRIPTION
        "Cisco UCS storage:SystemFsmStage:name managed object property"
    ::= { cucsStorageSystemFsmStageEntry 6 }

cucsStorageSystemFsmStageOrder OBJECT-TYPE
    SYNTAX       Gauge32
    MAX-ACCESS   read-only
    STATUS       current
    DESCRIPTION
        "Cisco UCS storage:SystemFsmStage:order managed object property"
    ::= { cucsStorageSystemFsmStageEntry 7 }

cucsStorageSystemFsmStageRetry OBJECT-TYPE
    SYNTAX       Gauge32
    MAX-ACCESS   read-only
    STATUS       current
    DESCRIPTION
        "Cisco UCS storage:SystemFsmStage:retry managed object property"
    ::= { cucsStorageSystemFsmStageEntry 8 }

cucsStorageSystemFsmStageStageStatus OBJECT-TYPE
    SYNTAX       CucsFsmFsmStageStatus
    MAX-ACCESS   read-only
    STATUS       current
    DESCRIPTION
        "Cisco UCS storage:SystemFsmStage:stageStatus managed
        object property"
    ::= { cucsStorageSystemFsmStageEntry 9 }

cucsStorageSystemFsmTaskTable OBJECT-TYPE
    SYNTAX           SEQUENCE OF CucsStorageSystemFsmTaskEntry
    MAX-ACCESS       not-accessible
    STATUS           current
    DESCRIPTION
        "Cisco UCS storage:SystemFsmTask managed object table"
    ::= { cucsStorageObjects 30 }

cucsStorageSystemFsmTaskEntry OBJECT-TYPE
    SYNTAX           CucsStorageSystemFsmTaskEntry
    MAX-ACCESS       not-accessible
    STATUS           current
    DESCRIPTION
        "Entry for the cucsStorageSystemFsmTaskTable table."
    INDEX { cucsStorageSystemFsmTaskInstanceId }
    ::= { cucsStorageSystemFsmTaskTable 1 }

CucsStorageSystemFsmTaskEntry ::= SEQUENCE {
    cucsStorageSystemFsmTaskInstanceId                               CucsManagedObjectId,
    cucsStorageSystemFsmTaskDn                                       CucsManagedObjectDn,
    cucsStorageSystemFsmTaskRn                                       SnmpAdminString,
    cucsStorageSystemFsmTaskCompletion                               CucsFsmCompletion,
    cucsStorageSystemFsmTaskFlags                                    CucsFsmFlags,
    cucsStorageSystemFsmTaskItem                                     CucsStorageSystemFsmTaskItem,
    cucsStorageSystemFsmTaskSeqId                                    Gauge32
}

cucsStorageSystemFsmTaskInstanceId OBJECT-TYPE
    SYNTAX       CucsManagedObjectId
    MAX-ACCESS   not-accessible
    STATUS       current
    DESCRIPTION
        "Instance identifier of the managed object."
    ::= { cucsStorageSystemFsmTaskEntry 1 }

cucsStorageSystemFsmTaskDn OBJECT-TYPE
    SYNTAX       CucsManagedObjectDn
    MAX-ACCESS   read-only
    STATUS       current
    DESCRIPTION
        "Cisco UCS storage:SystemFsmTask:dn managed object property"
    ::= { cucsStorageSystemFsmTaskEntry 2 }

cucsStorageSystemFsmTaskRn OBJECT-TYPE
    SYNTAX       SnmpAdminString
    MAX-ACCESS   read-only
    STATUS       current
    DESCRIPTION
        "Cisco UCS storage:SystemFsmTask:rn managed object property"
    ::= { cucsStorageSystemFsmTaskEntry 3 }

cucsStorageSystemFsmTaskCompletion OBJECT-TYPE
    SYNTAX       CucsFsmCompletion
    MAX-ACCESS   read-only
    STATUS       current
    DESCRIPTION
        "Cisco UCS storage:SystemFsmTask:completion managed
        object property"
    ::= { cucsStorageSystemFsmTaskEntry 4 }

cucsStorageSystemFsmTaskFlags OBJECT-TYPE
    SYNTAX       CucsFsmFlags
    MAX-ACCESS   read-only
    STATUS       current
    DESCRIPTION
        "Cisco UCS storage:SystemFsmTask:flags managed object property"
    ::= { cucsStorageSystemFsmTaskEntry 5 }

cucsStorageSystemFsmTaskItem OBJECT-TYPE
    SYNTAX       CucsStorageSystemFsmTaskItem
    MAX-ACCESS   read-only
    STATUS       current
    DESCRIPTION
        "Cisco UCS storage:SystemFsmTask:item managed object property"
    ::= { cucsStorageSystemFsmTaskEntry 6 }

cucsStorageSystemFsmTaskSeqId OBJECT-TYPE
    SYNTAX       Gauge32
    MAX-ACCESS   read-only
    STATUS       current
    DESCRIPTION
        "Cisco UCS storage:SystemFsmTask:seqId managed object property"
    ::= { cucsStorageSystemFsmTaskEntry 7 }

cucsStorageTransportableFlashModuleTable OBJECT-TYPE
    SYNTAX           SEQUENCE OF CucsStorageTransportableFlashModuleEntry
    MAX-ACCESS       not-accessible
    STATUS           current
    DESCRIPTION
        "Cisco UCS storage:TransportableFlashModule managed object table"
    ::= { cucsStorageObjects 33 }

cucsStorageTransportableFlashModuleEntry OBJECT-TYPE
    SYNTAX           CucsStorageTransportableFlashModuleEntry
    MAX-ACCESS       not-accessible
    STATUS           current
    DESCRIPTION
        "Entry for the cucsStorageTransportableFlashModuleTable table."
    INDEX { cucsStorageTransportableFlashModuleInstanceId }
    ::= { cucsStorageTransportableFlashModuleTable 1 }

CucsStorageTransportableFlashModuleEntry ::= SEQUENCE {
    cucsStorageTransportableFlashModuleInstanceId                    CucsManagedObjectId,
    cucsStorageTransportableFlashModuleDn                            CucsManagedObjectDn,
    cucsStorageTransportableFlashModuleRn                            SnmpAdminString,
    cucsStorageTransportableFlashModuleBlockSize                     Gauge32,
    cucsStorageTransportableFlashModuleConnectionProtocol            CucsStorageConnectionProtocol,
    cucsStorageTransportableFlashModuleId                            Gauge32,
    cucsStorageTransportableFlashModuleModel                         SnmpAdminString,
    cucsStorageTransportableFlashModuleNumberOfBlocks                Unsigned64,
    cucsStorageTransportableFlashModuleOperQualifierReason           SnmpAdminString,
    cucsStorageTransportableFlashModuleOperability                   CucsEquipmentOperability,
    cucsStorageTransportableFlashModulePresence                      CucsEquipmentPresence,
    cucsStorageTransportableFlashModuleRevision                      SnmpAdminString,
    cucsStorageTransportableFlashModuleSerial                        SnmpAdminString,
    cucsStorageTransportableFlashModuleSize                          Unsigned64,
    cucsStorageTransportableFlashModuleVendor                        SnmpAdminString,
    cucsStorageTransportableFlashModulePhysicalBlockSize             Gauge32
}

cucsStorageTransportableFlashModuleInstanceId OBJECT-TYPE
    SYNTAX       CucsManagedObjectId
    MAX-ACCESS   not-accessible
    STATUS       current
    DESCRIPTION
        "Instance identifier of the managed object."
    ::= { cucsStorageTransportableFlashModuleEntry 1 }

cucsStorageTransportableFlashModuleDn OBJECT-TYPE
    SYNTAX       CucsManagedObjectDn
    MAX-ACCESS   read-only
    STATUS       current
    DESCRIPTION
        "Cisco UCS storage:TransportableFlashModule:dn
        managed object property"
    ::= { cucsStorageTransportableFlashModuleEntry 2 }

cucsStorageTransportableFlashModuleRn OBJECT-TYPE
    SYNTAX       SnmpAdminString
    MAX-ACCESS   read-only
    STATUS       current
    DESCRIPTION
        "Cisco UCS storage:TransportableFlashModule:rn
        managed object property"
    ::= { cucsStorageTransportableFlashModuleEntry 3 }

cucsStorageTransportableFlashModuleBlockSize OBJECT-TYPE
    SYNTAX       Gauge32
    MAX-ACCESS   read-only
    STATUS       current
    DESCRIPTION
        "Cisco UCS storage:TransportableFlashModule:blockSize
        managed object property"
    ::= { cucsStorageTransportableFlashModuleEntry 4 }

cucsStorageTransportableFlashModuleConnectionProtocol OBJECT-TYPE
    SYNTAX       CucsStorageConnectionProtocol
    MAX-ACCESS   read-only
    STATUS       current
    DESCRIPTION
        "Cisco UCS storage:TransportableFlashModule:connectionProtocol
        managed object property"
    ::= { cucsStorageTransportableFlashModuleEntry 5 }

cucsStorageTransportableFlashModuleId OBJECT-TYPE
    SYNTAX       Gauge32
    MAX-ACCESS   read-only
    STATUS       current
    DESCRIPTION
        "Cisco UCS storage:TransportableFlashModule:id
        managed object property"
    ::= { cucsStorageTransportableFlashModuleEntry 6 }

cucsStorageTransportableFlashModuleModel OBJECT-TYPE
    SYNTAX       SnmpAdminString
    MAX-ACCESS   read-only
    STATUS       current
    DESCRIPTION
        "Cisco UCS storage:TransportableFlashModule:model
        managed object property"
    ::= { cucsStorageTransportableFlashModuleEntry 7 }

cucsStorageTransportableFlashModuleNumberOfBlocks OBJECT-TYPE
    SYNTAX       Unsigned64
    MAX-ACCESS   read-only
    STATUS       current
    DESCRIPTION
        "Cisco UCS storage:TransportableFlashModule:numberOfBlocks
        managed object property"
    ::= { cucsStorageTransportableFlashModuleEntry 8 }

cucsStorageTransportableFlashModuleOperQualifierReason OBJECT-TYPE
    SYNTAX       SnmpAdminString
    MAX-ACCESS   read-only
    STATUS       current
    DESCRIPTION
        "Cisco UCS storage:TransportableFlashModule:operQualifierReason
        managed object property"
    ::= { cucsStorageTransportableFlashModuleEntry 9 }

cucsStorageTransportableFlashModuleOperability OBJECT-TYPE
    SYNTAX       CucsEquipmentOperability
    MAX-ACCESS   read-only
    STATUS       current
    DESCRIPTION
        "Cisco UCS storage:TransportableFlashModule:operability
        managed object property"
    ::= { cucsStorageTransportableFlashModuleEntry 10 }

cucsStorageTransportableFlashModulePresence OBJECT-TYPE
    SYNTAX       CucsEquipmentPresence
    MAX-ACCESS   read-only
    STATUS       current
    DESCRIPTION
        "Cisco UCS storage:TransportableFlashModule:presence
        managed object property"
    ::= { cucsStorageTransportableFlashModuleEntry 11 }

cucsStorageTransportableFlashModuleRevision OBJECT-TYPE
    SYNTAX       SnmpAdminString
    MAX-ACCESS   read-only
    STATUS       current
    DESCRIPTION
        "Cisco UCS storage:TransportableFlashModule:revision
        managed object property"
    ::= { cucsStorageTransportableFlashModuleEntry 12 }

cucsStorageTransportableFlashModuleSerial OBJECT-TYPE
    SYNTAX       SnmpAdminString
    MAX-ACCESS   read-only
    STATUS       current
    DESCRIPTION
        "Cisco UCS storage:TransportableFlashModule:serial
        managed object property"
    ::= { cucsStorageTransportableFlashModuleEntry 13 }

cucsStorageTransportableFlashModuleSize OBJECT-TYPE
    SYNTAX       Unsigned64
    MAX-ACCESS   read-only
    STATUS       current
    DESCRIPTION
        "Cisco UCS storage:TransportableFlashModule:size
        managed object property"
    ::= { cucsStorageTransportableFlashModuleEntry 14 }

cucsStorageTransportableFlashModuleVendor OBJECT-TYPE
    SYNTAX       SnmpAdminString
    MAX-ACCESS   read-only
    STATUS       current
    DESCRIPTION
        "Cisco UCS storage:TransportableFlashModule:vendor
        managed object property"
    ::= { cucsStorageTransportableFlashModuleEntry 15 }

cucsStorageTransportableFlashModulePhysicalBlockSize OBJECT-TYPE
    SYNTAX       Gauge32
    MAX-ACCESS   read-only
    STATUS       current
    DESCRIPTION
        "Cisco UCS storage:TransportableFlashModule:physicalBlockSize
        managed object property"
    ::= { cucsStorageTransportableFlashModuleEntry 16 }

cucsStorageVDMemberEpTable OBJECT-TYPE
    SYNTAX           SEQUENCE OF CucsStorageVDMemberEpEntry
    MAX-ACCESS       not-accessible
    STATUS           current
    DESCRIPTION
        "Cisco UCS storage:VDMemberEp managed object table"
    ::= { cucsStorageObjects 90 }

cucsStorageVDMemberEpEntry OBJECT-TYPE
    SYNTAX           CucsStorageVDMemberEpEntry
    MAX-ACCESS       not-accessible
    STATUS           current
    DESCRIPTION
        "Entry for the cucsStorageVDMemberEpTable table."
    INDEX { cucsStorageVDMemberEpInstanceId }
    ::= { cucsStorageVDMemberEpTable 1 }

CucsStorageVDMemberEpEntry ::= SEQUENCE {
    cucsStorageVDMemberEpInstanceId                                  CucsManagedObjectId,
    cucsStorageVDMemberEpDn                                          CucsManagedObjectDn,
    cucsStorageVDMemberEpRn                                          SnmpAdminString,
    cucsStorageVDMemberEpConfigQual                                  CucsStorageVdMemberConfigQualifierType,
    cucsStorageVDMemberEpConfigQualifierReason                       SnmpAdminString,
    cucsStorageVDMemberEpConfigState                                 CucsStorageConfigState,
    cucsStorageVDMemberEpDeployAction                                CucsStorageDeployAction,
    cucsStorageVDMemberEpDiskDn                                      SnmpAdminString,
    cucsStorageVDMemberEpId                                          Gauge32,
    cucsStorageVDMemberEpModel                                       SnmpAdminString,
    cucsStorageVDMemberEpOperQualifierReason                         SnmpAdminString,
    cucsStorageVDMemberEpOperability                                 CucsEquipmentOperability,
    cucsStorageVDMemberEpPresence                                    CucsEquipmentPresence,
    cucsStorageVDMemberEpRevision                                    SnmpAdminString,
    cucsStorageVDMemberEpRole                                        CucsStorageDiskRole,
    cucsStorageVDMemberEpSerial                                      SnmpAdminString,
    cucsStorageVDMemberEpSpanId                                      Gauge32,
    cucsStorageVDMemberEpVendor                                      SnmpAdminString
}

cucsStorageVDMemberEpInstanceId OBJECT-TYPE
    SYNTAX       CucsManagedObjectId
    MAX-ACCESS   not-accessible
    STATUS       current
    DESCRIPTION
        "Instance identifier of the managed object."
    ::= { cucsStorageVDMemberEpEntry 1 }

cucsStorageVDMemberEpDn OBJECT-TYPE
    SYNTAX       CucsManagedObjectDn
    MAX-ACCESS   read-only
    STATUS       current
    DESCRIPTION
        "Cisco UCS storage:VDMemberEp:dn managed object property"
    ::= { cucsStorageVDMemberEpEntry 2 }

cucsStorageVDMemberEpRn OBJECT-TYPE
    SYNTAX       SnmpAdminString
    MAX-ACCESS   read-only
    STATUS       current
    DESCRIPTION
        "Cisco UCS storage:VDMemberEp:rn managed object property"
    ::= { cucsStorageVDMemberEpEntry 3 }

cucsStorageVDMemberEpConfigQual OBJECT-TYPE
    SYNTAX       CucsStorageVdMemberConfigQualifierType
    MAX-ACCESS   read-only
    STATUS       current
    DESCRIPTION
        "Cisco UCS storage:VDMemberEp:configQual managed object property"
    ::= { cucsStorageVDMemberEpEntry 4 }

cucsStorageVDMemberEpConfigQualifierReason OBJECT-TYPE
    SYNTAX       SnmpAdminString
    MAX-ACCESS   read-only
    STATUS       current
    DESCRIPTION
        "Cisco UCS storage:VDMemberEp:configQualifierReason
        managed object property"
    ::= { cucsStorageVDMemberEpEntry 5 }

cucsStorageVDMemberEpConfigState OBJECT-TYPE
    SYNTAX       CucsStorageConfigState
    MAX-ACCESS   read-only
    STATUS       current
    DESCRIPTION
        "Cisco UCS storage:VDMemberEp:configState managed object property"
    ::= { cucsStorageVDMemberEpEntry 6 }

cucsStorageVDMemberEpDeployAction OBJECT-TYPE
    SYNTAX       CucsStorageDeployAction
    MAX-ACCESS   read-only
    STATUS       current
    DESCRIPTION
        "Cisco UCS storage:VDMemberEp:deployAction managed
        object property"
    ::= { cucsStorageVDMemberEpEntry 7 }

cucsStorageVDMemberEpDiskDn OBJECT-TYPE
    SYNTAX       SnmpAdminString
    MAX-ACCESS   read-only
    STATUS       current
    DESCRIPTION
        "Cisco UCS storage:VDMemberEp:diskDn managed object property"
    ::= { cucsStorageVDMemberEpEntry 8 }

cucsStorageVDMemberEpId OBJECT-TYPE
    SYNTAX       Gauge32
    MAX-ACCESS   read-only
    STATUS       current
    DESCRIPTION
        "Cisco UCS storage:VDMemberEp:id managed object property"
    ::= { cucsStorageVDMemberEpEntry 9 }

cucsStorageVDMemberEpModel OBJECT-TYPE
    SYNTAX       SnmpAdminString
    MAX-ACCESS   read-only
    STATUS       current
    DESCRIPTION
        "Cisco UCS storage:VDMemberEp:model managed object property"
    ::= { cucsStorageVDMemberEpEntry 10 }

cucsStorageVDMemberEpOperQualifierReason OBJECT-TYPE
    SYNTAX       SnmpAdminString
    MAX-ACCESS   read-only
    STATUS       current
    DESCRIPTION
        "Cisco UCS storage:VDMemberEp:operQualifierReason
        managed object property"
    ::= { cucsStorageVDMemberEpEntry 11 }

cucsStorageVDMemberEpOperability OBJECT-TYPE
    SYNTAX       CucsEquipmentOperability
    MAX-ACCESS   read-only
    STATUS       current
    DESCRIPTION
        "Cisco UCS storage:VDMemberEp:operability managed object property"
    ::= { cucsStorageVDMemberEpEntry 12 }

cucsStorageVDMemberEpPresence OBJECT-TYPE
    SYNTAX       CucsEquipmentPresence
    MAX-ACCESS   read-only
    STATUS       current
    DESCRIPTION
        "Cisco UCS storage:VDMemberEp:presence managed object property"
    ::= { cucsStorageVDMemberEpEntry 13 }

cucsStorageVDMemberEpRevision OBJECT-TYPE
    SYNTAX       SnmpAdminString
    MAX-ACCESS   read-only
    STATUS       current
    DESCRIPTION
        "Cisco UCS storage:VDMemberEp:revision managed object property"
    ::= { cucsStorageVDMemberEpEntry 14 }

cucsStorageVDMemberEpRole OBJECT-TYPE
    SYNTAX       CucsStorageDiskRole
    MAX-ACCESS   read-only
    STATUS       current
    DESCRIPTION
        "Cisco UCS storage:VDMemberEp:role managed object property"
    ::= { cucsStorageVDMemberEpEntry 15 }

cucsStorageVDMemberEpSerial OBJECT-TYPE
    SYNTAX       SnmpAdminString
    MAX-ACCESS   read-only
    STATUS       current
    DESCRIPTION
        "Cisco UCS storage:VDMemberEp:serial managed object property"
    ::= { cucsStorageVDMemberEpEntry 16 }

cucsStorageVDMemberEpSpanId OBJECT-TYPE
    SYNTAX       Gauge32
    MAX-ACCESS   read-only
    STATUS       current
    DESCRIPTION
        "Cisco UCS storage:VDMemberEp:spanId managed object property"
    ::= { cucsStorageVDMemberEpEntry 17 }

cucsStorageVDMemberEpVendor OBJECT-TYPE
    SYNTAX       SnmpAdminString
    MAX-ACCESS   read-only
    STATUS       current
    DESCRIPTION
        "Cisco UCS storage:VDMemberEp:vendor managed object property"
    ::= { cucsStorageVDMemberEpEntry 18 }

cucsStorageVirtualDriveTable OBJECT-TYPE
    SYNTAX           SEQUENCE OF CucsStorageVirtualDriveEntry
    MAX-ACCESS       not-accessible
    STATUS           current
    DESCRIPTION
        "Cisco UCS storage:VirtualDrive managed object table"
    ::= { cucsStorageObjects 31 }

cucsStorageVirtualDriveEntry OBJECT-TYPE
    SYNTAX           CucsStorageVirtualDriveEntry
    MAX-ACCESS       not-accessible
    STATUS           current
    DESCRIPTION
        "Entry for the cucsStorageVirtualDriveTable table."
    INDEX { cucsStorageVirtualDriveInstanceId }
    ::= { cucsStorageVirtualDriveTable 1 }

CucsStorageVirtualDriveEntry ::= SEQUENCE {
    cucsStorageVirtualDriveInstanceId                                CucsManagedObjectId,
    cucsStorageVirtualDriveDn                                        CucsManagedObjectDn,
    cucsStorageVirtualDriveRn                                        SnmpAdminString,
    cucsStorageVirtualDriveBlockSize                                 Gauge32,
    cucsStorageVirtualDriveConnectionProtocol                        CucsStorageConnectionProtocol,
    cucsStorageVirtualDriveId                                        Gauge32,
    cucsStorageVirtualDriveModel                                     SnmpAdminString,
    cucsStorageVirtualDriveNumberOfBlocks                            Unsigned64,
    cucsStorageVirtualDriveOperQualifierReason                       SnmpAdminString,
    cucsStorageVirtualDriveOperability                               CucsEquipmentOperability,
    cucsStorageVirtualDrivePresence                                  CucsEquipmentPresence,
    cucsStorageVirtualDriveRevision                                  SnmpAdminString,
    cucsStorageVirtualDriveSerial                                    SnmpAdminString,
    cucsStorageVirtualDriveSize                                      Unsigned64,
    cucsStorageVirtualDriveType                                      CucsStorageLunType,
    cucsStorageVirtualDriveVendor                                    SnmpAdminString,
    cucsStorageVirtualDriveAccessPolicy                              CucsStorageAccessType,
    cucsStorageVirtualDriveActualWriteCachePolicy                    CucsStorageActualWriteType,
    cucsStorageVirtualDriveBootable                                  CucsStorageBootableType,
    cucsStorageVirtualDriveConfiguredWriteCachePolicy                CucsStorageConfiguredWriteType,
    cucsStorageVirtualDriveDriveCache                                CucsStorageCacheType,
    cucsStorageVirtualDriveDriveState                                CucsStorageVDriveState,
    cucsStorageVirtualDriveIoPolicy                                  CucsStorageIOType,
    cucsStorageVirtualDriveLc                                        CucsFsmLifecycle,
    cucsStorageVirtualDriveReadPolicy                                CucsStorageReadType,
    cucsStorageVirtualDriveStripSize                                 Unsigned64,
    cucsStorageVirtualDriveAdminActionTrigger                        CucsStorageAdminActionTrigger,
    cucsStorageVirtualDriveAdminName                                 SnmpAdminString,
    cucsStorageVirtualDriveAdminState                                CucsStorageAdminState,
    cucsStorageVirtualDriveChangeQualifier                           CucsStorageVdChangeQualifierType,
    cucsStorageVirtualDriveConfigQualifierReason                     SnmpAdminString,
    cucsStorageVirtualDriveConfigState                               CucsStorageConfigState,
    cucsStorageVirtualDriveDeployAction                              CucsStorageDeployAction,
    cucsStorageVirtualDriveDescr                                     SnmpAdminString,
    cucsStorageVirtualDriveLocale                                    SnmpAdminString,
    cucsStorageVirtualDriveName                                      SnmpAdminString,
    cucsStorageVirtualDriveOperDeviceId                              Gauge32,
    cucsStorageVirtualDriveOperState                                 CucsStorageUnitOperState,
    cucsStorageVirtualDriveUuid                                      SnmpAdminString,
    cucsStorageVirtualDriveVendorUuid                                SnmpAdminString,
    cucsStorageVirtualDriveAvailableSize                             Unsigned64,
    cucsStorageVirtualDrivePnDn                                      SnmpAdminString,
    cucsStorageVirtualDriveRefDn                                     SnmpAdminString,
    cucsStorageVirtualDriveChangeId                                  Unsigned64,
    cucsStorageVirtualDrivePhysicalBlockSize                         Gauge32,
    cucsStorageVirtualDriveDriveSecurity                             TruthValue,
    cucsStorageVirtualDriveSecurityFlags                             CucsStorageControllerFlags
}

cucsStorageVirtualDriveInstanceId OBJECT-TYPE
    SYNTAX       CucsManagedObjectId
    MAX-ACCESS   not-accessible
    STATUS       current
    DESCRIPTION
        "Instance identifier of the managed object."
    ::= { cucsStorageVirtualDriveEntry 1 }

cucsStorageVirtualDriveDn OBJECT-TYPE
    SYNTAX       CucsManagedObjectDn
    MAX-ACCESS   read-only
    STATUS       current
    DESCRIPTION
        "Cisco UCS storage:VirtualDrive:dn managed object property"
    ::= { cucsStorageVirtualDriveEntry 2 }

cucsStorageVirtualDriveRn OBJECT-TYPE
    SYNTAX       SnmpAdminString
    MAX-ACCESS   read-only
    STATUS       current
    DESCRIPTION
        "Cisco UCS storage:VirtualDrive:rn managed object property"
    ::= { cucsStorageVirtualDriveEntry 3 }

cucsStorageVirtualDriveBlockSize OBJECT-TYPE
    SYNTAX       Gauge32
    MAX-ACCESS   read-only
    STATUS       current
    DESCRIPTION
        "Cisco UCS storage:VirtualDrive:blockSize managed object property"
    ::= { cucsStorageVirtualDriveEntry 4 }

cucsStorageVirtualDriveConnectionProtocol OBJECT-TYPE
    SYNTAX       CucsStorageConnectionProtocol
    MAX-ACCESS   read-only
    STATUS       current
    DESCRIPTION
        "Cisco UCS storage:VirtualDrive:connectionProtocol
        managed object property"
    ::= { cucsStorageVirtualDriveEntry 5 }

cucsStorageVirtualDriveId OBJECT-TYPE
    SYNTAX       Gauge32
    MAX-ACCESS   read-only
    STATUS       current
    DESCRIPTION
        "Cisco UCS storage:VirtualDrive:id managed object property"
    ::= { cucsStorageVirtualDriveEntry 6 }

cucsStorageVirtualDriveModel OBJECT-TYPE
    SYNTAX       SnmpAdminString
    MAX-ACCESS   read-only
    STATUS       current
    DESCRIPTION
        "Cisco UCS storage:VirtualDrive:model managed object property"
    ::= { cucsStorageVirtualDriveEntry 7 }

cucsStorageVirtualDriveNumberOfBlocks OBJECT-TYPE
    SYNTAX       Unsigned64
    MAX-ACCESS   read-only
    STATUS       current
    DESCRIPTION
        "Cisco UCS storage:VirtualDrive:numberOfBlocks
        managed object property"
    ::= { cucsStorageVirtualDriveEntry 8 }

cucsStorageVirtualDriveOperQualifierReason OBJECT-TYPE
    SYNTAX       SnmpAdminString
    MAX-ACCESS   read-only
    STATUS       current
    DESCRIPTION
        "Cisco UCS storage:VirtualDrive:operQualifierReason
        managed object property"
    ::= { cucsStorageVirtualDriveEntry 9 }

cucsStorageVirtualDriveOperability OBJECT-TYPE
    SYNTAX       CucsEquipmentOperability
    MAX-ACCESS   read-only
    STATUS       current
    DESCRIPTION
        "Cisco UCS storage:VirtualDrive:operability managed
        object property"
    ::= { cucsStorageVirtualDriveEntry 10 }

cucsStorageVirtualDrivePresence OBJECT-TYPE
    SYNTAX       CucsEquipmentPresence
    MAX-ACCESS   read-only
    STATUS       current
    DESCRIPTION
        "Cisco UCS storage:VirtualDrive:presence managed object property"
    ::= { cucsStorageVirtualDriveEntry 11 }

cucsStorageVirtualDriveRevision OBJECT-TYPE
    SYNTAX       SnmpAdminString
    MAX-ACCESS   read-only
    STATUS       current
    DESCRIPTION
        "Cisco UCS storage:VirtualDrive:revision managed object property"
    ::= { cucsStorageVirtualDriveEntry 12 }

cucsStorageVirtualDriveSerial OBJECT-TYPE
    SYNTAX       SnmpAdminString
    MAX-ACCESS   read-only
    STATUS       current
    DESCRIPTION
        "Cisco UCS storage:VirtualDrive:serial managed object property"
    ::= { cucsStorageVirtualDriveEntry 13 }

cucsStorageVirtualDriveSize OBJECT-TYPE
    SYNTAX       Unsigned64
    MAX-ACCESS   read-only
    STATUS       current
    DESCRIPTION
        "Cisco UCS storage:VirtualDrive:size managed object property"
    ::= { cucsStorageVirtualDriveEntry 14 }

cucsStorageVirtualDriveType OBJECT-TYPE
    SYNTAX       CucsStorageLunType
    MAX-ACCESS   read-only
    STATUS       current
    DESCRIPTION
        "Cisco UCS storage:VirtualDrive:type managed object property"
    ::= { cucsStorageVirtualDriveEntry 15 }

cucsStorageVirtualDriveVendor OBJECT-TYPE
    SYNTAX       SnmpAdminString
    MAX-ACCESS   read-only
    STATUS       current
    DESCRIPTION
        "Cisco UCS storage:VirtualDrive:vendor managed object property"
    ::= { cucsStorageVirtualDriveEntry 16 }

cucsStorageVirtualDriveAccessPolicy OBJECT-TYPE
    SYNTAX       CucsStorageAccessType
    MAX-ACCESS   read-only
    STATUS       current
    DESCRIPTION
        "Cisco UCS storage:VirtualDrive:accessPolicy managed
        object property"
    ::= { cucsStorageVirtualDriveEntry 17 }

cucsStorageVirtualDriveActualWriteCachePolicy OBJECT-TYPE
    SYNTAX       CucsStorageActualWriteType
    MAX-ACCESS   read-only
    STATUS       current
    DESCRIPTION
        "Cisco UCS storage:VirtualDrive:actualWriteCachePolicy
        managed object property"
    ::= { cucsStorageVirtualDriveEntry 18 }

cucsStorageVirtualDriveBootable OBJECT-TYPE
    SYNTAX       CucsStorageBootableType
    MAX-ACCESS   read-only
    STATUS       current
    DESCRIPTION
        "Cisco UCS storage:VirtualDrive:bootable managed object property"
    ::= { cucsStorageVirtualDriveEntry 19 }

cucsStorageVirtualDriveConfiguredWriteCachePolicy OBJECT-TYPE
    SYNTAX       CucsStorageConfiguredWriteType
    MAX-ACCESS   read-only
    STATUS       current
    DESCRIPTION
        "Cisco UCS storage:VirtualDrive:configuredWriteCachePolicy
        managed object property"
    ::= { cucsStorageVirtualDriveEntry 20 }

cucsStorageVirtualDriveDriveCache OBJECT-TYPE
    SYNTAX       CucsStorageCacheType
    MAX-ACCESS   read-only
    STATUS       current
    DESCRIPTION
        "Cisco UCS storage:VirtualDrive:driveCache managed
        object property"
    ::= { cucsStorageVirtualDriveEntry 21 }

cucsStorageVirtualDriveDriveState OBJECT-TYPE
    SYNTAX       CucsStorageVDriveState
    MAX-ACCESS   read-only
    STATUS       current
    DESCRIPTION
        "Cisco UCS storage:VirtualDrive:driveState managed
        object property"
    ::= { cucsStorageVirtualDriveEntry 22 }

cucsStorageVirtualDriveIoPolicy OBJECT-TYPE
    SYNTAX       CucsStorageIOType
    MAX-ACCESS   read-only
    STATUS       current
    DESCRIPTION
        "Cisco UCS storage:VirtualDrive:ioPolicy managed object property"
    ::= { cucsStorageVirtualDriveEntry 23 }

cucsStorageVirtualDriveLc OBJECT-TYPE
    SYNTAX       CucsFsmLifecycle
    MAX-ACCESS   read-only
    STATUS       current
    DESCRIPTION
        "Cisco UCS storage:VirtualDrive:lc managed object property"
    ::= { cucsStorageVirtualDriveEntry 24 }

cucsStorageVirtualDriveReadPolicy OBJECT-TYPE
    SYNTAX       CucsStorageReadType
    MAX-ACCESS   read-only
    STATUS       current
    DESCRIPTION
        "Cisco UCS storage:VirtualDrive:readPolicy managed
        object property"
    ::= { cucsStorageVirtualDriveEntry 25 }

cucsStorageVirtualDriveStripSize OBJECT-TYPE
    SYNTAX       Unsigned64
    MAX-ACCESS   read-only
    STATUS       current
    DESCRIPTION
        "Cisco UCS storage:VirtualDrive:stripSize managed object property"
    ::= { cucsStorageVirtualDriveEntry 26 }

cucsStorageVirtualDriveAdminActionTrigger OBJECT-TYPE
    SYNTAX       CucsStorageAdminActionTrigger
    MAX-ACCESS   read-only
    STATUS       current
    DESCRIPTION
        "Cisco UCS storage:VirtualDrive:adminActionTrigger
        managed object property"
    ::= { cucsStorageVirtualDriveEntry 27 }

cucsStorageVirtualDriveAdminName OBJECT-TYPE
    SYNTAX       SnmpAdminString
    MAX-ACCESS   read-only
    STATUS       current
    DESCRIPTION
        "Cisco UCS storage:VirtualDrive:adminName managed object property"
    ::= { cucsStorageVirtualDriveEntry 28 }

cucsStorageVirtualDriveAdminState OBJECT-TYPE
    SYNTAX       CucsStorageAdminState
    MAX-ACCESS   read-only
    STATUS       current
    DESCRIPTION
        "Cisco UCS storage:VirtualDrive:adminState managed
        object property"
    ::= { cucsStorageVirtualDriveEntry 29 }

cucsStorageVirtualDriveChangeQualifier OBJECT-TYPE
    SYNTAX       CucsStorageVdChangeQualifierType
    MAX-ACCESS   read-only
    STATUS       current
    DESCRIPTION
        "Cisco UCS storage:VirtualDrive:changeQualifier
        managed object property"
    ::= { cucsStorageVirtualDriveEntry 30 }

cucsStorageVirtualDriveConfigQualifierReason OBJECT-TYPE
    SYNTAX       SnmpAdminString
    MAX-ACCESS   read-only
    STATUS       current
    DESCRIPTION
        "Cisco UCS storage:VirtualDrive:configQualifierReason
        managed object property"
    ::= { cucsStorageVirtualDriveEntry 31 }

cucsStorageVirtualDriveConfigState OBJECT-TYPE
    SYNTAX       CucsStorageConfigState
    MAX-ACCESS   read-only
    STATUS       current
    DESCRIPTION
        "Cisco UCS storage:VirtualDrive:configState managed
        object property"
    ::= { cucsStorageVirtualDriveEntry 32 }

cucsStorageVirtualDriveDeployAction OBJECT-TYPE
    SYNTAX       CucsStorageDeployAction
    MAX-ACCESS   read-only
    STATUS       current
    DESCRIPTION
        "Cisco UCS storage:VirtualDrive:deployAction managed
        object property"
    ::= { cucsStorageVirtualDriveEntry 33 }

cucsStorageVirtualDriveDescr OBJECT-TYPE
    SYNTAX       SnmpAdminString
    MAX-ACCESS   read-only
    STATUS       current
    DESCRIPTION
        "Cisco UCS storage:VirtualDrive:descr managed object property"
    ::= { cucsStorageVirtualDriveEntry 34 }

cucsStorageVirtualDriveLocale OBJECT-TYPE
    SYNTAX       SnmpAdminString
    MAX-ACCESS   read-only
    STATUS       current
    DESCRIPTION
        "Cisco UCS storage:VirtualDrive:locale managed object property"
    ::= { cucsStorageVirtualDriveEntry 35 }

cucsStorageVirtualDriveName OBJECT-TYPE
    SYNTAX       SnmpAdminString
    MAX-ACCESS   read-only
    STATUS       current
    DESCRIPTION
        "Cisco UCS storage:VirtualDrive:name managed object property"
    ::= { cucsStorageVirtualDriveEntry 36 }

cucsStorageVirtualDriveOperDeviceId OBJECT-TYPE
    SYNTAX       Gauge32
    MAX-ACCESS   read-only
    STATUS       current
    DESCRIPTION
        "Cisco UCS storage:VirtualDrive:operDeviceId managed
        object property"
    ::= { cucsStorageVirtualDriveEntry 37 }

cucsStorageVirtualDriveOperState OBJECT-TYPE
    SYNTAX       CucsStorageUnitOperState
    MAX-ACCESS   read-only
    STATUS       current
    DESCRIPTION
        "Cisco UCS storage:VirtualDrive:operState managed object property"
    ::= { cucsStorageVirtualDriveEntry 38 }

cucsStorageVirtualDriveUuid OBJECT-TYPE
    SYNTAX       SnmpAdminString
    MAX-ACCESS   read-only
    STATUS       current
    DESCRIPTION
        "Cisco UCS storage:VirtualDrive:uuid managed object property"
    ::= { cucsStorageVirtualDriveEntry 39 }

cucsStorageVirtualDriveVendorUuid OBJECT-TYPE
    SYNTAX       SnmpAdminString
    MAX-ACCESS   read-only
    STATUS       current
    DESCRIPTION
        "Cisco UCS storage:VirtualDrive:vendorUuid managed
        object property"
    ::= { cucsStorageVirtualDriveEntry 40 }

cucsStorageVirtualDriveAvailableSize OBJECT-TYPE
    SYNTAX       Unsigned64
    MAX-ACCESS   read-only
    STATUS       current
    DESCRIPTION
        "Cisco UCS storage:VirtualDrive:availableSize managed
        object property"
    ::= { cucsStorageVirtualDriveEntry 41 }

cucsStorageVirtualDrivePnDn OBJECT-TYPE
    SYNTAX       SnmpAdminString
    MAX-ACCESS   read-only
    STATUS       current
    DESCRIPTION
        "Cisco UCS storage:VirtualDrive:pnDn managed object property"
    ::= { cucsStorageVirtualDriveEntry 42 }

cucsStorageVirtualDriveRefDn OBJECT-TYPE
    SYNTAX       SnmpAdminString
    MAX-ACCESS   read-only
    STATUS       current
    DESCRIPTION
        "Cisco UCS storage:VirtualDrive:refDn managed object property"
    ::= { cucsStorageVirtualDriveEntry 43 }

cucsStorageVirtualDriveChangeId OBJECT-TYPE
    SYNTAX       Unsigned64
    MAX-ACCESS   read-only
    STATUS       current
    DESCRIPTION
        "Cisco UCS storage:VirtualDrive:changeId managed object property"
    ::= { cucsStorageVirtualDriveEntry 44 }

cucsStorageVirtualDrivePhysicalBlockSize OBJECT-TYPE
    SYNTAX       Gauge32
    MAX-ACCESS   read-only
    STATUS       current
    DESCRIPTION
        "Cisco UCS storage:VirtualDrive:physicalBlockSize
        managed object property"
    ::= { cucsStorageVirtualDriveEntry 45 }

cucsStorageVirtualDriveDriveSecurity OBJECT-TYPE
    SYNTAX       TruthValue
    MAX-ACCESS   read-only
    STATUS       current
    DESCRIPTION
        "Cisco UCS storage:VirtualDrive:driveSecurity managed
        object property"
    ::= { cucsStorageVirtualDriveEntry 46 }

cucsStorageVirtualDriveSecurityFlags OBJECT-TYPE
    SYNTAX       CucsStorageControllerFlags
    MAX-ACCESS   read-only
    STATUS       current
    DESCRIPTION
        "Cisco UCS storage:VirtualDrive:securityFlags managed
        object property"
    ::= { cucsStorageVirtualDriveEntry 47 }

cucsStorageVirtualDriveContainerTable OBJECT-TYPE
    SYNTAX           SEQUENCE OF CucsStorageVirtualDriveContainerEntry
    MAX-ACCESS       not-accessible
    STATUS           current
    DESCRIPTION
        "Cisco UCS storage:VirtualDriveContainer managed object table"
    ::= { cucsStorageObjects 114 }

cucsStorageVirtualDriveContainerEntry OBJECT-TYPE
    SYNTAX           CucsStorageVirtualDriveContainerEntry
    MAX-ACCESS       not-accessible
    STATUS           current
    DESCRIPTION
        "Entry for the cucsStorageVirtualDriveContainerTable table."
    INDEX { cucsStorageVirtualDriveContainerInstanceId }
    ::= { cucsStorageVirtualDriveContainerTable 1 }

CucsStorageVirtualDriveContainerEntry ::= SEQUENCE {
    cucsStorageVirtualDriveContainerInstanceId                       CucsManagedObjectId,
    cucsStorageVirtualDriveContainerDn                               CucsManagedObjectDn,
    cucsStorageVirtualDriveContainerRn                               SnmpAdminString,
    cucsStorageVirtualDriveContainerId                               Gauge32
}

cucsStorageVirtualDriveContainerInstanceId OBJECT-TYPE
    SYNTAX       CucsManagedObjectId
    MAX-ACCESS   not-accessible
    STATUS       current
    DESCRIPTION
        "Instance identifier of the managed object."
    ::= { cucsStorageVirtualDriveContainerEntry 1 }

cucsStorageVirtualDriveContainerDn OBJECT-TYPE
    SYNTAX       CucsManagedObjectDn
    MAX-ACCESS   read-only
    STATUS       current
    DESCRIPTION
        "Cisco UCS storage:VirtualDriveContainer:dn managed
        object property"
    ::= { cucsStorageVirtualDriveContainerEntry 2 }

cucsStorageVirtualDriveContainerRn OBJECT-TYPE
    SYNTAX       SnmpAdminString
    MAX-ACCESS   read-only
    STATUS       current
    DESCRIPTION
        "Cisco UCS storage:VirtualDriveContainer:rn managed
        object property"
    ::= { cucsStorageVirtualDriveContainerEntry 3 }

cucsStorageVirtualDriveContainerId OBJECT-TYPE
    SYNTAX       Gauge32
    MAX-ACCESS   read-only
    STATUS       current
    DESCRIPTION
        "Cisco UCS storage:VirtualDriveContainer:id managed
        object property"
    ::= { cucsStorageVirtualDriveContainerEntry 4 }

cucsStorageVirtualDriveEpTable OBJECT-TYPE
    SYNTAX           SEQUENCE OF CucsStorageVirtualDriveEpEntry
    MAX-ACCESS       not-accessible
    STATUS           current
    DESCRIPTION
        "Cisco UCS storage:VirtualDriveEp managed object table"
    ::= { cucsStorageObjects 115 }

cucsStorageVirtualDriveEpEntry OBJECT-TYPE
    SYNTAX           CucsStorageVirtualDriveEpEntry
    MAX-ACCESS       not-accessible
    STATUS           current
    DESCRIPTION
        "Entry for the cucsStorageVirtualDriveEpTable table."
    INDEX { cucsStorageVirtualDriveEpInstanceId }
    ::= { cucsStorageVirtualDriveEpTable 1 }

CucsStorageVirtualDriveEpEntry ::= SEQUENCE {
    cucsStorageVirtualDriveEpInstanceId                              CucsManagedObjectId,
    cucsStorageVirtualDriveEpDn                                      CucsManagedObjectDn,
    cucsStorageVirtualDriveEpRn                                      SnmpAdminString,
    cucsStorageVirtualDriveEpBootable                                CucsStorageBootableType,
    cucsStorageVirtualDriveEpContainerId                             Gauge32,
    cucsStorageVirtualDriveEpDriveState                              CucsStorageVDriveState,
    cucsStorageVirtualDriveEpId                                      Gauge32,
    cucsStorageVirtualDriveEpLc                                      CucsFsmLifecycle,
    cucsStorageVirtualDriveEpName                                    SnmpAdminString,
    cucsStorageVirtualDriveEpOperDeviceId                            Gauge32,
    cucsStorageVirtualDriveEpUuid                                    SnmpAdminString,
    cucsStorageVirtualDriveEpVdDn                                    SnmpAdminString,
    cucsStorageVirtualDriveEpVendorUuid                              SnmpAdminString
}

cucsStorageVirtualDriveEpInstanceId OBJECT-TYPE
    SYNTAX       CucsManagedObjectId
    MAX-ACCESS   not-accessible
    STATUS       current
    DESCRIPTION
        "Instance identifier of the managed object."
    ::= { cucsStorageVirtualDriveEpEntry 1 }

cucsStorageVirtualDriveEpDn OBJECT-TYPE
    SYNTAX       CucsManagedObjectDn
    MAX-ACCESS   read-only
    STATUS       current
    DESCRIPTION
        "Cisco UCS storage:VirtualDriveEp:dn managed object property"
    ::= { cucsStorageVirtualDriveEpEntry 2 }

cucsStorageVirtualDriveEpRn OBJECT-TYPE
    SYNTAX       SnmpAdminString
    MAX-ACCESS   read-only
    STATUS       current
    DESCRIPTION
        "Cisco UCS storage:VirtualDriveEp:rn managed object property"
    ::= { cucsStorageVirtualDriveEpEntry 3 }

cucsStorageVirtualDriveEpBootable OBJECT-TYPE
    SYNTAX       CucsStorageBootableType
    MAX-ACCESS   read-only
    STATUS       current
    DESCRIPTION
        "Cisco UCS storage:VirtualDriveEp:bootable managed
        object property"
    ::= { cucsStorageVirtualDriveEpEntry 4 }

cucsStorageVirtualDriveEpContainerId OBJECT-TYPE
    SYNTAX       Gauge32
    MAX-ACCESS   read-only
    STATUS       current
    DESCRIPTION
        "Cisco UCS storage:VirtualDriveEp:containerId managed
        object property"
    ::= { cucsStorageVirtualDriveEpEntry 5 }

cucsStorageVirtualDriveEpDriveState OBJECT-TYPE
    SYNTAX       CucsStorageVDriveState
    MAX-ACCESS   read-only
    STATUS       current
    DESCRIPTION
        "Cisco UCS storage:VirtualDriveEp:driveState managed
        object property"
    ::= { cucsStorageVirtualDriveEpEntry 6 }

cucsStorageVirtualDriveEpId OBJECT-TYPE
    SYNTAX       Gauge32
    MAX-ACCESS   read-only
    STATUS       current
    DESCRIPTION
        "Cisco UCS storage:VirtualDriveEp:id managed object property"
    ::= { cucsStorageVirtualDriveEpEntry 7 }

cucsStorageVirtualDriveEpLc OBJECT-TYPE
    SYNTAX       CucsFsmLifecycle
    MAX-ACCESS   read-only
    STATUS       current
    DESCRIPTION
        "Cisco UCS storage:VirtualDriveEp:lc managed object property"
    ::= { cucsStorageVirtualDriveEpEntry 8 }

cucsStorageVirtualDriveEpName OBJECT-TYPE
    SYNTAX       SnmpAdminString
    MAX-ACCESS   read-only
    STATUS       current
    DESCRIPTION
        "Cisco UCS storage:VirtualDriveEp:name managed object property"
    ::= { cucsStorageVirtualDriveEpEntry 9 }

cucsStorageVirtualDriveEpOperDeviceId OBJECT-TYPE
    SYNTAX       Gauge32
    MAX-ACCESS   read-only
    STATUS       current
    DESCRIPTION
        "Cisco UCS storage:VirtualDriveEp:operDeviceId
        managed object property"
    ::= { cucsStorageVirtualDriveEpEntry 10 }

cucsStorageVirtualDriveEpUuid OBJECT-TYPE
    SYNTAX       SnmpAdminString
    MAX-ACCESS   read-only
    STATUS       current
    DESCRIPTION
        "Cisco UCS storage:VirtualDriveEp:uuid managed object property"
    ::= { cucsStorageVirtualDriveEpEntry 11 }

cucsStorageVirtualDriveEpVdDn OBJECT-TYPE
    SYNTAX       SnmpAdminString
    MAX-ACCESS   read-only
    STATUS       current
    DESCRIPTION
        "Cisco UCS storage:VirtualDriveEp:vdDn managed object property"
    ::= { cucsStorageVirtualDriveEpEntry 12 }

cucsStorageVirtualDriveEpVendorUuid OBJECT-TYPE
    SYNTAX       SnmpAdminString
    MAX-ACCESS   read-only
    STATUS       current
    DESCRIPTION
        "Cisco UCS storage:VirtualDriveEp:vendorUuid managed
        object property"
    ::= { cucsStorageVirtualDriveEpEntry 13 }

cucsStorageVirtualDriveRefTable OBJECT-TYPE
    SYNTAX           SEQUENCE OF CucsStorageVirtualDriveRefEntry
    MAX-ACCESS       not-accessible
    STATUS           current
    DESCRIPTION
        "Cisco UCS storage:VirtualDriveRef managed object table"
    ::= { cucsStorageObjects 91 }

cucsStorageVirtualDriveRefEntry OBJECT-TYPE
    SYNTAX           CucsStorageVirtualDriveRefEntry
    MAX-ACCESS       not-accessible
    STATUS           current
    DESCRIPTION
        "Entry for the cucsStorageVirtualDriveRefTable table."
    INDEX { cucsStorageVirtualDriveRefInstanceId }
    ::= { cucsStorageVirtualDriveRefTable 1 }

CucsStorageVirtualDriveRefEntry ::= SEQUENCE {
    cucsStorageVirtualDriveRefInstanceId                             CucsManagedObjectId,
    cucsStorageVirtualDriveRefDnData                                 CucsManagedObjectDn,
    cucsStorageVirtualDriveRefRn                                     SnmpAdminString,
    cucsStorageVirtualDriveRefAdminName                              SnmpAdminString,
    cucsStorageVirtualDriveRefAdminState                             CucsStorageVirtualDriveRefAdminState,
    cucsStorageVirtualDriveRefConfigState                            CucsStorageConfigState,
    cucsStorageVirtualDriveRefDiskSelectionOrder                     Gauge32,
    cucsStorageVirtualDriveRefDiskSelectionTs                        DateAndTime,
    cucsStorageVirtualDriveRefLunDn                                  SnmpAdminString,
    cucsStorageVirtualDriveRefLunItemDn                              SnmpAdminString,
    cucsStorageVirtualDriveRefLunItemName                            SnmpAdminString,
    cucsStorageVirtualDriveRefLunName                                SnmpAdminString,
    cucsStorageVirtualDriveRefRaidLevel                              CucsStorageLunType,
    cucsStorageVirtualDriveRefSize                                   Unsigned64,
    cucsStorageVirtualDriveRefUuid                                   SnmpAdminString,
    cucsStorageVirtualDriveRefIsBootable                             CucsLstorageBootDevice,
    cucsStorageVirtualDriveRefOrder                                  Gauge32,
    cucsStorageVirtualDriveRefVendorUuid                             SnmpAdminString
}

cucsStorageVirtualDriveRefInstanceId OBJECT-TYPE
    SYNTAX       CucsManagedObjectId
    MAX-ACCESS   not-accessible
    STATUS       current
    DESCRIPTION
        "Instance identifier of the managed object."
    ::= { cucsStorageVirtualDriveRefEntry 1 }

cucsStorageVirtualDriveRefDnData OBJECT-TYPE
    SYNTAX       CucsManagedObjectDn
    MAX-ACCESS   read-only
    STATUS       current
    DESCRIPTION
        "Cisco UCS storage:VirtualDriveRef:dn managed object property"
    ::= { cucsStorageVirtualDriveRefEntry 2 }

cucsStorageVirtualDriveRefRn OBJECT-TYPE
    SYNTAX       SnmpAdminString
    MAX-ACCESS   read-only
    STATUS       current
    DESCRIPTION
        "Cisco UCS storage:VirtualDriveRef:rn managed object property"
    ::= { cucsStorageVirtualDriveRefEntry 3 }

cucsStorageVirtualDriveRefAdminName OBJECT-TYPE
    SYNTAX       SnmpAdminString
    MAX-ACCESS   read-only
    STATUS       current
    DESCRIPTION
        "Cisco UCS storage:VirtualDriveRef:adminName managed
        object property"
    ::= { cucsStorageVirtualDriveRefEntry 4 }

cucsStorageVirtualDriveRefAdminState OBJECT-TYPE
    SYNTAX       CucsStorageVirtualDriveRefAdminState
    MAX-ACCESS   read-only
    STATUS       current
    DESCRIPTION
        "Cisco UCS storage:VirtualDriveRef:adminState managed
        object property"
    ::= { cucsStorageVirtualDriveRefEntry 5 }

cucsStorageVirtualDriveRefConfigState OBJECT-TYPE
    SYNTAX       CucsStorageConfigState
    MAX-ACCESS   read-only
    STATUS       current
    DESCRIPTION
        "Cisco UCS storage:VirtualDriveRef:configState
        managed object property"
    ::= { cucsStorageVirtualDriveRefEntry 6 }

cucsStorageVirtualDriveRefDiskSelectionOrder OBJECT-TYPE
    SYNTAX       Gauge32
    MAX-ACCESS   read-only
    STATUS       current
    DESCRIPTION
        "Cisco UCS storage:VirtualDriveRef:diskSelectionOrder
        managed object property"
    ::= { cucsStorageVirtualDriveRefEntry 7 }

cucsStorageVirtualDriveRefDiskSelectionTs OBJECT-TYPE
    SYNTAX       DateAndTime
    MAX-ACCESS   read-only
    STATUS       current
    DESCRIPTION
        "Cisco UCS storage:VirtualDriveRef:diskSelectionTs
        managed object property"
    ::= { cucsStorageVirtualDriveRefEntry 8 }

cucsStorageVirtualDriveRefLunDn OBJECT-TYPE
    SYNTAX       SnmpAdminString
    MAX-ACCESS   read-only
    STATUS       current
    DESCRIPTION
        "Cisco UCS storage:VirtualDriveRef:lunDn managed object property"
    ::= { cucsStorageVirtualDriveRefEntry 9 }

cucsStorageVirtualDriveRefLunItemDn OBJECT-TYPE
    SYNTAX       SnmpAdminString
    MAX-ACCESS   read-only
    STATUS       current
    DESCRIPTION
        "Cisco UCS storage:VirtualDriveRef:lunItemDn managed
        object property"
    ::= { cucsStorageVirtualDriveRefEntry 10 }

cucsStorageVirtualDriveRefLunItemName OBJECT-TYPE
    SYNTAX       SnmpAdminString
    MAX-ACCESS   read-only
    STATUS       current
    DESCRIPTION
        "Cisco UCS storage:VirtualDriveRef:lunItemName
        managed object property"
    ::= { cucsStorageVirtualDriveRefEntry 11 }

cucsStorageVirtualDriveRefLunName OBJECT-TYPE
    SYNTAX       SnmpAdminString
    MAX-ACCESS   read-only
    STATUS       current
    DESCRIPTION
        "Cisco UCS storage:VirtualDriveRef:lunName managed
        object property"
    ::= { cucsStorageVirtualDriveRefEntry 12 }

cucsStorageVirtualDriveRefRaidLevel OBJECT-TYPE
    SYNTAX       CucsStorageLunType
    MAX-ACCESS   read-only
    STATUS       current
    DESCRIPTION
        "Cisco UCS storage:VirtualDriveRef:raidLevel managed
        object property"
    ::= { cucsStorageVirtualDriveRefEntry 13 }

cucsStorageVirtualDriveRefSize OBJECT-TYPE
    SYNTAX       Unsigned64
    MAX-ACCESS   read-only
    STATUS       current
    DESCRIPTION
        "Cisco UCS storage:VirtualDriveRef:size managed object property"
    ::= { cucsStorageVirtualDriveRefEntry 14 }

cucsStorageVirtualDriveRefUuid OBJECT-TYPE
    SYNTAX       SnmpAdminString
    MAX-ACCESS   read-only
    STATUS       current
    DESCRIPTION
        "Cisco UCS storage:VirtualDriveRef:uuid managed object property"
    ::= { cucsStorageVirtualDriveRefEntry 15 }

cucsStorageVirtualDriveRefIsBootable OBJECT-TYPE
    SYNTAX       CucsLstorageBootDevice
    MAX-ACCESS   read-only
    STATUS       current
    DESCRIPTION
        "Cisco UCS storage:VirtualDriveRef:isBootable managed
        object property"
    ::= { cucsStorageVirtualDriveRefEntry 16 }

cucsStorageVirtualDriveRefOrder OBJECT-TYPE
    SYNTAX       Gauge32
    MAX-ACCESS   read-only
    STATUS       current
    DESCRIPTION
        "Cisco UCS storage:VirtualDriveRef:order managed object property"
    ::= { cucsStorageVirtualDriveRefEntry 17 }

cucsStorageVirtualDriveRefVendorUuid OBJECT-TYPE
    SYNTAX       SnmpAdminString
    MAX-ACCESS   read-only
    STATUS       current
    DESCRIPTION
        "Cisco UCS storage:VirtualDriveRef:vendorUuid managed
        object property"
    ::= { cucsStorageVirtualDriveRefEntry 18 }

cucsStorageVsanRefTable OBJECT-TYPE
    SYNTAX           SEQUENCE OF CucsStorageVsanRefEntry
    MAX-ACCESS       not-accessible
    STATUS           current
    DESCRIPTION
        "Cisco UCS storage:VsanRef managed object table"
    ::= { cucsStorageObjects 32 }

cucsStorageVsanRefEntry OBJECT-TYPE
    SYNTAX           CucsStorageVsanRefEntry
    MAX-ACCESS       not-accessible
    STATUS           current
    DESCRIPTION
        "Entry for the cucsStorageVsanRefTable table."
    INDEX { cucsStorageVsanRefInstanceId }
    ::= { cucsStorageVsanRefTable 1 }

CucsStorageVsanRefEntry ::= SEQUENCE {
    cucsStorageVsanRefInstanceId                                     CucsManagedObjectId,
    cucsStorageVsanRefDn                                             CucsManagedObjectDn,
    cucsStorageVsanRefRn                                             SnmpAdminString,
    cucsStorageVsanRefConfigQualifier                                CucsVnicConfigIssues,
    cucsStorageVsanRefName                                           SnmpAdminString,
    cucsStorageVsanRefOperVnetDn                                     SnmpAdminString,
    cucsStorageVsanRefOperVnetName                                   SnmpAdminString,
    cucsStorageVsanRefSwitchId                                       CucsStorageVsanRefSwitchId,
    cucsStorageVsanRefVnet                                           Gauge32,
    cucsStorageVsanRefZoningState                                    CucsFabricZoningState
}

cucsStorageVsanRefInstanceId OBJECT-TYPE
    SYNTAX       CucsManagedObjectId
    MAX-ACCESS   not-accessible
    STATUS       current
    DESCRIPTION
        "Instance identifier of the managed object."
    ::= { cucsStorageVsanRefEntry 1 }

cucsStorageVsanRefDn OBJECT-TYPE
    SYNTAX       CucsManagedObjectDn
    MAX-ACCESS   read-only
    STATUS       current
    DESCRIPTION
        "Cisco UCS storage:VsanRef:dn managed object property"
    ::= { cucsStorageVsanRefEntry 2 }

cucsStorageVsanRefRn OBJECT-TYPE
    SYNTAX       SnmpAdminString
    MAX-ACCESS   read-only
    STATUS       current
    DESCRIPTION
        "Cisco UCS storage:VsanRef:rn managed object property"
    ::= { cucsStorageVsanRefEntry 3 }

cucsStorageVsanRefConfigQualifier OBJECT-TYPE
    SYNTAX       CucsVnicConfigIssues
    MAX-ACCESS   read-only
    STATUS       current
    DESCRIPTION
        "Cisco UCS storage:VsanRef:configQualifier managed
        object property"
    ::= { cucsStorageVsanRefEntry 4 }

cucsStorageVsanRefName OBJECT-TYPE
    SYNTAX       SnmpAdminString
    MAX-ACCESS   read-only
    STATUS       current
    DESCRIPTION
        "Cisco UCS storage:VsanRef:name managed object property"
    ::= { cucsStorageVsanRefEntry 5 }

cucsStorageVsanRefOperVnetDn OBJECT-TYPE
    SYNTAX       SnmpAdminString
    MAX-ACCESS   read-only
    STATUS       current
    DESCRIPTION
        "Cisco UCS storage:VsanRef:operVnetDn managed object property"
    ::= { cucsStorageVsanRefEntry 6 }

cucsStorageVsanRefOperVnetName OBJECT-TYPE
    SYNTAX       SnmpAdminString
    MAX-ACCESS   read-only
    STATUS       current
    DESCRIPTION
        "Cisco UCS storage:VsanRef:operVnetName managed object property"
    ::= { cucsStorageVsanRefEntry 7 }

cucsStorageVsanRefSwitchId OBJECT-TYPE
    SYNTAX       CucsStorageVsanRefSwitchId
    MAX-ACCESS   read-only
    STATUS       current
    DESCRIPTION
        "Cisco UCS storage:VsanRef:switchId managed object property"
    ::= { cucsStorageVsanRefEntry 8 }

cucsStorageVsanRefVnet OBJECT-TYPE
    SYNTAX       Gauge32
    MAX-ACCESS   read-only
    STATUS       current
    DESCRIPTION
        "Cisco UCS storage:VsanRef:vnet managed object property"
    ::= { cucsStorageVsanRefEntry 9 }

cucsStorageVsanRefZoningState OBJECT-TYPE
    SYNTAX       CucsFabricZoningState
    MAX-ACCESS   read-only
    STATUS       current
    DESCRIPTION
        "Cisco UCS storage:VsanRef:zoningState managed object property"
    ::= { cucsStorageVsanRefEntry 10 }

END
