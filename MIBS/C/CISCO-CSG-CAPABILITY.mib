-- *****************************************************************
-- CISCO-CSG-CAPABILITY.my: CSG Agent capability MIB  
--
-- May 2003, Barron Housel
--
-- Copyright (c) 2003 by cisco Systems, Inc.
-- All rights reserved.
-- *****************************************************************
CISCO-CSG-CAPABILITY DEFINITIONS ::= BEGIN

IMPORTS
        MODULE-IDENTITY
                FROM SNMPv2-SMI
                
        AGENT-CAPABILITIES
                FROM SNMPv2-CONF
                
        ciscoAgentCapability
                FROM CISCO-SMI; 
                

ciscoCsgCapability MODULE-IDENTITY
                LAST-UPDATED    "200305010000Z"
                ORGANIZATION    "Cisco Systems, Inc."
                CONTACT-INFO
                        "       Cisco Systems
                                Customer Service
                        
                        Postal: 170 West Tasman Drive
                                San Jose, CA  95134
                                USA
                        
                           Tel: +1 800 553-NETS
                        
                        E-mail: cs-csg@cisco.com"
                DESCRIPTION
                        "Agent capabilities for the CISCO-CSG-MIB."
                REVISION        "200305010000Z"
                DESCRIPTION
                        "Initial version of this MIB module."
        ::= { ciscoAgentCapability 999 }

ciscoCsgCapabilityV14R02ZA1 AGENT-CAPABILITIES

PRODUCT-RELEASE "Cisco IOS 12.2(14)ZA1"
  STATUS          current
  DESCRIPTION     "IOS 12.2(14)ZA1 Cisco CISCO-CSG-MIB.my User Agent
                   MIB capabilities."

SUPPORTS        CISCO-CSG-MIB
  INCLUDES      {
                        ciscoUserGroup,
                        ciscoAgentGroup,
                        ciscoQuotaMgrGroup,
                        ciscoUserDbGroup,
                        ciscoCsgNotifEnableGroup,
                        ciscoCsgNotifGroup
                }

::= { ciscoCsgCapability 1 }

END
