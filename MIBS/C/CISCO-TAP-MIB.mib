-- MIB file created 20-May-2004 02:14:14, by
--   SMICng version 2.2.11-beta(PRO)(Solaris), January 20, 2001. Enterprise key cisco.com

CISCO-TAP-MIB DEFINITIONS ::= BEGIN

-- From file: "CISCO-TAP-MIB.my"
-- Compile options "4 7 F H N W 03 06 0B 0G 0N 0T"

IMPORTS
    InetAddressType, InetAddress, InetAddressPrefixLength, 
    InetPortNumber
            FROM INET-ADDRESS-MIB
    RowStatus, TruthValue, DateAndTime, MacAddress
            FROM SNMPv2-TC-v1
    SnmpAdminString
            FROM SNMP-FRAMEWORK-MIB
    InterfaceIndexOrZero
            FROM IF-MIB
    Dscp
            FROM CISCO-QOS-PIB-MIB
    ciscoMgmt
            FROM CISCO-SMI
    Counter, Gauge
            FROM RFC1155-SMI
    OBJECT-TYPE
            FROM RFC-1212
    TRAP-TYPE
            FROM RFC-1215;

cTapMIB OBJECT IDENTIFIER ::= { ciscoMgmt 252 }
-- MODULE-IDENTITY
--  LastUpdated
--    200207250000Z
--  OrgName
--    Cisco Systems, Inc.
--  ContactInfo
--          Cisco Systems
--           Customer Service
--    
--    Postal:170 W. Tasman Drive
--           San Jose, CA  95134
--           USA
--    
--       Tel:+1 800 553-NETS
--    
--    E-mail:cs-li@cisco.com
--  Descr
--    This module manages Cisco's intercept feature.
--  RevDate
--    200207250000Z
--  RevDescr
--    Initial version of this MIB module.

cTapMIBNotifications OBJECT IDENTIFIER ::= { cTapMIB 0 }
cTapMIBObjects  OBJECT IDENTIFIER ::= { cTapMIB 1 }
cTapMIBConformance OBJECT IDENTIFIER ::= { cTapMIB 2 }
cTapMediationGroup OBJECT IDENTIFIER ::= { cTapMIBObjects 1 }
cTapStreamGroup OBJECT IDENTIFIER ::= { cTapMIBObjects 2 }
cTapDebugGroup  OBJECT IDENTIFIER ::= { cTapMIBObjects 3 }
cTapMIBCompliances OBJECT IDENTIFIER ::= { cTapMIBConformance 1 }
cTapMIBGroups   OBJECT IDENTIFIER ::= { cTapMIBConformance 2 }

cTapMediationNewIndex OBJECT-TYPE
    SYNTAX INTEGER(1..2147483647)
    ACCESS read-only
    STATUS mandatory
    DESCRIPTION
        "This object contains a value which may be used as an index
        value for a new cTapMediationEntry. Whenever read, the agent
        will change the value to a new non-conflicting value.  This is
        to reduce the probability of errors during creation of new
        cTapMediationTable entries."
    ::= { cTapMediationGroup 1 }

cTapMediationTable OBJECT-TYPE
    SYNTAX SEQUENCE OF CTapMediationEntry
    ACCESS not-accessible
    STATUS mandatory
    DESCRIPTION
        "This table lists the Mediation Devices with which the
        intercepting device communicates. These may be on the same or
        different Mediation Devices.
        
        This table is written by the Mediation Device, and is always
        volatile. This is because intercepts may disappear during a
        restart of the intercepting equipment."
    ::= { cTapMediationGroup 2 }

cTapMediationEntry OBJECT-TYPE
    SYNTAX CTapMediationEntry
    ACCESS not-accessible
    STATUS mandatory
    DESCRIPTION
        "The entry describes a single session maintained with an
        application on a Mediation Device."
    INDEX { cTapMediationContentId }
    ::= { cTapMediationTable 1 }

CTapMediationEntry ::= SEQUENCE {
    cTapMediationContentId INTEGER,
    cTapMediationDestAddressType InetAddressType,
    cTapMediationDestAddress InetAddress,
    cTapMediationDestPort InetPortNumber,
    cTapMediationSrcInterface InterfaceIndexOrZero,
    cTapMediationRtcpPort InetPortNumber,
    cTapMediationDscp Dscp,
    cTapMediationDataType INTEGER,
    cTapMediationRetransmitType INTEGER,
    cTapMediationTimeout DateAndTime,
    cTapMediationTransport INTEGER,
    cTapMediationNotificationEnable TruthValue,
    cTapMediationStatus RowStatus
    }

cTapMediationContentId OBJECT-TYPE
    SYNTAX INTEGER(1..2147483647)
    ACCESS not-accessible
    STATUS mandatory
    DESCRIPTION
        "cTapMediationContentId is a session identifier, from the
        intercept application's perspective, and a content identifier
        from the Mediation Device's perspective. The Mediation Device
        is responsible for making sure these are unique, although the
        SNMP RowStatus row creation process will help by not allowing
        it to create conflicting entries. Before creating a new entry,
        a value for this variable may be obtained by reading
        cTapMediationNewIndex to reduce the probability of a value
        collision."
    ::= { cTapMediationEntry 1 }

cTapMediationDestAddressType OBJECT-TYPE
    SYNTAX InetAddressType
--    Rsyntax INTEGER {
--        ?? enum value of zero may cause problems
--        unknown(0),
--        ipv4(1),
--        ipv6(2),
--        ipv4z(3),
--        ipv6z(4),
--        dns(16)
--        }
    ACCESS read-write
    STATUS mandatory
    DESCRIPTION
        "The type of cTapMediationDestAddress."
    ::= { cTapMediationEntry 2 }

cTapMediationDestAddress OBJECT-TYPE
    SYNTAX InetAddress
--    Rsyntax OCTET STRING(SIZE(0..255))
    ACCESS read-write
    STATUS mandatory
    DESCRIPTION
        "The IP Address of the Mediation Device's network interface
        to which to direct intercepted traffic."
    ::= { cTapMediationEntry 3 }

cTapMediationDestPort OBJECT-TYPE
    SYNTAX InetPortNumber
--    Rsyntax Gauge(0..65535)
    ACCESS read-write
    STATUS mandatory
    DESCRIPTION
        "The port number on the Mediation Device's network interface
        to which to direct intercepted traffic."
    ::= { cTapMediationEntry 4 }

cTapMediationSrcInterface OBJECT-TYPE
    SYNTAX InterfaceIndexOrZero
--    Rsyntax INTEGER(0..2147483647)
    ACCESS read-write
    STATUS mandatory
    DESCRIPTION
        "The interface on the intercepting device from which to
        transmit intercepted data. If zero, any interface may be used
        according to normal IP practice."
    ::= { cTapMediationEntry 5 }

cTapMediationRtcpPort OBJECT-TYPE
    SYNTAX InetPortNumber
--    Rsyntax Gauge(0..65535)
    ACCESS read-only
    STATUS mandatory
    DESCRIPTION
        "The port number on the intercepting device to which the
        Mediation Devices directs RTCP Receiver Reports and Nacks.
        This object is only relevant when the value of
        cTapMediationTransport is 'rtpNack'.
        
        This port is assigned by the intercepting device, rather than
        by the Mediation Device or manager application.  The value of
        this MIB object has no effect before activating the
        cTapMediationEntry."
    ::= { cTapMediationEntry 6 }

cTapMediationDscp OBJECT-TYPE
    SYNTAX Dscp
--    Rsyntax INTEGER(0..63)
    ACCESS read-write
    STATUS mandatory
    DESCRIPTION
        "The Differentiated Services Code Point the intercepting
        device applies to the IP packets encapsulating the
        intercepted traffic."
    DEFVAL { 34 }
    ::= { cTapMediationEntry 7 }

cTapMediationDataType OBJECT-TYPE
    SYNTAX INTEGER(0..127)
    ACCESS read-write
    STATUS mandatory
    DESCRIPTION
        "If RTP with Ack/Nack resilience is selected as a transport,
        the mediation process requires an RTP payload type for data
        transmissions, and a second RTP payload type for
        retransmissions.  This is the RTP payload type for
        transmissions.
        
        This object is only effective when the value of
        cTapMediationTransport is 'rtpNack'."
    DEFVAL { 0 }
    ::= { cTapMediationEntry 8 }

cTapMediationRetransmitType OBJECT-TYPE
    SYNTAX INTEGER(0..127)
    ACCESS read-write
    STATUS mandatory
    DESCRIPTION
        "If RTP with Ack/Nack resilience is selected as a transport,
        the mediation process requires an RTP payload type for data
        transmissions, and a second RTP payload type for
        retransmissions.  This is the RTP payload type for
        retransmissions.
        
        This object is only effective when the value of
        cTapMediationTransport is 'rtpNack'."
    DEFVAL { 0 }
    ::= { cTapMediationEntry 9 }

cTapMediationTimeout OBJECT-TYPE
    SYNTAX DateAndTime
--    Rsyntax OCTET STRING(SIZE(8|11))
    ACCESS read-write
    STATUS mandatory
    DESCRIPTION
        "The time at which this row and all related Stream Table rows
        should be automatically removed, and the intercept function
        cease. Since the initiating network manager may be the only
        device able to manage a specific intercept or know of its
        existence, this acts as a fail-safe for the failure or removal
        of the network manager. The object is only effective when the
        value of cTapMediationStatus is 'active'."
    ::= { cTapMediationEntry 10 }

cTapMediationTransport OBJECT-TYPE
    SYNTAX INTEGER {
        udp(1),
        rtpNack(2),
        tcp(3),
        sctp(4)
        }
    ACCESS read-write
    STATUS mandatory
    DESCRIPTION
        "The protocol used in transferring intercepted data to the
        Mediation Device. The following protocols may be supported:
                   udp:     PacketCable udp format
                   rtpNack: RTP with Nack resilience
                   tcp:     TCP with head of line blocking
                   sctp:    SCTP with head of line blocking "
    ::= { cTapMediationEntry 11 }

cTapMediationNotificationEnable OBJECT-TYPE
    SYNTAX TruthValue
--    Rsyntax INTEGER {
--        true(1),
--        false(2)
--        }
    ACCESS read-write
    STATUS mandatory
    DESCRIPTION
        "This variable controls the generation of any notifications or
        informs by the MIB agent for this table entry."
    DEFVAL { true }
    ::= { cTapMediationEntry 12 }

cTapMediationStatus OBJECT-TYPE
    SYNTAX RowStatus
--    Rsyntax INTEGER {
--        active(1),
--        notInService(2),
--        notReady(3),
--        createAndGo(4),
--        createAndWait(5),
--        destroy(6)
--        }
    ACCESS read-write
    STATUS mandatory
    DESCRIPTION
        "The status of this conceptual row. This object is used to
         manage creation, modification and deletion of rows in this
         table.
        
         cTapMediationTimeout may be modified at any time (even while the
         row is active). But when the row is active, the other writable
         objects may not be modified without setting its value to
         'notInService'.
        
         The entry may not be deleted or deactivated by setting its
         value to 'destroy' or 'notInService' if there is any associated
         entry in cTapStreamIpTable, or other such tables when such are
         defined."
    ::= { cTapMediationEntry 13 }

cTapMediationCapabilities OBJECT-TYPE
    SYNTAX OCTET STRING(SIZE(1..2))
        -- BITS are:
        --   ipV4SrcInterface(0)
        --   ipV6SrcInterface(1)
        --   udp(2)
        --   rtpNack(3)
        --   tcp(4)
        --   sctp(5)
    ACCESS read-only
    STATUS mandatory
    DESCRIPTION
        "This object displays the device capabilities with respect to
        certain fields in Mediation Device table. This may be dependent
        on hardware capabilities, software capabilities.
        The following values may be supported:
            ipV4SrcInterface:  SNMP ifIndex Value may be used to select
                               the interface (denoted by
                               cTapMediationSrcInterface) on the
                               intercepting device from which to
                               transmit intercepted data to an IPv4
                               address Mediation Device.
        
            ipV6SrcInterface:  SNMP ifIndex Value may be used to select
                               the interface (denoted by
                               cTapMediationSrcInterface) on the
                               intercepting device from which to
                               transmit intercepted data to an IPv6
                               address Mediation Device.
        
            udp:               UDP may be used as transport protocol
                               (denoted by cTapMediationTransport) in
                               transferring intercepted data to the
                               Mediation Device.
        
            rtcpNack:          RTP with Nack resilience may be used
                               as transport protocol (denoted by
                               cTapMediationTransport) in transferring
                               intercepted data to the Mediation
                               Device.
        
            tcp:               TCP may be used as transport protocol
                               (denoted by cTapMediationTransport) in
                               transferring intercepted data to the
                               Mediation Device.
        
            sctp:              SCTP may be used as transport protocol
                               (denoted by cTapMediationTransport) in
                               transferring intercepted data to the
                               Mediation Device."
    ::= { cTapMediationGroup 3 }

cTapStreamCapabilities OBJECT-TYPE
    SYNTAX OCTET STRING(SIZE(1..2))
        -- BITS are:
        --   tapEnable(0)
        --   interface(1)
        --   ipV4(2)
        --   ipV6(3)
        --   l4Port(4)
        --   dscp(5)
        --   dstMacAddr(6)
        --   srcMacAddr(7)
        --   ethernetPid(8)
        --   dstLlcSap(9)
        --   srcLlcSap(10)
    ACCESS read-only
    STATUS mandatory
    DESCRIPTION
        "This object displays what types of intercept streams can be
        configured on this type of device. This may be dependent on
        hardware capabilities, software capabilities. The following
        fields may be supported:
            interface:   SNMP ifIndex Value may be used to select
                         interception of all data crossing an
                         interface or set of interfaces.
            tapEnable:   set if table entries with
                         cTapStreamIpInterceptEnable set to 'false'
                         are used to pre-screen packets for intercept;
                         otherwise these entries are ignored.
            ipV4:        IPv4 Address or prefix may be used to select
                         traffic to be intercepted.
            ipV6:        IPv6 Address or prefix may be used to select
                         traffic to be intercepted.
            l4Port:      TCP/UDP Ports may be used to select traffic
                         to be intercepted.
            dscp:        DSCP may be used to select traffic to be
                         intercepted.
            dstMacAddr:  Destination MAC Address may be used to select
                         traffic to be intercepted.
            srcMacAddr:  Source MAC Address may be used to select
                         traffic to be intercepted.
            ethernetPid: Ethernet Protocol Identifier may be used to
                         select traffic to be intercepted.
            dstLlcSap:   IEEE 802.2 Destination SAP may be used to
                         select traffic to be intercepted.
            srcLlcSap:   IEEE 802.2 Source SAP may be used to select
                         traffic to be intercepted."
    ::= { cTapStreamGroup 1 }

cTapStreamIpTable OBJECT-TYPE
    SYNTAX SEQUENCE OF CTapStreamIpEntry
    ACCESS not-accessible
    STATUS mandatory
    DESCRIPTION
        "The Intercept Stream IP Table lists the IPv4 and IPv6 streams
        to be intercepted.  The same data stream may be required by
        multiple taps, and one might assume that often the intercepted
        stream is a small subset of the traffic that could be
        intercepted.
        
        This essentially provides options for packet selection, only
        some of which might be used. For example, if all traffic to or
        from a given interface is to be intercepted, one would
        configure an entry which lists the interface, and wild-card
        everything else.  If all traffic to or from a given IP Address
        is to be intercepted, one would configure two such entries
        listing the IP Address as source and destination respectively,
        and wild-card everything else.  If a particular voice on a
        teleconference is to be intercepted, on the other hand, one
        would extract the multicast (destination) IP address, the
        source IP Address, the protocol (UDP), and the source and
        destination ports from the call control exchange and list all
        necessary information.
        
        The first index indicates which Mediation Device the
        intercepted traffic will be diverted to. The second index
        permits multiple classifiers to be used together, such as
        having an IP address as source or destination. "
    ::= { cTapStreamGroup 2 }

cTapStreamIpEntry OBJECT-TYPE
    SYNTAX CTapStreamIpEntry
    ACCESS not-accessible
    STATUS mandatory
    DESCRIPTION
        "A stream entry indicates a single data stream to be
        intercepted to a Mediation Device. Many selected data
        streams may go to the same application interface, and many
        application interfaces are supported."
    INDEX { cTapMediationContentId, cTapStreamIpIndex }
    ::= { cTapStreamIpTable 1 }

CTapStreamIpEntry ::= SEQUENCE {
    cTapStreamIpIndex INTEGER,
    cTapStreamIpInterface INTEGER,
    cTapStreamIpAddrType InetAddressType,
    cTapStreamIpDestinationAddress InetAddress,
    cTapStreamIpDestinationLength InetAddressPrefixLength,
    cTapStreamIpSourceAddress InetAddress,
    cTapStreamIpSourceLength InetAddressPrefixLength,
    cTapStreamIpTosByte INTEGER,
    cTapStreamIpTosByteMask INTEGER,
    cTapStreamIpFlowId INTEGER,
    cTapStreamIpProtocol INTEGER,
    cTapStreamIpDestL4PortMin InetPortNumber,
    cTapStreamIpDestL4PortMax InetPortNumber,
    cTapStreamIpSourceL4PortMin InetPortNumber,
    cTapStreamIpSourceL4PortMax InetPortNumber,
    cTapStreamIpInterceptEnable TruthValue,
    cTapStreamIpInterceptedPackets Counter,
    cTapStreamIpInterceptDrops Counter,
    cTapStreamIpStatus RowStatus
    }

cTapStreamIpIndex OBJECT-TYPE
    SYNTAX INTEGER(1..2147483647)
    ACCESS not-accessible
    STATUS mandatory
    DESCRIPTION
        "The index of the stream itself."
    ::= { cTapStreamIpEntry 1 }

cTapStreamIpInterface OBJECT-TYPE
    SYNTAX INTEGER(-1|0|1..2147483647)
    ACCESS read-write
    STATUS mandatory
    DESCRIPTION
        "The ifIndex value of the interface over which traffic to be
        intercepted is received or transmitted. The interface may be
        physical or virtual. If this is the only parameter specified,
        and it is other than -1 or 0, all traffic on the selected
        interface will be chosen.
        
        If the value is zero, matching traffic may be received or
        transmitted on any interface.  Additional selection parameters
        must be selected to limit the scope of traffic intercepted.
        This is most useful on non-routing platforms or on intercepts
        placed elsewhere than a subscriber interface.
        
        If the value is -1, one or both of
        cTapStreamIpDestinationAddress and cTapStreamIpSourceAddress
        must be specified with prefix length greater than zero.
        Matching traffic on the interface pointed to by ipRouteIfIndex
        or ipCidrRouteIfIndex values associated with those values is
        intercepted, whichever is specified to be more focused than a
        default route.  If routing changes, either by operator action
        or by routing protocol events, the interface will change with
        it. This is primarily intended for use on subscriber interfaces
        and other places where routing is guaranteed to be
        symmetrical.
        
        In both of these cases, it is possible to have the same packet
        selected for intersection on both its ingress and egress
        interface.  Nonetheless, only one instance of the packet is
        sent to the Mediation Device.
        
        This value must be set when creating a stream entry, either to
        select an interface, to select all interfaces, or to select the
        interface that routing chooses. Some platforms may not
        implement the entire range of options."
    REFERENCE
        "RFC 1213, RFC 2096"
    ::= { cTapStreamIpEntry 2 }

cTapStreamIpAddrType OBJECT-TYPE
    SYNTAX InetAddressType
--    Rsyntax INTEGER {
--        ?? enum value of zero may cause problems
--        unknown(0),
--        ipv4(1),
--        ipv6(2),
--        ipv4z(3),
--        ipv6z(4),
--        dns(16)
--        }
    ACCESS read-write
    STATUS mandatory
    DESCRIPTION
        "The type of address, used in packet selection."
    DEFVAL { ipv4 }
    ::= { cTapStreamIpEntry 3 }

cTapStreamIpDestinationAddress OBJECT-TYPE
    SYNTAX InetAddress
--    Rsyntax OCTET STRING(SIZE(0..255))
    ACCESS read-write
    STATUS mandatory
    DESCRIPTION
        "The Destination address or prefix used in packet selection.
        This address will be of the type specified in
        cTapStreamIpAddrType."
    DEFVAL { '00000000'H }
    ::= { cTapStreamIpEntry 4 }

cTapStreamIpDestinationLength OBJECT-TYPE
    SYNTAX InetAddressPrefixLength
--    Rsyntax Gauge
    ACCESS read-write
    STATUS mandatory
    DESCRIPTION
        "The length of the Destination Prefix. A value of zero causes
        all addresses to match.  This prefix length will be consistent
        with the type specified in cTapStreamIpAddrType."
    DEFVAL { 0 }
    ::= { cTapStreamIpEntry 5 }

cTapStreamIpSourceAddress OBJECT-TYPE
    SYNTAX InetAddress
--    Rsyntax OCTET STRING(SIZE(0..255))
    ACCESS read-write
    STATUS mandatory
    DESCRIPTION
        "The Source Address used in packet selection. This address will
        be of the type specified in cTapStreamIpAddrType."
    DEFVAL { '00000000'H }
    ::= { cTapStreamIpEntry 6 }

cTapStreamIpSourceLength OBJECT-TYPE
    SYNTAX InetAddressPrefixLength
--    Rsyntax Gauge
    ACCESS read-write
    STATUS mandatory
    DESCRIPTION
        "The length of the Source Prefix. A value of zero causes all
        addresses to match. This prefix length will be consistent with
        the type specified in cTapStreamIpAddrType."
    DEFVAL { 0 }
    ::= { cTapStreamIpEntry 7 }

cTapStreamIpTosByte OBJECT-TYPE
    SYNTAX INTEGER(0..255)
    ACCESS read-write
    STATUS mandatory
    DESCRIPTION
        "The value of the TOS byte, when masked with
        cTapStreamIpTosByteMask, of traffic to be intercepted.
        If cTapStreamIpTosByte & (~cTapStreamIpTosByteMask) != 0,
        configuration is rejected."
    DEFVAL { 0 }
    ::= { cTapStreamIpEntry 8 }

cTapStreamIpTosByteMask OBJECT-TYPE
    SYNTAX INTEGER(0..255)
    ACCESS read-write
    STATUS mandatory
    DESCRIPTION
        "The value of the TOS byte in an IPv4 or IPv6 header is ANDed
        with cTapStreamIpTosByteMask and compared with
        cTapStreamIpTosByte.
        
        If the values are equal, the comparison is equal. If the mask
        is zero and the TosByte value is zero, the result is to always
        accept."
    DEFVAL { 0 }
    ::= { cTapStreamIpEntry 9 }

cTapStreamIpFlowId OBJECT-TYPE
    SYNTAX INTEGER(-1|0..1048575)
    ACCESS read-write
    STATUS mandatory
    DESCRIPTION
        "The flow identifier in an IPv6 header. -1 indicates that the
        Flow Id is unused."
    DEFVAL { -1 }
    ::= { cTapStreamIpEntry 10 }

cTapStreamIpProtocol OBJECT-TYPE
    SYNTAX INTEGER(-1|0..255)
    ACCESS read-write
    STATUS mandatory
    DESCRIPTION
        "The IP protocol to match against the IPv4 protocol number or
        the IPv6 Next- Header number in the packet. -1 means 'any IP
        protocol'."
    DEFVAL { -1 }
    ::= { cTapStreamIpEntry 11 }

cTapStreamIpDestL4PortMin OBJECT-TYPE
    SYNTAX InetPortNumber
--    Rsyntax Gauge(0..65535)
    ACCESS read-write
    STATUS mandatory
    DESCRIPTION
        "The minimum value that the layer-4 destination port number in
        the packet must have in order to match.  This value must be
        equal to or less than the value specified for this entry in
        cTapStreamIpDestL4PortMax.
        
        If both cTapStreamIpDestL4PortMin and cTapStreamIpDestL4PortMax
        are at their default values, the port number is effectively
        unused."
    DEFVAL { 0 }
    ::= { cTapStreamIpEntry 12 }

cTapStreamIpDestL4PortMax OBJECT-TYPE
    SYNTAX InetPortNumber
--    Rsyntax Gauge(0..65535)
    ACCESS read-write
    STATUS mandatory
    DESCRIPTION
        "The maximum value that the layer-4 destination port number in
        the packet must have in order to match this classifier entry.
        This value must be equal to or greater than the value specified
        for this entry in cTapStreamIpDestL4PortMin.
        
        If both cTapStreamIpDestL4PortMin and cTapStreamIpDestL4PortMax
        are at their default values, the port number is effectively
        unused."
    DEFVAL { 65535 }
    ::= { cTapStreamIpEntry 13 }

cTapStreamIpSourceL4PortMin OBJECT-TYPE
    SYNTAX InetPortNumber
--    Rsyntax Gauge(0..65535)
    ACCESS read-write
    STATUS mandatory
    DESCRIPTION
        "The minimum value that the layer-4 destination port number in
        the packet must have in order to match.  This value must be
        equal to or less than the value specified for this entry in
        cTapStreamIpSourceL4PortMax.
        
        If both cTapStreamIpSourceL4PortMin and
        cTapStreamIpSourceL4PortMax are at their default values, the
        port number is effectively unused."
    DEFVAL { 0 }
    ::= { cTapStreamIpEntry 14 }

cTapStreamIpSourceL4PortMax OBJECT-TYPE
    SYNTAX InetPortNumber
--    Rsyntax Gauge(0..65535)
    ACCESS read-write
    STATUS mandatory
    DESCRIPTION
        "The maximum value that the layer-4 destination port number in
        the packet must have in order to match this classifier entry.
        This value must be equal to or greater than the value specified
        for this entry in cTapStreamIpSourceL4PortMin.
        
        If both cTapStreamIpSourceL4PortMin and
        cTapStreamIpSourceL4PortMax are at their default values, the
        port number is effectively unused."
    DEFVAL { 65535 }
    ::= { cTapStreamIpEntry 15 }

cTapStreamIpInterceptEnable OBJECT-TYPE
    SYNTAX TruthValue
--    Rsyntax INTEGER {
--        true(1),
--        false(2)
--        }
    ACCESS read-write
    STATUS mandatory
    DESCRIPTION
        "If 'true', the tap should intercept matching traffic.
        If 'false', this entry is used to pre-screen packets for
        intercept."
    DEFVAL { true }
    ::= { cTapStreamIpEntry 16 }

cTapStreamIpInterceptedPackets OBJECT-TYPE
    SYNTAX Counter
    ACCESS read-only
    STATUS mandatory
    DESCRIPTION
        "The number of packets matching this data stream specification
        that have been intercepted."
    ::= { cTapStreamIpEntry 17 }

cTapStreamIpInterceptDrops OBJECT-TYPE
    SYNTAX Counter
    ACCESS read-only
    STATUS mandatory
    DESCRIPTION
        "The number of packets matching this data stream specification
        that, having been intercepted, were dropped in the lawful
        intercept process."
    ::= { cTapStreamIpEntry 18 }

cTapStreamIpStatus OBJECT-TYPE
    SYNTAX RowStatus
--    Rsyntax INTEGER {
--        active(1),
--        notInService(2),
--        notReady(3),
--        createAndGo(4),
--        createAndWait(5),
--        destroy(6)
--        }
    ACCESS read-write
    STATUS mandatory
    DESCRIPTION
        "The status of this conceptual row. This object manages
        creation, modification, and deletion of rows in this table.
        cTapStreamIpInterceptEnable may be modified any time even the
        value of this entry rowStatus object is 'active'.  When other
        rows must be changed, cTapStreamIpStatus must be first set to
        'notInService'."
    ::= { cTapStreamIpEntry 19 }

cTapStream802Table OBJECT-TYPE
    SYNTAX SEQUENCE OF CTapStream802Entry
    ACCESS not-accessible
    STATUS mandatory
    DESCRIPTION
        "The Intercept Stream 802 Table lists the IEEE 802 data streams
        to be intercepted.  The same data stream may be required by
        multiple taps, and one might assume that often the intercepted
        stream is a small subset of the traffic that could be
        intercepted.
        
        This essentially provides options for packet selection, only
        some of which might be used. For example, if all traffic to or
        from a given interface is to be intercepted, one would
        configure an entry which lists the interface, and wild-card
        everything else.  If all traffic to or from a given MAC Address
        is to be intercepted, one would configure two such entries
        listing the MAC Address as source and destination respectively,
        and wild-card everything else.
        
        The first index indicates which Mediation Device the
        intercepted traffic will be diverted to. The second index
        permits multiple classifiers to be used together, such as
        having a MAC address as source or destination. "
    ::= { cTapStreamGroup 3 }

cTapStream802Entry OBJECT-TYPE
    SYNTAX CTapStream802Entry
    ACCESS not-accessible
    STATUS mandatory
    DESCRIPTION
        "A stream entry indicates a single data stream to be
        intercepted to a Mediation Device. Many selected data
        streams may go to the same application interface, and many
        application interfaces are supported."
    INDEX { cTapMediationContentId, cTapStream802Index }
    ::= { cTapStream802Table 1 }

CTapStream802Entry ::= SEQUENCE {
    cTapStream802Index INTEGER,
    cTapStream802Fields OCTET STRING,
    cTapStream802Interface INTEGER,
    cTapStream802DestinationAddress MacAddress,
    cTapStream802SourceAddress MacAddress,
    cTapStream802EthernetPid INTEGER,
    cTapStream802SourceLlcSap INTEGER,
    cTapStream802DestinationLlcSap INTEGER,
    cTapStream802InterceptEnable TruthValue,
    cTapStream802InterceptedPackets Counter,
    cTapStream802InterceptDrops Counter,
    cTapStream802Status RowStatus
    }

cTapStream802Index OBJECT-TYPE
    SYNTAX INTEGER(1..2147483647)
    ACCESS not-accessible
    STATUS mandatory
    DESCRIPTION
        "The index of the stream itself."
    ::= { cTapStream802Entry 1 }

cTapStream802Fields OBJECT-TYPE
    SYNTAX OCTET STRING(SIZE(1..2))
        -- BITS are:
        --   interface(0)
        --   dstMacAddress(1)
        --   srcMacAddress(2)
        --   ethernetPid(3)
        --   dstLlcSap(4)
        --   srcLlcSap(5)
    ACCESS read-write
    STATUS mandatory
    DESCRIPTION
        "This object displays what attributes must be tested to
        identify traffic which requires interception. The packet
        matches if all flagged fields match.
        
             interface:     indicates that traffic on the stated
                            interface is to be intercepted
             dstMacAddress: indicates that traffic destined to a
                            given address should be intercepted
             srcMacAddress: indicates that traffic sourced from a
                            given address should be intercepted
             ethernetPid:   indicates that traffic with a stated
                            Ethernet Protocol Identifier should be
                            intercepted
             dstLlcSap:     indicates that traffic with an certain
                            802.2 LLC Destination SAP should be
                            intercepted
             srcLlcSap:     indicates that traffic with an certain
                            802.2 LLC Source SAP should be
                            intercepted
        
        At least one of the bits has to be set in order to activate an
        entry.  If the bit is not on, the corresponding MIB object
        value has no effect, and need not be specified when creating
        the entry."
    ::= { cTapStream802Entry 2 }

cTapStream802Interface OBJECT-TYPE
    SYNTAX INTEGER(-1|0|1..2147483647)
    ACCESS read-write
    STATUS mandatory
    DESCRIPTION
        "The ifIndex value of the interface over which traffic to be
        intercepted is received or transmitted. The interface may be
        physical or virtual. If this is the only parameter specified,
        and it is other than -1 or 0, all traffic on the selected
        interface will be chosen.
        
        If the value is zero, matching traffic may be received or
        transmitted on any interface.  Additional selection parameters
        must be selected to limit the scope of traffic intercepted.
        This is most useful on non-routing platforms or on intercepts
        placed elsewhere than a subscriber interface.
        
        If the value is -1, one or both of
        cTapStream802DestinationAddress and cTapStream802SourceAddress
        must be specified.  Matching traffic on the interface pointed
        to by the dot1dTpFdbPort values associated with those values is
        intercepted, whichever is specified.  If dot1dTpFdbPort
        changes, either by operator action or by protocol events, the
        interface will change with it. This is primarily intended for
        use on subscriber interfaces and other places where routing is
        guaranteed to be symmetrical.
        
        In both of these cases, it is possible to have the same packet
        selected for intersection on both its ingress and egress
        interface.  Nonetheless, only one instance of the packet is
        sent to the Mediation Device.
        
        This value must be set when creating a stream entry, either to
        select an interface, to select all interfaces, or to select the
        interface that bridging learns. Some platforms may not
        implement the entire range of options."
    REFERENCE
        "RFC 1493"
    ::= { cTapStream802Entry 3 }

cTapStream802DestinationAddress OBJECT-TYPE
    SYNTAX MacAddress
--    Rsyntax OCTET STRING(SIZE(6))
    ACCESS read-write
    STATUS mandatory
    DESCRIPTION
        "The Destination address used in packet selection."
    ::= { cTapStream802Entry 4 }

cTapStream802SourceAddress OBJECT-TYPE
    SYNTAX MacAddress
--    Rsyntax OCTET STRING(SIZE(6))
    ACCESS read-write
    STATUS mandatory
    DESCRIPTION
        "The Source Address used in packet selection."
    ::= { cTapStream802Entry 5 }

cTapStream802EthernetPid OBJECT-TYPE
    SYNTAX INTEGER(0..65535)
    ACCESS read-write
    STATUS mandatory
    DESCRIPTION
        "The value of the Ethernet Protocol Identifier, which may be
        found on Ethernet traffic or IEEE 802.2 SNAP traffic."
    ::= { cTapStream802Entry 6 }

cTapStream802DestinationLlcSap OBJECT-TYPE
    SYNTAX INTEGER(0..65535)
    ACCESS read-write
    STATUS mandatory
    DESCRIPTION
        "The value of the IEEE 802.2 Destination SAP."
    ::= { cTapStream802Entry 7 }

cTapStream802SourceLlcSap OBJECT-TYPE
    SYNTAX INTEGER(0..65535)
    ACCESS read-write
    STATUS mandatory
    DESCRIPTION
        "The value of the IEEE 802.2 Source SAP."
    ::= { cTapStream802Entry 8 }

cTapStream802InterceptEnable OBJECT-TYPE
    SYNTAX TruthValue
--    Rsyntax INTEGER {
--        true(1),
--        false(2)
--        }
    ACCESS read-write
    STATUS mandatory
    DESCRIPTION
        "If 'true', the tap enables interception of matching traffic.
        If cTapStreamCapabilities flag tapEnable is zero, this may not
        be set to 'false'."
    DEFVAL { true }
    ::= { cTapStream802Entry 9 }

cTapStream802InterceptedPackets OBJECT-TYPE
    SYNTAX Counter
    ACCESS read-only
    STATUS mandatory
    DESCRIPTION
        "The number of packets matching this data stream specification
        that have been intercepted."
    ::= { cTapStream802Entry 10 }

cTapStream802InterceptDrops OBJECT-TYPE
    SYNTAX Counter
    ACCESS read-only
    STATUS mandatory
    DESCRIPTION
        "The number of packets matching this data stream specification
        that, having been intercepted, were dropped in the lawful
        intercept process."
    ::= { cTapStream802Entry 11 }

cTapStream802Status OBJECT-TYPE
    SYNTAX RowStatus
--    Rsyntax INTEGER {
--        active(1),
--        notInService(2),
--        notReady(3),
--        createAndGo(4),
--        createAndWait(5),
--        destroy(6)
--        }
    ACCESS read-write
    STATUS mandatory
    DESCRIPTION
        "The status of this conceptual row. This object manages
        creation, modification, and deletion of rows in this table.
        cTapStream802InterceptEnable can be modified any time even the
        value of this entry rowStatus object is active.  When other
        rows must be changed, cTapStream802Status must be first set to
        'notInService'."
    ::= { cTapStream802Entry 12 }

cTapDebugTable OBJECT-TYPE
    SYNTAX SEQUENCE OF CTapDebugEntry
    ACCESS not-accessible
    STATUS mandatory
    DESCRIPTION
        "A table that contains Lawful Intercept debug information
        available on this device. This table is used to map an error
        code to a text message for further information."
    ::= { cTapDebugGroup 1 }

cTapDebugEntry OBJECT-TYPE
    SYNTAX CTapDebugEntry
    ACCESS not-accessible
    STATUS mandatory
    DESCRIPTION
        "A list of the debug messages."
    INDEX { cTapDebugIndex }
    ::= { cTapDebugTable 1 }

CTapDebugEntry ::= SEQUENCE {
    cTapDebugIndex Gauge,
    cTapDebugMessage SnmpAdminString
    }

cTapDebugIndex OBJECT-TYPE
    SYNTAX Gauge
    ACCESS not-accessible
    STATUS mandatory
    DESCRIPTION
        "Indicates an error code."
    ::= { cTapDebugEntry 1 }

cTapDebugMessage OBJECT-TYPE
    SYNTAX SnmpAdminString
--    Rsyntax OCTET STRING(SIZE(0..255))
    ACCESS read-only
    STATUS mandatory
    DESCRIPTION
        "A text string contains the description of an error code."
    ::= { cTapDebugEntry 2 }

cTapMIBActive TRAP-TYPE
-- Reverse mappable trap
    ENTERPRISE cTapMIB
--  Status
--    mandatory
    DESCRIPTION
        "This Notification is sent when an intercepting router or
        switch is first capable of intercepting a packet corresponding
        to a configured data stream. If the configured data stream is
        an IP one, the value of the corresponding cTapStreamIpStatus 
        is included in this notification. If the configured data stream
        is an IEEE 802 one, the value of the corresponding 
        cTapStream802Status is included in this notification. 
        
        This notification may be generated in conjunction with the
        intercept application, which is designed to expect the
        notification to be sent as reliably as possible, e.g., through
        the use of a finite number of retransmissions until
        acknowledged, as and when such mechanisms are available; for
        example, with SNMPv3, this would be an InformRequest.  Filter
        installation can take a long period of time, during which call
        progress may be delayed."
    ::= 1

cTapMediationTimedOut TRAP-TYPE
-- Reverse mappable trap
    ENTERPRISE cTapMIB
    VARIABLES {
        cTapMediationStatus }
--  Status
--    mandatory
    DESCRIPTION
        "When an intercept is autonomously removed by an intercepting
        device, such as due to the time specified in
        cTapMediationTimeout arriving, the device notifies the manager
        of the action."
    ::= 2

cTapMediationDebug TRAP-TYPE
-- Reverse mappable trap
    ENTERPRISE cTapMIB
    VARIABLES {
        cTapMediationContentId, cTapDebugIndex }
--  Status
--    mandatory
    DESCRIPTION
        "When there is intervention needed due to some events related
        to entries configured in cTapMediationTable, the device
        notifies the manager of the event.
        
        This notification may be generated in conjunction with the
        intercept application, which is designed to expect the
        notification to be sent as reliably as possible, e.g., through
        the use of a finite number of retransmissions until
        acknowledged, as and when such mechanisms are available; for
        example, with SNMPv3, this would be an InformRequest."
    ::= 3

cTapStreamIpDebug TRAP-TYPE
-- Reverse mappable trap
    ENTERPRISE cTapMIB
    VARIABLES {
        cTapMediationContentId, cTapStreamIpIndex, cTapDebugIndex }
--  Status
--    mandatory
    DESCRIPTION
        "When there is intervention needed due to some events related
        to entries configured in cTapStreamIpTable, the device
        notifies the manager of the event.
        
        This notification may be generated in conjunction with the
        intercept application, which is designed to expect the
        notification to be sent as reliably as possible, e.g., through
        the use of a finite number of retransmissions until
        acknowledged, as and when such mechanisms are available; for
        example, with SNMPv3, this would be an InformRequest."
    ::= 4

cTapMediationComplianceGroup OBJECT IDENTIFIER ::= { cTapMIBGroups 1 }
-- OBJECT-GROUP
--  Status
--    mandatory
--  Descr
--    These objects are necessary for description of the data
--    streams directed to a Mediation Device.
--  objects
--    cTapMediationNewIndex, cTapMediationDestAddressType, 
--    cTapMediationDestAddress, cTapMediationDestPort, 
--    cTapMediationSrcInterface, cTapMediationRtcpPort, 
--    cTapMediationDscp, cTapMediationDataType, 
--    cTapMediationRetransmitType, cTapMediationTimeout, 
--    cTapMediationTransport, cTapMediationNotificationEnable, 
--    cTapMediationStatus

cTapStreamComplianceGroup OBJECT IDENTIFIER ::= { cTapMIBGroups 2 }
-- OBJECT-GROUP
--  Status
--    mandatory
--  Descr
--    These objects are necessary for a description of the packets
--    to select for interception.
--  objects
--    cTapStreamCapabilities

cTapStreamIpComplianceGroup OBJECT IDENTIFIER ::= { cTapMIBGroups 3 }
-- OBJECT-GROUP
--  Status
--    mandatory
--  Descr
--    These objects are necessary for a description of IPv4 and IPv6
--    packets to select for interception.
--  objects
--    cTapStreamIpInterface, cTapStreamIpAddrType, 
--    cTapStreamIpDestinationAddress, cTapStreamIpDestinationLength, 
--    cTapStreamIpSourceAddress, cTapStreamIpSourceLength, 
--    cTapStreamIpTosByte, cTapStreamIpTosByteMask, 
--    cTapStreamIpFlowId, cTapStreamIpProtocol, 
--    cTapStreamIpDestL4PortMin, cTapStreamIpDestL4PortMax, 
--    cTapStreamIpSourceL4PortMin, cTapStreamIpSourceL4PortMax, 
--    cTapStreamIpInterceptEnable, cTapStreamIpInterceptedPackets, 
--    cTapStreamIpInterceptDrops, cTapStreamIpStatus

cTapStream802ComplianceGroup OBJECT IDENTIFIER ::= { cTapMIBGroups 4 }
-- OBJECT-GROUP
--  Status
--    mandatory
--  Descr
--    These objects are necessary for a description of IEEE 802
--    packets to select for interception.
--  objects
--    cTapStream802Fields, cTapStream802Interface, 
--    cTapStream802DestinationAddress, cTapStream802SourceAddress, 
--    cTapStream802EthernetPid, cTapStream802SourceLlcSap, 
--    cTapStream802DestinationLlcSap, cTapStream802InterceptEnable, 
--    cTapStream802InterceptedPackets, cTapStream802InterceptDrops, 
--    cTapStream802Status

cTapMediationCpbComplianceGroup OBJECT IDENTIFIER ::= { cTapMIBGroups 6 }
-- OBJECT-GROUP
--  Status
--    mandatory
--  Descr
--    These objects are necessary for a description of the 
--    mediation device to select for Lawful Intercept.
--  objects
--    cTapMediationCapabilities

cTapDebugComplianceGroup OBJECT IDENTIFIER ::= { cTapMIBGroups 7 }
-- OBJECT-GROUP
--  Status
--    mandatory
--  Descr
--    These objects are necessary for debug information.
--  objects
--    cTapDebugMessage

cTapNotificationGroup OBJECT IDENTIFIER ::= { cTapMIBGroups 5 }
-- NOTIFICATION-GROUP
--  Status
--    mandatory
--  Descr
--    These notifications are used to present status from the
--    intercepting device to the Mediation Device.
--  notifications
--    cTapMIBActive, cTapMediationTimedOut, cTapMediationDebug, 
--    cTapStreamIpDebug

cTapMIBCompliance OBJECT IDENTIFIER ::= { cTapMIBCompliances 1 }
-- MODULE-COMPLIANCE
--  Status
--    mandatory
--  Descr
--    The compliance statement for entities which implement the
--    Cisco Intercept MIB
--  Module
--    >>current<<
--   MandGroup
--    cTapMediationComplianceGroup
--   MandGroup
--    cTapStreamComplianceGroup
--   MandGroup
--    cTapMediationCpbComplianceGroup
--   MandGroup
--    cTapNotificationGroup


END
