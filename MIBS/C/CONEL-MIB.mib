CONEL-MIB DEFINITIONS ::= BEGIN

IMPORTS
			enterprises
				FROM RFC1155-SMI;

conel			OBJECT IDENTIFIER ::= { enterprises 30140 }

products		OBJECT IDENTIFIER ::= { conel 1 }

routerER75		OBJECT IDENTIFIER ::= { products 1 }
routerER75i		OBJECT IDENTIFIER ::= { products 2 }
routerUR5		OBJECT IDENTIFIER ::= { products 3 }
routerUR5i		OBJECT IDENTIFIER ::= { products 4 }
routerXR5i		OBJECT IDENTIFIER ::= { products 5 }
routerER75iV2		OBJECT IDENTIFIER ::= { products 6 }
routerUR5V2		OBJECT IDENTIFIER ::= { products 7 }
routerUR5iV2		OBJECT IDENTIFIER ::= { products 8 }
routerXR5iV2		OBJECT IDENTIFIER ::= { products 9 }
routerLR77V2		OBJECT IDENTIFIER ::= { products 10 }
routerCR10V2		OBJECT IDENTIFIER ::= { products 11 }
routerUCR11V2		OBJECT IDENTIFIER ::= { products 12 }
routerUR5iV2L		OBJECT IDENTIFIER ::= { products 13 }
routerSpectre3G		OBJECT IDENTIFIER ::= { products 14 }
routerSpectreRT		OBJECT IDENTIFIER ::= { products 15 }
routerRR75i		OBJECT IDENTIFIER ::= { products 16 }
routerSpectreLTEAT	OBJECT IDENTIFIER ::= { products 17 }
routerXR5iV2E		OBJECT IDENTIFIER ::= { products 18 }
routerBiviasV2HC	OBJECT IDENTIFIER ::= { products 19 }
routerBiviasV2LC	OBJECT IDENTIFIER ::= { products 20 }
routerSpectreLTEVZ	OBJECT IDENTIFIER ::= { products 21 }
routerBiviasV2LL	OBJECT IDENTIFIER ::= { products 22 }
routerBiviasV2LH	OBJECT IDENTIFIER ::= { products 23 }
routerBiviasV2HH	OBJECT IDENTIFIER ::= { products 24 }
routerLR77V2L		OBJECT IDENTIFIER ::= { products 25 }
routerSpectreV3HSPA	OBJECT IDENTIFIER ::= { products 26 }
routerSpectreV3LTE	OBJECT IDENTIFIER ::= { products 27 }
routerSpectreV3CDMA	OBJECT IDENTIFIER ::= { products 28 }
routerSpectreV3ERT	OBJECT IDENTIFIER ::= { products 29 }
routerSpectreV3TLTE	OBJECT IDENTIFIER ::= { products 32 }
routerSpectreV3LTEUS	OBJECT IDENTIFIER ::= { products 35 }
routerSpectreV3LLTE	OBJECT IDENTIFIER ::= { products 36 }
routerSpectreV3LLTEUS	OBJECT IDENTIFIER ::= { products 37 }
routerSpectreV3ERTUS	OBJECT IDENTIFIER ::= { products 38 }
routerSpectreV3LERT	OBJECT IDENTIFIER ::= { products 39 }
routerSpectreV3LERTUS	OBJECT IDENTIFIER ::= { products 40 }
routerSpectreV3TLTEUS	OBJECT IDENTIFIER ::= { products 41 }
routerICR321X		OBJECT IDENTIFIER ::= { products 42 }
routerICR323X		OBJECT IDENTIFIER ::= { products 43 }
routerICR324X		OBJECT IDENTIFIER ::= { products 44 }

END
