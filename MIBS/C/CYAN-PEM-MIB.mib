CYAN-PEM-MIB DEFINITIONS ::= BEGIN
IMPORTS
    MODULE-IDENTITY,
    OBJECT-TYPE,
    Integer32,
    Unsigned32
                    FROM SNMPv2-SMI

    DisplayString
                    FROM SNMPv2-TC

    CyanAdminStateTc,
    CyanOpStateQualTc,
    CyanOpStateTc,
    CyanSecServiceStateTc
                    FROM CYAN-TC-MIB

    CyanTypeTc,
    cyanEntityModules
		    FROM CYAN-MIB

    MODULE-COMPLIANCE, 
    OBJECT-GROUP
	            FROM SNMPv2-CONF;


cyanPemModule MODULE-IDENTITY
    LAST-UPDATED "201412070545Z" -- Sun Dec  7 05:45:29 2014
    ORGANIZATION "Cyan, Inc."
    CONTACT-INFO
        "
        E-mail:  support@cyaninc.com

        Postal:  Cyan, Inc.
               1390 N. McDowell Blvd., # G-327
               Petaluma, CA  94954
               USA

        Tel:     +1-707-735-2300"

    DESCRIPTION    "MIB module for Power Entry Module"

    REVISION     "201412070545Z" -- Sun Dec  7 05:45:29 2014
    DESCRIPTION  "Release 6.0 build 1416362081"

    ::= { cyanEntityModules 30 } 

cyanPemMibObjects           OBJECT IDENTIFIER ::={ cyanPemModule 1 }

cyanPemTable    OBJECT-TYPE
    SYNTAX        SEQUENCE OF CyanPemEntry
    MAX-ACCESS    not-accessible
    STATUS        current
    DESCRIPTION
        "A list of Pem entries."
    ::= { cyanPemMibObjects 1 }

cyanPemEntry    OBJECT-TYPE
    SYNTAX        CyanPemEntry
    MAX-ACCESS    not-accessible
    STATUS        current
    DESCRIPTION
        "An entry of Pem."
    INDEX {
        cyanPemShelfId ,
        cyanPemPemId 
    }
    ::= { cyanPemTable 1 }

CyanPemEntry  ::=
    SEQUENCE {
        cyanPemShelfId    Unsigned32,
        cyanPemPemId    Unsigned32,
        cyanPemAdminState    CyanAdminStateTc,
        cyanPemAssetTag    DisplayString,
        cyanPemAutoinserviceSoakTimeSec    Integer32,
        cyanPemBaseMacAddress    DisplayString,
        cyanPemDescription    DisplayString,
        cyanPemIdentifier    DisplayString,
        cyanPemMacBlockSize    Unsigned32,
        cyanPemMfgCleiCode    DisplayString,
        cyanPemMfgEciCode    DisplayString,
        cyanPemMfgModuleId    Unsigned32,
        cyanPemMfgPartNumber    DisplayString,
        cyanPemMfgRevision    DisplayString,
        cyanPemMfgSerialNumber    DisplayString,
        cyanPemName    DisplayString,
        cyanPemOidClass    DisplayString,
        cyanPemOperState    CyanOpStateTc,
        cyanPemOperStateQual    CyanOpStateQualTc,
        cyanPemOssLabel    DisplayString,
        cyanPemOwner    DisplayString,
        cyanPemPartNumber    DisplayString,
        cyanPemSecServState    CyanSecServiceStateTc,
        cyanPemType    CyanTypeTc
    }

cyanPemShelfId OBJECT-TYPE
    SYNTAX       Unsigned32 (0..255)
    MAX-ACCESS   not-accessible
    STATUS       current
    DESCRIPTION
        "Shelf Id"

    ::= { cyanPemEntry 1 }
cyanPemPemId OBJECT-TYPE
    SYNTAX       Unsigned32
    MAX-ACCESS   not-accessible
    STATUS       current
    DESCRIPTION
        "Power Entry Module Id"

    ::= { cyanPemEntry 2 }

cyanPemAdminState OBJECT-TYPE
    SYNTAX       CyanAdminStateTc
    MAX-ACCESS   read-only
    STATUS       current
    DESCRIPTION
        "Administrative state"

    ::= { cyanPemEntry 3 }

cyanPemAssetTag OBJECT-TYPE
    SYNTAX       DisplayString (SIZE(0..124))
    MAX-ACCESS   read-only
    STATUS       current
    DESCRIPTION
        "Asset Tag"

    ::= { cyanPemEntry 4 }

cyanPemAutoinserviceSoakTimeSec OBJECT-TYPE
    SYNTAX       Integer32
    MAX-ACCESS   read-only
    STATUS       current
    DESCRIPTION
        "Auto-In-Service soak time"

    ::= { cyanPemEntry 5 }

cyanPemBaseMacAddress OBJECT-TYPE
    SYNTAX       DisplayString
    MAX-ACCESS   read-only
    STATUS       current
    DESCRIPTION
        "Base MAC address of a range of addresses"

    ::= { cyanPemEntry 6 }

cyanPemDescription OBJECT-TYPE
    SYNTAX       DisplayString (SIZE(0..255))
    MAX-ACCESS   read-only
    STATUS       current
    DESCRIPTION
        "Description"

    ::= { cyanPemEntry 7 }

cyanPemIdentifier OBJECT-TYPE
    SYNTAX       DisplayString
    MAX-ACCESS   read-only
    STATUS       current
    DESCRIPTION
        "string OID"

    ::= { cyanPemEntry 8 }

cyanPemMacBlockSize OBJECT-TYPE
    SYNTAX       Unsigned32 (0..255)
    MAX-ACCESS   read-only
    STATUS       current
    DESCRIPTION
        "Number of MAC addresses allocated from the base MAC address"

    ::= { cyanPemEntry 9 }

cyanPemMfgCleiCode OBJECT-TYPE
    SYNTAX       DisplayString (SIZE(0..10))
    MAX-ACCESS   read-only
    STATUS       current
    DESCRIPTION
        "Common Language Equipment Identifier"

    ::= { cyanPemEntry 10 }

cyanPemMfgEciCode OBJECT-TYPE
    SYNTAX       DisplayString (SIZE(0..6))
    MAX-ACCESS   read-only
    STATUS       current
    DESCRIPTION
        "Equipment Catalog Item"

    ::= { cyanPemEntry 11 }

cyanPemMfgModuleId OBJECT-TYPE
    SYNTAX       Unsigned32
    MAX-ACCESS   read-only
    STATUS       current
    DESCRIPTION
        "Module ID"

    ::= { cyanPemEntry 12 }

cyanPemMfgPartNumber OBJECT-TYPE
    SYNTAX       DisplayString (SIZE(0..16))
    MAX-ACCESS   read-only
    STATUS       current
    DESCRIPTION
        "Manufacturing part number"

    ::= { cyanPemEntry 13 }

cyanPemMfgRevision OBJECT-TYPE
    SYNTAX       DisplayString (SIZE(0..4))
    MAX-ACCESS   read-only
    STATUS       current
    DESCRIPTION
        "Mfg revision number"

    ::= { cyanPemEntry 14 }

cyanPemMfgSerialNumber OBJECT-TYPE
    SYNTAX       DisplayString (SIZE(0..16))
    MAX-ACCESS   read-only
    STATUS       current
    DESCRIPTION
        "Mfg serial number"

    ::= { cyanPemEntry 15 }

cyanPemName OBJECT-TYPE
    SYNTAX       DisplayString
    MAX-ACCESS   read-only
    STATUS       current
    DESCRIPTION
        "Cyan name"

    ::= { cyanPemEntry 16 }

cyanPemOidClass OBJECT-TYPE
    SYNTAX       DisplayString
    MAX-ACCESS   read-only
    STATUS       current
    DESCRIPTION
        "OID Class"

    ::= { cyanPemEntry 17 }

cyanPemOperState OBJECT-TYPE
    SYNTAX       CyanOpStateTc
    MAX-ACCESS   read-only
    STATUS       current
    DESCRIPTION
        "Primary Operation State"

    ::= { cyanPemEntry 18 }

cyanPemOperStateQual OBJECT-TYPE
    SYNTAX       CyanOpStateQualTc
    MAX-ACCESS   read-only
    STATUS       current
    DESCRIPTION
        "Operation state qualifier"

    ::= { cyanPemEntry 19 }

cyanPemOssLabel OBJECT-TYPE
    SYNTAX       DisplayString (SIZE(0..80))
    MAX-ACCESS   read-only
    STATUS       current
    DESCRIPTION
        "CyMS label"

    ::= { cyanPemEntry 20 }

cyanPemOwner OBJECT-TYPE
    SYNTAX       DisplayString (SIZE(0..80))
    MAX-ACCESS   read-only
    STATUS       current
    DESCRIPTION
        "Owner"

    ::= { cyanPemEntry 21 }

cyanPemPartNumber OBJECT-TYPE
    SYNTAX       DisplayString (SIZE(0..11))
    MAX-ACCESS   read-only
    STATUS       current
    DESCRIPTION
        "Cyan part number"

    ::= { cyanPemEntry 22 }

cyanPemSecServState OBJECT-TYPE
    SYNTAX       CyanSecServiceStateTc
    MAX-ACCESS   read-only
    STATUS       current
    DESCRIPTION
        "Secondary service state"

    ::= { cyanPemEntry 23 }

cyanPemType OBJECT-TYPE
    SYNTAX       CyanTypeTc
    MAX-ACCESS   read-only
    STATUS       current
    DESCRIPTION
        "Equipment type"

    ::= { cyanPemEntry 24 }

cyanPemObjectGroup OBJECT-GROUP
    OBJECTS {
        cyanPemAdminState,
        cyanPemAssetTag,
        cyanPemAutoinserviceSoakTimeSec,
        cyanPemBaseMacAddress,
        cyanPemDescription,
        cyanPemIdentifier,
        cyanPemMacBlockSize,
        cyanPemMfgCleiCode,
        cyanPemMfgEciCode,
        cyanPemMfgModuleId,
        cyanPemMfgPartNumber,
        cyanPemMfgRevision,
        cyanPemMfgSerialNumber,
        cyanPemName,
        cyanPemOidClass,
        cyanPemOperState,
        cyanPemOperStateQual,
        cyanPemOssLabel,
        cyanPemOwner,
        cyanPemPartNumber,
        cyanPemSecServState,
        cyanPemType
    }

    STATUS current
    DESCRIPTION        "Group of objects that comes with Pem module"
    ::= {cyanPemModule 20}

cyanPemCompliance MODULE-COMPLIANCE
    STATUS current
    DESCRIPTION
        "The basic info needed to be a cyan Pem"
    MODULE
    MANDATORY-GROUPS {
        cyanPemObjectGroup
    }
    ::= { cyanPemModule 30 }


END
