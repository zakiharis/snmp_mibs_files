-- *****************************************************************
-- CISCO-CASA-FA-CAPABILITY.my:  Cisco forwarding agent capability mib
--
-- March 2000, Jason Cox
--
-- Copyright (c) 2000 by cisco Systems, Inc.
-- All rights reserved.
--
-- *****************************************************************
--
CISCO-CASA-FA-CAPABILITY DEFINITIONS ::= BEGIN

IMPORTS
        MODULE-IDENTITY
                FROM SNMPv2-SMI
        AGENT-CAPABILITIES
                FROM SNMPv2-CONF
        ciscoAgentCapability
                FROM CISCO-SMI;

ciscoCasaFaCapability MODULE-IDENTITY
                LAST-UPDATED    "200012010000Z"
                ORGANIZATION    "Cisco Systems, Inc."
                CONTACT-INFO
                        "       Cisco Systems
                                Customer Service
                        
                        Postal: 170 West Tasman Drive
                                San Jose, CA  95134
                                USA
                        
                           Tel: +1 800 553-NETS
                        
                        E-mail: cs-snmp@cisco.com"
                DESCRIPTION
                        "Agent capabilities for the CASA-FA-MIB"
                REVISION        "200012010000Z"
                DESCRIPTION
                        "Initial version of this MIB module."
        ::= { ciscoAgentCapability 135 }

ciscoCasaFaCapabilityV12R01 AGENT-CAPABILITIES

PRODUCT-RELEASE "Cisco IOS 12.2"
STATUS		current
DESCRIPTION	"IOS 12.1 Cisco Casa Forwarding Agent MIB capabilities"

SUPPORTS	CISCO-CASA-FA-MIB
  INCLUDES	{ ciscoCasaFaDispatchGroup, ciscoCasaFaADGroup
                }
	
  VARIATION ccfaDispatchBytesIn
    ACCESS    not-implemented
    DESCRIPTION "not implemented"

  VARIATION ccfaDispatchHCBytesIn
    ACCESS    not-implemented
    DESCRIPTION "not implemented"

  VARIATION ccfaDispatchBytesOut
    ACCESS    not-implemented
    DESCRIPTION "not implemented"

  VARIATION ccfaDispatchHCBytesOut
    ACCESS    not-implemented
    DESCRIPTION "not implemented"

  VARIATION ccfaDispatchPacketsIn
    ACCESS    not-implemented
    DESCRIPTION "not implemented"

  VARIATION ccfaDispatchHCPacketsIn
    ACCESS    not-implemented
    DESCRIPTION "not implemented"

  VARIATION ccfaDispatchPacketsOut
    ACCESS    not-implemented
    DESCRIPTION "not implemented"

  VARIATION ccfaDispatchHCPacketsOut
    ACCESS    not-implemented
    DESCRIPTION "not implemented"

  VARIATION ccfaAdvertisedDispatchAddress
    ACCESS    not-implemented
    DESCRIPTION "not implemented"

        ::= { ciscoCasaFaCapability 1 }

END
