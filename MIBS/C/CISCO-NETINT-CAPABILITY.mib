-- *****************************************************************
-- CISCO-NETINT-CAPABILITY.my:
-- Cisco CISCO-NETINT-MIB AGENT-CAPABILITIES
--
-- July 2007, Edward Pham 
--
-- Copyright (c) 2007 by Cisco Systems, Inc.
-- All rights reserved.
-- *****************************************************************

CISCO-NETINT-CAPABILITY DEFINITIONS ::= BEGIN

IMPORTS
        MODULE-IDENTITY
                FROM SNMPv2-SMI
        AGENT-CAPABILITIES
                FROM SNMPv2-CONF
        ciscoAgentCapability
                FROM CISCO-SMI;

ciscoNetintCapability MODULE-IDENTITY
        LAST-UPDATED    "200707030000Z"
        ORGANIZATION    "Cisco Systems, Inc."
        CONTACT-INFO
                "       Cisco Systems
                        Customer Service

                Postal: 170 West Tasman Drive
                        San Jose, CA  95134
                        USA

                   Tel: +1 800 553-NETS

                E-mail: cs-lan-switch-snmp@cisco.com"
        DESCRIPTION
                "The capabilities description of CISCO-NETINT-MIB."
        REVISION        "200707030000Z"
        DESCRIPTION
                "Initial version of this MIB module."
        ::= { ciscoAgentCapability 452 }

ciscoNetintCapV12R0233SXHPCat6k AGENT-CAPABILITIES
    PRODUCT-RELEASE     "Cisco IOS 12.2(33)SXH on Catalyst 6000/6500
                         series devices."
    STATUS              current
    DESCRIPTION         "CISCO-NETINT-MIB capabilities."

    SUPPORTS            CISCO-NETINT-MIB
        INCLUDES        { 
                          ciscoThrottleGroup
                        }

    ::= { ciscoNetintCapability 1 }

END
