--Cambium MIB Release CAMBIUM_MIB_VERSION

CAMBIUM-PMP80211-MIB DEFINITIONS ::= BEGIN

IMPORTS
		OBJECT-TYPE, MODULE-IDENTITY, NOTIFICATION-TYPE, enterprises,
		IpAddress, Integer32, Counter32, Counter64, TimeTicks
				FROM SNMPv2-SMI
		OBJECT-GROUP
				FROM SNMPv2-CONF
		MacAddress, DisplayString
				FROM SNMPv2-TC;

pmpMibTree MODULE-IDENTITY
	LAST-UPDATED "201304261238Z"
	ORGANIZATION 
		"Cambium Networks Inc."
	CONTACT-INFO 
		"Cambium Networks Support"
	DESCRIPTION 
		"This module contains MIB definitions for APs."

	REVISION "201304261238Z"
	DESCRIPTION 
		"Initial Production Version."

::= { cambium 21 }

cambium				 OBJECT IDENTIFIER ::= { enterprises 17713 }

cambiumPmp80211SystemStatus	 OBJECT IDENTIFIER ::= { pmpMibTree 1 }
cambiumGeneralStatus	 OBJECT IDENTIFIER ::= { cambiumPmp80211SystemStatus 1 }
cambiumRFStatus			 OBJECT IDENTIFIER ::= { cambiumPmp80211SystemStatus 2 }
cambiumGPSStatus		 OBJECT IDENTIFIER ::= { cambiumPmp80211SystemStatus 3 }
cambiumLinkStatus		 OBJECT IDENTIFIER ::= { cambiumPmp80211SystemStatus 4 }
cambiumAcsStatus		 OBJECT IDENTIFIER ::= { cambiumPmp80211SystemStatus 5 }
cambiumMcastStatus		 OBJECT IDENTIFIER ::= { cambiumPmp80211SystemStatus 6 }
cambiumDhcpStatus		 OBJECT IDENTIFIER ::= { cambiumPmp80211SystemStatus 7 }
cambiumLicenseInfo	 OBJECT IDENTIFIER ::= { cambiumPmp80211SystemStatus 8 }
cambiumRadiusVSAStatus	 OBJECT IDENTIFIER ::= { cambiumPmp80211SystemStatus 9 }
cambiumPmp80211SystemMonitoring	 OBJECT IDENTIFIER ::= { pmpMibTree 2 }
cambiumPerformanceMonitoring   OBJECT IDENTIFIER ::= { cambiumPmp80211SystemMonitoring 1 }
cambiumRealTimeStatsMonitoring	OBJECT IDENTIFIER ::= { cambiumPmp80211SystemMonitoring 2 }
cambiumAdvancedPerformanceMonitoring OBJECT IDENTIFIER ::= { cambiumPmp80211SystemMonitoring 3 }
cambiumpmp80211SystemConfiguration	OBJECT IDENTIFIER ::= { pmpMibTree 3 }
cambiumSystemLog	 OBJECT IDENTIFIER ::= { cambiumpmp80211SystemConfiguration 1 }
cambiumDHCP			 OBJECT IDENTIFIER ::= { cambiumpmp80211SystemConfiguration 2 }
cambiumSSHServer	 OBJECT IDENTIFIER ::= { cambiumpmp80211SystemConfiguration 3 }
network				 OBJECT IDENTIFIER ::= { cambiumpmp80211SystemConfiguration 4 }
networkLan			 OBJECT IDENTIFIER ::= { network 2 }
networkWan			 OBJECT IDENTIFIER ::= { network 3 }
snmp				 OBJECT IDENTIFIER ::= { cambiumpmp80211SystemConfiguration 5 }
cambiumSystem		 OBJECT IDENTIFIER ::= { cambiumpmp80211SystemConfiguration 6 }
systemConfig		 OBJECT IDENTIFIER ::= { cambiumSystem 1 }
systemNtpServer		 OBJECT IDENTIFIER ::= { cambiumSystem 2 }
cambiumWebServer	 OBJECT IDENTIFIER ::= { cambiumpmp80211SystemConfiguration 7 }
wireless			 OBJECT IDENTIFIER ::= { cambiumpmp80211SystemConfiguration 8 }
wirelessDevice		 OBJECT IDENTIFIER ::= { wireless 1 }
wirelessInterface	 OBJECT IDENTIFIER ::= { wireless 2 }
wirelessPrefList	 OBJECT IDENTIFIER ::= { wireless 3 }
wirelessMIRList		 OBJECT IDENTIFIER ::= { wireless 4 }
wirelessRadius		 OBJECT IDENTIFIER ::= { wireless 5 }
wirelessRadiusServerList  OBJECT IDENTIFIER ::= { wireless 6 }
wirelessRadiusCertificateList  OBJECT IDENTIFIER ::= { wireless 7 }
wirelessRadiusCertificateListRow1  OBJECT IDENTIFIER ::= { wirelessRadiusCertificateList 1 }
wirelessRadiusCertificateListRow2  OBJECT IDENTIFIER ::= { wirelessRadiusCertificateList 2 }
wirelessRadiusCertificateListRow3  OBJECT IDENTIFIER ::= { wirelessRadiusCertificateList 3 }
wirelessRadiusCertificateSet  OBJECT IDENTIFIER ::= { wireless 8 }
wirelessRadiusExtraCertificateSet  OBJECT IDENTIFIER ::= { wireless 9 }
l2Firewall			 OBJECT IDENTIFIER ::= { cambiumpmp80211SystemConfiguration 9 }
l3Firewall			 OBJECT IDENTIFIER ::= { cambiumpmp80211SystemConfiguration 10 }
confQoS				 OBJECT IDENTIFIER ::= { cambiumpmp80211SystemConfiguration 11 }
dmz					 OBJECT IDENTIFIER ::= { cambiumpmp80211SystemConfiguration 12 }
portForwarding		 OBJECT IDENTIFIER ::= { cambiumpmp80211SystemConfiguration 13 }
vlans				 OBJECT IDENTIFIER ::= { cambiumpmp80211SystemConfiguration 14 }
dlkm                 OBJECT IDENTIFIER ::= { cambiumpmp80211SystemConfiguration 15 }
routing				 OBJECT IDENTIFIER ::= { cambiumpmp80211SystemConfiguration 16 }
cambiumDeviceAgent	 OBJECT IDENTIFIER ::= { cambiumpmp80211SystemConfiguration 20 }
upnpd                OBJECT IDENTIFIER ::= { cambiumpmp80211SystemConfiguration 21 }
lldpd                OBJECT IDENTIFIER ::= { cambiumpmp80211SystemConfiguration 23 }
mgmtVLAN			 OBJECT IDENTIFIER ::= { network 4 }
dataVLAN			 OBJECT IDENTIFIER ::= { network 5 }
mcastVLAN			 OBJECT IDENTIFIER ::= { network 15 }
networkBridge		 OBJECT IDENTIFIER ::= { network 7 }
mgmtIF				 OBJECT IDENTIFIER ::= { network 20 }
networkAliases		OBJECT IDENTIFIER ::= { network 27 }
cambiumpmp80211SystemActions  OBJECT IDENTIFIER ::= { pmpMibTree 4 }
cambiumpmp80211SystemTraps	OBJECT IDENTIFIER ::= { pmpMibTree 0 }
cambiumpmp80211Tools  OBJECT IDENTIFIER ::= { pmpMibTree 6 }
cambiumLinkTest		 OBJECT IDENTIFIER ::= { cambiumpmp80211Tools 1 }
caminfo				 OBJECT IDENTIFIER ::= { cambiumpmp80211Tools 2 }
cambiumToolBar		 OBJECT IDENTIFIER ::= { cambiumpmp80211Tools 3 }
cambiumCfg			 OBJECT IDENTIFIER ::= { cambiumpmp80211Tools 4 }
cambiumIDM			 OBJECT IDENTIFIER ::= { cambiumpmp80211Tools 5 }
cambiumACSCfg		 OBJECT IDENTIFIER ::= { cambiumpmp80211Tools 6 }
cambiumToolBarOpts	 OBJECT IDENTIFIER ::= { cambiumToolBar 1 }
cambiumToolBarStates OBJECT IDENTIFIER ::= { cambiumToolBar 2 }
multicast            OBJECT IDENTIFIER ::= { wireless 10 }

cambiumCurrentSWInfo  OBJECT-TYPE
	SYNTAX	   DisplayString (SIZE(1..128))
	MAX-ACCESS read-only
	STATUS	   current
	DESCRIPTION 
		"Software information - version, etc.
	 Device Allocation: AP, SM"
	::= { cambiumGeneralStatus 1 }

cambiumHWInfo  OBJECT-TYPE
	SYNTAX     Integer32 (-1|0|1|2|3|4|5|6|7|8|9|10|11|12)
	MAX-ACCESS read-only
	STATUS	   current
	DESCRIPTION 
		"Hardware SKU:
			-1 - Not available
			0 - 5 GHz Connectorized Radio with Sync
			1 - 5 GHz Connectorized Radio
			2 - 5 GHz Integrated Radio
			3 - 2.4 GHz Connectorized Radio with Sync
			4 - 2.4 GHz Connectorized Radio
			5 - 2.4 GHz Integrated Radio
			6 - Force 200 ROW
			7 - Reserved
			8 - Force 200
			9 - Force 200 FCC
			10 - Reserved
			11 - Force 180 ROW
			12 - Force 180 FCC
		Device Allocation: AP, SM"
	::= { cambiumGeneralStatus 2 }

cambiumDateTime	 OBJECT-TYPE
		SYNTAX	   DisplayString (SIZE(1..128))
		MAX-ACCESS read-only
		STATUS	   current
		DESCRIPTION
		"Date and Time in format mm/dd/yyyy:hh:mm:ss
		Device Allocation: AP, SM"
		::= { cambiumGeneralStatus 3 }

cambiumSystemUptime	 OBJECT-TYPE
		SYNTAX	   DisplayString (SIZE(1..128))
		MAX-ACCESS read-only
		STATUS	   current
		DESCRIPTION
		"Device UpTime in format days, hours, minutes, and seconds -> dddd:hh:mm:ss
		Device Allocation: AP, SM"
		::= { cambiumGeneralStatus 4 }

cambiumWirelessMACAddress  OBJECT-TYPE
		SYNTAX	   DisplayString (SIZE(11..17))
		MAX-ACCESS read-only
		STATUS	   current
		DESCRIPTION
		"The device Wireless MAC address
		Device Allocation: AP, SM"
		::= { cambiumGeneralStatus 5 }

cambiumDFSStatus  OBJECT-TYPE
		SYNTAX	   Integer32 (1..6)
		MAX-ACCESS read-only
		STATUS	   current
		DESCRIPTION
		"DFS Status:
			1 - N/A, 
			2 - Channel Availability Check, 
			3 - In-Service,
			4 - Radar Signal Detected,
			5 - In-Service Monitoring at Alternative Channel,
			6 - System Not In Service due to DFS
		Device Allocation: AP, SM"
		::= { cambiumGeneralStatus 6 }

cambiumEffectiveSyncSource OBJECT-TYPE
		SYNTAX	   Integer32 (1|2|3|4)
		MAX-ACCESS read-only 
		STATUS	   current
		DESCRIPTION
		"Sync Source Status:
			1 - GPS Sync Up, 
			2 - GPS Sync Down, 
			3 - CMM4 Sync,
			4 - CMM3 Sync
		Device Allocation: AP"
		::= { cambiumGeneralStatus 7 }

cambiumEffectiveCountryCode OBJECT-TYPE
		SYNTAX	   DisplayString (SIZE(2))
		MAX-ACCESS read-only
		STATUS	   current
		DESCRIPTION
		"Current device Country Code
		Device Allocation: AP, SM"
		::= { cambiumGeneralStatus 8 }

cambiumEffectiveAntennaGain OBJECT-TYPE
		SYNTAX	   Integer32 (0..40)
		MAX-ACCESS read-only
		STATUS	   current
		DESCRIPTION
		"Effective Antenna Gain in dBi
		Device Allocation: AP, SM"
		::= { cambiumGeneralStatus 9 }

cambiumEffectiveTDDRatio OBJECT-TYPE
		SYNTAX	   Integer32 (0..4)
		MAX-ACCESS read-only 
		STATUS	   current
		DESCRIPTION
		"Effective DL/UL Ratio:
			1 - 75/25, 
			2 - 50/50, 
			3 - 30/70, 
			4 - Flexible
		Device Allocation: AP, SM"
		::= { cambiumGeneralStatus 10 }

cambiumEffectiveSSID OBJECT-TYPE
		SYNTAX	   DisplayString (SIZE(0..128))
		MAX-ACCESS read-only
		STATUS	   current
		DESCRIPTION
		"Effective SSID
		Device Allocation: AP"
		::= { cambiumGeneralStatus 11 }

cambiumEffectiveAuthenticationType OBJECT-TYPE
		SYNTAX	   Integer32 (0|1|2|3)
		MAX-ACCESS read-only
		STATUS	   current
		DESCRIPTION
		"Effective Authentication Type:
			1 - Open,
			2 - WPA2,
			3 - EAP-TTLS"
		::= { cambiumGeneralStatus 12 }

cambiumEffectiveDeviceName OBJECT-TYPE
		SYNTAX	   DisplayString (SIZE(0..128))
		MAX-ACCESS read-only
		STATUS	   current
		DESCRIPTION
		"Effective Device Name
		Device Allocation: AP, SM"
		::= { cambiumGeneralStatus 13 }

cambiumUbootVersion OBJECT-TYPE
		SYNTAX	   DisplayString (SIZE(0..128))
		MAX-ACCESS read-only
		STATUS	   current
		DESCRIPTION
		"U-boot version
		Device Allocation: AP, SM"
		::= { cambiumGeneralStatus 14 }

cambiumLANMACAddress  OBJECT-TYPE
		SYNTAX	   DisplayString (SIZE(11..17))
		MAX-ACCESS read-only
		STATUS	   current
		DESCRIPTION
		"The device LAN MAC address
		Device Allocation: AP, SM"
		::= { cambiumGeneralStatus 15 }

cambiumCurrentuImageIVersion OBJECT-TYPE
		SYNTAX	   DisplayString (SIZE(0..20))
		MAX-ACCESS read-only
		STATUS	   current
		DESCRIPTION
		"Version of firmware on uimagei partition
		Device Allocation: AP"
		::= { cambiumGeneralStatus 16 }
		
cambiumCurrentuImageVersion OBJECT-TYPE
		SYNTAX	   DisplayString (SIZE(0..20))
		MAX-ACCESS read-only
		STATUS	   current
		DESCRIPTION
		"Version of firmware on uimage partition
		Device Allocation: AP, SM"
		::= { cambiumGeneralStatus 17 }

cambiumDeviceLatitude OBJECT-TYPE
		SYNTAX	   DisplayString
		MAX-ACCESS read-only
		STATUS	   current
		DESCRIPTION
				"Current location information. GPS cordinates (latitude).
				Device Allocation: AP, SM"
		::= { cambiumGeneralStatus 18 }

cambiumDeviceLongitude OBJECT-TYPE
		SYNTAX	   DisplayString
		MAX-ACCESS read-only
		STATUS	   current
		DESCRIPTION
				"Current location information.GPS cordinates (longitude).
				Device Allocation: AP, SM"
		::= { cambiumGeneralStatus 19 }

sysRebootCounter OBJECT-TYPE
		SYNTAX	   Integer32
		MAX-ACCESS read-only
		STATUS	   current
		DESCRIPTION
				"Device Reboot Counter
				 Device Allocation: AP, SM"
		::= { cambiumGeneralStatus 20 }

cambiumDFSStatusStr	 OBJECT-TYPE
		SYNTAX	   DisplayString (SIZE(0..128))
		MAX-ACCESS read-only
		STATUS	   current
		DESCRIPTION
		"DFS Status (text)
		Device Allocation: AP, SM"
		::= { cambiumGeneralStatus 21 }

cambiumDriverType  OBJECT-TYPE
		SYNTAX	   Integer32 (1|2)
		MAX-ACCESS read-only
		STATUS	   current
		DESCRIPTION
		"SM current driver (TDD - 1, standard Wi-Fi - 2).
		Device Allocation: SM"
		::= { cambiumGeneralStatus 22 }

cambiumESN	OBJECT-TYPE
		SYNTAX	   DisplayString (SIZE(13))
		MAX-ACCESS read-only
		STATUS	   current
		DESCRIPTION
		"Device' serial number (ESN), based on MAC address
		Device Allocation: AP, SM"
		::= { cambiumGeneralStatus 30 }
		
cambiumEPMPMSN OBJECT-TYPE
		SYNTAX	   DisplayString (SIZE(13))
		MAX-ACCESS read-only
		STATUS	   current
		DESCRIPTION
		"CNS MSN serial number: AP, SM"
		::= { cambiumGeneralStatus 31 }

cambiumFactoryReset OBJECT-TYPE
		SYNTAX	   Integer32 (0|1)
		MAX-ACCESS read-only
		STATUS	   current
		DESCRIPTION
		"Factory Reset feature state.
		Default allocation: AP, SM"
		::= { cambiumGeneralStatus 32 }

cambiumSubModeType OBJECT-TYPE
		SYNTAX	   Integer32 (1|2|3|4|5)
		MAX-ACCESS read-only
		STATUS	   current
		DESCRIPTION
		"Protocol (Sub) Mode type:
			1 - TDD,
			2 - TDD PTP,
			3 - Standard WiFi,
			4 - ePTP Slave,
			5 - ePTP Master
			Device Allocation: AP, SM"
		::= { cambiumGeneralStatus 33 }

cambiumSTAConnectedRFFrequency OBJECT-TYPE
		SYNTAX	   Integer32 (2407..5970)
		MAX-ACCESS read-only
		STATUS	   current
		DESCRIPTION
		"The frequency connected to AP
		Device Allocation: SM"
		::= { cambiumRFStatus 1 }

cambiumSTAConnectedRFBandwidth OBJECT-TYPE
		SYNTAX	   Integer32 (1|2)
		MAX-ACCESS read-only 
		STATUS	   current
		DESCRIPTION
		"Connected RF Bandwidth: 
			1 for 20MHz, 
			2 for 40 MHz
		Device Allocation: SM"
		::= { cambiumRFStatus 2 }

cambiumSTADLRSSI OBJECT-TYPE
		SYNTAX	   Integer32
		MAX-ACCESS read-only
		STATUS	   current
		DESCRIPTION
		"SM RSSI in dBm
		Device Allocation: SM"
		::= { cambiumRFStatus 3 }

cambiumSTADLCINR OBJECT-TYPE
		SYNTAX	   Integer32
		MAX-ACCESS read-only
		STATUS	   obsolete
		DESCRIPTION
		"SM CINR in dBm
		Device Allocation: SM"
		::= { cambiumRFStatus 4 }

cambiumSTAConductedTXPower OBJECT-TYPE
		SYNTAX	   Integer32 (-25..30)
		MAX-ACCESS read-only
		STATUS	   current
		DESCRIPTION
		"Current TX Power (Board Output Conducted) in dBm
		Device Allocation: SM"
		::= { cambiumRFStatus 5 }

cambiumSTAUplinkMCSMode OBJECT-TYPE
		SYNTAX	   Integer32 (1..7|9..15)
		MAX-ACCESS read-only 
		STATUS	   current
		DESCRIPTION
		"UL MCS Mode: 
			1 for MCS1, 
			2 for MCS2, 
			3 for MCS3, 
			4 for MCS4, 
			5 for MCS5, 
			6 for MCS6, 
			7 for MCS7, 
			9 for MCS9, 
			10 for MCS10, 
			11 for MCS11, 
			12 for MCS12, 
			13 for MCS13, 
			14 for MCS14, 
			15 for MCS15
		Device Allocation: SM"
		::= { cambiumRFStatus 6 }

cambiumSTADownlinkMCSMode OBJECT-TYPE
		SYNTAX	   Integer32 (1..7|9..15)
		MAX-ACCESS read-only 
		STATUS	   current
		DESCRIPTION
		"DL MCS Mode: 
			1 for MCS1, 
			2 for MCS2, 
			3 for MCS3, 
			4 for MCS4, 
			5 for MCS5, 
			6 for MCS6, 
			7 for MCS7, 
			9 for MCS9, 
			10 for MCS10, 
			11 for MCS11, 
			12 for MCS12, 
			13 for MCS13, 
			14 for MCS14, 
			15 for MCS15
		Device Allocation: SM"
		::= { cambiumRFStatus 7 }

cambiumSTAConnectedAP OBJECT-TYPE
		SYNTAX	   DisplayString (SIZE(1..128))
		MAX-ACCESS read-only
		STATUS	   current
		DESCRIPTION
		"Connected AP Name (SSID), If no AP is connected, Scanning should be returned
		Device Allocation: SM"
		::= { cambiumRFStatus 8 }

cambiumSTAPowerControlMode OBJECT-TYPE
		SYNTAX	   Integer32 (-1|0|1|2)
		MAX-ACCESS read-only
		STATUS	   current
		DESCRIPTION
		"Power Control Mode on SM:
			-1 - No Value,
			0 - Disable, 
			1 - Open Loop, 
			2 - Close Loop
		Device Allocation: SM"
		::= { cambiumRFStatus 9 }

cambiumAPNumberOfConnectedSTA OBJECT-TYPE
		SYNTAX	   Integer32 (1..128)
		MAX-ACCESS read-only
		STATUS	   current
		DESCRIPTION
		"Number Of connected stations
		Device Allocation: AP"
		::= { cambiumRFStatus 10 }

cambiumAPConnectedSTAListTable OBJECT-TYPE
	SYNTAX	   SEQUENCE OF CambiumAPConnectedSTAListEntry
	MAX-ACCESS not-accessible
	STATUS	   obsolete
	DESCRIPTION
		"This table contains information relevant to the Connected Subscriber Modules:
			Subscriber Module MAC Address,
			Subscriber Module AID,
			Subscriber Module Channel,
			UL RSSI per SM,
			DL RSSI per SM,
			DL CINR per SM,
			UL CINR per SM,
			UL MCS Mode per SM,
			DL MCS Mode per SM,
			Subscriber Module IP Address
		Device Allocation: AP"
	::= { cambiumRFStatus 11 }

cambiumAPConnectedSTAListEntry OBJECT-TYPE
	SYNTAX	   CambiumAPConnectedSTAListEntry
	MAX-ACCESS not-accessible
	STATUS	   obsolete
	DESCRIPTION
		"Wireless parameters mapping for particular station.
		Device Allocation: AP"
	INDEX	{ cambiumAPNumberOfConnectedSTA }
	::= { cambiumAPConnectedSTAListTable 1 }

CambiumAPConnectedSTAListEntry ::= SEQUENCE {
		connectedSTAListMAC			   DisplayString,
		connectedSTAListAID			   Integer32,
		connectedSTAListChannel		   Integer32,
		connectedSTAListULRSSI		   Integer32,
		connectedSTAListDLRSSI		   Integer32,
		connectedSTAListULCINR		   Integer32,
		connectedSTAListDLCINR		   Integer32,
		connectedSTAListULMCS		   Integer32,
		connectedSTAListDLMCS		   Integer32,
		connectedSTAListIP			   IpAddress,
		connectedSTAListMirSrc		   DisplayString,
		connectedSTAListMirULRate	   DisplayString,
		connectedSTAListMirDLRate	   DisplayString
	}
									  
connectedSTAListMAC OBJECT-TYPE
	SYNTAX	   DisplayString (SIZE(0|11..17))
	MAX-ACCESS read-only
	STATUS	   obsolete
	DESCRIPTION
		"Connected SM WLAN MAC Address
		Device Allocation: AP"
	::= { cambiumAPConnectedSTAListEntry 1 }

connectedSTAListAID OBJECT-TYPE
	SYNTAX	   Integer32
	MAX-ACCESS read-only
	STATUS	   obsolete
	DESCRIPTION
		"Association ID
		Device Allocation: AP"
	::= { cambiumAPConnectedSTAListEntry 2 }

connectedSTAListChannel OBJECT-TYPE
	SYNTAX	   Integer32
	MAX-ACCESS read-only
	STATUS	   obsolete
	DESCRIPTION
		"Connected SM Channel
		Device Allocation: AP"
	::= { cambiumAPConnectedSTAListEntry 3 }

connectedSTAListULRSSI OBJECT-TYPE
	SYNTAX	   Integer32
	MAX-ACCESS read-only
	STATUS	   obsolete
	DESCRIPTION
		"UL RSSI per SM
		Device Allocation: AP"
	::= { cambiumAPConnectedSTAListEntry 4 }

connectedSTAListDLRSSI OBJECT-TYPE
	SYNTAX	   Integer32
	MAX-ACCESS read-only
	STATUS	   obsolete
	DESCRIPTION
		"DL RSSI per SM
		Device Allocation: AP"
	::= { cambiumAPConnectedSTAListEntry 5 }

connectedSTAListULCINR OBJECT-TYPE
	SYNTAX	   Integer32
	MAX-ACCESS read-only
	STATUS	   obsolete
	DESCRIPTION
		"UL CINR per SM
		Device Allocation: AP"
	::= { cambiumAPConnectedSTAListEntry 6 }

connectedSTAListDLCINR OBJECT-TYPE
	SYNTAX	   Integer32
	MAX-ACCESS read-only
	STATUS	   obsolete
	DESCRIPTION
		"DL CINR per SM
		Device Allocation: AP"
	::= { cambiumAPConnectedSTAListEntry 7 }

connectedSTAListULMCS OBJECT-TYPE
	SYNTAX	   Integer32 (1..15)
	MAX-ACCESS read-only
	STATUS	   obsolete
	DESCRIPTION
		"UL MCS Mode per SM:
			1 for MCS1, 
			2 for MCS2, 
			3 for MCS3, 
			4 for MCS4, 
			5 for MCS5, 
			6 for MCS6, 
			7 for MCS7, 
			9 for MCS9, 
			10 for MCS10, 
			11 for MCS11, 
			12 for MCS12, 
			13 for MCS13, 
			14 for MCS14, 
			15 for MCS15
		Device Allocation: AP"
	::= { cambiumAPConnectedSTAListEntry 8 }

connectedSTAListDLMCS OBJECT-TYPE
	SYNTAX	   Integer32 (1..15)
	MAX-ACCESS read-only
	STATUS	   obsolete
	DESCRIPTION
		"DL MCS Mode per SM:
			1 for MCS1, 
			2 for MCS2, 
			3 for MCS3, 
			4 for MCS4, 
			5 for MCS5, 
			6 for MCS6, 
			7 for MCS7, 
			9 for MCS9, 
			10 for MCS10, 
			11 for MCS11, 
			12 for MCS12, 
			13 for MCS13, 
			14 for MCS14, 
			15 for MCS15
		Device Allocation: AP"
	::= { cambiumAPConnectedSTAListEntry 9 }

connectedSTAListIP OBJECT-TYPE
	SYNTAX	   IpAddress
	MAX-ACCESS read-only
	STATUS	   obsolete
	DESCRIPTION
		"Connected SM WLAN IP Address
		Device Allocation: AP"
	::= { cambiumAPConnectedSTAListEntry 10 }

connectedSTAListMirSrc OBJECT-TYPE
	SYNTAX	   DisplayString
	MAX-ACCESS read-only
	STATUS	   obsolete
	DESCRIPTION
		"Connected SM MIR source: RADIUS server or profile ID
		Device Allocation: AP"
	::= { cambiumAPConnectedSTAListEntry 12 }

connectedSTAListMirULRate OBJECT-TYPE
	SYNTAX	   DisplayString
	MAX-ACCESS read-only
	STATUS	   obsolete
	DESCRIPTION
		"Connected SM MIR UL Rate
		Device Allocation: AP"
	::= { cambiumAPConnectedSTAListEntry 13 }

connectedSTAListMirDLRate OBJECT-TYPE
	SYNTAX	   DisplayString
	MAX-ACCESS read-only
	STATUS	   obsolete
	DESCRIPTION
		"Connected SM MIR DL Rate
		Device Allocation: AP"
	::= { cambiumAPConnectedSTAListEntry 14 }

cambiumSTADistanceKm OBJECT-TYPE
		SYNTAX	   DisplayString
		MAX-ACCESS read-only
		STATUS	   current
		DESCRIPTION
		"The distance between AP and SM in kilometers
		Device Allocation: SM"
		::= { cambiumRFStatus 12 } 

cambiumSTADistanceMil OBJECT-TYPE
		SYNTAX	   DisplayString
		MAX-ACCESS read-only
		STATUS	   current
		DESCRIPTION
		"The distance between AP and SM in miles
		Device Allocation: SM"
		::= { cambiumRFStatus 13 }	 

cambiumPropagationDelay OBJECT-TYPE
		SYNTAX	   Integer32 (-2000..5000000)
		MAX-ACCESS read-only
		STATUS	   current
		DESCRIPTION
		"SM use the calculated propagation delay to adjust the UL starting time
		Device Allocation: SM"
		::= { cambiumRFStatus 14 }	 

cambiumSTAConnectedAPListTable OBJECT-TYPE
	SYNTAX	   SEQUENCE OF CambiumSTAConnectedAPListEntry
	MAX-ACCESS not-accessible
	STATUS	   obsolete
	DESCRIPTION
		"This table contains information relevant to the Connected Subscriber Modules:
			SSID - AP Name (SSID)
			BSSID - AP MAC Address
			Channel - Operating channgel number
			Frequency - AP Operating frequency
			Bandwitdth - AP Operating Bandwidth
			Rate - AP Operating Rate
			CINR - AP Signal to Noise Ratio
			RSSI - AP Received Signal Strength Indication
			Noise - AP Noise level
			INT - Beacon Interval
			NE_ST - Last Network Entry State
			NE_AGE - Time from last Network Entry event
			SCAN_AGE - Time from last AP scanning
			Remaining_SM  - Capacity on AP from beacon
			CAPS - IEEE80211 capability flags
			MeetNEAttemptCriteria - status for eachAP after scanning
		Device Allocation: SM"
	::= { cambiumRFStatus 15 }

cambiumSTAConnectedAPListEntry OBJECT-TYPE
	SYNTAX	   CambiumSTAConnectedAPListEntry
	MAX-ACCESS not-accessible
	STATUS	   obsolete
	DESCRIPTION
		"Wireless parameters mapping for particular station.
		Device Allocation: SM"
	INDEX	{ connectedAPListSSID }
	::= { cambiumSTAConnectedAPListTable 1 }

CambiumSTAConnectedAPListEntry ::= SEQUENCE {
		connectedAPListSSID		 DisplayString,
		connectedAPListBSSID	 DisplayString,
		connectedAPListChannel	 Integer32,
		connectedAPListFrequency Integer32,
		connectedAPListBandwidth DisplayString,
		connectedAPListRate		 DisplayString,
		connectedAPListCINR		 Integer32,
		connectedAPListRSSI		 Integer32,
		connectedAPListNoise	 Integer32,
		connectedAPListINT		 Integer32,
		connectedAPListNEState	 Integer32,
		connectedAPListNEAge	 DisplayString,
		connectedAPListScanAge	DisplayString,		
		connectedAPListRemainingSTA	 Integer32,
		connectedAPListCAPS		 DisplayString,
		connectedAPAuthMethod	   DisplayString,
		connectedAPListMeetNEAttemptCriteria DisplayString
	}

connectedAPListSSID OBJECT-TYPE
	SYNTAX	   DisplayString
	MAX-ACCESS read-only
	STATUS	   obsolete
	DESCRIPTION
		"AP Name (SSID)
		Device Allocation: SM"
	::= { cambiumSTAConnectedAPListEntry 1 }

connectedAPListBSSID OBJECT-TYPE
	SYNTAX	   DisplayString
	MAX-ACCESS read-only
	STATUS	   obsolete
	DESCRIPTION
		"AP MAC Address
		Device Allocation: SM"
	::= { cambiumSTAConnectedAPListEntry 2 }

connectedAPListChannel OBJECT-TYPE
	SYNTAX	   Integer32
	MAX-ACCESS read-only
	STATUS	   obsolete
	DESCRIPTION
		"Operating channgel number
		Device Allocation: SM"
	::= { cambiumSTAConnectedAPListEntry 3 }

connectedAPListFrequency OBJECT-TYPE
	SYNTAX	   Integer32
	MAX-ACCESS read-only
	STATUS	   obsolete
	DESCRIPTION
		"AP Operating frequency
		Device Allocation: SM"
	::= { cambiumSTAConnectedAPListEntry 4 }

connectedAPListBandwidth OBJECT-TYPE
	SYNTAX	   DisplayString
	MAX-ACCESS read-only
	STATUS	   obsolete
	DESCRIPTION
		"AP Operating Bandwidth
		Device Allocation: SM"
	::= { cambiumSTAConnectedAPListEntry 5 }

connectedAPListRate OBJECT-TYPE
	SYNTAX	   DisplayString
	MAX-ACCESS read-only
	STATUS	   obsolete
	DESCRIPTION
		"AP Operating Rate
		Device Allocation: SM"
	::= { cambiumSTAConnectedAPListEntry 6 }

connectedAPListCINR OBJECT-TYPE
	SYNTAX	   Integer32
	MAX-ACCESS read-only
	STATUS	   obsolete
	DESCRIPTION
		"AP	 Carrier to Interference Noise Ratio
		Device Allocation: SM"
	::= { cambiumSTAConnectedAPListEntry 7 }

connectedAPListRSSI	 OBJECT-TYPE
	SYNTAX	   Integer32
	MAX-ACCESS read-only
	STATUS	   obsolete
	DESCRIPTION
		"AP Received Signal Strength Indication
		Device Allocation: SM"
	::= { cambiumSTAConnectedAPListEntry 8 }

connectedAPListNoise  OBJECT-TYPE
	SYNTAX	   Integer32
	MAX-ACCESS read-only
	STATUS	   obsolete
	DESCRIPTION
		"AP Noise level
		Device Allocation: SM"
	::= { cambiumSTAConnectedAPListEntry 9 }

connectedAPListINT	OBJECT-TYPE
	SYNTAX	   Integer32
	MAX-ACCESS read-only
	STATUS	   obsolete
	DESCRIPTION
		"Beacon Interval
		Device Allocation: SM"
	::= { cambiumSTAConnectedAPListEntry 10 }

connectedAPListNEState	OBJECT-TYPE
	SYNTAX	   Integer32
	MAX-ACCESS read-only
	STATUS	   obsolete
	DESCRIPTION
		"Last Network Entry State
		Device Allocation: SM"
	::= { cambiumSTAConnectedAPListEntry 11 }

connectedAPListNEAge OBJECT-TYPE
	SYNTAX	   DisplayString
	MAX-ACCESS read-only
	STATUS	   obsolete
	DESCRIPTION
		"Time from last Network Entry event
		Device Allocation: SM"
	::= { cambiumSTAConnectedAPListEntry 12 }

connectedAPListScanAge OBJECT-TYPE
	SYNTAX	   DisplayString
	MAX-ACCESS read-only
	STATUS	   obsolete
	DESCRIPTION
		"Time from last AP scanning
		Device Allocation: SM"
	::= { cambiumSTAConnectedAPListEntry 13 }

connectedAPListRemainingSTA	 OBJECT-TYPE
	SYNTAX	   Integer32
	MAX-ACCESS read-only
	STATUS	   obsolete
	DESCRIPTION
		"Remaining SM on AP
		Device Allocation: SM"
	::= { cambiumSTAConnectedAPListEntry 14 }

connectedAPListCAPS OBJECT-TYPE
	SYNTAX	   DisplayString
	MAX-ACCESS read-only
	STATUS	   obsolete
	DESCRIPTION
		"IEEE80211 capability flags
		Device Allocation: SM"
	::= { cambiumSTAConnectedAPListEntry 15 }	
	
connectedAPAuthMethod OBJECT-TYPE
	SYNTAX	   DisplayString
	MAX-ACCESS read-only
	STATUS	   obsolete
	DESCRIPTION
		   "Authentication Method
		   Device Allocation: SM"
	::= { cambiumSTAConnectedAPListEntry 16 }

connectedAPListMeetNEAttemptCriteria OBJECT-TYPE
	SYNTAX	   DisplayString
	MAX-ACCESS read-only
	STATUS	   obsolete
	DESCRIPTION
		   "Status meet NE attempt criteria
		   Device Allocation: SM"
	::= { cambiumSTAConnectedAPListEntry 17 } 

wirelessInterfaceConnectionState OBJECT-TYPE
	SYNTAX Integer32 (1|2|3)
	MAX-ACCESS read-only
	STATUS	   current
	DESCRIPTION
		"Connection State:
			1 - Scanning,
			2 - Connecting,
			3 - Connected
		Device Allocation: SM"
	::= { cambiumRFStatus 16 }

cambiumSTAPriority OBJECT-TYPE
		SYNTAX	   Integer32 (0|1|2)
		MAX-ACCESS read-only
		STATUS	   current
		DESCRIPTION
		"SM priority value:
			0 - Normal,
			1 - High,
			2 - Low
		Device Allocation: SM"
		::= { cambiumRFStatus 17 }

cambiumSTADLSNR OBJECT-TYPE
		SYNTAX	   Integer32
		MAX-ACCESS read-only
		STATUS	   current
		DESCRIPTION
		"SM SNR in dBm
		Device Allocation: SM"
		::= { cambiumRFStatus 18 }

cambiumConnectedAPMACAddress OBJECT-TYPE
		SYNTAX	   DisplayString (SIZE(0|11..17))
		MAX-ACCESS read-only
		STATUS	   current
		DESCRIPTION
		"Connected AP MAC Address
		Device Allocation: SM"
		::= { cambiumRFStatus 19 }

cambiumSTAConnectedAPTable OBJECT-TYPE
	SYNTAX	   SEQUENCE OF CambiumSTAConnectedAPEntry
	MAX-ACCESS not-accessible
	STATUS	   current
	DESCRIPTION
		"This table contains information relevant to the Connected Subscriber Modules:
			SSID - AP Name (SSID)
			BSSID - AP MAC Address
			Channel - Operating channgel number
			Frequency - AP Operating frequency
			Bandwitdth - AP Operating Bandwidth
			Rate - AP Operating Rate
			SNR - AP Signal to Noise Ratio
			RSSI - AP Received Signal Strength Indication
			Noise - AP Noise level
			INT - Beacon Interval
			NE_ST - Last Network Entry State
			NE_AGE - Time from last Network Entry event
			SCAN_AGE - Time from last AP scanning
			Remaining_SM  - Capacity on AP from beacon
			CAPS - IEEE80211 capability flags
			MeetNEAttemptCriteria - status for eachAP after scanning
		Device Allocation: SM"
	::= { cambiumRFStatus 20 }

cambiumSTAConnectedAPEntry OBJECT-TYPE
	SYNTAX	   CambiumSTAConnectedAPEntry
	MAX-ACCESS not-accessible
	STATUS	   current
	DESCRIPTION
		"Wireless parameters mapping for particular station.
		Device Allocation: SM"
	INDEX	{ connectedAPListSSID }
	::= { cambiumSTAConnectedAPTable 1 }

CambiumSTAConnectedAPEntry ::= SEQUENCE {
		connectedAPSSID		 DisplayString,
		connectedAPBSSID	 DisplayString,
		connectedAPChannel	 Integer32,
		connectedAPFrequency Integer32,
		connectedAPBandwidth DisplayString,
		connectedAPRate		 DisplayString,
		connectedAPSNR		 Integer32,
		connectedAPRSSI		 Integer32,
		connectedAPNoise	 Integer32,
		connectedAPINT		 Integer32,
		connectedAPNEState	 Integer32,
		connectedAPNEAge	 DisplayString,
		connectedAPScanAge	 DisplayString,		 
		connectedAPRemainingSTA	 Integer32,
		connectedAPCAPS		 DisplayString,
		connectedAPAuthenticationMethod		 DisplayString,
		connectedAPMeetNEAttemptCriteria DisplayString
	}

connectedAPSSID OBJECT-TYPE
	SYNTAX	   DisplayString
	MAX-ACCESS read-only
	STATUS	   current
	DESCRIPTION
		"AP Name (SSID)
		Device Allocation: SM"
	::= { cambiumSTAConnectedAPEntry 1 }

connectedAPBSSID OBJECT-TYPE
	SYNTAX	   DisplayString
	MAX-ACCESS read-only
	STATUS	   current
	DESCRIPTION
		"AP MAC Address
		Device Allocation: SM"
	::= { cambiumSTAConnectedAPEntry 2 }

connectedAPChannel OBJECT-TYPE
	SYNTAX	   Integer32
	MAX-ACCESS read-only
	STATUS	   current
	DESCRIPTION
		"Operating channgel number
		Device Allocation: SM"
	::= { cambiumSTAConnectedAPEntry 3 }

connectedAPFrequency OBJECT-TYPE
	SYNTAX	   Integer32
	MAX-ACCESS read-only
	STATUS	   current
	DESCRIPTION
		"AP Operating frequency
		Device Allocation: SM"
	::= { cambiumSTAConnectedAPEntry 4 }

connectedAPBandwidth OBJECT-TYPE
	SYNTAX	   DisplayString
	MAX-ACCESS read-only
	STATUS	   current
	DESCRIPTION
		"AP Operating Bandwidth
		Device Allocation: SM"
	::= { cambiumSTAConnectedAPEntry 5 }

connectedAPRate OBJECT-TYPE
	SYNTAX	   DisplayString
	MAX-ACCESS read-only
	STATUS	   current
	DESCRIPTION
		"AP Operating Rate
		Device Allocation: SM"
	::= { cambiumSTAConnectedAPEntry 6 }

connectedAPSNR OBJECT-TYPE
	SYNTAX	   Integer32
	MAX-ACCESS read-only
	STATUS	   current
	DESCRIPTION
		"AP Signal to Noise Ratio
		Device Allocation: SM"
	::= { cambiumSTAConnectedAPEntry 7 }

connectedAPRSSI	 OBJECT-TYPE
	SYNTAX	   Integer32
	MAX-ACCESS read-only
	STATUS	   current
	DESCRIPTION
		"AP Received Signal Strength Indication
		Device Allocation: SM"
	::= { cambiumSTAConnectedAPEntry 8 }

connectedAPNoise  OBJECT-TYPE
	SYNTAX	   Integer32
	MAX-ACCESS read-only
	STATUS	   current
	DESCRIPTION
		"AP Noise level
		Device Allocation: SM"
	::= { cambiumSTAConnectedAPEntry 9 }

connectedAPINT	OBJECT-TYPE
	SYNTAX	   Integer32
	MAX-ACCESS read-only
	STATUS	   current
	DESCRIPTION
		"Beacon Interval
		Device Allocation: SM"
	::= { cambiumSTAConnectedAPEntry 10 }

connectedAPNEState	OBJECT-TYPE
	SYNTAX	   Integer32
	MAX-ACCESS read-only
	STATUS	   current
	DESCRIPTION
		"Last Network Entry State
		Device Allocation: SM"
	::= { cambiumSTAConnectedAPEntry 11 }

connectedAPNEAge OBJECT-TYPE
	SYNTAX	   DisplayString
	MAX-ACCESS read-only
	STATUS	   current
	DESCRIPTION
		"Time from last Network Entry event
		Device Allocation: SM"
	::= { cambiumSTAConnectedAPEntry 12 }

connectedAPScanAge OBJECT-TYPE
	SYNTAX	   DisplayString
	MAX-ACCESS read-only
	STATUS	   current
	DESCRIPTION
		"Time from last AP scanning
		Device Allocation: SM"
	::= { cambiumSTAConnectedAPEntry 13 }

connectedAPRemainingSTA	 OBJECT-TYPE
	SYNTAX	   Integer32
	MAX-ACCESS read-only
	STATUS	   current
	DESCRIPTION
		"Remaining SM on AP
		Device Allocation: SM"
	::= { cambiumSTAConnectedAPEntry 14 }

connectedAPCAPS OBJECT-TYPE
	SYNTAX	   DisplayString
	MAX-ACCESS read-only
	STATUS	   current
	DESCRIPTION
		"IEEE80211 capability flags
		Device Allocation: SM"
	::= { cambiumSTAConnectedAPEntry 15 }	
	
connectedAPAuthenticationMethod OBJECT-TYPE
	SYNTAX	   DisplayString
	MAX-ACCESS read-only
	STATUS	   current
	DESCRIPTION
		   "Authentication Method
		   Device Allocation: SM"
	::= { cambiumSTAConnectedAPEntry 16 }

connectedAPMeetNEAttemptCriteria OBJECT-TYPE
	SYNTAX	   DisplayString
	MAX-ACCESS read-only
	STATUS	   current
	DESCRIPTION
		   "Status meet NE attempt criteria
		   Device Allocation: SM"
	::= { cambiumSTAConnectedAPEntry 17 }

staTxCapacity OBJECT-TYPE
	SYNTAX	   Integer32 (0..100)
	MAX-ACCESS read-only
	STATUS	   current
	DESCRIPTION
			"TX Capacity for SM
			 Device Allocation: SM"
	::= { cambiumRFStatus 21 }

staTxQuality OBJECT-TYPE
	SYNTAX	   Integer32 (0..100)
	MAX-ACCESS read-only
	STATUS	   current
	DESCRIPTION
			"TX Quality for SM
			 Device Allocation: SM"
	::= { cambiumRFStatus 22 }

acsState OBJECT-TYPE
	SYNTAX	   Integer32 (0..3)
	MAX-ACCESS read-only
	STATUS	   current
	DESCRIPTION
		"Indicates the state of the Automatic Channel Selection (ACS) feature:
		 0 - Disabled,
		 1 - Enabled,
		 2 - Running,
		 3 - Aborting
		Device Allocation: AP"
	::= { cambiumAcsStatus 1 }

cambiumEffectiveMcastGroupLimit OBJECT-TYPE
	SYNTAX	   Integer32 (0..10)
	MAX-ACCESS read-only
	STATUS	   current
	DESCRIPTION
		"Disaplays the Effective Multicast Group Limit number:
		 0 - 10 Groups
		Device Allocation: SM"
	::= { cambiumMcastStatus 1 }

cambiumSubscribedMcastGroupNum OBJECT-TYPE
	SYNTAX	   Integer32 (0..5)
	MAX-ACCESS read-only
	STATUS	   current
	DESCRIPTION
		"Disaplays the number of subscribed Multicast Groups:
		 0 - 5 Groups
		Device Allocation: SM"
	::= { cambiumMcastStatus 2 }

cambiumAPMcastTotalGroupCount OBJECT-TYPE
	SYNTAX	   Integer32 (0..512)
	MAX-ACCESS read-only
	STATUS	   current
	DESCRIPTION
		"Disaplays the count of subscribed Multicast Groups:
		 0 - 512 Groups
		Device Allocation: AP"
	::= { cambiumMcastStatus 3 }

cambiumMcastHandlingStatus OBJECT-TYPE
	SYNTAX	   Integer32 (0|3)
	MAX-ACCESS read-only
	STATUS	   current
	DESCRIPTION
		"Disaplays the status of the Multicast features:
			0 - Fixed MCS
			3 - Multicast to Unicast
		Device Allocation: AP"
	::= { cambiumMcastStatus 4 }

cambiumSubscribedMcastGroupTable OBJECT-TYPE
	SYNTAX	   SEQUENCE OF CambiumSubscribedMcastGroupEntry
	MAX-ACCESS not-accessible
	STATUS	   current
	DESCRIPTION
		"This table contains Registered Multicast Group information:
			Multicast Group IP
		Device Allocation: SM"
	::= { cambiumMcastStatus 10 }

cambiumSubscribedMcastGroupEntry OBJECT-TYPE
	SYNTAX	   CambiumSubscribedMcastGroupEntry
	MAX-ACCESS not-accessible
	STATUS	   current
	DESCRIPTION 
				"Multicast group information for particular subscription
				Device Allocation: SM"
	INDEX	{ cambiumSubscribedMcastGroupNum }
	::= { cambiumSubscribedMcastGroupTable 1 }

CambiumSubscribedMcastGroupEntry ::= SEQUENCE {
		cambiumRegisteredMcastGroupIP			 IpAddress
	}

cambiumRegisteredMcastGroupIP OBJECT-TYPE
		SYNTAX	   IpAddress
		MAX-ACCESS read-only
		STATUS	   current
		DESCRIPTION
				"Registered Multicast Group IP
				Device Allocation: SM"
		::= { cambiumSubscribedMcastGroupEntry 1 }

dhcpServerStartIP  OBJECT-TYPE
	SYNTAX	   IpAddress
	MAX-ACCESS read-write
	STATUS	   current
	DESCRIPTION
		"Dhcp server start address
		Device Allocation: STA"
	::= { cambiumDhcpStatus 1 }

dhcpServerEndIP	 OBJECT-TYPE
	SYNTAX	   IpAddress
	MAX-ACCESS read-write
	STATUS	   current
	DESCRIPTION
		"Dhcp server end address
		Device Allocation: STA"
	::= { cambiumDhcpStatus 2 }

dhcpServerGatewayIP	 OBJECT-TYPE
	SYNTAX	   IpAddress
	MAX-ACCESS read-write
	STATUS	   current
	DESCRIPTION
		"DHCP Gateway IP Address
		Device Allocation: STA"
	::= { cambiumDhcpStatus 3 }

dhcpServerDNSIP	 OBJECT-TYPE
	SYNTAX	   IpAddress
	MAX-ACCESS read-write
	STATUS	   current
	DESCRIPTION
		"DHCP server DNS IP Address
		Device Allocation: STA"
	::= { cambiumDhcpStatus 4 }

dhcpServerStaticHostTable  OBJECT-TYPE
	SYNTAX SEQUENCE OF DhcpServerStaticHostEntry
	MAX-ACCESS not-accessible
	STATUS	   current
	DESCRIPTION
		"Table for DHCP static MAC to IP"
	::= { cambiumDhcpStatus 5 }

cambLicenseVersion OBJECT-TYPE
		SYNTAX	   DisplayString (SIZE(0|1))
		MAX-ACCESS read-only
		STATUS	   current
		DESCRIPTION
		"Device Operational Lincense Version
		Device Allocation: AP, SM"
		::= { cambiumLicenseInfo 1 }

cambLicenseSMcntUnlock OBJECT-TYPE
		SYNTAX	   DisplayString (SIZE(0|1))
		MAX-ACCESS read-only
		STATUS	   current
		DESCRIPTION
		"Full Capacity AP feature unlock, based on information from
		 Operational Lincense
		Device Allocation: AP, SM"
		::= { cambiumLicenseInfo 2 }

cambLicenseMACaddr OBJECT-TYPE
		SYNTAX	   DisplayString (SIZE(0|17))
		MAX-ACCESS read-only
		STATUS	   current
		DESCRIPTION
		"Device Operational Lincense MAC address
		Device Allocation: AP, SM"
		::= { cambiumLicenseInfo 3 }

cambLicenseCountry OBJECT-TYPE
		SYNTAX	   DisplayString (SIZE(0|1..2))
		MAX-ACCESS read-only
		STATUS	   current
		DESCRIPTION
		"Country Code for ETSI locked device, based on information from
		 Operational Lincense
		Device Allocation: AP, SM"
		::= { cambiumLicenseInfo 4 }

cambLicenseStatus OBJECT-TYPE
		SYNTAX	   Integer32 (0..4)
		MAX-ACCESS read-only
		STATUS	   current
		DESCRIPTION
		"Device Operational Lincense Status:
		 0 - Unknown
		 1 - License Valid
		 2 - Validation procedure was not provided
		 3 - Validation Fail
		 4 - License not valid for current device
		Device Allocation: AP, SM"
		::= { cambiumLicenseInfo 5 }

dhcpServerStaticHostEntry OBJECT-TYPE
	SYNTAX	   DhcpServerStaticHostEntry
	MAX-ACCESS not-accessible
	STATUS	   current
	DESCRIPTION
		"DHCP Hosts Table Entry
		Device Allocation: STA"
	INDEX	{ dhcpStaticIndex }
	::= { dhcpServerStaticHostTable 1 }

DhcpServerStaticHostEntry ::= SEQUENCE {
	dhcpStaticIndex
		Integer32,
	dhcpStaticMAC
		DisplayString,
	dhcpStaticIP
		IpAddress
}

dhcpStaticIndex	 OBJECT-TYPE
	SYNTAX	   Integer32 (0..65535)
	MAX-ACCESS read-only
	STATUS	   current
	DESCRIPTION
		"DHCP Static Table Index"
	::= { dhcpServerStaticHostEntry 1 }

dhcpStaticMAC  OBJECT-TYPE
	SYNTAX	   DisplayString (SIZE(0|17))
	MAX-ACCESS read-only
	STATUS	   current
	DESCRIPTION
		"DHCP Static MAC"
	::= { dhcpServerStaticHostEntry 2 }

dhcpStaticIP  OBJECT-TYPE
	SYNTAX	   IpAddress
	MAX-ACCESS read-only
	STATUS	   current
	DESCRIPTION
		"DHCP Static IP"
	::= { dhcpServerStaticHostEntry 3 }

dhcpServerLeaseTable  OBJECT-TYPE
		SYNTAX SEQUENCE OF DhcpServerLeaseEntry
		MAX-ACCESS not-accessible
		STATUS	   current
		DESCRIPTION
				"DHCP Assigned IP Address Table"
		::= { cambiumDhcpStatus 6 }

networkRadiusVSAmgmtVLANVID  OBJECT-TYPE
	SYNTAX	   Integer32 (0|1..4095)
	MAX-ACCESS read-only
	STATUS	   current
	DESCRIPTION
		"VSA Management VLAN ID"
	::= { cambiumRadiusVSAStatus 1 }

networkRadiusVSAmgmtVLANVP  OBJECT-TYPE
	SYNTAX	   Integer32 (0|1..7)
	MAX-ACCESS read-only
	STATUS	   current
	DESCRIPTION
		"VSA Management VLAN VP"
	::= { cambiumRadiusVSAStatus 2 }

networkRadiusVSAdataVLANVID  OBJECT-TYPE
	SYNTAX	   Integer32 (0|1..4095)
	MAX-ACCESS read-only
	STATUS	   current
	DESCRIPTION
		"VSA Data VLAN ID"
	::= { cambiumRadiusVSAStatus 3 }

networkRadiusVSAdataVLANVP  OBJECT-TYPE
	SYNTAX	   Integer32 (0|1..7)
	MAX-ACCESS read-only
	STATUS	   current
	DESCRIPTION
		"VSA Data VLAN VP"
	::= { cambiumRadiusVSAStatus 4 }

networkRadiusVSAmgmtIFVID  OBJECT-TYPE
	SYNTAX	   Integer32 (0|1..4095)
	MAX-ACCESS read-only
	STATUS	   current
	DESCRIPTION
		"VSA Separate Management Interface VLAN ID"
	::= { cambiumRadiusVSAStatus 5 }

networkRadiusVSAmgmtIFVP  OBJECT-TYPE
	SYNTAX	   Integer32 (0|1..7)
	MAX-ACCESS read-only
	STATUS	   current
	DESCRIPTION
		"VSA Separate Management Interface VLAN VP"
	::= { cambiumRadiusVSAStatus 6 }

networkRadiusVSAmcastVLANVID  OBJECT-TYPE
	SYNTAX	   Integer32 (0|1..4095)
	MAX-ACCESS read-only
	STATUS	   current
	DESCRIPTION
		"VSA Multicast VLAN ID"
	::= { cambiumRadiusVSAStatus 7 }

networkRadiusVSAmembershipVLANTable OBJECT-TYPE
	SYNTAX SEQUENCE OF NetworkRadiusVSAmembershipVLANEntry
	MAX-ACCESS not-accessible
	STATUS     current
	DESCRIPTION
		"VSA Membership VLAN Table"
	INDEX   { networkRadiusVSAmembershipVLANIndex }
        ::= { cambiumRadiusVSAStatus 10 }

networkRadiusVSAmembershipVLANEntry OBJECT-TYPE
	SYNTAX	   NetworkRadiusVSAmembershipVLANEntry
	MAX-ACCESS not-accessible
	STATUS	   current
	DESCRIPTION
		"VSA Membership VLAN Table Rule Entry"
	INDEX	{ networkRadiusVSAmembershipVLANIndex }
	::= { networkRadiusVSAmembershipVLANTable 1 }

NetworkRadiusVSAmembershipVLANEntry ::= SEQUENCE {
	networkRadiusVSAmembershipVLANIndex
		Integer32,
	networkRadiusVSAmembershipVLANVIDBegin
		Integer32,
	networkRadiusVSAmembershipVLANVIDEnd
		Integer32
}

networkRadiusVSAmembershipVLANIndex  OBJECT-TYPE
	SYNTAX	  Integer32 (0..16)
	MAX-ACCESS read-only
	STATUS	   current
	DESCRIPTION
		"VSA Membership VLAN Table Entry Index"
		::= { networkRadiusVSAmembershipVLANEntry 1 }

networkRadiusVSAmembershipVLANVIDBegin  OBJECT-TYPE
	SYNTAX	   Integer32 (0|1..4095)
	MAX-ACCESS read-only
	STATUS	   current
	DESCRIPTION
		"VSA Membership VLAN Table Entry VLAN ID Begin"
	::= { networkRadiusVSAmembershipVLANEntry 2 }

networkRadiusVSAmembershipVLANVIDEnd  OBJECT-TYPE
	SYNTAX	   Integer32 (0|1..4095)
	MAX-ACCESS read-only
	STATUS	   current
	DESCRIPTION
		"VSA Membership VLAN Table Entry VLAN ID End"
	::= { networkRadiusVSAmembershipVLANEntry 3 }

networkRadiusVSAmappingVLANTable OBJECT-TYPE
	SYNTAX SEQUENCE OF NetworkRadiusVSAmappingVLANEntry
	MAX-ACCESS not-accessible
	STATUS     current
	DESCRIPTION
		"VSA Mapping VLAN Table Rule Entry"
	INDEX   { networkRadiusVSAmappingVLANIndex }
	::= { cambiumRadiusVSAStatus 20 }

networkRadiusVSAmappingVLANEntry  OBJECT-TYPE
	SYNTAX	   NetworkRadiusVSAmappingVLANEntry
	MAX-ACCESS not-accessible
	STATUS	   current
	DESCRIPTION
		"VSA Mapping VLAN Table Rule Entry"
	INDEX	{ networkRadiusVSAmappingVLANIndex }
	::= { networkRadiusVSAmappingVLANTable 1 }

NetworkRadiusVSAmappingVLANEntry ::= SEQUENCE {
	networkRadiusVSAmappingVLANIndex
		Integer32,
	networkRadiusVSAmappingVLANCVLAN
		Integer32,
	networkRadiusVSAmappingVLANSVLAN
		Integer32
}

networkRadiusVSAmappingVLANIndex  OBJECT-TYPE
	SYNTAX	  Integer32 (0..16)
	MAX-ACCESS read-only
	STATUS	   current
	DESCRIPTION
		"VSA Mapping VLAN Table Entry Index"
		::= { networkRadiusVSAmappingVLANEntry 1 }

networkRadiusVSAmappingVLANCVLAN  OBJECT-TYPE
	SYNTAX	   Integer32 (0|1..4095)
	MAX-ACCESS read-only
	STATUS	   current
	DESCRIPTION
		"VSA Mapping VLAN Table C-VLAN ID"
	::= { networkRadiusVSAmappingVLANEntry 2 }

networkRadiusVSAmappingVLANSVLAN  OBJECT-TYPE
	SYNTAX	   Integer32 (0|1..4095)
	MAX-ACCESS read-only
	STATUS	   current
	DESCRIPTION
		"VSA Mapping VLAN Table S-VLAN ID"
	::= { networkRadiusVSAmappingVLANEntry 3 }

dhcpServerLeaseEntry OBJECT-TYPE
	SYNTAX	   DhcpServerLeaseEntry
	MAX-ACCESS not-accessible
	STATUS	   current
	DESCRIPTION
		"DHCP Assigned IP Address Entry
		Device Allocation: STA"
	INDEX	{ dhcpLeaseIndex }
	::= { dhcpServerLeaseTable 1 }

DhcpServerLeaseEntry ::= SEQUENCE {
	dhcpLeaseIndex
		Integer32,
	dhcpLeaseMAC
		DisplayString,
	dhcpLeaseIP
		IpAddress,
	dhcpLeaseDevName
		DisplayString
}

dhcpLeaseIndex	OBJECT-TYPE
	SYNTAX	   Integer32 (0..65535)
	MAX-ACCESS read-only
	STATUS	   current
	DESCRIPTION
		"DHCP lease table index"
	::= { dhcpServerLeaseEntry 1 }

dhcpLeaseMAC  OBJECT-TYPE
	SYNTAX	   DisplayString (SIZE(0|17))
	MAX-ACCESS read-only
	STATUS	   current
	DESCRIPTION
		"DHCP Assigned MAC Address"
	::= { dhcpServerLeaseEntry 2 }

dhcpLeaseIP	 OBJECT-TYPE
	SYNTAX	   IpAddress
	MAX-ACCESS read-only
	STATUS	   current
	DESCRIPTION
		"DHCP Assigned IP Address"
	::= { dhcpServerLeaseEntry 3 }

dhcpLeaseDevName  OBJECT-TYPE
	SYNTAX	   DisplayString
	MAX-ACCESS read-only
	STATUS	   current
	DESCRIPTION
		"DHCP Assigned Device Name"
	::= { dhcpServerLeaseEntry 4 }

cambiumAPConnectedSTATable OBJECT-TYPE
	SYNTAX	   SEQUENCE OF CambiumAPConnectedSTAEntry
	MAX-ACCESS not-accessible
	STATUS	   current
	DESCRIPTION
		"This table contains information relevant to the Connected Subscriber Modules:
			Subscriber Module MAC Address,
			Subscriber Module AID,
			Subscriber Module Channel,
			UL RSSI per SM,
			DL RSSI per SM,
			UL SNR per SM,
			DL SNR per SM,
			UL MCS Mode per SM,
			DL MCS Mode per SM,
			Subscriber Module IP Address,
			SM Priority,
			MIR,
			MIR UL Rate,
			MIR DL Rate,
		Device Allocation: AP"
	::= { cambiumRFStatus 30 }

cambiumAPConnectedSTAEntry OBJECT-TYPE
	SYNTAX	   CambiumAPConnectedSTAEntry
	MAX-ACCESS not-accessible
	STATUS	   current
	DESCRIPTION
		"Wireless parameters mapping for particular station.
		Device Allocation: AP"
	INDEX	{ cambiumAPNumberOfConnectedSTA }
	::= { cambiumAPConnectedSTATable 1 }

CambiumAPConnectedSTAEntry ::= SEQUENCE {
	connectedSTAMAC			   DisplayString,
	connectedSTAAID			   Integer32,
	connectedSTAChannel		   Integer32,
	connectedSTAULRSSI		   Integer32,
	connectedSTADLRSSI		   Integer32,
	connectedSTAULSNR		   Integer32,
	connectedSTADLSNR		   Integer32,
	connectedSTAULMCS		   Integer32,
	connectedSTADLMCS		   Integer32,
	connectedSTAIP			   IpAddress,
	connectedSTAPriority	   DisplayString,
	connectedSTAMirSrc		   DisplayString,
	connectedSTAMirULRate	   DisplayString,
	connectedSTAMirDLRate	   DisplayString,
	connectedSTAClickTHWAddr   DisplayString,
	connectedSTAClickTWebPort  Integer32,
	connectedSTAClickTWebSec   Integer32,
	connectedSTAClickTHostName DisplayString,
	connectedSTATXCapacity	   Integer32,
	connectedSTATXQuality	   Integer32,
	connectedSTAMcastTotalGroups Integer32,
	connectedSTAMcastGRP0	   IpAddress,
	connectedSTAMcastGRP1	   IpAddress,
	connectedSTAMcastGRP2	   IpAddress,
	connectedSTAMcastGRP3	   IpAddress,
	connectedSTAMcastGRP4	   IpAddress,
	connectedSTASessionTime	   DisplayString,
	connectedSTADLRateMbps	   DisplayString,
	connectedSTADistance       Integer32
}

connectedSTAMAC OBJECT-TYPE
	SYNTAX	   DisplayString (SIZE(0|11..17))
	MAX-ACCESS read-only
	STATUS	   current
	DESCRIPTION
		"Connected SM WLAN MAC Address
		Device Allocation: AP"
	::= { cambiumAPConnectedSTAEntry 1 }

connectedSTAAID OBJECT-TYPE
	SYNTAX	   Integer32
	MAX-ACCESS read-only
	STATUS	   current
	DESCRIPTION
		"Association ID
		Device Allocation: AP"
	::= { cambiumAPConnectedSTAEntry 2 }

connectedSTAChannel OBJECT-TYPE
	SYNTAX	   Integer32
	MAX-ACCESS read-only
	STATUS	   current
	DESCRIPTION
		"Connected SM Channel
		Device Allocation: AP"
	::= { cambiumAPConnectedSTAEntry 3 }

connectedSTAULRSSI OBJECT-TYPE
	SYNTAX	   Integer32
	MAX-ACCESS read-only
	STATUS	   current
	DESCRIPTION
		"UL RSSI per SM
		Device Allocation: AP"
	::= { cambiumAPConnectedSTAEntry 4 }

connectedSTADLRSSI OBJECT-TYPE
	SYNTAX	   Integer32
	MAX-ACCESS read-only
	STATUS	   current
	DESCRIPTION
		"DL RSSI per SM
		Device Allocation: AP"
	::= { cambiumAPConnectedSTAEntry 5 }

connectedSTAULSNR OBJECT-TYPE
	SYNTAX	   Integer32
	MAX-ACCESS read-only
	STATUS	   current
	DESCRIPTION
		"UL SNR per SM
		Device Allocation: AP"
	::= { cambiumAPConnectedSTAEntry 6 }

connectedSTADLSNR OBJECT-TYPE
	SYNTAX	   Integer32
	MAX-ACCESS read-only
	STATUS	   current
	DESCRIPTION
		"DL SNR per SM
		Device Allocation: AP"
	::= { cambiumAPConnectedSTAEntry 7 }

connectedSTAULMCS OBJECT-TYPE
	SYNTAX	   Integer32 (1..15)
	MAX-ACCESS read-only
	STATUS	   current
	DESCRIPTION
		"UL MCS Mode per SM:
			1 for MCS1, 
			2 for MCS2, 
			3 for MCS3, 
			4 for MCS4, 
			5 for MCS5, 
			6 for MCS6, 
			7 for MCS7, 
			9 for MCS9, 
			10 for MCS10, 
			11 for MCS11, 
			12 for MCS12, 
			13 for MCS13, 
			14 for MCS14, 
			15 for MCS15
		Device Allocation: AP"
	::= { cambiumAPConnectedSTAEntry 8 }

connectedSTADLMCS OBJECT-TYPE
	SYNTAX	   Integer32 (1..15)
	MAX-ACCESS read-only
	STATUS	   current
	DESCRIPTION
		"DL MCS Mode per SM:
			1 for MCS1, 
			2 for MCS2, 
			3 for MCS3, 
			4 for MCS4, 
			5 for MCS5, 
			6 for MCS6, 
			7 for MCS7, 
			9 for MCS9, 
			10 for MCS10, 
			11 for MCS11, 
			12 for MCS12, 
			13 for MCS13, 
			14 for MCS14, 
			15 for MCS15
		Device Allocation: AP"
	::= { cambiumAPConnectedSTAEntry 9 }

connectedSTAIP OBJECT-TYPE
	SYNTAX	   IpAddress
	MAX-ACCESS read-only
	STATUS	   current
	DESCRIPTION
		"Connected SM WLAN IP Address
		Device Allocation: AP"
	::= { cambiumAPConnectedSTAEntry 10 }

connectedSTAPriority OBJECT-TYPE
	SYNTAX	   DisplayString
	MAX-ACCESS read-only
	STATUS	   current
	DESCRIPTION
		"Connected SM Priority
		Device Allocation: AP"
	::= { cambiumAPConnectedSTAEntry 11 }

connectedSTAMirSrc OBJECT-TYPE
	SYNTAX	   DisplayString
	MAX-ACCESS read-only
	STATUS	   current
	DESCRIPTION
		"Connected SM MIR source: RADIUS server or profile ID
		Device Allocation: AP"
	::= { cambiumAPConnectedSTAEntry 12 }

connectedSTAMirULRate OBJECT-TYPE
	SYNTAX	   DisplayString
	MAX-ACCESS read-only
	STATUS	   current
	DESCRIPTION
		"Connected SM MIR UL Rate
		Device Allocation: AP"
	::= { cambiumAPConnectedSTAEntry 13 }

connectedSTAMirDLRate OBJECT-TYPE
	SYNTAX	   DisplayString
	MAX-ACCESS read-only
	STATUS	   current
	DESCRIPTION
		"Connected SM MIR DL Rate
		Device Allocation: AP"
	::= { cambiumAPConnectedSTAEntry 14 }
	
connectedSTAClickTHWAddr OBJECT-TYPE
	SYNTAX	   DisplayString
	MAX-ACCESS read-only
	STATUS	   current
	DESCRIPTION
		"Connected SM BR or NAT HW addr 
		Device Allocation: AP"
	::= { cambiumAPConnectedSTAEntry 15 }

connectedSTAClickTWebPort OBJECT-TYPE
	SYNTAX	   Integer32
	MAX-ACCESS read-only
	STATUS	   current
	DESCRIPTION
		"Connected SM WEB port 
		Device Allocation: AP"
	::= { cambiumAPConnectedSTAEntry 16 }

connectedSTAClickTWebSec OBJECT-TYPE
	SYNTAX	   Integer32
	MAX-ACCESS read-only
	STATUS	   current
	DESCRIPTION
		"Connected SM WEB security (HTTPS) 
		Device Allocation: AP"
	::= { cambiumAPConnectedSTAEntry 17 }

connectedSTAClickTHostName OBJECT-TYPE
	SYNTAX	   DisplayString
	MAX-ACCESS read-only
	STATUS	   current
	DESCRIPTION
		"Connected SM Host Name 
		Device Allocation: AP"
	::= { cambiumAPConnectedSTAEntry 18 }

connectedSTAMcastTotalGroups OBJECT-TYPE
	SYNTAX	   Integer32
	MAX-ACCESS read-only
	STATUS	   current
	DESCRIPTION
		"Connected SM Total multicast groups
		subscribed count
		Device Allocation: AP"
	::= { cambiumAPConnectedSTAEntry 21 }

connectedSTAMcastGRP0 OBJECT-TYPE
	SYNTAX	   IpAddress
	MAX-ACCESS read-only
	STATUS	   current
	DESCRIPTION
		"Connected SM subscribed multicast
		group 0
		Device Allocation: AP"
	::= { cambiumAPConnectedSTAEntry 22 }

connectedSTAMcastGRP1 OBJECT-TYPE
	SYNTAX	   IpAddress
	MAX-ACCESS read-only
	STATUS	   current
	DESCRIPTION
		"Connected SM subscribed multicast
		group 1
		Device Allocation: AP"
	::= { cambiumAPConnectedSTAEntry 23 }

connectedSTAMcastGRP2 OBJECT-TYPE
	SYNTAX	   IpAddress
	MAX-ACCESS read-only
	STATUS	   current
	DESCRIPTION
		"Connected SM subscribed multicast
		group 2
		Device Allocation: AP"
	::= { cambiumAPConnectedSTAEntry 24 }

connectedSTAMcastGRP3 OBJECT-TYPE
	SYNTAX	   IpAddress
	MAX-ACCESS read-only
	STATUS	   current
	DESCRIPTION
		"Connected SM subscribed multicast
		group 3
		Device Allocation: AP"
	::= { cambiumAPConnectedSTAEntry 25 }

connectedSTAMcastGRP4 OBJECT-TYPE
	SYNTAX	   IpAddress
	MAX-ACCESS read-only
	STATUS	   current
	DESCRIPTION
		"Connected SM subscribed multicast
		group 4
		Device Allocation: AP"
	::= { cambiumAPConnectedSTAEntry 26 }

connectedSTASessionTime OBJECT-TYPE
	SYNTAX	   DisplayString
	MAX-ACCESS read-only
	STATUS	   current
	DESCRIPTION
		"Connected SM time since allocation 
		Device Allocation: AP"
	::= { cambiumAPConnectedSTAEntry 27 }
	
connectedSTADLRateMbps OBJECT-TYPE
	SYNTAX	   DisplayString
	MAX-ACCESS read-only
	STATUS	   current
	DESCRIPTION
		"Connected SM DL Rate in MBits/sec
		Device Allocation: AP"
	::= { cambiumAPConnectedSTAEntry 28 }

connectedSTADistance OBJECT-TYPE
	SYNTAX	   Integer32
	MAX-ACCESS read-only
	STATUS	   current
	DESCRIPTION
		"STA distnce to AP
		Device Allocation: AP"
	::= { cambiumAPConnectedSTAEntry 29 }

cambiumAPBridgeTable OBJECT-TYPE
	SYNTAX	   SEQUENCE OF CambiumAPBridgeEntry
	MAX-ACCESS not-accessible
	STATUS	   current
	DESCRIPTION
		"This table contains information relevant to the particular AP bridge
		 interfaces list:
			Bridge Name,
			Device MAC Address,
			Device Port,
			SM MAC Address,
			Aging Time in seconds
		Device Allocation: AP"
	::= { cambiumRFStatus 40 }

cambiumAPBridgeEntry OBJECT-TYPE
	SYNTAX	   CambiumAPBridgeEntry
	MAX-ACCESS not-accessible
	STATUS	   current
	DESCRIPTION
		"Interface list for particular bridge.
		Device Allocation: AP"
	INDEX	{ camAPBrTabDevMACAddress }
	::= { cambiumAPBridgeTable 1 }

CambiumAPBridgeEntry ::= SEQUENCE {
	camAPBrTabBridgeName	DisplayString,
	camAPBrTabDevMACAddress DisplayString,
	camAPBrTabDevPort		DisplayString,
	camAPBrTabSTAMACAddress DisplayString,
	camAPBrTabAgingTime		Counter32
}

camAPBrTabBridgeName OBJECT-TYPE
	SYNTAX	   DisplayString
	MAX-ACCESS read-only
	STATUS	   current
	DESCRIPTION
		"Bridge Name
		Device Allocation: AP"
	::= { cambiumAPBridgeEntry 1 }

camAPBrTabDevMACAddress OBJECT-TYPE
	SYNTAX	   DisplayString
	MAX-ACCESS read-only
	STATUS	   current
	DESCRIPTION
		"Device MAC Address
		Device Allocation: AP"
	::= { cambiumAPBridgeEntry 2 }

camAPBrTabDevPort OBJECT-TYPE
	SYNTAX	   DisplayString
	MAX-ACCESS read-only
	STATUS	   current
	DESCRIPTION
		"Device Port
		Device Allocation: AP"
	::= { cambiumAPBridgeEntry 3 }

camAPBrTabSTAMACAddress OBJECT-TYPE
	SYNTAX	   DisplayString
	MAX-ACCESS read-only
	STATUS	   current
	DESCRIPTION
		"SM MAC Address
		Device Allocation: AP"
	::= { cambiumAPBridgeEntry 4 }

camAPBrTabAgingTime OBJECT-TYPE
	SYNTAX	   Counter32
	MAX-ACCESS read-only
	STATUS	   current
	DESCRIPTION
		"Aging time in seconds
		Device Allocation: AP"
	::= { cambiumAPBridgeEntry 5 }

cambiumSTABridgeTable OBJECT-TYPE
	SYNTAX	   SEQUENCE OF CambiumSTABridgeEntry
	MAX-ACCESS not-accessible
	STATUS	   current
	DESCRIPTION
		"This table contains information relevant to the particular SM bridge
		 interfaces list:
			Bridge Name,
			Device MAC Address,
			Device Port,
			Aging Time in seconds
		Device Allocation: SM"
	::= { cambiumRFStatus 50 }

cambiumSTABridgeEntry OBJECT-TYPE
	SYNTAX	   CambiumSTABridgeEntry
	MAX-ACCESS not-accessible
	STATUS	   current
	DESCRIPTION
		"Interface list for particular bridge.
		Device Allocation: SM"
	INDEX	{ camSTABrTabDevMACAddress }
	::= { cambiumSTABridgeTable 1 }

CambiumSTABridgeEntry ::= SEQUENCE {
	camSTABrTabBridgeName		DisplayString,
	camSTABrTabDevMACAddress	DisplayString,
	camSTABrTabDevPort			DisplayString,
	camSTABrTabAgingTime		Counter32
}

camSTABrTabBridgeName OBJECT-TYPE
	SYNTAX	   DisplayString
	MAX-ACCESS read-only
	STATUS	   current
	DESCRIPTION
		"Bridge Name
		Device Allocation: SM"
	::= { cambiumSTABridgeEntry 1 }

camSTABrTabDevMACAddress OBJECT-TYPE
	SYNTAX	   DisplayString
	MAX-ACCESS read-only
	STATUS	   current
	DESCRIPTION
		"Device MAC Address
		Device Allocation: SM"
	::= { cambiumSTABridgeEntry 2 }

camSTABrTabDevPort OBJECT-TYPE
	SYNTAX	   DisplayString
	MAX-ACCESS read-only
	STATUS	   current
	DESCRIPTION
		"Device Port
		Device Allocation: SM"
	::= { cambiumSTABridgeEntry 3 }

camSTABrTabAgingTime OBJECT-TYPE
	SYNTAX	   Counter32
	MAX-ACCESS read-only
	STATUS	   current
	DESCRIPTION
		"Aging time in seconds
		Device Allocation: SM"
	::= { cambiumSTABridgeEntry 4 }

cambiumSTAMAC OBJECT-TYPE
	SYNTAX	   DisplayString (SIZE(17))
	MAX-ACCESS read-only
	STATUS	   current
	DESCRIPTION
			"String with dropped SM's MAC address
			 Device Allocation: AP"
	::= { cambiumRFStatus 60 }

cambiumSTADropReason OBJECT-TYPE
	SYNTAX	   DisplayString (SIZE(0..64))
	MAX-ACCESS read-only
	STATUS	   current
	DESCRIPTION
			"String with SM's drop reason
			 Device Allocation: AP"
	::= { cambiumRFStatus 61 }

cambiumNetworkEntryFailureSTAMAC OBJECT-TYPE
	SYNTAX	   DisplayString (SIZE(17))
	MAX-ACCESS read-only
	STATUS	   current
	DESCRIPTION
			"String with rejected SM's MAC 
			 Device Allocation: AP "
	::= { cambiumRFStatus 62 }

cambiumNetworkEntryFailureReason OBJECT-TYPE
	SYNTAX	   DisplayString (SIZE(0..64))
	MAX-ACCESS read-only
	STATUS	   current
	DESCRIPTION
			"String with SM's reject reason
			 Device Allocation: AP "
	::= { cambiumRFStatus 63 }	

connectedSTATXCapacity OBJECT-TYPE
	SYNTAX	   Integer32 (0..100)
	MAX-ACCESS read-only
	STATUS	   current
	DESCRIPTION
		"TX Capacity per SM
		Device Allocation: AP"
	::= { cambiumAPConnectedSTAEntry 19 }

connectedSTATXQuality OBJECT-TYPE
	SYNTAX	   Integer32 (0..100)
	MAX-ACCESS read-only
	STATUS	   current
	DESCRIPTION
		"TX Quality per SM
		Device Allocation: AP"
	::= { cambiumAPConnectedSTAEntry 20 }

cambiumGPSCurrentSyncState OBJECT-TYPE
		SYNTAX	   Integer32 (0..5)
		MAX-ACCESS read-only
		STATUS	   current
		DESCRIPTION
		"GPS Current SYNC State:
			0 - The Initialization State
			1 - The No Synchronization State
			2 - The Synchronization State
			3 - The Hold Off State
			4 - The Regaining Sync State
			5 - The Free Run State
		Device Allocation: AP"
		::= { cambiumGPSStatus 1 }
		
cambiumGPSLatitude OBJECT-TYPE
		SYNTAX	   DisplayString (SIZE(0..128))
		MAX-ACCESS read-only
		STATUS	   current
		DESCRIPTION
		"Current location information from GPS Device. GPS cordinates (latitude).
		Device Allocation: AP, SM"
		::= { cambiumGPSStatus 2 }
		
cambiumGPSLongitude OBJECT-TYPE
		SYNTAX	   DisplayString (SIZE(0..128))
		MAX-ACCESS read-only
		STATUS	   current
		DESCRIPTION
		"Current location information from GPS Device. GPS cordinates (longitude).
		Device Allocation: AP, SM"
		::= { cambiumGPSStatus 3 }
		
cambiumGPSHeight OBJECT-TYPE
		SYNTAX	   DisplayString (SIZE(0..128))
		MAX-ACCESS read-only
		STATUS	   current
		DESCRIPTION
		"Current location information from GPS Device. GPS coordinates (Height).
		Device Allocation: AP, SM"
		::= { cambiumGPSStatus 4 }
		
cambiumGPSTime OBJECT-TYPE
		SYNTAX	   DisplayString (SIZE(0..128))
		MAX-ACCESS read-only
		STATUS	   current
		DESCRIPTION
		"Current Time/Date information from GPS Device. GPS (Time).
		Device Allocation: AP, SM"
		::= { cambiumGPSStatus 5 }
		
cambiumGPSNumTrackedSat OBJECT-TYPE
		SYNTAX	   Integer32 (1..128)
		MAX-ACCESS read-only
		STATUS	   current
		DESCRIPTION
		"Current Satellite information from GPS Device. GPS (Number of Satellites Tracked).
		Device Allocation: AP, SM"
		::= { cambiumGPSStatus 6 }
		
cambiumGPSNumVisibleSat OBJECT-TYPE
		SYNTAX	   Integer32 (1..128)
		MAX-ACCESS read-only
		STATUS	   current
		DESCRIPTION
		"Current Satellite information from GPS Device. GPS (Number of Satellites Visible).
		Device Allocation: AP, SM"
		::= { cambiumGPSStatus 7 }
	   
cambiumGPSSatSNRTable OBJECT-TYPE
		SYNTAX SEQUENCE OF CambiumGPSSatSNREntry
		MAX-ACCESS not-accessible
		STATUS	   current
		DESCRIPTION
		"Table of Current Satellite information from GPS Device. GPS (SNR of Satellites).
		Device Allocation: AP, SM"
		::= { cambiumGPSStatus 8 }
		
cambiumGPSSatSNREntry OBJECT-TYPE
		SYNTAX	   CambiumGPSSatSNREntry
		MAX-ACCESS not-accessible
		STATUS	   current
		DESCRIPTION
		"Satellite SNR values for Visible and Tracked Satellites 
		Device Allocation: AP"
		 INDEX	 { gpsSatelliteId }
		 ::= { cambiumGPSSatSNRTable 1 }
	
CambiumGPSSatSNREntry  ::= SEQUENCE {
	gpsSatelliteId Integer32,
	gpsSnrValue Integer32,
	gpsSatelliteStatus Integer32
	}
	
gpsSatelliteId OBJECT-TYPE
		 SYNTAX Integer32 (0..255)
		 MAX-ACCESS read-only
		 STATUS	 current
		 DESCRIPTION
			"Satellite ID for which SNR is displayed"
		 ::= {cambiumGPSSatSNREntry 1 }

gpsSnrValue OBJECT-TYPE
		 SYNTAX Integer32 (0..99)
		 MAX-ACCESS read-only
		 STATUS current
		 DESCRIPTION
			"SNR value for a satellite"
		::= {cambiumGPSSatSNREntry 2 }

gpsSatelliteStatus OBJECT-TYPE
		SYNTAX Integer32 (1|2)
		MAX-ACCESS read-only
		STATUS current
		DESCRIPTION
			"Satellite Status whether they are visible or tracked
			 1 - Visible
			 2 - Tracked"
		DEFVAL { 1 }
		::= {cambiumGPSSatSNREntry	3} 
		
cambiumGPSDeviceInfo OBJECT-TYPE
		SYNTAX	   DisplayString (SIZE(0..128))
		MAX-ACCESS read-only
		STATUS	   current
		DESCRIPTION
		"GPS Device Information
		Device Allocation: AP, SM"
		::= { cambiumGPSStatus 9 }
		
cambiumGPSFirmwareUpdateStatus	OBJECT-TYPE
	SYNTAX	   Integer32 (0..10)
	MAX-ACCESS read-only
	STATUS	   current
	DESCRIPTION 
		"Software Update Status OID
			0 - No GPS FW Update is progress or No FW update is required,
			1 - GPS FW Update is in progress, Uploading SW package to device,
			2 - GPS FW Update is in progress, Verifying SHA2 signature,
			3 - GPS FW Update is in progress, Executing pre-update script,
			4 - GPS FW Update is in progress, Uploading Firmware to GPS device,
			5 - GPS FW Update is in progress, Uploading Firmware to GPS device,
			6 - GPS FW Update is in progress, Executing post-update script,
			7 - GPS FW Update is finished, waiting for reboot,
			8 - GPS FW Update is Required, Please upgrade to latest GPS FW,
		When GPS FW Update is successfully, return value is 7,
		GUI or NMS indicate that GPS FW update was successful,
		Device can be rebooted.
		Device Allocation: AP, SM"
	::= { cambiumGPSStatus 10} 
		
cambiumLANStatus OBJECT-TYPE
		SYNTAX	   Integer32 (0|1|2)
		MAX-ACCESS read-only
		STATUS	   current
		DESCRIPTION
		"Use the RFC-1213 ifTable to view the physical port status. 
		This attribute indicates the Linux driver status of the port.
		LAN Status:
			0 - Down,
			1 - Up,
			2 - Disabled
		Device Allocation: AP, SM"
		::= { cambiumLinkStatus 1 }

cambiumWLANStatus OBJECT-TYPE
		SYNTAX	   Integer32 (0|1|2)
		MAX-ACCESS read-only
		STATUS	   current
		DESCRIPTION
		"WLAN Status:
			0 - Down, 
			1 - Up
		Device Allocation: AP, SM"
		::= { cambiumLinkStatus 2 }

cambiumEffectiveDeviceIPAddress OBJECT-TYPE
		SYNTAX	   IpAddress
		MAX-ACCESS read-only
		STATUS	   current
		DESCRIPTION
		"Current Device IP address
		Device Allocation: AP, SM"
		::= { cambiumLinkStatus 3 }

cambiumEffectiveSTANetworkMode OBJECT-TYPE
		SYNTAX	   Integer32 (1|2|3)
		MAX-ACCESS read-only
		STATUS	   current
		DESCRIPTION
		"Effective SM Network Mode:
			1 - NAT,
			2 - Bridge,
			3 - Router
		Device Allocation: SM"
		::= { cambiumLinkStatus 4 }

cambiumEffectiveDeviceLANNetMask OBJECT-TYPE
		SYNTAX	   IpAddress
		MAX-ACCESS read-only
		STATUS	   current
		DESCRIPTION
		"Current Device Network Mask
		Device Allocation: AP, SM"
		::= { cambiumLinkStatus 5 }

cambiumEffectiveDeviceDefaultGateWay OBJECT-TYPE
		SYNTAX	   IpAddress
		MAX-ACCESS read-only
		STATUS	   current
		DESCRIPTION
		"Effective Device Default Gateway IP Address,
		NOTE: This parameters lists only the first gateway IP
		Device Allocation: AP, SM"
		::= { cambiumLinkStatus 6 }

cambiumEffectiveDeviceDNSIPAddress OBJECT-TYPE
		SYNTAX	   IpAddress
		MAX-ACCESS read-only
		STATUS	   current
		DESCRIPTION
		"Current Device DNS IP Address,
		NOTE: This parameter displays only the first DNS IP
		Device Allocation: AP, SM"
		::= { cambiumLinkStatus 7 }

cambiumEffectiveWANIPAddress OBJECT-TYPE
		SYNTAX	   IpAddress
		MAX-ACCESS read-only
		STATUS	   current
		DESCRIPTION
		"Current Device WLAN IP address
		Device Allocation: SM"
		::= { cambiumLinkStatus 8 }

cambiumEffectiveDeviceWANNetMask OBJECT-TYPE
		SYNTAX	   IpAddress
		MAX-ACCESS read-only
		STATUS	   current
		DESCRIPTION
		"Current Device Network Mask
		Device Allocation: SM"
		::= { cambiumLinkStatus 9 }

cambiumEffectiveDeviceWANPPPoEStatus OBJECT-TYPE
	SYNTAX	   Integer32 (0|1)
	MAX-ACCESS read-only
	STATUS	   current
	DESCRIPTION
		"WAN PPPoE Status:
			0 - Disabled
			1 - Enabled-Connected
			2 - Enabled-Connecting
			3 - Enabled-Disconnected
		Device Allocation: SM"
	DEFVAL	{ 0 }
	::= { cambiumLinkStatus 10 }

cambiumLANModeStatus  OBJECT-TYPE
	SYNTAX	   Integer32 (-1|0|1)
	MAX-ACCESS read-only
	STATUS	   current
	DESCRIPTION
		"LAN Mode Status
			-1 - No data,
			 0 - Half,
			 1 - Full
		Device Allocation: AP, SM"
	::= { cambiumLinkStatus 11 }

cambiumLANSpeedStatus  OBJECT-TYPE
	SYNTAX	   Integer32 (-1|10|100|1000)
	MAX-ACCESS read-only
	STATUS	   current
	DESCRIPTION
		"LAN Speed Status
			-1 - No data,
			 10 - 10 Mb/s,
			 100 - 100 Mb/s,
			 1000 - 1000 Mb/s
		Device Allocation: AP, SM"
	::= { cambiumLinkStatus 12 }

cambiumDHCPOption82Status OBJECT-TYPE
	SYNTAX	   Integer32 (0|1)
	MAX-ACCESS read-only
	STATUS	   current
	DESCRIPTION
		"DHCP Option82 Status:
			0 - Disabled
			1 - Enabled
		Device Allocation: AP"
	::= { cambiumLinkStatus 13 }

cambiumLAN2ModeStatus  OBJECT-TYPE
	SYNTAX	   Integer32 (-1|0|1)
	MAX-ACCESS read-only
	STATUS	   current
	DESCRIPTION
		"2nd LAN Mode Status
			-1 - No data,
			 0 - Half,
			 1 - Full
		Device Allocation: AP, SM"
	::= { cambiumLinkStatus 14 }

cambiumLAN2SpeedStatus  OBJECT-TYPE
	SYNTAX	   Integer32 (-1|10|100|1000)
	MAX-ACCESS read-only
	STATUS	   current
	DESCRIPTION
		"2nd LAN Speed Status
			-1 - No data,
			 10 - 10 Mb/s,
			 100 - 100 Mb/s,
			 1000 - 1000 Mb/s
		Device Allocation: AP, SM"
	::= { cambiumLinkStatus 15 }

cambiumLAN2Status OBJECT-TYPE
		SYNTAX	   Integer32 (0|1|2)
		MAX-ACCESS read-only
		STATUS	   current
		DESCRIPTION
		"Use the RFC-1213 ifTable to view the physical port status.
		This attribute indicates the Linux driver status of the port.
		2nd LAN Status:
			0 - Down,
			1 - Up,
			2 - Disabled
		Device Allocation: AP, SM"
		::= { cambiumLinkStatus 16 }

cambiumARPTable	 OBJECT-TYPE
	SYNTAX SEQUENCE OF CambiumARPEntry
	MAX-ACCESS not-accessible
	STATUS	   current
	DESCRIPTION
		"Neibour devices IP/MAC pair
		 Table"
	::= { cambiumLinkStatus 20 }

cambiumManagementIFStatus OBJECT-TYPE
		SYNTAX	   Integer32 (0|1)
		MAX-ACCESS read-only
		STATUS	   current
		DESCRIPTION
		"Separate Management Interface Status:
			0 - Down, 
			1 - Up 
		Device Allocation: SM"
		::= { cambiumLinkStatus 25 }

cambiumManagementIFIPAddress OBJECT-TYPE
		SYNTAX	   IpAddress
		MAX-ACCESS read-only
		STATUS	   current
		DESCRIPTION
		"Current Device Separate Management IP address
		Device Allocation: SM"
		::= { cambiumLinkStatus 26 }

cambiumManagementIFNetMask OBJECT-TYPE
		SYNTAX	   IpAddress
		MAX-ACCESS read-only
		STATUS	   current
		DESCRIPTION
		"Current Device Separate Management Network Mask
		Device Allocation: SM"
		::= { cambiumLinkStatus 27 }

cambiumManagementIFGateway OBJECT-TYPE
		SYNTAX	   IpAddress
		MAX-ACCESS read-only
		STATUS	   current
		DESCRIPTION
		"Current Device Separate Management Gateway
		Device Allocation: SM"
		::= { cambiumLinkStatus 28 }

cambiumEffectiveNetworkLanMTU OBJECT-TYPE
		SYNTAX	   Integer32 (0|576..1700)
		MAX-ACCESS read-only
		STATUS	   current
		DESCRIPTION
			"SM NAT LAN MTU size
			Device Allocation: SM"
		DEFVAL	{ 1500 }
		::= { cambiumLinkStatus 29 }

cambiumEffectiveNetworkBridgeMTU OBJECT-TYPE
		SYNTAX	   Integer32 (0|576..1700)
		MAX-ACCESS read-only
		STATUS	   current
		DESCRIPTION
			"Device Bridge MTU size
			Device Allocation: AP, SM"
		DEFVAL	{ 1500 }
		::= { cambiumLinkStatus 30 }

cambiumStaticRoutesTable  OBJECT-TYPE
	SYNTAX SEQUENCE OF CambiumStaticRoutesEntry
	MAX-ACCESS not-accessible
	STATUS	   current
	DESCRIPTION
		"Static Routes Table"
	::= { cambiumLinkStatus 31 }

cambiumIPAliasTable OBJECT-TYPE
	SYNTAX SEQUENCE OF CambiumIPAliasEntry
	MAX-ACCESS not-accessible
	STATUS	   current
	DESCRIPTION
		"IP aliases list table.
		Device Allocation: AP, SM"
	::= { cambiumLinkStatus 32 }

cambiumCnsServConsStat OBJECT-TYPE
		SYNTAX	   DisplayString (SIZE(0..128))
		MAX-ACCESS read-only
		STATUS	   current
		DESCRIPTION
			"cnMaestro Connection Status:
			Cambium provides cloud management of Cambium devices, called cnMaestro.
			This describes the state of the connection to the cnMaestro"
		::= { cambiumLinkStatus 33 }

cambiumCnsServAccountID  OBJECT-TYPE
		SYNTAX	   DisplayString (SIZE(0..128))
		MAX-ACCESS read-only
		STATUS	   current
		DESCRIPTION
			"cnMaestro Account ID:
			Displays cnMaestro Account ID, 
			This is the account ID for the customer.
			It is returned from the cloud management system."
		::= { cambiumLinkStatus 34 }

cambiumAPCnsMGMTState  OBJECT-TYPE
		SYNTAX	   Integer32 (0..1)
		MAX-ACCESS read-only
		STATUS	   current
		DESCRIPTION
		"AP Device management State"
		::= { cambiumLinkStatus 35 }

cambiumIPAliasEntry OBJECT-TYPE
	SYNTAX	   CambiumIPAliasEntry
	MAX-ACCESS not-accessible
	STATUS	   current
	DESCRIPTION
		"IP aliases list table entry.
		Device Allocation: AP, SM."
	INDEX	{ cambiumIPAliasTableIndex }
	::= { cambiumIPAliasTable 1 }

CambiumIPAliasEntry ::= SEQUENCE {
	cambiumIPAliasTableIndex
		Integer32,
	cambiumIPAliasIP
		IpAddress,
	cambiumIPAliasNetmask
		IpAddress
}

cambiumIPAliasTableIndex  OBJECT-TYPE
	SYNTAX	  Integer32 (0..10)
	MAX-ACCESS read-only
	STATUS	   current
	DESCRIPTION
		"IP aliases table index."
		::= { cambiumIPAliasEntry 1 }

cambiumIPAliasIP  OBJECT-TYPE
	SYNTAX	   IpAddress
	MAX-ACCESS read-only
	STATUS	   current
	DESCRIPTION
		"IP alias IP address."
	::= { cambiumIPAliasEntry 2 }

cambiumIPAliasNetmask  OBJECT-TYPE
	SYNTAX	   IpAddress
	MAX-ACCESS read-only
	STATUS	   current
	DESCRIPTION
		"IP alias netmask."
	::= { cambiumIPAliasEntry 3 }

cambiumARPEntry OBJECT-TYPE
	SYNTAX	   CambiumARPEntry
	MAX-ACCESS not-accessible
	STATUS	   current
	DESCRIPTION
		"Neighbour device IP/MAC pair entry"
	INDEX	{ cambiumARPIndex }
	::= { cambiumARPTable 1 }

CambiumARPEntry ::= SEQUENCE {
	cambiumARPIndex
		Integer32,
	cambiumARPMAC
		DisplayString,
	cambiumARPIP
		IpAddress,
	cambiumARPInterface
		DisplayString
}

cambiumARPIndex	 OBJECT-TYPE
	SYNTAX	  Integer32 (0..1024)
	MAX-ACCESS read-only
	STATUS	   current
	DESCRIPTION
		"Index"
	::= { cambiumARPEntry 1 }

cambiumARPMAC  OBJECT-TYPE
	SYNTAX	   DisplayString (SIZE(0|17))
	MAX-ACCESS read-only
	STATUS	   current
	DESCRIPTION
		"Neighbour device MAC Address"
	::= { cambiumARPEntry 2 }

cambiumARPIP  OBJECT-TYPE
	SYNTAX	   IpAddress
	MAX-ACCESS read-only
	STATUS	   current
	DESCRIPTION
		"Neighbour device IP Address"
	::= { cambiumARPEntry 3 }

cambiumARPInterface	 OBJECT-TYPE
	SYNTAX	   DisplayString (SIZE(0|16))
	MAX-ACCESS read-only
	STATUS	   current
	DESCRIPTION
		"Neighbour device Interface"
	::= { cambiumARPEntry 4 }

cambiumStaticRoutesEntry OBJECT-TYPE
	SYNTAX	   CambiumStaticRoutesEntry
	MAX-ACCESS not-accessible
	STATUS	   current
	DESCRIPTION
		"Static Routes Dest/Getway pair entry"
	INDEX	{ cambiumStaticRoutesIndex }
	::= { cambiumStaticRoutesTable 1 }

CambiumStaticRoutesEntry ::= SEQUENCE {
	cambiumStaticRoutesIndex
		Integer32,
	cambiumStaticRoutesDestIP
		IpAddress,
	cambiumStaticRoutesGW
		IpAddress,
	cambiumStaticRoutesNetmask
		IpAddress,
	cambiumStaticRoutesInterface
		DisplayString
}

cambiumStaticRoutesIndex  OBJECT-TYPE
	SYNTAX	  Integer32 (0..32)
	MAX-ACCESS read-only
	STATUS	   current
	DESCRIPTION
		"Index"
	::= { cambiumStaticRoutesEntry 1 }

cambiumStaticRoutesDestIP  OBJECT-TYPE
	SYNTAX	   IpAddress
	MAX-ACCESS read-only
	STATUS	   current
	DESCRIPTION
		"Destination IP"
	::= { cambiumStaticRoutesEntry 2 }

cambiumStaticRoutesGW  OBJECT-TYPE
	SYNTAX	   IpAddress
	MAX-ACCESS read-only
	STATUS	   current
	DESCRIPTION
		"Getway IP"
	::= { cambiumStaticRoutesEntry 3 }

cambiumStaticRoutesNetmask	OBJECT-TYPE
	SYNTAX	   IpAddress
	MAX-ACCESS read-only
	STATUS	   current
	DESCRIPTION
		"Dest IP Netmask"
	::= { cambiumStaticRoutesEntry 4 }

cambiumStaticRoutesInterface  OBJECT-TYPE
	SYNTAX	   DisplayString (SIZE(0|16))
	MAX-ACCESS read-only
	STATUS	   current
	DESCRIPTION
		"Static Routes Interface Name"
	::= { cambiumStaticRoutesEntry 5 }

cambiumStatsForceUpdate OBJECT-TYPE
		SYNTAX	   Integer32 (0|1)
		MAX-ACCESS read-write
		STATUS	   current
		DESCRIPTION
		"Cambium Statistics Update/Reset Action
		Statistic is updated automatically in the background each 15sec
		SNMP-GET on This OID forces update of subsequent Statistics tree
		SNMP-SET on This OID Resets all of the subsequent Statistic
		Device Allocation: AP, SM"
		::= { cambiumPerformanceMonitoring 1 }

cambiumEthRXBytes OBJECT-TYPE
		SYNTAX	   Counter64
		MAX-ACCESS read-only
		STATUS	   current
		DESCRIPTION
		"Total Ethernet RX bytes
		Device Allocation: AP, SM"
		::= { cambiumPerformanceMonitoring 2 }

cambiumEthRXPackets OBJECT-TYPE
		SYNTAX	   Counter64
		MAX-ACCESS read-only
		STATUS	   current
		DESCRIPTION
		"Total Ethernet RX packets
		Device Allocation: AP, SM"
		::= { cambiumPerformanceMonitoring 3 }

cambiumEthRXErrors OBJECT-TYPE
		SYNTAX	   Counter64
		MAX-ACCESS read-only
		STATUS	   current
		DESCRIPTION
		"Total Ethernet RX errors
		Device Allocation: AP, SM"
		::= { cambiumPerformanceMonitoring 4 }

cambiumEthRXDrops OBJECT-TYPE
		SYNTAX	   Counter64
		MAX-ACCESS read-only
		STATUS	   current
		DESCRIPTION
		"Total Ethernet RX drops
		Device Allocation: AP, SM"
		::= { cambiumPerformanceMonitoring 5 }

cambiumEthRXMulticast OBJECT-TYPE
		SYNTAX	   Counter64
		MAX-ACCESS read-only
		STATUS	   current
		DESCRIPTION
		"Total Ethernet RX multicast
		Device Allocation: AP, SM"
		::= { cambiumPerformanceMonitoring 6 }

cambiumEthRXBroadcast OBJECT-TYPE
		SYNTAX	   Counter64
		MAX-ACCESS read-only
		STATUS	   current
		DESCRIPTION
		"Total Ethernet RX broadcast
		Device Allocation: AP, SM"
		::= { cambiumPerformanceMonitoring 7 }

cambiumEthTXBytes OBJECT-TYPE
		SYNTAX	   Counter64
		MAX-ACCESS read-only
		STATUS	   current
		DESCRIPTION
		"Total Ethernet TX bytes
		Device Allocation: AP, SM"
		::= { cambiumPerformanceMonitoring 8 }

cambiumEthTXPackets OBJECT-TYPE
		SYNTAX	   Counter64
		MAX-ACCESS read-only
		STATUS	   current
		DESCRIPTION
		"Total Ethernet TX packets
		Device Allocation: AP, SM"
		::= { cambiumPerformanceMonitoring 9 }

cambiumEthTXErrors OBJECT-TYPE
		SYNTAX	   Counter64
		MAX-ACCESS read-only
		STATUS	   current
		DESCRIPTION
		"Total Ethernet TX errors
		Device Allocation: AP, SM"
		::= { cambiumPerformanceMonitoring 10 }

cambiumEthTXDrops OBJECT-TYPE
		SYNTAX	   Counter64
		MAX-ACCESS read-only
		STATUS	   current
		DESCRIPTION
		"Total Ethernet TX drops
		Device Allocation: AP, SM"
		::= { cambiumPerformanceMonitoring 11 }

cambiumEthTXMulticast OBJECT-TYPE
		SYNTAX	   Counter64
		MAX-ACCESS read-only
		STATUS	   current
		DESCRIPTION
		"Total Ethernet TX multicast
		Device Allocation: AP, SM"
		::= { cambiumPerformanceMonitoring 12 }
		
cambiumEthTXBroadcast OBJECT-TYPE
		SYNTAX	   Counter64
		MAX-ACCESS read-only
		STATUS	   current
		DESCRIPTION
		"Total Ethernet TX broadcast
		Device Allocation: AP, SM"
		::= { cambiumPerformanceMonitoring 13 }

cambiumAthRXBytes OBJECT-TYPE
		SYNTAX	   Counter64
		MAX-ACCESS read-only
		STATUS	   obsolete
		DESCRIPTION
		"Total Wireless RX bytes
		Device Allocation: AP, SM"
		::= { cambiumPerformanceMonitoring 21 }

cambiumAthRXPackets OBJECT-TYPE
		SYNTAX	   Counter64
		MAX-ACCESS read-only
		STATUS	   obsolete
		DESCRIPTION
		"Total Wireless RX packets
		Device Allocation: AP, SM"
		::= { cambiumPerformanceMonitoring 22 }

cambiumAthRXErrors OBJECT-TYPE
		SYNTAX	   Counter64
		MAX-ACCESS read-only
		STATUS	   obsolete
		DESCRIPTION
		"Total Wireless RX errors
		Device Allocation: AP, SM"
		::= { cambiumPerformanceMonitoring 23 }

cambiumAthRXDrops OBJECT-TYPE
		SYNTAX	   Counter64
		MAX-ACCESS read-only
		STATUS	   obsolete
		DESCRIPTION
		"Total Wireless RX drops
		Device Allocation: AP, SM"
		::= { cambiumPerformanceMonitoring 24 }

cambiumAthRXMulticast OBJECT-TYPE
		SYNTAX	   Counter64
		MAX-ACCESS read-only
		STATUS	   obsolete
		DESCRIPTION
		"Total Wireless RX multicast
		Device Allocation: AP, SM"
		::= { cambiumPerformanceMonitoring 25 }

cambiumAthRXBroadcast OBJECT-TYPE
		SYNTAX	   Counter64
		MAX-ACCESS read-only
		STATUS	   obsolete
		DESCRIPTION
		"Total Wireless RX broadcast
		Device Allocation: AP, SM"
		::= { cambiumPerformanceMonitoring 26 }

cambiumAthTXBytes OBJECT-TYPE
		SYNTAX	   Counter64
		MAX-ACCESS read-only
		STATUS	   obsolete
		DESCRIPTION
		"Total Wireless TX bytes
		Device Allocation: AP, SM"
		::= { cambiumPerformanceMonitoring 27 }

cambiumAthTXPackets OBJECT-TYPE
		SYNTAX	   Counter64
		MAX-ACCESS read-only
		STATUS	   obsolete
		DESCRIPTION
		"Total Wireless TX packets
		Device Allocation: AP, SM"
		::= { cambiumPerformanceMonitoring 28 }

cambiumAthTXErrors OBJECT-TYPE
		SYNTAX	   Counter64
		MAX-ACCESS read-only
		STATUS	   obsolete
		DESCRIPTION
		"Total Wireless TX errors
		Device Allocation: AP, SM"
		::= { cambiumPerformanceMonitoring 29 }

cambiumAthTXDrops OBJECT-TYPE
		SYNTAX	   Counter64
		MAX-ACCESS read-only
		STATUS	   obsolete
		DESCRIPTION
		"Total Wireless TX drops
		Device Allocation: AP, SM"
		::= { cambiumPerformanceMonitoring 30 }

cambiumAthTXMulticast OBJECT-TYPE
		SYNTAX	   Counter64
		MAX-ACCESS read-only
		STATUS	   obsolete
		DESCRIPTION
		"Total Wireless TX multicast
		Device Allocation: AP, SM"
		::= { cambiumPerformanceMonitoring 31 }

cambiumAthTXBroadcast OBJECT-TYPE
		SYNTAX	   Counter64
		MAX-ACCESS read-only
		STATUS	   obsolete
		DESCRIPTION
		"Total Wireless TX broadcast
		Device Allocation: AP, SM"
		::= { cambiumPerformanceMonitoring 32 }

sysNetworkEntryAttempt OBJECT-TYPE
		SYNTAX	   Counter32
		MAX-ACCESS read-only
		STATUS	   current
		DESCRIPTION
				"Number of attempt to enter the AP network
				Device Allocation: AP"
		::= { cambiumPerformanceMonitoring 33 }

sysNetworkEntrySuccess OBJECT-TYPE
		SYNTAX	   Counter32
		MAX-ACCESS read-only
		STATUS	   current
		DESCRIPTION
				"Number of successful network entry into the AP
				Device Allocation: AP"
		::= { cambiumPerformanceMonitoring 34 }

sysNetworkEntryAuthenticationFailure OBJECT-TYPE
		SYNTAX	   Counter32
		MAX-ACCESS read-only
		STATUS	   current
		DESCRIPTION
				"Number of failed network entry into the AP due to
				authentication failure
				Device Allocation: AP"
		::= { cambiumPerformanceMonitoring 35 }

sysDFSDetectedCount OBJECT-TYPE
		SYNTAX	   Counter32
		MAX-ACCESS read-only
		STATUS	   current
		DESCRIPTION
				"Number of DFS detected during channel initialization or during
				service which causes channel remap
				Device Allocation: AP, SM"
		::= { cambiumPerformanceMonitoring 36 }

ulWLanKbitCount OBJECT-TYPE
		SYNTAX	   Counter64
		MAX-ACCESS read-only
		STATUS	   current
		DESCRIPTION
				"Aggregated total Uplink data traffic in kilobits
				Device Allocation: AP, SM"
		::= { cambiumPerformanceMonitoring 37 }

dlWLanKbitCount OBJECT-TYPE
		SYNTAX	   Counter64
		MAX-ACCESS read-only
		STATUS	   current
		DESCRIPTION
				"Aggregated total Downlink data traffic in kilobits
				Device Allocation: AP, SM"
		::= { cambiumPerformanceMonitoring 38 }

ulWLanTotalPacketCount OBJECT-TYPE
		SYNTAX	   Counter64
		MAX-ACCESS read-only
		STATUS	   current
		DESCRIPTION
				"Aggregated number of total Uplink data packet transmitted by
				SM or received by AP
				Device Allocation: AP, SM"
		::= { cambiumPerformanceMonitoring 39 }

sysRebootCount OBJECT-TYPE
		SYNTAX	   Integer32
		MAX-ACCESS read-only
		STATUS	   obsolete
		DESCRIPTION
				"Device Reboot Counter
				Device Allocation: AP, SM"
		::= { cambiumPerformanceMonitoring 41 }

dlWLanTotalPacketCount OBJECT-TYPE
		SYNTAX	   Counter64
		MAX-ACCESS read-only
		STATUS	   current
		DESCRIPTION
				"Aggregated number of total Downlink data packet transmitted by
				AP or received by SM
				Device Allocation: AP, SM"
		::= { cambiumPerformanceMonitoring 42 }

ulWLanMultiBroadcastKbitCount OBJECT-TYPE
		SYNTAX	   Counter64
		MAX-ACCESS read-only
		STATUS	   current
		DESCRIPTION
				"Aggregated total Uplink multicast and broadcast data traffic in
				kilobits
				Device Allocation: AP, SM"
		::= { cambiumPerformanceMonitoring 43 }

dlWLanMultiBroadcastKbitCount OBJECT-TYPE
		SYNTAX	   Counter64
		MAX-ACCESS read-only
		STATUS	   current
		DESCRIPTION
				"Aggregated total Downlink multicast and broadcast data traffic
				in kilobits
				Device Allocation: AP, SM"
		::= { cambiumPerformanceMonitoring 44 }

wLanSessionDroppedCount OBJECT-TYPE
		SYNTAX	   Counter32
		MAX-ACCESS read-only
		STATUS	   current
		DESCRIPTION
				"Aggregated number of SM session dropped due to no responses of
				bandwidth request response
				Device Allocation: AP, SM"
		::= { cambiumPerformanceMonitoring 45 }

cambiumTDDStatsPerSTATable OBJECT-TYPE
	SYNTAX	   SEQUENCE OF CambiumTDDStatsPerSTAEntry
	MAX-ACCESS not-accessible
	STATUS	   current
	DESCRIPTION
		   "This table contains information relevant to customer TDD Statistics
		   for connected SMs:
		   - station MAC Address,
		   - uplink data traffic in Kbits for a single SM;
		   - downlink data traffic in Kbits for a single SM;
		   - number of uplink total data packet received at AP for a single SM;
		   - number of downlink total data packet transmitted at AP for a single
			 SM;
		   - number of uplink data packet dropped due to data integrity error or
			 other RF related packer errors for a single SM;
		   - number of downlink data packet dropped due to no-acknowledgement or
			 other RF related packet error for a single SM;
		   - number of downlink data packet dropped due to data buffer/queue
			 overflow or other system internal buffer/sending related packet
			 error for a single SM;
		   - number of downlink data packet retransmitted due to no-acknowledge
			 for a single SM.
		   Device Allocation: AP"
	::= { cambiumPerformanceMonitoring 46 }

cambiumTDDStatsPerSTAEntry OBJECT-TYPE
	SYNTAX	   CambiumTDDStatsPerSTAEntry
	MAX-ACCESS not-accessible
	STATUS	   current
	DESCRIPTION
		   "Customer TDD Statistics for particular SM
		   Device Allocation: AP"
	INDEX	{ cambiumTDDStatsPerSTAIndex }
	::= { cambiumTDDStatsPerSTATable 1 }

CambiumTDDStatsPerSTAEntry ::= SEQUENCE {
		cambiumTDDStatsPerSTAIndex				Integer32,
		cambiumTDDStatsListMAC					DisplayString,
		ulWLanPerUserKbitCount					Counter64,
		dlWLanPerUserKbitCount					Counter64,
		ulWLanPerUserTotalPacketCount			Counter64,
		dlWLanPerUserTotalPacketCount			Counter64,
		ulWLanPerUserErrorDroppedPacketCount	Counter64,
		dlWLanPerUserErrorDroppedPacketCount	Counter64,
		dlWLanPerUserCapacityDroppedPacketCount Counter64,
		dlWLanPerUserRetransmitPacketCount		Counter64,
		dlWLanPerUserTxPower					Integer32
	}

cambiumTDDStatsPerSTAIndex OBJECT-TYPE
	SYNTAX	   Integer32 (0..120)
	MAX-ACCESS read-only
	STATUS	   current
	DESCRIPTION
		   "Table index"
	::= { cambiumTDDStatsPerSTAEntry 1 }

cambiumTDDStatsListMAC OBJECT-TYPE
	SYNTAX	   DisplayString (SIZE(0|11..17))
	MAX-ACCESS read-only
	STATUS	   current
	DESCRIPTION
		   "Connected SM WLAN MAC Address
		   Device Allocation: AP"
	::= { cambiumTDDStatsPerSTAEntry 2 }
	
ulWLanPerUserKbitCount OBJECT-TYPE
	SYNTAX	   Counter64
	MAX-ACCESS read-only
	STATUS	   current
	DESCRIPTION
		   "Uplink data traffic in Kbits for a single SM
		   Device Allocation: AP"
	::= { cambiumTDDStatsPerSTAEntry 3 }

dlWLanPerUserKbitCount OBJECT-TYPE
	SYNTAX	   Counter64
	MAX-ACCESS read-only
	STATUS	   current
	DESCRIPTION
		   "Downlink data traffic in Kbits for a single SM
		   Device Allocation: AP"
	::= { cambiumTDDStatsPerSTAEntry 4 }

ulWLanPerUserTotalPacketCount OBJECT-TYPE
	SYNTAX	   Counter64
	MAX-ACCESS read-only
	STATUS	   current
	DESCRIPTION
		   "Number of uplink total data packet received at AP for a single SM
		   Device Allocation: AP"
	::= { cambiumTDDStatsPerSTAEntry 5 }

dlWLanPerUserTotalPacketCount OBJECT-TYPE
	SYNTAX	   Counter64
	MAX-ACCESS read-only
	STATUS	   current
	DESCRIPTION
		   "Number of downlink total data packet transmitted at AP for a single
		  SM 
		   Device Allocation: AP"
	::= { cambiumTDDStatsPerSTAEntry 6 }

ulWLanPerUserErrorDroppedPacketCount OBJECT-TYPE
	SYNTAX	   Counter64
	MAX-ACCESS read-only
	STATUS	   current
	DESCRIPTION
		   "Number of uplink data packet dropped due to data integrity error or
		   other RF related packer errors for a single SM
		   Device Allocation: AP"
	::= { cambiumTDDStatsPerSTAEntry 7 }

dlWLanPerUserErrorDroppedPacketCount OBJECT-TYPE
	SYNTAX	   Counter64
	MAX-ACCESS read-only
	STATUS	   current
	DESCRIPTION
		   "Number of downlink data packet dropped due to no-acknowledgement or
		   other RF related packet error for a single SM
		   Device Allocation: AP"
	::= { cambiumTDDStatsPerSTAEntry 8 }

dlWLanPerUserCapacityDroppedPacketCount OBJECT-TYPE
	SYNTAX	   Counter64
	MAX-ACCESS read-only
	STATUS	   current
	DESCRIPTION
		   "Number of downlink data packet dropped due to data buffer/queue
		   overflow or other system internal buffer/sending related packet error
		   for a single SM
		   Device Allocation: AP"
	::= { cambiumTDDStatsPerSTAEntry 9 }

dlWLanPerUserRetransmitPacketCount OBJECT-TYPE
	SYNTAX	   Counter64
	MAX-ACCESS read-only
	STATUS	   current
	DESCRIPTION
		   "Number of downlink data packet retransmitted due to no-acknowledge
		   for a single SM
		   Device Allocation: AP"
	::= { cambiumTDDStatsPerSTAEntry 10 }

dlWLanPerUserTxPower OBJECT-TYPE
	SYNTAX	   Integer32
	MAX-ACCESS read-only
	STATUS	   current
	DESCRIPTION
		   "Downlink TxPower of data packages for a single SM
		   Device Allocation: AP"
	::= { cambiumTDDStatsPerSTAEntry 11 }

ulWLanErrorDroppedPacketCount OBJECT-TYPE
		SYNTAX	   Counter64
		MAX-ACCESS read-only
		STATUS	   current
		DESCRIPTION
				"Aggregated number of total Uplink data packet dropped due to
				data integrity error or other data packet association or RF
				error in packet
				Device Allocation: AP, SM"
		::= { cambiumPerformanceMonitoring 47 }

dlWLanErrorDroppedPacketCount OBJECT-TYPE
		SYNTAX	   Counter64
		MAX-ACCESS read-only
		STATUS	   current
		DESCRIPTION
				"Aggregated number of total Downlink data packet dropped due to
				data integrity error or other data packet association error in
				packet
				Device Allocation: AP, SM"
		::= { cambiumPerformanceMonitoring 48 }

ulWLanCapacityDroppedPacketCount OBJECT-TYPE
		SYNTAX	   Counter64
		MAX-ACCESS read-only
		STATUS	   current
		DESCRIPTION
				"Aggregated number of total Uplink data packet dropped due to
				WLAN capacity issue in packets
				Device Allocation: AP, SM"
		::= { cambiumPerformanceMonitoring 49 }

dlWLanCapacityDroppedPacketCount OBJECT-TYPE
		SYNTAX	   Counter64
		MAX-ACCESS read-only
		STATUS	   current
		DESCRIPTION
				"Aggregated number of total Downlink data packet dropped due to
				exceed data buffer, over capacity or internal packet package
				sent issues in packet
				Device Allocation: AP, SM"
		::= { cambiumPerformanceMonitoring 50 }

ulWLanTotalAvailableFrameTimePerSecond OBJECT-TYPE
		SYNTAX	   Counter32
		MAX-ACCESS read-only
		STATUS	   current
		DESCRIPTION
				"Aggregated number of total uplink available frame time can be
				scheduled for traffic in micro second for 1 second period
				Device Allocation: AP"
		::= { cambiumPerformanceMonitoring 51 }

dlWLanTotalAvailableFrameTimePerSecond OBJECT-TYPE
		SYNTAX	   Counter32
		MAX-ACCESS read-only
		STATUS	   current
		DESCRIPTION
				"Aggregated number of total downlink available frame time can be
				scheduled for traffic in micro second for 1 second period
				Device Allocation: AP"
		::= { cambiumPerformanceMonitoring 52 }

ulWLanTotalUsedFrameTimePerSecond OBJECT-TYPE
		SYNTAX	   Counter32
		MAX-ACCESS read-only
		STATUS	   current
		DESCRIPTION
				"Aggregated number of uplink frame time schedule to be used in
				microsecond for 1 second period
				Device Allocation: AP"
		::= { cambiumPerformanceMonitoring 53 }

dlWLanTotalUsedFrameTimePerSecond OBJECT-TYPE
		SYNTAX	   Counter32
		MAX-ACCESS read-only
		STATUS	   current
		DESCRIPTION
				"Aggregated number of downlink frame time scheduled to be used
				per frame for 1 second period
				Device Allocation: AP"
		::= { cambiumPerformanceMonitoring 54 }

ulWLanTotalOverheadFrameTimePerSecond OBJECT-TYPE
		SYNTAX	   Counter32
		MAX-ACCESS read-only
		STATUS	   current
		DESCRIPTION
				"Aggregated number of uplink frame time is used for overhead
				(preamble and inter-frame gap) in microsecond for 1 second
				period
				Device Allocation: AP"
		::= { cambiumPerformanceMonitoring 55 }

dlWLanTotalOverheadFrameTimePerSecond OBJECT-TYPE
		SYNTAX	   Counter32
		MAX-ACCESS read-only
		STATUS	   current
		DESCRIPTION
				"Aggregated number of downlink frame time is used for overhead
				(preamble ans inter-frame gap) per frame for 1 second period
				Device Allocation: AP"
		::= { cambiumPerformanceMonitoring 56 }

cambiumMCSTable OBJECT-TYPE
	SYNTAX	   SEQUENCE OF CambiumMCSEntry
	MAX-ACCESS not-accessible
	STATUS	   obsolete
	DESCRIPTION
		   "This table contains information relevant to customer TDD Statistics
		   for MCS RX and TX rates:
		   - MCS number (MCSxx);
		   - Aggregated number of uplink frame time used for MCSxx in
			 microsecond for 1 second period;
		   - Aggregated number of downlink frame time used for MCSxx in
			 microsecond for 1 second period.
		   Device Allocation: AP"
	::= { cambiumPerformanceMonitoring 57 }

cambiumMCSEntry OBJECT-TYPE
	SYNTAX	   CambiumMCSEntry
	MAX-ACCESS not-accessible
	STATUS	   obsolete
	DESCRIPTION
		   "MCS table
		   Device Allocation: AP"
	INDEX	{ cambiumMCSIndex }
	::= { cambiumMCSTable 1 }

CambiumMCSEntry ::= SEQUENCE {
		cambiumMCSIndex					Integer32,
		cambiumMCSNumber				DisplayString,
		ulWLanMCSUsedFrameTimePerSecond Counter32,
		dlWLanMCSUsedFrameTimePerSecond Counter32
	}

cambiumMCSIndex OBJECT-TYPE
	SYNTAX	   Integer32 (0..24)
	MAX-ACCESS read-only
	STATUS	   obsolete
	DESCRIPTION
		   "MCS index
		   Device Allocation: AP"
	::= { cambiumMCSEntry 1 }

cambiumMCSNumber OBJECT-TYPE
	SYNTAX	   DisplayString
	MAX-ACCESS read-only
	STATUS	   obsolete
	DESCRIPTION
		   "MCS number (MCSxx)
		   Device Allocation: AP"
	::= { cambiumMCSEntry 2 }

ulWLanMCSUsedFrameTimePerSecond OBJECT-TYPE
	SYNTAX	   Counter32
	MAX-ACCESS read-only
	STATUS	   obsolete
	DESCRIPTION
		   "Aggregated number of uplink frame time used for MCSxx in
			microsecond for 1 second period
		   Device Allocation: AP"
	::= { cambiumMCSEntry 3 }

dlWLanMCSUsedFrameTimePerSecond OBJECT-TYPE
	SYNTAX	   Counter32
	MAX-ACCESS read-only
	STATUS	   obsolete
	DESCRIPTION
		   "Aggregated number of downlink frame time used for MCSxx in
			microsecond for 1 second period
		   Device Allocation: AP"
	::= { cambiumMCSEntry 4 }

ulWLanRetransPacketCount OBJECT-TYPE
		SYNTAX	   Counter64
		MAX-ACCESS read-only
		STATUS	   current
		DESCRIPTION
				"Aggregated number of total Uplink data packet retransmitted due
				to no-acknowledgement.
				Device Allocation: SM"
		::= { cambiumPerformanceMonitoring 58 }

dlWLanRetransPacketCount OBJECT-TYPE
		SYNTAX	   Counter64
		MAX-ACCESS read-only
		STATUS	   current
		DESCRIPTION
				"Aggregated number of total Downlink data packet retransmitted
				due to no-acknowledgement
				Device Allocation: AP"
		::= { cambiumPerformanceMonitoring 59 }

ulWLanBroadcastPacketCount OBJECT-TYPE
		SYNTAX	   Counter32
		MAX-ACCESS read-only
		STATUS	   current
		DESCRIPTION
				"Aggregated total Uplink broadcast packet counter
				Device Allocation: AP, SM"
		::= { cambiumPerformanceMonitoring 60 }

dlWLanBroadcastPacketCount OBJECT-TYPE
		SYNTAX	   Counter32
		MAX-ACCESS read-only
		STATUS	   current
		DESCRIPTION
				"Aggregated total Downlink broadcast packet counter
				Device Allocation: AP, SM"
		::= { cambiumPerformanceMonitoring 61 }

ulWLanMulticastPacketCount OBJECT-TYPE
		SYNTAX	   Counter32
		MAX-ACCESS read-only
		STATUS	   current
		DESCRIPTION
				"Aggregated total Uplink multicast packet counter
				Device Allocation: AP, SM"
		::= { cambiumPerformanceMonitoring 62 }

dlWLanMulticastPacketCount OBJECT-TYPE
		SYNTAX	   Counter32
		MAX-ACCESS read-only
		STATUS	   current
		DESCRIPTION
				"Aggregated total Downlink multicast packet counter
				Device Allocation: AP, SM"
		::= { cambiumPerformanceMonitoring 63 }

sysCPUUsage OBJECT-TYPE
		SYNTAX	   Counter32
		MAX-ACCESS read-only
		STATUS	   current
		DESCRIPTION
				"CPU Usage, measuring up to 0.1%
				Range: 0..1000
				Device Allocation: AP, SM"
		::= { cambiumPerformanceMonitoring 64 }

rxEtherLanKbitCount OBJECT-TYPE
		SYNTAX	   Counter64
		MAX-ACCESS read-only
		STATUS	   current
		DESCRIPTION
		"Total Ethernet RX bytes
		Device Allocation: AP, SM"
		::= { cambiumPerformanceMonitoring 65 }

rxEtherLanTotalPacketCount OBJECT-TYPE
		SYNTAX	   Counter64
		MAX-ACCESS read-only
		STATUS	   current
		DESCRIPTION
		"Total Ethernet RX packets
		Device Allocation: AP, SM"
		::= { cambiumPerformanceMonitoring 66 }

rxEtherLanErrorPacketCount OBJECT-TYPE
		SYNTAX	   Counter64
		MAX-ACCESS read-only
		STATUS	   current
		DESCRIPTION
		"Total Ethernet RX errors
		Device Allocation: AP, SM"
		::= { cambiumPerformanceMonitoring 67 }

rxEtherLanDroppedPacketCount OBJECT-TYPE
		SYNTAX	   Counter64
		MAX-ACCESS read-only
		STATUS	   current
		DESCRIPTION
		"Total Ethernet RX drops
		Device Allocation: AP, SM"
		::= { cambiumPerformanceMonitoring 68 }

rxEtherLanMulticastPacketCount OBJECT-TYPE
		SYNTAX	   Counter64
		MAX-ACCESS read-only
		STATUS	   current
		DESCRIPTION
		"Total Ethernet RX multicast
		Device Allocation: AP, SM"
		::= { cambiumPerformanceMonitoring 69 }

rxEtherLanBroadcastPacketCount OBJECT-TYPE
		SYNTAX	   Counter64
		MAX-ACCESS read-only
		STATUS	   current
		DESCRIPTION
		"Total Ethernet RX broadcast
		Device Allocation: AP, SM"
		::= { cambiumPerformanceMonitoring 70 }

rxEtherLanMultiBroadcastKbitCount OBJECT-TYPE
		SYNTAX	   Counter64
		MAX-ACCESS read-only
		STATUS	   current
		DESCRIPTION
		"Aggregated total Ethernet RX multicast and broadcast data traffic 
		Device Allocation: AP, SM"
		::= { cambiumPerformanceMonitoring 71 }

txEtherLanKbitCount OBJECT-TYPE
		SYNTAX	   Counter64
		MAX-ACCESS read-only
		STATUS	   current
		DESCRIPTION
		"Total Ethernet TX bytes
		Device Allocation: AP, SM"
		::= { cambiumPerformanceMonitoring 72 }

txEtherLanTotalPacketCount OBJECT-TYPE
		SYNTAX	   Counter64
		MAX-ACCESS read-only
		STATUS	   current
		DESCRIPTION
		"Total Ethernet TX packets
		Device Allocation: AP, SM"
		::= { cambiumPerformanceMonitoring 73 }

txEtherLanErrorPacketCount OBJECT-TYPE
		SYNTAX	   Counter64
		MAX-ACCESS read-only
		STATUS	   current
		DESCRIPTION
		"Total Ethernet TX errors
		Device Allocation: AP, SM"
		::= { cambiumPerformanceMonitoring 74 }

txEtherLanDroppedPacketCount OBJECT-TYPE
		SYNTAX	   Counter64
		MAX-ACCESS read-only
		STATUS	   current
		DESCRIPTION
		"Total Ethernet TX drops
		Device Allocation: AP, SM"
		::= { cambiumPerformanceMonitoring 75 }

txEtherLanMulticastPacketCount OBJECT-TYPE
		SYNTAX	   Counter64
		MAX-ACCESS read-only
		STATUS	   current
		DESCRIPTION
		"Total Ethernet TX multicast
		Device Allocation: AP, SM"
		::= { cambiumPerformanceMonitoring 76 }
		
txEtherLanBroadcastPacketCount OBJECT-TYPE
		SYNTAX	   Counter64
		MAX-ACCESS read-only
		STATUS	   current
		DESCRIPTION
		"Total Ethernet TX broadcast
		Device Allocation: AP, SM"
		::= { cambiumPerformanceMonitoring 77 }

txEtherLanMultiBroadcastKbitCount OBJECT-TYPE
		SYNTAX	   Counter64
		MAX-ACCESS read-only
		STATUS	   current
		DESCRIPTION
		"Aggregated total Ethernet TX multicast and broadcast data traffic
		Device Allocation: AP, SM"
		::= { cambiumPerformanceMonitoring 78 }

cambiumStatsResetTimer OBJECT-TYPE
		SYNTAX	   TimeTicks
		MAX-ACCESS read-only
		STATUS	   current
		DESCRIPTION
				"Status time to indicate when is the last time stats are reset
				Device Allocation: AP, SM"
		::= { cambiumPerformanceMonitoring 79 }

ulWLanMCS00Packets OBJECT-TYPE
		SYNTAX	   Counter64
		MAX-ACCESS read-only
		STATUS	   current
		DESCRIPTION
				"Aggregated number of uplink packet received for MCS00
				Device Allocation: AP"
		::= { cambiumPerformanceMonitoring 80 }

ulWLanMCS01Packets OBJECT-TYPE
		SYNTAX	   Counter64
		MAX-ACCESS read-only
		STATUS	   current
		DESCRIPTION
				"Aggregated number of uplink packet received for MCS01
				Device Allocation: AP"
		::= { cambiumPerformanceMonitoring 81 }

ulWLanMCS02Packets OBJECT-TYPE
		SYNTAX	   Counter64
		MAX-ACCESS read-only
		STATUS	   current
		DESCRIPTION
				"Aggregated number of uplink packet received for MCS02
				Device Allocation: AP"
		::= { cambiumPerformanceMonitoring 82 }

ulWLanMCS03Packets OBJECT-TYPE
		SYNTAX	   Counter64
		MAX-ACCESS read-only
		STATUS	   current
		DESCRIPTION
				"Aggregated number of uplink packet received for MCS03
				Device Allocation: AP"
		::= { cambiumPerformanceMonitoring 83 }

ulWLanMCS04Packets OBJECT-TYPE
		SYNTAX	   Counter64
		MAX-ACCESS read-only
		STATUS	   current
		DESCRIPTION
				"Aggregated number of uplink packet received for MCS04
				Device Allocation: AP"
		::= { cambiumPerformanceMonitoring 84 }

ulWLanMCS05Packets OBJECT-TYPE
		SYNTAX	   Counter64
		MAX-ACCESS read-only
		STATUS	   current
		DESCRIPTION
				"Aggregated number of uplink packet received for MCS05
				Device Allocation: AP"
		::= { cambiumPerformanceMonitoring 85 }

ulWLanMCS06Packets OBJECT-TYPE
		SYNTAX	   Counter64
		MAX-ACCESS read-only
		STATUS	   current
		DESCRIPTION
				"Aggregated number of uplink packet received for MCS06
				Device Allocation: AP"
		::= { cambiumPerformanceMonitoring 86 }

ulWLanMCS07Packets OBJECT-TYPE
		SYNTAX	   Counter64
		MAX-ACCESS read-only
		STATUS	   current
		DESCRIPTION
				"Aggregated number of uplink packet received for MCS07
				Device Allocation: AP"
		::= { cambiumPerformanceMonitoring 87 }

ulWLanMCS08Packets OBJECT-TYPE
		SYNTAX	   Counter64
		MAX-ACCESS read-only
		STATUS	   current
		DESCRIPTION
				"Aggregated number of uplink packet received for MCS08
				Device Allocation: AP"
		::= { cambiumPerformanceMonitoring 88 }

ulWLanMCS09Packets OBJECT-TYPE
		SYNTAX	   Counter64
		MAX-ACCESS read-only
		STATUS	   current
		DESCRIPTION
				"Aggregated number of uplink packet received for MCS09
				Device Allocation: AP"
		::= { cambiumPerformanceMonitoring 89 }

ulWLanMCS10Packets OBJECT-TYPE
		SYNTAX	   Counter64
		MAX-ACCESS read-only
		STATUS	   current
		DESCRIPTION
				"Aggregated number of uplink packet received for MCS10
				Device Allocation: AP"
		::= { cambiumPerformanceMonitoring 90 }

ulWLanMCS11Packets OBJECT-TYPE
		SYNTAX	   Counter64
		MAX-ACCESS read-only
		STATUS	   current
		DESCRIPTION
				"Aggregated number of uplink packet received for MCS11
				Device Allocation: AP"
		::= { cambiumPerformanceMonitoring 91 }

ulWLanMCS12Packets OBJECT-TYPE
		SYNTAX	   Counter64
		MAX-ACCESS read-only
		STATUS	   current
		DESCRIPTION
				"Aggregated number of uplink packet received for MCS12
				Device Allocation: AP"
		::= { cambiumPerformanceMonitoring 92 }

ulWLanMCS13Packets OBJECT-TYPE
		SYNTAX	   Counter64
		MAX-ACCESS read-only
		STATUS	   current
		DESCRIPTION
				"Aggregated number of uplink packet received for MCS13
				Device Allocation: AP"
		::= { cambiumPerformanceMonitoring 93 }

ulWLanMCS14Packets OBJECT-TYPE
		SYNTAX	   Counter64
		MAX-ACCESS read-only
		STATUS	   current
		DESCRIPTION
				"Aggregated number of uplink packet received for MCS14
				Device Allocation: AP"
		::= { cambiumPerformanceMonitoring 94 }

ulWLanMCS15Packets OBJECT-TYPE
		SYNTAX	   Counter64
		MAX-ACCESS read-only
		STATUS	   current
		DESCRIPTION
				"Aggregated number of uplink packet received for MCS15
				Device Allocation: AP"
		::= { cambiumPerformanceMonitoring 95 }

dlWLanMCS00Packets OBJECT-TYPE
		SYNTAX	   Counter64
		MAX-ACCESS read-only
		STATUS	   current
		DESCRIPTION
				"Aggregated number of downlink packet received for MCS00
				Device Allocation: AP"
		::= { cambiumPerformanceMonitoring 96 }

dlWLanMCS01Packets OBJECT-TYPE
		SYNTAX	   Counter64
		MAX-ACCESS read-only
		STATUS	   current
		DESCRIPTION
				"Aggregated number of downlink packet received for MCS01
				Device Allocation: AP"
		::= { cambiumPerformanceMonitoring 97 }

dlWLanMCS02Packets OBJECT-TYPE
		SYNTAX	   Counter64
		MAX-ACCESS read-only
		STATUS	   current
		DESCRIPTION
				"Aggregated number of downlink packet received for MCS02
				Device Allocation: AP"
		::= { cambiumPerformanceMonitoring 98 }

dlWLanMCS03Packets OBJECT-TYPE
		SYNTAX	   Counter64
		MAX-ACCESS read-only
		STATUS	   current
		DESCRIPTION
				"Aggregated number of downlink packet received for MCS03
				Device Allocation: AP"
		::= { cambiumPerformanceMonitoring 99 }

dlWLanMCS04Packets OBJECT-TYPE
		SYNTAX	   Counter64
		MAX-ACCESS read-only
		STATUS	   current
		DESCRIPTION
				"Aggregated number of downlink packet received for MCS04
				Device Allocation: AP"
		::= { cambiumPerformanceMonitoring 100 }

dlWLanMCS05Packets OBJECT-TYPE
		SYNTAX	   Counter64
		MAX-ACCESS read-only
		STATUS	   current
		DESCRIPTION
				"Aggregated number of downlink packet received for MCS05
				Device Allocation: AP"
		::= { cambiumPerformanceMonitoring 101 }

dlWLanMCS06Packets OBJECT-TYPE
		SYNTAX	   Counter64
		MAX-ACCESS read-only
		STATUS	   current
		DESCRIPTION
				"Aggregated number of downlink packet received for MCS06
				Device Allocation: AP"
		::= { cambiumPerformanceMonitoring 102 }

dlWLanMCS07Packets OBJECT-TYPE
		SYNTAX	   Counter64
		MAX-ACCESS read-only
		STATUS	   current
		DESCRIPTION
				"Aggregated number of downlink packet received for MCS07
				Device Allocation: AP"
		::= { cambiumPerformanceMonitoring 103 }

dlWLanMCS08Packets OBJECT-TYPE
		SYNTAX	   Counter64
		MAX-ACCESS read-only
		STATUS	   current
		DESCRIPTION
				"Aggregated number of downlink packet received for MCS08
				Device Allocation: AP"
		::= { cambiumPerformanceMonitoring 104 }

dlWLanMCS09Packets OBJECT-TYPE
		SYNTAX	   Counter64
		MAX-ACCESS read-only
		STATUS	   current
		DESCRIPTION
				"Aggregated number of downlink packet received for MCS09
				Device Allocation: AP"
		::= { cambiumPerformanceMonitoring 105 }

dlWLanMCS10Packets OBJECT-TYPE
		SYNTAX	   Counter64
		MAX-ACCESS read-only
		STATUS	   current
		DESCRIPTION
				"Aggregated number of downlink packet received for MCS10
				Device Allocation: AP"
		::= { cambiumPerformanceMonitoring 106 }

dlWLanMCS11Packets OBJECT-TYPE
		SYNTAX	   Counter64
		MAX-ACCESS read-only
		STATUS	   current
		DESCRIPTION
				"Aggregated number of downlink packet received for MCS11
				Device Allocation: AP"
		::= { cambiumPerformanceMonitoring 107 }

dlWLanMCS12Packets OBJECT-TYPE
		SYNTAX	   Counter64
		MAX-ACCESS read-only
		STATUS	   current
		DESCRIPTION
				"Aggregated number of downlink packet received for MCS12
				Device Allocation: AP"
		::= { cambiumPerformanceMonitoring 108 }

dlWLanMCS13Packets OBJECT-TYPE
		SYNTAX	   Counter64
		MAX-ACCESS read-only
		STATUS	   current
		DESCRIPTION
				"Aggregated number of downlink packet received for MCS13
				Device Allocation: AP"
		::= { cambiumPerformanceMonitoring 109 }

dlWLanMCS14Packets OBJECT-TYPE
		SYNTAX	   Counter64
		MAX-ACCESS read-only
		STATUS	   current
		DESCRIPTION
				"Aggregated number of downlink packet received for MCS14
				Device Allocation: AP"
		::= { cambiumPerformanceMonitoring 110 }

dlWLanMCS15Packets OBJECT-TYPE
		SYNTAX	   Counter64
		MAX-ACCESS read-only
		STATUS	   current
		DESCRIPTION
				"Aggregated number of downlink packet received for MCS15
				Device Allocation: AP"
		::= { cambiumPerformanceMonitoring 111 }

syslogServerIPFirst	 OBJECT-TYPE
		SYNTAX	   IpAddress
		MAX-ACCESS read-write
		STATUS	   current
		DESCRIPTION
		"Syslog Server IP Address 1
		Device Allocation: AP, SM"
		::= { cambiumSystemLog 1 }

syslogServerIPSecond  OBJECT-TYPE
		SYNTAX	   IpAddress
		MAX-ACCESS read-write
		STATUS	   current
		DESCRIPTION
		"Syslog Server IP Address 2
		Device Allocation: AP, SM"
		::= { cambiumSystemLog 2 }

syslogServerIPThird	 OBJECT-TYPE
		SYNTAX	   IpAddress
		MAX-ACCESS read-write
		STATUS	   current
		DESCRIPTION
		"Syslog Server IP Address 3
		Device Allocation: AP, SM"
		::= { cambiumSystemLog 3 }

syslogServerIPFourth  OBJECT-TYPE
		SYNTAX	   IpAddress
		MAX-ACCESS read-write
		STATUS	   current
		DESCRIPTION
		"Syslog Server IP Address 4
		Device Allocation: AP, SM"
		::= { cambiumSystemLog 4 }

syslogServerLogToWeb  OBJECT-TYPE
		SYNTAX	   Integer32 (0|1)
		MAX-ACCESS read-write
		STATUS	   current
		DESCRIPTION
		"Enable Log to WEB Interface:
			0 - Disable, 
			1 - Enable
		Device Allocation: AP, SM"
		DEFVAL	{ 0 }
		::= { cambiumSystemLog 5 }

syslogServerLogMask	 OBJECT-TYPE
		SYNTAX	   Integer32 (0..255)
		MAX-ACCESS read-write
		STATUS	   current
		DESCRIPTION
		"Log Level Mask:
			0x00 - all messages, 
			0x01 - emerg,
			0x02 - alert, 
			0x04 - crit,
			0x08 - err,
			0x10 - warning,
			0x20 - notice,
			0x40 - info,
			0x80 - debug
		Device Allocation: AP, SM"
		DEFVAL	{ 0 }
		::= { cambiumSystemLog 6 }

dhcpLanEnable  OBJECT-TYPE
		SYNTAX	   Integer32 (0|1)
		MAX-ACCESS read-write
		STATUS	   current
		DESCRIPTION
		"Local DHCP Server Enable:
			0 - Disable
			1 - Enable
		Device Allocation: SM"
		DEFVAL	{ 0 }
		::= { cambiumDHCP 1 }

dhcpLanStart  OBJECT-TYPE
	SYNTAX	   Integer32 (-2147483647..2147483647)
	MAX-ACCESS read-write
	STATUS	   current
	DESCRIPTION 
		"Local DHCP Server IP Start Address
		Offset from the Network address.
		Device Allocation: SM"
	DEFVAL	{ 1 }
	::= { cambiumDHCP 2 }

dhcpLanLimit  OBJECT-TYPE
	SYNTAX	   Integer32 (-2147483647..2147483647)
	MAX-ACCESS read-write
	STATUS	   current
	DESCRIPTION 
		"Local DHCP Server IP End Address
		Offset from the Network address.
		Device Allocation: SM"
	DEFVAL	{ 10 }
	::= { cambiumDHCP 3 }

dhcpLanLeasetime  OBJECT-TYPE
	SYNTAX	   Integer32 (0..24)
	MAX-ACCESS read-write
	STATUS	   current
	DESCRIPTION 
		"Local DHCP Lease Setup in hours
		Valid Range: 1 hour - 24 hours
		Device Allocation: SM"
	DEFVAL	{ 24 }
	::= { cambiumDHCP 4 }
	
dhcpLanHostTable  OBJECT-TYPE
	SYNTAX SEQUENCE OF DhcpLanHostEntry
	MAX-ACCESS not-accessible
	STATUS	   current
	DESCRIPTION 
		"Table for DHCP Hosts
		Device Allocation: SM"
	::= { cambiumDHCP 5 }

dhcpLanHostEntry  OBJECT-TYPE
	SYNTAX	DhcpLanHostEntry
	MAX-ACCESS not-accessible
	STATUS	   current
	DESCRIPTION 
		"DHCP Hosts Table Entry
		Device Allocation: SM"
	INDEX	{ dhcpLanHostIndex }
	::= { dhcpLanHostTable 1 }

DhcpLanHostEntry ::= SEQUENCE {
	dhcpLanHostIndex
		Integer32,
	dhcpLanHostIP
		IpAddress,
	dhcpLanHostMAC
		DisplayString,
	dhcpLanHostName
		DisplayString
}

dhcpLanHostIndex OBJECT-TYPE
		SYNTAX	   Integer32 (0..8)
		MAX-ACCESS read-write
		STATUS	   current
		DESCRIPTION
		"DHCP host Table Index
		Table Entry is cleared if Index is set to zero
		Device Allocation: SM"
		::= { dhcpLanHostEntry 1 }

dhcpLanHostIP  OBJECT-TYPE
	SYNTAX	   IpAddress
	MAX-ACCESS read-write
	STATUS	   current
	DESCRIPTION 
		"DHCP Lan Host IP
		'ignore' or the IP address to be used for DHCP host
		Device Allocation: SM"
	::= { dhcpLanHostEntry 2 }

dhcpLanHostMAC	OBJECT-TYPE
	SYNTAX	   DisplayString (SIZE(0|17))
	MAX-ACCESS read-write
	STATUS	   current
	DESCRIPTION 
		"The hardware address of this host
		Device Allocation: SM"
	::= { dhcpLanHostEntry 3 }

dhcpLanHostName	 OBJECT-TYPE
	SYNTAX	   DisplayString (SIZE(0|1..128))
	MAX-ACCESS read-write
	STATUS	   current
	DESCRIPTION 
		"Optional hostname to assign
		Device Allocation: SM"
	::= { dhcpLanHostEntry 4 }

dhcpOption82  OBJECT-TYPE
		SYNTAX	   Integer32 (0|1)
		MAX-ACCESS read-write
		STATUS	   current
		DESCRIPTION
				"DHCP Option82:
				 0 - Disable
				 1 - Enable
				Device Allocation: AP"
		DEFVAL	{ 0 }
		::= { cambiumDHCP 6 }

cambiumSSHServerEnable	OBJECT-TYPE
		SYNTAX	   Integer32 (0|1)
		MAX-ACCESS read-write
		STATUS	   current
		DESCRIPTION
				"Cambium SSH Server:
						0 - Disable,
						1 - Enable
				Device Allocation: AP, SM"
	DEFVAL	{ 1 }
		::= { cambiumSSHServer 1 }

networkMode	 OBJECT-TYPE
		SYNTAX	   Integer32 (1|2|3)
		MAX-ACCESS read-write
		STATUS	   current
		DESCRIPTION
		"SM Network Mode:
			1 - NAT,
			2 - Bridge,
			3 - Router
		Device Allocation: SM"
		::= { network 1 }

networkSTP OBJECT-TYPE
		SYNTAX	   Integer32 (0|1)
		MAX-ACCESS read-write
		STATUS	   current
		DESCRIPTION
		"Spanning Tree Protocol:
			0 - Disable STP (Default mode)
			1 - Enable STP
		Device Allocation: AP, SM"
		DEFVAL	{ 0 }
		::= { network 6 }

networkLanIPAddressMode	 OBJECT-TYPE
	SYNTAX	   Integer32 (1|2)
	MAX-ACCESS read-write
	STATUS	   current
	DESCRIPTION 
		"SM NAT LAN IP Address Mode
			1 - Static, 
			2 - DHCP
		Device Allocation: AP, SM"
	DEFVAL	{ 1 }
	::= { networkLan 1 }

networkLanIPAddr  OBJECT-TYPE
	SYNTAX	   IpAddress
	MAX-ACCESS read-write
	STATUS	   current
	DESCRIPTION 
		"SM NAT LAN IP Address
		Device Allocation: SM"
	::= { networkLan 2 }

networkLanNetmask  OBJECT-TYPE
	SYNTAX	   IpAddress
	MAX-ACCESS read-write
	STATUS	   current
	DESCRIPTION 
		"SM NAT LAN IP Subnet Mask
		Device Allocation: SM"
	::= { networkLan 3 }

networkLanGatewayIP	 OBJECT-TYPE
	SYNTAX	   IpAddress
	MAX-ACCESS read-write
	STATUS	   current
	DESCRIPTION 
		"SM NAT LAN Gateway IP Address
		Device Allocation: SM"
	::= { networkLan 4 }

networkLanDNSIPAddr	 OBJECT-TYPE
	SYNTAX	   IpAddress
	MAX-ACCESS read-write
	STATUS	   obsolete
	DESCRIPTION
		"SM NAT LAN DNS Server IP Address
		Device Allocation: SM"
	::= { networkLan 5 }

networkLanMTU  OBJECT-TYPE
	SYNTAX	   Integer32 (0|576..1700)
	MAX-ACCESS read-write
	STATUS	   current
	DESCRIPTION
		"SM NAT LAN MTU size
		Device Allocation: SM"
	DEFVAL	{ 1500 }
	::= { networkLan 6 }

networkLanDNSIPAddrPrimary	OBJECT-TYPE
	SYNTAX	   IpAddress
	MAX-ACCESS read-write
	STATUS	   current
	DESCRIPTION 
		"SM NAT LAN DNS Server IP Address
		Device Allocation: SM
		Primary Server IP"
	::= { networkLan 7 }

networkLanDNSIPAddrSecondary  OBJECT-TYPE
	SYNTAX	   IpAddress
	MAX-ACCESS read-write
	STATUS	   current
	DESCRIPTION
		"SM NAT LAN DNS Server IP Address
		Device Allocation: SM
		Secondary Server IP"
	::= { networkLan 8 }

networkLanAutoNegotiation  OBJECT-TYPE
	SYNTAX	   Integer32 (0|1)
	MAX-ACCESS read-write
	STATUS	   current
	DESCRIPTION
		"Lan Autonegotiation 
			0 - Disable,
			1 - Enable
		Device Allocation: AP, SM"
		DEFVAL	{ 1 }
	::= { networkLan 9 }

networkLanSpeed	 OBJECT-TYPE
	SYNTAX	   Integer32 (10|100|1000)
	MAX-ACCESS read-write
	STATUS	   current
	DESCRIPTION
		"LAN Speed 
			10	 - 10 Mb/s,
			100	 - 100 Mb/s,
			1000 - 1000 Mb/s
		Device Allocation: AP, SM"
		DEFVAL	{ 100 }
	::= { networkLan 10 }

networkLanDuplex  OBJECT-TYPE
	SYNTAX	   Integer32 (0|1)
	MAX-ACCESS read-write
	STATUS	   current
	DESCRIPTION
		"LAN Duplex Mode 
			0 - Half,
			1 - Full
		Device Allocation: AP, SM"
		DEFVAL	{ 1 }
	::= { networkLan 11 }
	
networkBroadcastStormEnabled  OBJECT-TYPE
	SYNTAX	   Integer32 (0|1)
	MAX-ACCESS read-write
	STATUS	   current
	DESCRIPTION
		"Broadcast Strom Control 
			0 - Disabled,
			1 - Enabled
		Device Allocation: AP, SM"
		DEFVAL	{ 0 }
	::= { networkLan 12 }
	
networkBroadcastStormRate  OBJECT-TYPE
	SYNTAX	   Integer32 (0..16000)
	MAX-ACCESS read-write
	STATUS	   current
	DESCRIPTION
		"Broadcast Strom Control Rate
			in frames per second
		Device Allocation: AP, SM"
		DEFVAL	{ 0 }
	::= { networkLan 13 }

networkLan2Enabled	OBJECT-TYPE
	SYNTAX	   Integer32 (0|1)
	MAX-ACCESS read-write
	STATUS	   current
	DESCRIPTION
		"AUX Lan Port Enabled 
			0 - Disable,
			1 - Enable
		Device Allocation: AP, SM"
		DEFVAL	{ 1 }
	::= { networkLan 20 }

networkLan2AutoNegotiation	OBJECT-TYPE
	SYNTAX	   Integer32 (0|1)
	MAX-ACCESS read-write
	STATUS	   current
	DESCRIPTION
		"Lan Autonegotiation 
			0 - Disable,
			1 - Enable
		Device Allocation: AP, SM"
		DEFVAL	{ 1 }
	::= { networkLan 21 }

networkLan2Speed  OBJECT-TYPE
	SYNTAX	   Integer32 (10|100)
	MAX-ACCESS read-write
	STATUS	   current
	DESCRIPTION
		"LAN Speed 
			10	 - 10 Mb/s,
			100	 - 100 Mb/s
		Device Allocation: AP, SM"
		DEFVAL	{ 100 }
	::= { networkLan 22 }

networkLan2Duplex  OBJECT-TYPE
	SYNTAX	   Integer32 (0|1)
	MAX-ACCESS read-write
	STATUS	   current
	DESCRIPTION
		"LAN Duplex Mode 
			0 - Half,
			1 - Full
		Device Allocation: AP, SM"
		DEFVAL	{ 1 }
	::= { networkLan 23 }
	
networkLan2PoEEnabled  OBJECT-TYPE
	SYNTAX	   Integer32 (0|1)
	MAX-ACCESS read-write
	STATUS	   current
	DESCRIPTION
		"PoE Enabled 
			0 - Disabled,
			1 - Enabled
		Device Allocation: SM"
		DEFVAL	{ 1 }
	::= { networkLan 24 }

networkLanEnabled  OBJECT-TYPE
	SYNTAX	   Integer32 (0|1)
	MAX-ACCESS read-write
	STATUS	   current
	DESCRIPTION
		"Lan Port Enabled
			0 - Disable,
			1 - Enable
		Device Allocation: SM"
		DEFVAL	{ 1 }
	::= { networkLan 25 }

networkWanIPAddressMode	 OBJECT-TYPE
		SYNTAX	   Integer32 (1|2)
		MAX-ACCESS read-write
		STATUS	   current
		DESCRIPTION
		"SM NAT WAN IP Address Mode
			1 - Static, 
			2 - DHCP
		Device Allocation: SM"
		DEFVAL	{ 1 }
		::= { networkWan 1 }

networkWanIPAddr  OBJECT-TYPE
		SYNTAX	   IpAddress
		MAX-ACCESS read-write
		STATUS	   current
		DESCRIPTION
		"SM NAT WAN IP Address
		Device Allocation: SM"
		::= { networkWan 2 }
		
networkWanNetmask  OBJECT-TYPE
		SYNTAX	   IpAddress
		MAX-ACCESS read-write
		STATUS	   current
		DESCRIPTION
		"SM NAT WAN IP Subnet Mask
		Device Allocation: SM"
		::= { networkWan 3 }

networkWanGatewayIP	 OBJECT-TYPE
		SYNTAX	   IpAddress
		MAX-ACCESS read-write
		STATUS	   current
		DESCRIPTION
		"SM NAT WAN Gateway IP Address
		Device Allocation: SM"
		::= { networkWan 4 }

networkWanDNSIPAddr	 OBJECT-TYPE
	SYNTAX	   IpAddress
	MAX-ACCESS read-write
	STATUS	   obsolete
	DESCRIPTION
		"SM NAT WAN DNS Server IP Address
		Device Allocation: SM"
	::= { networkWan 5 }

networkWanMTU  OBJECT-TYPE
	SYNTAX	   Integer32 (0|576..1700)
	MAX-ACCESS read-write
	STATUS	   current
	DESCRIPTION
		"SM NAT WAN MTU size
		Device Allocation: SM"
	DEFVAL	{ 1500 }
	::= { networkWan 6 }

networkWanDNSIPAddrPrimary	OBJECT-TYPE
	SYNTAX	   IpAddress
	MAX-ACCESS read-write
	STATUS	   current
	DESCRIPTION
		"SM NAT WAN DNS Server IP Address
		Device Allocation: SM
		Primary Server IP"
	::= { networkWan 7 }

networkWanDNSIPAddrSecondary  OBJECT-TYPE
	SYNTAX	   IpAddress
	MAX-ACCESS read-write
	STATUS	   current
	DESCRIPTION
		"SM NAT WAN DNS Server IP Address
		Device Allocation: SM
		Secondary Server IP"
	::= { networkWan 8 }

networkWanPPPoE	 OBJECT-TYPE
		SYNTAX	   Integer32 (0|1)
		MAX-ACCESS read-write
		STATUS	   current
		DESCRIPTION
		"SM only.Enable or Disable PPPoE
		mode. 1 is enable 0 is disable"
		DEFVAL	{ 0 }
		::= { networkWan 9 }
		
networkWanPPPoEUsername	 OBJECT-TYPE
		SYNTAX	   DisplayString (SIZE(0..128))
		MAX-ACCESS read-write
		STATUS	   current
		DESCRIPTION
		"SM only.Username to authenticate with
		PPPoE Server"
		::= { networkWan 10 }
		
networkWanPPPoEPassword	 OBJECT-TYPE
		SYNTAX	   DisplayString (SIZE(0..128))
		MAX-ACCESS read-write
		STATUS	   current
		DESCRIPTION
		"SM only.Password to authenticate with
		PPPoE Server"
		::= { networkWan 11 }
		
networkWanPPPoEAC  OBJECT-TYPE
		SYNTAX	   DisplayString (SIZE(0..128))
		MAX-ACCESS read-write
		STATUS	   current
		DESCRIPTION
		"SM only.PPPoE Access Concentrator Name"
		::= { networkWan 12 }
		
networkWanPPPoEService	OBJECT-TYPE
		SYNTAX	   DisplayString (SIZE(0..128))
		MAX-ACCESS read-write
		STATUS	   current
		DESCRIPTION
		"SM only.PPPoE Service Name"
		::= { networkWan 13 }
		
networkWanPPPoEAuth	 OBJECT-TYPE
		SYNTAX	   Integer32 (0|1|2)
		MAX-ACCESS read-write
		STATUS	   current
		DESCRIPTION
		"SM only.This indicates type of authentication
		with PPPoE Server. Options are
		0 - All
		1 - PAP
		2 - CHAP"
		DEFVAL	{ 0 }
		::= { networkWan 14 }
		
networkWanPPPoEMTU	OBJECT-TYPE
		SYNTAX	   Integer32 (0|576..1492)
		MAX-ACCESS read-write
		STATUS	   current
		DESCRIPTION
		"SM only.MTU size to be used for PPPoE
		connection"
		DEFVAL	{ 1492 }
		::= { networkWan 15 }
		
networkWanPPPoEKeepAlive OBJECT-TYPE
		SYNTAX	   Integer32 (0|5..180)
		MAX-ACCESS read-write
		STATUS	   current
		DESCRIPTION
		"SM only.Time in seconds for the keep Alive
		messages from PPPoE client to PPPoE
		Server"
		DEFVAL	{ 10 }
		::= { networkWan 16 }
		
networkWanPPPoEMSSClamping OBJECT-TYPE
		SYNTAX	   Integer32 (0|1)
		MAX-ACCESS read-write
		STATUS	   current
		DESCRIPTION
		"SM only.Enable or disable MSS Clamping
		0 - Disable
		1 - Enable"
		DEFVAL	{ 0 }
		::= { networkWan 17 }		
		
networkBridgeIPAddressMode	OBJECT-TYPE
	SYNTAX	   Integer32 (1|2)
	MAX-ACCESS read-write
	STATUS	   current
	DESCRIPTION 
		"Device Bridge IP Address Mode
			1 - Static, 
			2 - DHCP
		Device Allocation: AP, SM"
	DEFVAL	{ 1 }
	::= { networkBridge 1 }

networkBridgeIPAddr	 OBJECT-TYPE
	SYNTAX	   IpAddress
	MAX-ACCESS read-write
	STATUS	   current
	DESCRIPTION 
		"Device Bridge IP Address
		Device Allocation: AP, SM"
	::= { networkBridge 2 }

networkBridgeNetmask  OBJECT-TYPE
	SYNTAX	   IpAddress
	MAX-ACCESS read-write
	STATUS	   current
	DESCRIPTION 
		"Device Bridge IP Subnet Mask
		Device Allocation: AP, SM"
	::= { networkBridge 3 }

networkBridgeGatewayIP	OBJECT-TYPE
	SYNTAX	   IpAddress
	MAX-ACCESS read-write
	STATUS	   current
	DESCRIPTION 
		"Device Bridge Gateway IP Address
		Device Allocation: AP, SM"
	::= { networkBridge 4 }

networkBridgeDNSIPAddr	OBJECT-TYPE
	SYNTAX	   IpAddress
	MAX-ACCESS read-write
	STATUS	   obsolete
	DESCRIPTION
		"Device Bridge DNS Server IP Address
		Device Allocation: AP, SM"
	::= { networkBridge 5 }

networkBridgeMTU  OBJECT-TYPE
	SYNTAX	   Integer32 (0|576..1700)
	MAX-ACCESS read-write
	STATUS	   current
	DESCRIPTION
		"Device Bridge MTU size
		Device Allocation: AP, SM"
	DEFVAL	{ 1500 }
	::= { networkBridge 6 }

networkBridgeDNSIPAddrPrimary  OBJECT-TYPE
	SYNTAX	   IpAddress
	MAX-ACCESS read-write
	STATUS	   current
	DESCRIPTION
		"Device Bridge DNS Server IP Address
		Device Allocation: AP, SM
		Primary Server IP"
	::= { networkBridge 7 }

networkBridgeDNSIPAddrSecondary	 OBJECT-TYPE
	SYNTAX	   IpAddress
	MAX-ACCESS read-write
	STATUS	   current
	DESCRIPTION
		"Device Bridge DNS Server IP Address
		Device Allocation: AP, SM
		Secondary Server IP"
	::= { networkBridge 8 }

networkPortSecurity OBJECT-TYPE
		SYNTAX	   Integer32 (0|1)
		MAX-ACCESS read-write
		STATUS	   current
		DESCRIPTION
				"LAN Port Security switch:
						0 - Disable
						1 - Enable
				Device Allocation: SM"
		DEFVAL	{ 0 }
		::= { network 8 }

networkPortSecurityMax OBJECT-TYPE
		SYNTAX	   Integer32 (0..255)
		MAX-ACCESS read-write
		STATUS	   current
		DESCRIPTION
			"Number of secure MAC addresses:
						1-254 - Fixed Learned MAC limit
				Device Allocation: SM"
		DEFVAL	{ 5 }
		::= { network 9 }

networkPortSecurityAgingTime OBJECT-TYPE
		SYNTAX	   Integer32 (0..1440)
		MAX-ACCESS read-write
		STATUS	   current
		DESCRIPTION
				"Security MAC address aging time:
						This prameter indicates on how long to store learned MAC address in the cache in seconds,
						0 - do not delete MAC address from the buffer,
						Default - is 300 seconds.
				Device Allocation: AP, SM"
		DEFVAL	{ 300 }
		::= { network 10 }

mcastGroupLimit OBJECT-TYPE
		SYNTAX	   Integer32 (0|1..5)
		MAX-ACCESS read-write
		STATUS	   current
		DESCRIPTION
				"Multicast Group Limit:
						Default - 3 Multicast Groups for SM, unlimited for AP.
				Device Allocation: SM"
		DEFVAL	{ 3 }
		::= { network 17 }

mgmtIFEnable OBJECT-TYPE
		SYNTAX	   Integer32 (0|1)
		MAX-ACCESS read-write
		STATUS	   current
		DESCRIPTION
				"Separate Management Interface Enabled:
				0 - Disabled,
				1 - Enabled
				Device Allocation: SM"
		DEFVAL	{ 0 }
		::= { mgmtIF 1 }

mgmtIFVLAN OBJECT-TYPE
		SYNTAX	   Integer32 (0|1)
		MAX-ACCESS read-write
		STATUS	   current
		DESCRIPTION
				"Separate Management Interface VLAN Enabled:
				0 - Disabled,
				1 - Enabled
				Device Allocation: SM"
		DEFVAL	{ 0 }
		::= { mgmtIF 2 }

mgmtIFVID OBJECT-TYPE
		SYNTAX	   Integer32 (0..4094)
		MAX-ACCESS read-write
		STATUS	   current
		DESCRIPTION
				"Separate Management Interface VLAN
				Device Allocation: SM"
		::= { mgmtIF 3 }

mgmtIFVP OBJECT-TYPE
		SYNTAX	   Integer32 (0..7)
		MAX-ACCESS read-write
		STATUS	   current
		DESCRIPTION
				"Separate Management Interface VP
				Device Allocation: SM"
		::= { mgmtIF 4 }

mgmtIFIPAddressMode OBJECT-TYPE
		SYNTAX	   Integer32 (1|2)
		MAX-ACCESS read-write
		STATUS	   current
		DESCRIPTION
				"Separate Management IP Address Mode
			1 - Static,
			2 - DHCP
		Device Allocation: SM"
		::= { mgmtIF 5 }

mgmtIFIPAddr OBJECT-TYPE
		SYNTAX	   IpAddress
		MAX-ACCESS read-write
		STATUS	   current
		DESCRIPTION
				"Separate Management IP Address
				Device Allocation: SM"
		::= { mgmtIF 6 }

mgmtIFNetmask OBJECT-TYPE
		SYNTAX	   IpAddress
		MAX-ACCESS read-write
		STATUS	   current
		DESCRIPTION
				"Separate Management IP Subnet Mask
				Device Allocation: SM"
		::= { mgmtIF 7 }

mgmtIFGateway OBJECT-TYPE
		SYNTAX	   IpAddress
		MAX-ACCESS read-write
		STATUS	   current
		DESCRIPTION
				"Separate Management IP Gateway
				Device Allocation: SM"
		::= { mgmtIF 8 }

cambiumIPAliasCnfTable	 OBJECT-TYPE
	SYNTAX SEQUENCE OF CambiumIPAliasCnfEntry
	MAX-ACCESS not-accessible
	STATUS	   current
	DESCRIPTION
		"Static Network Table"
	::= { networkAliases 1 }

cambiumIPAliasCnfEntry OBJECT-TYPE
	SYNTAX	   CambiumIPAliasCnfEntry
	MAX-ACCESS not-accessible
	STATUS	   current
	DESCRIPTION
		"Static Network Table Entry
		Device Allocation: SM"
	INDEX	{ cambiumIPAliasesIndex }
	::= { cambiumIPAliasCnfTable 1 }

CambiumIPAliasCnfEntry ::= SEQUENCE {
	cambiumIPAliasesIndex
		Integer32,
	cambiumIPAliasesIpAddr
		IpAddress,
	cambiumIPAliasesNetmask
		IpAddress,
	cambiumIPAliasesInfo
		DisplayString
}

cambiumIPAliasesIndex OBJECT-TYPE
	SYNTAX	   Integer32 (0..16)
	MAX-ACCESS read-write 
	STATUS	   current
	DESCRIPTION
	"IP Alias Table Index
	Table Entry is cleared if Index is set to zero
	Device Allocation: AP, SM"
	::= { cambiumIPAliasCnfEntry 1 }

cambiumIPAliasesIpAddr	OBJECT-TYPE
	SYNTAX	   IpAddress
	MAX-ACCESS read-write
	STATUS	   current
	DESCRIPTION 
		"Network IP Alliases address"
	::= { cambiumIPAliasCnfEntry 2 }

cambiumIPAliasesNetmask OBJECT-TYPE
	SYNTAX		IpAddress
	MAX-ACCESS	read-write
	STATUS		current
	DESCRIPTION 
		"Network Dest IP Netmask"
	::= { cambiumIPAliasCnfEntry 3 }

cambiumIPAliasesInfo  OBJECT-TYPE
	SYNTAX	   DisplayString (SIZE(0..128))
	MAX-ACCESS read-write
	STATUS	   current
	DESCRIPTION
		"Network Info message"
	::= { cambiumIPAliasCnfEntry 4 }

cambiumIPAliasesEnable	OBJECT-TYPE
	SYNTAX	   Integer32 (0|1)
	MAX-ACCESS read-write
	STATUS	   current
	DESCRIPTION
		"Enable/Disable IP Aliases in Router mode
		Device Allocation: SM"
	::= { networkAliases 2 }

networkLanDefaultIP OBJECT-TYPE
		SYNTAX	   IpAddress
		MAX-ACCESS read-write
		STATUS	   current
		DESCRIPTION
				"Default Network IP
				Device Allocation: SM"
		::= { network 25 }

networkRelaydEnable OBJECT-TYPE
		SYNTAX	   Integer32 (0|1)
		MAX-ACCESS read-write
		STATUS	   current
		DESCRIPTION
		"Relay for forwarding DHCP packets:
			0 - Disable
			1 - Enable
		Device Allocation: AP,SM"
	DEFVAL	{ 0 }
	::= { network 26 }

networkUPNP OBJECT-TYPE
        SYNTAX     Integer32 (0|1)
        MAX-ACCESS read-write
        STATUS     current
        DESCRIPTION
                "Enable UPnP on SM in NAT mode
                0 - Disable,
                1 - Enable
                Device Allocation: SM"
        ::= { upnpd 1 }

networkNATPMP OBJECT-TYPE
        SYNTAX     Integer32 (0|1)
        MAX-ACCESS read-write
        STATUS     current
        DESCRIPTION
                "Enable NAT-PMP on SM in NAT mode
                0 - Disable,
                1 - Enable
                Device Allocation: SM"
        ::= { upnpd 2 }

networkLLDP OBJECT-TYPE
        SYNTAX     Integer32 (0|1)
        MAX-ACCESS read-write
        STATUS     current
        DESCRIPTION
                "Enable LLDP
                0 - Disable,
                1 - Enable
                Device Allocation: AP,SM"
        ::= { lldpd 1 }

networkLLDPMode OBJECT-TYPE
        SYNTAX     Integer32 (1|2)
        MAX-ACCESS read-write
        STATUS     current
        DESCRIPTION
                "LLDP mode
				1 - receive and transmit LLDPDU
				2 - only receive LLDPDU
                Device Allocation: AP,SM"
        ::= { lldpd 2 }

snmpReadOnlyCommunity  OBJECT-TYPE
	SYNTAX	   DisplayString
	MAX-ACCESS read-write
	STATUS	   current
	DESCRIPTION 
		"SNMP read-only community name
		Device Allocation: AP, SM"
	DEFVAL	{ "public" }
	::= { snmp 1 }

snmpReadWriteCommunity	OBJECT-TYPE
	SYNTAX	   DisplayString
	MAX-ACCESS read-write
	STATUS	   current
	DESCRIPTION 
		"SNMP read-write community name
		Device Allocation: AP, SM"
	DEFVAL	{ "private" }
	::= { snmp 2 }

snmpSystemName	OBJECT-TYPE
	SYNTAX	   DisplayString
	MAX-ACCESS read-write
	STATUS	   current
	DESCRIPTION 
		"SNMP System Name
		Device Allocation: AP, SM"
	DEFVAL	{ "CambiumNetworks" }
	::= { snmp 3 }

snmpSystemDescription  OBJECT-TYPE
	SYNTAX	   DisplayString
	MAX-ACCESS read-write
	STATUS	   current
	DESCRIPTION 
		"SNMP System Description
		Device Allocation: AP, SM"
	::= { snmp 4 }

snmpTrapEnable	OBJECT-TYPE
		SYNTAX	   Integer32 (0|1)
		MAX-ACCESS read-write
		STATUS	   current
		DESCRIPTION
		"SNMP Trap Support Enable
			0 - Disable, 
			1 - Enable
		Device Allocation: AP, SM"
		DEFVAL	{ 0 }
		::= { snmp 5 }

snmpTrapCommunity  OBJECT-TYPE
		SYNTAX	   DisplayString
		MAX-ACCESS read-write
		STATUS	   current
		DESCRIPTION
		"SNMP Trap Community
		Device Allocation: AP, SM"
		::= { snmp 6 }

snmpTrapTable  OBJECT-TYPE
		SYNTAX SEQUENCE OF SNMPTrapEntry
		MAX-ACCESS not-accessible
		STATUS	   current
		DESCRIPTION
		"SNMP Trap Servers Table
		Device Allocation: AP, SM"
		::= { snmp 7 }

snmpTrapEntry  OBJECT-TYPE
		SYNTAX	SNMPTrapEntry
		MAX-ACCESS not-accessible
		STATUS	   current
		DESCRIPTION
		"SNMP Trap Table Entry
		Device Allocation: AP, SM"
		INDEX	{ snmpTrapEntryIndex }
		::= { snmpTrapTable 1 }

SNMPTrapEntry ::= SEQUENCE {
		snmpTrapEntryIndex
				Integer32,
		snmpTrapEntryIP
				IpAddress,
		snmpTrapEntryPort
				Integer32
}

snmpTrapEntryIndex OBJECT-TYPE
		SYNTAX	   Integer32 (0..4)
		MAX-ACCESS read-write
		STATUS	   current
		DESCRIPTION
		"SNMP Trap Server IP Table Index
		Table Entry is cleared if Index is set to zero
		Device Allocation: AP, SM"
		::= { snmpTrapEntry 1 }

snmpTrapEntryIP OBJECT-TYPE
		SYNTAX	   IpAddress
		MAX-ACCESS read-write
		STATUS	   current
		DESCRIPTION
		"SNMP Trap Server IP Address
		Device Allocation: AP, SM"
		::= { snmpTrapEntry 2 }

snmpTrapEntryPort OBJECT-TYPE
		SYNTAX	   Integer32 (0..65535)
		MAX-ACCESS read-write
		STATUS	   current
		DESCRIPTION
		"SNMP Trap Server Port Number
		Device Allocation: AP, SM"
		DEFVAL	{ 162 }
		::= { snmpTrapEntry 3 }

snmpDomainAccessEnable	OBJECT-TYPE
		SYNTAX	   Integer32 (0|1)
		MAX-ACCESS read-write
		STATUS	   current
		DESCRIPTION
		"SNMP Access Domain Enable
			0 - Disable, 
			1 - Enable
		Device Allocation: AP, SM"
		DEFVAL	{ 0 }
		::= { snmp 8 }

snmpDomainAccessIP OBJECT-TYPE
		SYNTAX	   DisplayString(SIZE(0|7..15))
		MAX-ACCESS read-write
		STATUS	   current
		DESCRIPTION
		"SNMP Access Domain IP Address
		Device Allocation: AP, SM"
		::= { snmp 9 }

snmpDomainAccessIPMask OBJECT-TYPE
		SYNTAX	   DisplayString(SIZE(0|7..15))
		MAX-ACCESS read-write
		STATUS	   current
		DESCRIPTION
		"SNMP Access Domain IP Mask
		Device Allocation: AP, SM"
		::= { snmp 10 }

systemConfigTimezone  OBJECT-TYPE
	SYNTAX	   DisplayString
	MAX-ACCESS read-write
	STATUS	   current
	DESCRIPTION 
		"Time Zone
		Device Allocation: AP, SM"
	DEFVAL	{ "GMT" }
	::= { systemConfig 1 }

systemConfigDeviceName	OBJECT-TYPE
		SYNTAX	   DisplayString (SIZE(0|1..128))
		MAX-ACCESS read-write
		STATUS	   current
		DESCRIPTION
		"SM Device Name
		Device Allocation: AP, SM"
		DEFVAL	{ "Cambium-STA" }
		::= { systemConfig 2 }
		
systemConfigETSILicense	 OBJECT-TYPE
		SYNTAX	   DisplayString (SIZE(0..128))
		MAX-ACCESS read-write
		STATUS	   obsolete
		DESCRIPTION
		"ETSI Country Code. 
		Set the country code using license key on AP. Visit Cambium Webserver
		to get the license key. The country code set in license key will
		be used to set country code on AP if the key validation pass. This 
		parameter is for AP only.
		Device Allocation: AP"
		DEFVAL	{ "ETSIkey" }
		::= { systemConfig 3 }		  

systemConfigSWLockBit  OBJECT-TYPE
		SYNTAX	   Integer32 (0|1)
		MAX-ACCESS read-only
		STATUS	   current
		DESCRIPTION
		"Software Lock Bit.
		This bit indicates if the Software Lock Bit is set or not.
		If the software bit is set then country code needs to be
		set using License Key from Cambium Webserver
			0 - Bit not Set, 
			1 - Bit is set
		Device Allocation: AP, SM"
		DEFVAL	{ 0 }
		::= { systemConfig 4 } 

systemConfigHWLockBit  OBJECT-TYPE
		SYNTAX	   Integer32 (0|1)
		MAX-ACCESS read-only
		STATUS	   current
		DESCRIPTION
		"Hardware Lock Bit.
		This bit indicates if the hardware Lock Bit is set or not.
		If the hardware bit is set then country code cannot be changed.
			0 - Bit not Set, 
			1 - Bit is set
		Device Allocation: AP, SM"
		DEFVAL	{ 0 }
		::= { systemConfig 5 }								  

systemDeviceLocLatitude	 OBJECT-TYPE
		SYNTAX	   DisplayString (SIZE(0..128))
		MAX-ACCESS read-write
		STATUS	   current
		DESCRIPTION
		"Device GPS Location Latitude.
		Coordinates of device in (h ddd.ddddd) format.
		Used to display location at Google Maps service.
		Device Allocation: AP, SM"
		::= { systemConfig 6 }

systemDeviceLocLongitude  OBJECT-TYPE
		SYNTAX	   DisplayString (SIZE(0..128))
		MAX-ACCESS read-write
		STATUS	   current
		DESCRIPTION
		"Device GPS Location Longitude.
		Coordinates of device in (h ddd.ddddd) format.
		Used to display location at Google Maps service.
		Device Allocation: AP, SM"
		::= { systemConfig 7 }
		
systemDeviceLocHeight  OBJECT-TYPE
		SYNTAX	   DisplayString (SIZE(0..128))
		MAX-ACCESS read-write
		STATUS	   current
		DESCRIPTION
		"Device GPS Location Longitude.
		Altitude of device above/below mean sea level.
		Device Allocation: AP, SM"
		::= { systemConfig 8 }

-- skip systemConfig 9 for GPSKey License

systemConfigisGPSkeyOK  OBJECT-TYPE
        SYNTAX     Integer32 (0|1)
        MAX-ACCESS read-only
        STATUS     obsolete
        DESCRIPTION
		"GPS Lock.
		This field indicates if the GPS Key is OK. Based on this the GPS
		is locked on the board.
			0 - GPS Key is bad. Sync Source defaulted to Internal GPS only
			1 - GPS Key is good. User can set sync source to any value 
		Device Allocation: AP"
        DEFVAL  { 0 }
        ::= { systemConfig 10 }

systemConfigGPSLockBit  OBJECT-TYPE
        SYNTAX     Integer32 (0..2)
        MAX-ACCESS read-only
        STATUS     obsolete
        DESCRIPTION
                "GPS Lock Bit.
                This bit indicates if the GPS feature Lock Bit is set or not.
                If the hardware bit is set then GPS synchronisation can't be used.
                        0 - No limitation of usage GPS synchronisation,
                        1 - GPS synchronisation not allowed,
                        2 - The GPSkey required to allow synchronisation
                Device Allocation: AP"
        DEFVAL  { 0 }
        ::= { systemConfig 11 }

systemConfigSMLockBit  OBJECT-TYPE
        SYNTAX     Integer32 (0..2)
        MAX-ACCESS read-only
        STATUS     current
        DESCRIPTION
		"SM Lock Bit
                This bit indicates if the AP is locked for Maximum SM registrations support.
                If the bit is set then maximum of 10 SMs can be registered on the AP.
                        0 - No limitation, up to 120 SM registrations are supported,
                        1 - AP is tiered with 10 SM registrations
                Device Allocation: AP"
        DEFVAL  { 0 }
        ::= { systemConfig 12 }

systemConfigSMLimit  OBJECT-TYPE
        SYNTAX     Integer32 (0..120)
        MAX-ACCESS read-only
        STATUS     current
        DESCRIPTION
		"SM Registrations limit, based on Operational License content.
		Indicates the maximum number of SMs with could be registered to an AP.
		Valid only in TDD mode if device is AP Lite.
		Device Allocation: AP"
        DEFVAL  { 0 }
        ::= { systemConfig 13 }
		
powerSequenceFactoryDefault OBJECT-TYPE
	SYNTAX	   Integer32 (0|1)
	MAX-ACCESS read-write
	STATUS	   current
	DESCRIPTION
		"Set this to enable or disable the ability to factory default the radio's 
		configuration using the power cycle sequence(explained in the User Guide). 
			0 - Disabled 
			1 - Enabled
		Device Allocation: AP, SM"
	DEFVAL	{ 1 }
	::= { systemConfig 15 }

systemConfigLockedCC OBJECT-TYPE
	SYNTAX	   DisplayString (SIZE(0|1..2))
	MAX-ACCESS read-only
	STATUS	   current
	DESCRIPTION
		"Return Locked Country Value in case if device is locked for particular country.
		Device Allocation: AP, SM"
	::= { systemConfig 16 }

systemConfigMinAntGain OBJECT-TYPE
	SYNTAX	   Integer32 (0..40)
	MAX-ACCESS read-only
	STATUS	   current
	DESCRIPTION
		"Return Minimum allowed Antenna Gain.
		Device Allocation: AP, SM"
	::= { systemConfig 17 }

systemConfigOperationalLicense OBJECT-TYPE
	SYNTAX	   DisplayString (SIZE(0..128))
	MAX-ACCESS read-write
	STATUS	   current
	DESCRIPTION
		"Device Operational License. 
		Set Operational License on AP to extend basic functionality. 
		Visit Cambium Webserver to get the license key. ETSI country code and 
		maximum SMs count value will be set on AP if the key validation pass.
		License is required on locked devices only.
		Device Allocation: AP"
	::= { systemConfig 18 }

systemNtpServerIPMode OBJECT-TYPE 
	SYNTAX	   Integer32 (1|2)
	MAX-ACCESS read-write
	STATUS	   current
	DESCRIPTION
		"NTP Server IP Address receive mode
			1 - Static, 
			2 - DHCP
		Device Allocation: AP, SM"
	DEFVAL	{ 2 }
	::= { systemNtpServer 1 }

systemNtpServerPrimaryIP  OBJECT-TYPE
	SYNTAX	   IpAddress
	MAX-ACCESS read-write
	STATUS	   current
	DESCRIPTION 
		"NTP Server 1 IP Address
		Device Allocation: AP, SM"
	::= { systemNtpServer 2 }
	
systemNtpServerSecondaryIP	OBJECT-TYPE
	SYNTAX	   IpAddress
	MAX-ACCESS read-write
	STATUS	   current
	DESCRIPTION 
		"NTP Server 2 IP Address
		Device Allocation: AP, SM"
	::= { systemNtpServer 3 }

webService OBJECT-TYPE 
		SYNTAX	   Integer32 (1|2)
		MAX-ACCESS read-write
		STATUS	   current
		DESCRIPTION
		"Web Service
			1 - HTTP, 
			2 - HTTPS
		Device Allocation: AP, SM"
		DEFVAL	{ 1 }
		::= { cambiumWebServer 1 }

httpPort  OBJECT-TYPE
	SYNTAX	   Integer32 (0..65535)
	MAX-ACCESS read-write
	STATUS	   current
	DESCRIPTION 
		"HTTP Port
		Device Allocation: AP, SM"
	DEFVAL	{ 80 }
	::= { cambiumWebServer 2 }

httpsPort  OBJECT-TYPE
	SYNTAX	   Integer32 (0..65535)
	MAX-ACCESS read-write
	STATUS	   current
	DESCRIPTION 
		"HTTPs Port"
	DEFVAL	{ 443 }
	::= { cambiumWebServer 3 }

wirelessDeviceCountryCode  OBJECT-TYPE
	SYNTAX	   DisplayString (SIZE(0|2))
	MAX-ACCESS read-write
	STATUS	   current
	DESCRIPTION 
		"Country Code. 
		If US Lock SKU, this is US and cannot be changed. 
		If not locked, for 9350, it will be None, for 9344, it will be Follow AP CC. 
		When user change CC at SM, the SM Scan Frequency Type  will be FA
		Device Allocation: AP"
	DEFVAL	{ "NS" }
	::= { wirelessDevice 1 }

wirelessType  OBJECT-TYPE
		SYNTAX	   Integer32 (1|2)
		MAX-ACCESS read-write
		STATUS	   obsolete
		DESCRIPTION
				"Wireless type:
						1 - tdd driver,
						2 - 80211 (aquila) driver
				Device Allocation: AP, SM"
	DEFVAL	{ 1 }
	::= { wirelessDevice 2 }

wirelessDefaultCountryCode	OBJECT-TYPE
	SYNTAX	   DisplayString (SIZE(0|2))
	MAX-ACCESS read-write
	STATUS	   current
	DESCRIPTION 
		"Default Country Code."
	DEFVAL	{ "OT" }
	::= { wirelessDevice 3 }

wirelessInterfaceMode  OBJECT-TYPE
	SYNTAX	   Integer32 (1|2|3)
	MAX-ACCESS read-write
	STATUS	   current
	DESCRIPTION 
		"Wireless Interface Mode:
			1 for AP, 
			2 for SM, 
			3 for Spectrum Analyzer
		Device Allocation: AP, SM"
	::= { wirelessInterface 1 }

wirelessInterfaceSSID  OBJECT-TYPE
	SYNTAX	   DisplayString (SIZE(1..32))
	MAX-ACCESS read-write
	STATUS	   current
	DESCRIPTION 
		"Wireless SSID
		Device Allocation: AP"
	DEFVAL	{ "Cambium-AP" }
	::= { wirelessInterface 2 }

wirelessInterfaceEncryption	 OBJECT-TYPE
	SYNTAX	   Integer32 (1|2|3)
	MAX-ACCESS read-write
	STATUS	   current
	DESCRIPTION 
		"Wireless authentication type:
			1 - Open mode,
			2 - wpa2 mode,
			3 - EAP-TTLS
		Device Allocation: AP"
	DEFVAL	{ 2 }
	::= { wirelessInterface 3 }

wirelessInterfaceEncryptionKey	OBJECT-TYPE
	SYNTAX	   DisplayString (SIZE(0|8..63))
	MAX-ACCESS read-write
	STATUS	   current
	DESCRIPTION 
		"Pre-shared authentication key.
		Device Allocation: AP"
	DEFVAL	{ "Cam39-Tai!wdmv" }
	::= { wirelessInterface 4 }

wirelessInterfaceHTMode	 OBJECT-TYPE
	SYNTAX	   Integer32 (1..4)
	MAX-ACCESS read-write
	STATUS	   current
	DESCRIPTION 
		"Frequency Bandwidth
			1 - 20Mhz, 
			2 - 40Mhz, 
			3 - 10Mhz,
			4 - 5MHz
		Device Allocation: AP"
	DEFVAL	{ 1 }
	::= { wirelessInterface 5 }

wirelessInterfaceTXPower  OBJECT-TYPE
	SYNTAX	   Integer32 (-24..30)
	MAX-ACCESS read-write
	STATUS	   current
	DESCRIPTION 
		"TX Power (Board Output Conducted)
		Device Allocation: AP"
	DEFVAL	{ 7 }
	::= { wirelessInterface 6 }

wirelessInterfaceTDDAntennaGain	 OBJECT-TYPE
	SYNTAX	   Integer32 (0..40)
	MAX-ACCESS read-write
	STATUS	   current
	DESCRIPTION 
		"Antenna Gain
		Device Allocation: AP, SM"
	DEFVAL	{ 16 }
	::= { wirelessInterface 7 }

wirelessInterfaceTDDRatio  OBJECT-TYPE
	SYNTAX	   Integer32 (1|2|3|4)
	MAX-ACCESS read-write
	STATUS	   current
	DESCRIPTION 
		"DL/UL Ratio: 
			1 - 75/25,
			2 - 50/50,
			3 - 30/70,
			4 - Flexible
		Device Allocation: AP"
	DEFVAL	{ 4 }
	::= { wirelessInterface 9 }

wirelessInterfaceTPCTRL	 OBJECT-TYPE
	SYNTAX	   Integer32 (-80..-40)
	MAX-ACCESS read-write
	STATUS	   current
	DESCRIPTION 
		"Set/get target receive level (TRL)
		Device Allocation: AP"
	DEFVAL	{ -60 }
	::= { wirelessInterface 10 }

wirelessInterfaceTPCMode  OBJECT-TYPE
	SYNTAX	   Integer32 (0|1|2)
	MAX-ACCESS read-write
	STATUS	   obsolete
	DESCRIPTION 
		"Power mode selection.
		Values:0 - Disable, 1 - Open Loop, 2 - Close Loop
		When system is in Fixed mode (75/35, 50/50, 30/70), this parameter can only be Close or Open Loop.
		When system is in Flexible mode, this parameter can be either Close Loop, Open Loop or Disable.
		The default TPC mode is Close Loop.
		Device Allocation: AP"
	DEFVAL	{ 2 }
	::= { wirelessInterface 11 }

wirelessInterfacePTPMode  OBJECT-TYPE
		SYNTAX	   Integer32 (0|1|2)
		MAX-ACCESS read-write
		STATUS	   current
		DESCRIPTION
		"PTP Setting
			0 - Off
			1 - Connect First SM,
			2 - MAC Address Limited
		Device Allocation: AP"
		DEFVAL	{ 1 }
		::= { wirelessInterface 12 }

wirelessInterfacePTPMACAddress	OBJECT-TYPE
		SYNTAX	   DisplayString (SIZE(0|11..17))
		MAX-ACCESS read-write
		STATUS	   current
		DESCRIPTION
		"PTP MAC Address
		Device Allocation: AP"
		::= { wirelessInterface 13 }

wirelessInterfaceSyncSource	 OBJECT-TYPE
		SYNTAX	   Integer32 (1|2|3|4)
		MAX-ACCESS read-write
		STATUS	   current
		DESCRIPTION
		"1PPS Sync Source
			1 - GPS,
			2 - CMM4,
			3 - Internal Free Run,
			4 - CMM3
		Device Allocation: AP"
		DEFVAL	{ 3 }
		::= { wirelessInterface 14 }

wirelessInterfaceSyncHoldTime  OBJECT-TYPE
		SYNTAX	   Integer32 (20..864000)
		MAX-ACCESS read-write
		STATUS	   current
		DESCRIPTION
		"GPS Sync Hold Time in seconds
		Device Allocation: AP"
		DEFVAL	{ 30 }
		::= { wirelessInterface 15 }

wirelessInterfaceScanFrequencyListTwenty  OBJECT-TYPE
		SYNTAX	   DisplayString (SIZE(0|1..1064))
		MAX-ACCESS read-write
		STATUS	   current
		DESCRIPTION
		"Scan Frequency List for 20 MHz
		Device Allocation: SM"
		::= { wirelessInterface 16 }

wirelessInterfaceScanFrequencyListForty	 OBJECT-TYPE
		SYNTAX	   DisplayString (SIZE(0|1..1064))
		MAX-ACCESS read-write
		STATUS	   current
		DESCRIPTION
		"Scan Frequency List for 40 MHz
		Device Allocation: SM"
		::= { wirelessInterface 17 }

centerFrequency	 OBJECT-TYPE
	SYNTAX	   Integer32 (0|2407..5970)
	MAX-ACCESS read-write
	STATUS	   current
	DESCRIPTION 
		"Per freq band: 5725 GHz for 5G SKU, 2407 for 2.4G SKU
		Device Allocation: AP"
	::= { wirelessInterface 18 }

dfsAlternative1CenterFrequency	OBJECT-TYPE
	SYNTAX	   Integer32 (0|2407..5970)
	MAX-ACCESS read-write
	STATUS	   current
	DESCRIPTION 
		"Per freq band
		Device Allocation: AP"
	::= { wirelessInterface 19 }

dfsAlternative2CenterFrequency	OBJECT-TYPE
	SYNTAX	   Integer32 (0|2407..5970)
	MAX-ACCESS read-write
	STATUS	   current
	DESCRIPTION 
		"Per freq band
		Device Allocation: AP"
	::= { wirelessInterface 20 }

wirelessMaximumCellSize	 OBJECT-TYPE
		SYNTAX	   Integer32 (0..65)
		MAX-ACCESS read-write
		STATUS	   current
		DESCRIPTION
		"Maximum Cell Size in units
		wirelessCellSizeUnit defines the unit type: 
			1 - Miles 
			2 - Kilometers
		Device Allocation: AP"
	DEFVAL	{ 3 }
		::= { wirelessInterface 21 }

wirelessCellSizeUnit  OBJECT-TYPE
		SYNTAX	   Integer32 (1|2)
		MAX-ACCESS read-write
		STATUS	   current
		DESCRIPTION
		"Maximum Cell Size units:
			1 - Miles
			2 - Kilometers
		Device Allocation: AP"
		::= { wirelessInterface 22 }

wirelessMaximumSTA	OBJECT-TYPE
		SYNTAX	   Integer32 (0|1..120)
		MAX-ACCESS read-write
		STATUS	   current
		DESCRIPTION
		"Maximum Number of SM
		Device Allocation: AP"
		DEFVAL	{ 60 }
		::= { wirelessInterface 23 }

wirelessRadiusTimeout  OBJECT-TYPE
	SYNTAX	   Integer32 (1..20)
	MAX-ACCESS read-write
	STATUS	   current
	DESCRIPTION 
		"RADIUS server response timeout
		Device Allocation: AP"
	DEFVAL	{ 5 }
	::= { wirelessRadius 1 }

wirelessRadiusRetry	 OBJECT-TYPE
	SYNTAX	   Integer32 (0..5)
	MAX-ACCESS read-write
	STATUS	   current
	DESCRIPTION 
		"RADIUS server retry
		Device Allocation: AP"
	DEFVAL	{ 1 }
	::= { wirelessRadius 2 }
	
wirelessRadiusGUIUserAuth  OBJECT-TYPE
	SYNTAX	   Integer32 (0|1|2)
	MAX-ACCESS read-write
	STATUS	   current
	DESCRIPTION 
		"SM GUI User Authentication Option
			0 - Device Local Only
			1 - Remote RADIUS Server Only
			2 - Remote RADIUS Server and Fallback to Local
		Device Allocation: AP"
	DEFVAL	{ 0 }
	::= { wirelessRadius 3 }
	
wirelessRadiusCurrentGUIUserAuth  OBJECT-TYPE
	SYNTAX	   Integer32 (0|1|2)
	MAX-ACCESS read-only
	STATUS	   current
	DESCRIPTION 
		"Current GUI User Authentication Option
			0 - Device Local Only
			1 - Remote RADIUS Server Only
			2 - Remote RADIUS Server and Fallback to Local
		Device Allocation: SM"
	::= { wirelessRadius 4 }
	
wirelessRadiusSeverInfo	 OBJECT-TYPE
	SYNTAX	   DisplayString (SIZE(0..128))
	MAX-ACCESS read-only
	STATUS	   current
	DESCRIPTION 
		"RADIUS server info
		Device Allocation: SM"
	::= { wirelessRadius 5 }
	
wirelessRadiusIdentityStr  OBJECT-TYPE
	SYNTAX	   DisplayString (SIZE(1..128))
	MAX-ACCESS read-write
	STATUS	   current
	DESCRIPTION 
		"Authentication Identity String
		Device Allocation: SM"
	DEFVAL	{ "anonymous" }
	::= { wirelessRadius 6 }

wirelessRadiusIdentityRealm	 OBJECT-TYPE
	SYNTAX	   DisplayString (SIZE(0..128))
	MAX-ACCESS read-write
	STATUS	   current
	DESCRIPTION 
		"Authentication Identity Realm
		Device Allocation: SM"
	DEFVAL	{ "cambiumnetworks.com" }
	::= { wirelessRadius 7 }
	
wirelessRadiusUsername	OBJECT-TYPE
	SYNTAX	   DisplayString (SIZE(1..128))
	MAX-ACCESS read-write
	STATUS	   current
	DESCRIPTION 
		"Authentication Username
		Device Allocation: SM"
	DEFVAL	{ "cambium-station" }
	::= { wirelessRadius 8 }
	
wirelessRadiusPassword	OBJECT-TYPE
	SYNTAX	   DisplayString (SIZE(0..128))
	MAX-ACCESS read-write
	STATUS	   current
	DESCRIPTION 
		"Authentication Password
		Device Allocation: SM"
	DEFVAL	{ "cambium" }
	::= { wirelessRadius 9 }

useMACAddressAsWirelessRadiusUsername  OBJECT-TYPE
	SYNTAX	   Integer32 (0|1|2)
	MAX-ACCESS read-write
	STATUS	   current
	DESCRIPTION 
		"For using an Ethernet MAC address instead of RADIUS username
		0 - Off (default),
		1 - using ':' as format,
		2 - using '-' as format
		Device Allocation: SM"
	DEFVAL	{ 0 }
	::= { wirelessRadius 10 }

wirelessRadiusServerTable  OBJECT-TYPE
		SYNTAX SEQUENCE OF WirelessRadiusServerEntry
		MAX-ACCESS not-accessible
		STATUS	   current
		DESCRIPTION
			"RADIUS servers table
			Device Allocation: AP"
		::= { wirelessRadiusServerList 1 }
		
wirelessRadiusServerEntry  OBJECT-TYPE
		SYNTAX	WirelessRadiusServerEntry
		MAX-ACCESS not-accessible
		STATUS	   current
		DESCRIPTION
			"RADIUS servers table entry
			Device Allocation: AP"
		INDEX	{ wirelessRadiusServerIndex }
		
		::= { wirelessRadiusServerTable 1 }
		
WirelessRadiusServerEntry ::= SEQUENCE {
		wirelessRadiusServerIndex
				Integer32,
		wirelessRadiusServerIP
				IpAddress,
		wirelessRadiusServerPort
				Integer32,
		wirelessRadiusServerSecret
				DisplayString
}

wirelessRadiusServerIndex  OBJECT-TYPE
		SYNTAX	   Integer32 (0..3)
		MAX-ACCESS read-write
		STATUS	   current
		DESCRIPTION
			"RADIUS servers limiting number
			Device Allocation: AP"
		::= { wirelessRadiusServerEntry 1 }
		
wirelessRadiusServerIP	OBJECT-TYPE
		SYNTAX	   IpAddress
		MAX-ACCESS read-write
		STATUS	   current
		DESCRIPTION
			"RADIUS server IP address
			Device Allocation: AP"
		::= { wirelessRadiusServerEntry 2 }
		
wirelessRadiusServerPort  OBJECT-TYPE
		SYNTAX	   Integer32(1..65535)
		MAX-ACCESS read-write
		STATUS	   current
		DESCRIPTION
			"RADIUS server port
			Device Allocation: AP"
		DEFVAL	{ 1812 }
		::= { wirelessRadiusServerEntry 3 }
		
wirelessRadiusServerSecret	OBJECT-TYPE
		SYNTAX	   DisplayString (SIZE(0|1..128))
		MAX-ACCESS read-write
		STATUS	   current
		DESCRIPTION
			"RADIUS server port
			Device Allocation: AP"
		::= { wirelessRadiusServerEntry 4 }
		
wirelessRadiusDefaultCertificate OBJECT-TYPE
		SYNTAX	   OCTET STRING (SIZE(0..8192))
		MAX-ACCESS read-only
		STATUS	   current
		DESCRIPTION
			"Default RADIUS certificate
			Device Allocation: SM"
		::= { wirelessRadiusCertificateSet 1 }
		
wirelessRadiusUser1Certificate OBJECT-TYPE
		SYNTAX	   OCTET STRING (SIZE(0|1..8192))
		MAX-ACCESS read-write
		STATUS	   current
		DESCRIPTION
			"Default RADIUS certificate
			Device Allocation: SM"
		::= { wirelessRadiusCertificateSet 2 }
		
wirelessRadiusUser2Certificate OBJECT-TYPE
		SYNTAX	   OCTET STRING (SIZE(0|1..8192))
		MAX-ACCESS read-write
		STATUS	   current
		DESCRIPTION
			"Default RADIUS certificate
			Device Allocation: SM"
		::= { wirelessRadiusCertificateSet 3 }
		
wirelessRadiusUseDefaultCertificate	 OBJECT-TYPE
		SYNTAX	   Integer32(0|1)
		MAX-ACCESS read-write
		STATUS	   current
		DESCRIPTION
			"RADIUS default certificate use
			Device Allocation: SM"
		DEFVAL	{ 1 }
		::= { wirelessRadiusCertificateSet 4 }
		
wirelessRadiusPMP320Certificate OBJECT-TYPE
		SYNTAX	   OCTET STRING (SIZE(0..8192))
		MAX-ACCESS read-only
		STATUS	   current
		DESCRIPTION
			"PMP320 RADIUS certificate
			Device Allocation: SM"
		::= { wirelessRadiusExtraCertificateSet 1 }
		
wirelessRadiusUsePMP320Certificate	OBJECT-TYPE
		SYNTAX	   Integer32(0|1)
		MAX-ACCESS read-write
		STATUS	   current
		DESCRIPTION
			"RADIUS PMP320 certificate use
			Device Allocation: SM"
		DEFVAL	{ 1 }
		::= { wirelessRadiusExtraCertificateSet 2 }
		
wirelessRadiusPMP450Certificate OBJECT-TYPE
		SYNTAX	   OCTET STRING (SIZE(0..8192))
		MAX-ACCESS read-only
		STATUS	   current
		DESCRIPTION
			"PMP450 RADIUS certificate
			Device Allocation: SM"
		::= { wirelessRadiusExtraCertificateSet 3 }
		
wirelessRadiusUsePMP450Certificate	OBJECT-TYPE
		SYNTAX	   Integer32(0|1)
		MAX-ACCESS read-write
		STATUS	   current
		DESCRIPTION
			"RADIUS PMP450 certificate use
			Device Allocation: SM"
		DEFVAL	{ 1 }
		::= { wirelessRadiusExtraCertificateSet 4 }

wirelessRadiusUseDefCertificate	 OBJECT-TYPE
		SYNTAX	   Integer32(0|1)
		MAX-ACCESS read-write
		STATUS	   obsolete
		DESCRIPTION
			"RADIUS default certificate use
			Device Allocation: SM"
		DEFVAL	{ 1 }
		::= { wirelessRadiusCertificateListRow1 1 }

wirelessRadiusUser1CertificateName	OBJECT-TYPE
		SYNTAX	   DisplayString
		MAX-ACCESS read-write
		STATUS	   obsolete
		DESCRIPTION
			"First user RADIUS certificate name
			Device Allocation: AP"
		DEFVAL	{ "cert2" }
		::= { wirelessRadiusCertificateListRow2 1 }

wirelessRadiusUser2CertificateName	OBJECT-TYPE
		SYNTAX	   DisplayString
		MAX-ACCESS read-write
		STATUS	   obsolete
		DESCRIPTION
			"Second user RADIUS certificate name
			Device Allocation: AP"
		DEFVAL	{ "cert3" }
		::= { wirelessRadiusCertificateListRow3 1 }

wirelessRadiusDefCertificateView  OBJECT-TYPE
		SYNTAX	   DisplayString
		MAX-ACCESS read-only
		STATUS	   obsolete
		DESCRIPTION
			"RADIUS default certificate view
			Device Allocation: AP"
		::= { wirelessRadiusCertificateListRow1 2 }

wirelessRadiusUser1CertificateView	OBJECT-TYPE
		SYNTAX	   DisplayString
		MAX-ACCESS read-only
		STATUS	   obsolete
		DESCRIPTION
			"First user RADIUS certificate view
			Device Allocation: AP"
		::= { wirelessRadiusCertificateListRow2 2 }

wirelessRadiusUser2CertificateView	OBJECT-TYPE
		SYNTAX	   DisplayString
		MAX-ACCESS read-only
		STATUS	   obsolete
		DESCRIPTION
			"Second user RADIUS certificate view
			Device Allocation: AP"
		::= { wirelessRadiusCertificateListRow3 2 }
		
dfsAlternative1Bandwidth  OBJECT-TYPE
	SYNTAX	   Integer32 (1|2|3|4)
	MAX-ACCESS read-write
	STATUS	   current
	DESCRIPTION 
		"Frequency Bandwidth
			1 - 20Mhz, 
			2 - 40Mhz, 
			3 - 10Mhz, 
			4 - 5Mhz, 
		Device Allocation: AP"
	DEFVAL	{ 1 }
	::= { wirelessInterface 24 }

dfsAlternative2Bandwidth  OBJECT-TYPE
	SYNTAX	   Integer32 (1|2|3|4)
	MAX-ACCESS read-write
	STATUS	   current
	DESCRIPTION 
		"Frequency Bandwidth
			1 - 20Mhz, 
			2 - 40Mhz, 
			3 - 10Mhz, 
			4 - 5Mhz, 
		Device Allocation: AP"
	DEFVAL	{ 1 }
	::= { wirelessInterface 25 }

wirelessAcceptableAPRSSIThreshold  OBJECT-TYPE
		SYNTAX	   Integer32 (-100..-20)
		MAX-ACCESS read-write
		STATUS	   current
		DESCRIPTION
		"AP RSSI Threshold
		Device Allocation: SM"
		DEFVAL	{ -90 }
		::= { wirelessInterface 26 }

wirelessAcceptableAPCINRThreshold  OBJECT-TYPE
		SYNTAX	   Integer32 (-5..60)
		MAX-ACCESS read-write
		STATUS	   obsolete
		DESCRIPTION
		"AP CINR Threshold
		Device Allocation: SM"
		DEFVAL	{ 0 }
		::= { wirelessInterface 27 }

wirelessInterfaceUnblockUSfreqs	 OBJECT-TYPE
		SYNTAX	   Integer32 (0|1)
		MAX-ACCESS read-write
		STATUS	   obsolete
		DESCRIPTION
		"Block US 5.2 and 5.4 bands
		5.2 and 5.4 bands are blocked until DFS certification is acheived
		Device Allocation: AP, SM"
		::= { wirelessInterface 28 }

wirelessMIREnable  OBJECT-TYPE
		SYNTAX	   Integer32 (0|1)
		MAX-ACCESS read-write
		STATUS	   current
		DESCRIPTION
		"Maximum Information Rate (MIR) Limiting:
			0 - Disable,
			1 - Enable
		Device Allocation: AP"
		DEFVAL	{ 0 }
		::= { wirelessInterface 29 }

wirelessMIRSTAProfileNumber	 OBJECT-TYPE
		SYNTAX	   Integer32 (0..15)
		MAX-ACCESS read-write
		STATUS	   current
		DESCRIPTION
		"Maximum Information Rate (MIR) Limiting Profile Number on SM
		Device Allocation: SM"
		::= { wirelessInterface 30 }

wirelessMIRAPDefaultProfileNumber  OBJECT-TYPE
		SYNTAX	   Integer32 (0..15)
		MAX-ACCESS read-write
		STATUS	   current
		DESCRIPTION
		"Maximum Information Rate (MIR) Limiting Default Profile number on AP
		This Profile Number will be used by AP is SM provides improper profile
		Device Allocation: AP"
		::= { wirelessInterface 31 }

wirelessMIRProfileTable	 OBJECT-TYPE
		SYNTAX SEQUENCE OF WirelessMIRProfileEntry
		MAX-ACCESS not-accessible
		STATUS	   current
		DESCRIPTION
		"Maximum Information Rate (MIR) Limiting profile Table
		Device Allocation: AP"
		::= { wirelessMIRList 1 }

wirelessMIRProfileEntry	 OBJECT-TYPE
		SYNTAX	WirelessMIRProfileEntry
		MAX-ACCESS not-accessible
		STATUS	   current
		DESCRIPTION
		"Maximum Information Rate (MIR) Limiting profile Table Entry
		Device Allocation: AP"
		INDEX	{ wirelessMIRProfileIndex }
		::= { wirelessMIRProfileTable 1 }

WirelessMIRProfileEntry ::= SEQUENCE {
		wirelessMIRProfileIndex
				Integer32,
		wirelessMIRProfileNumber
				Integer32,
		wirelessMIRProfileDescription
				DisplayString,
		wirelessDLMIR
				Integer32,
		wirelessULMIR
				Integer32
}

wirelessMIRProfileIndex	 OBJECT-TYPE
		SYNTAX	   Integer32 (0..16)
		MAX-ACCESS read-write
		STATUS	   current
		DESCRIPTION
		"Maximum Information Rate (MIR) Limiting profile Number
		Device Allocation: AP"
		::= { wirelessMIRProfileEntry 1 }

wirelessMIRProfileNumber  OBJECT-TYPE
		SYNTAX	   Integer32 (0..15)
		MAX-ACCESS read-write
		STATUS	   current
		DESCRIPTION
		"Number of MIR profile
		Device Allocation: AP"
		::= { wirelessMIRProfileEntry 2 }

wirelessMIRProfileDescription  OBJECT-TYPE
		SYNTAX	   DisplayString (SIZE(0|1..128))
		MAX-ACCESS read-write
		STATUS	   current
		DESCRIPTION
		"MIR profile description
		Device Allocation: AP"
		::= { wirelessMIRProfileEntry 3 }


wirelessDLMIR  OBJECT-TYPE
		SYNTAX	   Integer32 (100..1000000)
		MAX-ACCESS read-write
		STATUS	   current
		DESCRIPTION
		"DL MIR in kilobits per second
		Device Allocation: AP"
		::= { wirelessMIRProfileEntry 4 }

wirelessULMIR  OBJECT-TYPE
		SYNTAX	   Integer32 (100..1000000)
		MAX-ACCESS read-write
		STATUS	   current
		DESCRIPTION
		"UL MIR in kilobits per second
		Device Allocation: AP"
		::= { wirelessMIRProfileEntry 5 }

wirelessInterfaceScanFrequencyBandwidth OBJECT-TYPE
	SYNTAX	   Integer32 (1..15)
	MAX-ACCESS read-write
	STATUS	   current
	DESCRIPTION 
		"Frequency Bandwidth as bitmask, fields are:
			1 - 20Mhz, 
			2 - 40Mhz, 
			4 - 10Mhz, 
			8 - 5Mhz
		Device Allocation: SM"
	DEFVAL	{ 1 }
	::= { wirelessInterface 32 }

wirelessInterfaceGuardInterval OBJECT-TYPE
		SYNTAX Integer32 (1|2)
		MAX-ACCESS read-write
		STATUS	   current
		DESCRIPTION
		"Guard Interval:
			1 - Long GuardInterval,
			2 - Short GuardInterval
		Device Allocation: AP"
		DEFVAL	{ 1 }
	::= { wirelessInterface 33 }

wirelessInterfaceiFreqReuseMode OBJECT-TYPE
			SYNTAX Integer32 (0|1|2)
		MAX-ACCESS read-write
		STATUS	   current
		DESCRIPTION
		"Frequency Reuse Mode:
			0 - Off,
			1 - Frequency-Reuse-Front,
			2 - Frequency-Reuse-Back
		Device Allocation: AP"
		DEFVAL	{ 0 }
		::= { wirelessInterface 34 }
		
wirelessSTAPriority	 OBJECT-TYPE
		SYNTAX	   Integer32 (0|1|2)
		MAX-ACCESS read-write
		STATUS	   current
		DESCRIPTION
		"SM priority value:
			0 - Normal,
			1 - High,
			2 - Low
		Device Allocation: SM"
		DEFVAL	{ 0 }
		::= { wirelessInterface 35 }

wirelessSmoothingBit  OBJECT-TYPE
		SYNTAX	   Integer32 (0|1)
		MAX-ACCESS read-write
		STATUS	   obsolete
		DESCRIPTION
		"Smoothing Bit values:
			0 - Bit is cleared, smoothing is off,
			1 - Bit is set, smoothing is on
		Device Allocation: AP"
		DEFVAL	{ 0 }
		::= { wirelessInterface 36 }
		
wirelessSecurityMethod	OBJECT-TYPE
		SYNTAX	   Integer32 (0..6)
		MAX-ACCESS read-write
		STATUS	   current
		DESCRIPTION
				"Allowed types of authentications on SM side
				(Preferred AP list is not set)
				Use bitmask to enable pereferred methods, 0 - means enable method:
				set 0-th bit to 0 - Open method (110b)
				set 1-st bit to 0 - WPA2 method (101b)
				set 2-nd bit to 0 - EAP-TTLS method (011b)
				0x00 - All enabled"
		DEFVAL	{ 0 }
		::= { wirelessInterface 37 }

wirelessAcceptableAPSNRThreshold  OBJECT-TYPE
		SYNTAX	   Integer32 (-5..60)
		MAX-ACCESS read-write
		STATUS	   current
		DESCRIPTION
		"AP CINR Threshold
		Device Allocation: SM"
		DEFVAL	{ 0 }
		::= { wirelessInterface 38 }

wirelessMgmtPacketRate	OBJECT-TYPE
		SYNTAX	   Integer32 (0|1)
		MAX-ACCESS read-write
		STATUS	   current
		DESCRIPTION
		"Management rate:
			0 - MCS0
			1 - MCS1
		Device Allocation: AP"
		DEFVAL	{ 1 }
		::= { wirelessInterface 39 }

wirelessStaIsolate	OBJECT-TYPE
		SYNTAX	   Integer32 (0|1)
		MAX-ACCESS read-write
		STATUS	   current
		DESCRIPTION
		"Enables or disables bridging within the AP driver
		between SMs.
			0 - Disabled
			1 - Enabled
		Device Allocation: AP"
		DEFVAL	{ 0 }
		::= { wirelessInterface 40 }

wirelessCcaEnable	OBJECT-TYPE
		SYNTAX		Integer32 (0|1)
		MAX-ACCESS	read-write
		STATUS		current
		DESCRIPTION
		"Clear Channel Assignment:
			0 - Disable
			1 - Enable
		Device Allocation: AP"
		DEFVAL	{ 0 }
		::= { wirelessInterface 41 }

wirelessInterfaceScanFrequencyListTen  OBJECT-TYPE
		SYNTAX	   DisplayString (SIZE(0|1..1064))
		MAX-ACCESS read-write
		STATUS	   current
		DESCRIPTION
		"Scan Frequency List for 10MHz
		Device Allocation: SM"
		::= { wirelessInterface 42 }

wirelessInterfaceScanFrequencyListFive	OBJECT-TYPE
		SYNTAX	   DisplayString (SIZE(0|1..1064))
		MAX-ACCESS read-write
		STATUS	   current
		DESCRIPTION
		"Scan Frequency List for 5MHz
		Device Allocation: SM"
		::= { wirelessInterface 43 }

wirelessMulticastEnhanceMode  OBJECT-TYPE
		SYNTAX	   Integer32 (0|3)
		MAX-ACCESS read-write
		STATUS	   current
		DESCRIPTION
		"Multicast enhancement mode 
			0 - Disabled
			3 - IGMP Snooping + MC Passthru
		Device Allocation: AP"
		DEFVAL	{ 0 }
		::= { wirelessInterface 44 }

wirelessTXPowerManualLimit	OBJECT-TYPE
	SYNTAX	   Integer32 (0|1)
	MAX-ACCESS read-write
	STATUS	   current
	DESCRIPTION 
		"Allow user to limit MAX output TX Power
		Device Allocation: SM"
	DEFVAL	{ 0 }
	::= { wirelessInterface 48 }

wirelessRateMaxMCS OBJECT-TYPE
	SYNTAX	   Integer32 (1..15)
	MAX-ACCESS read-write
	STATUS	   current
	DESCRIPTION 
		"Allow user to set MAX TX rate
		Not allowed for SNMP processing
		Device Allocation: AP, SM"
	::= { wirelessInterface 49 }

wirelessSMWifiDistance	OBJECT-TYPE
		SYNTAX	   Integer32 (1..52)
		MAX-ACCESS read-write
		STATUS	   current
		DESCRIPTION
		"Distance to AP for SM in Standard Wi-Fi mode
		wirelessCellSizeUnitdefines the unit type:
			1 - Miles
			2 - Kilometers
		Device Allocation: SM"
	DEFVAL	{ 1 }
		::= { wirelessInterface 50 }

wirelessInterfaceProtocolMode  OBJECT-TYPE
		SYNTAX	   Integer32 (1|2|3|4)
		MAX-ACCESS read-write
		STATUS	   current
		DESCRIPTION
	   "Protocol Module Mode:
		   1 - TDD
		   2 - AP/SM WiFi
		   3 - PTP.LL
		   4 - TDD PTP
	   Device Allocation: AP/SM"
   DEFVAL  { 1 }
		::= { wirelessInterface 51 }

forceMcastBcast4Addr  OBJECT-TYPE
		SYNTAX	   Integer32 (0|1)
		MAX-ACCESS read-write
		STATUS	   current
		DESCRIPTION
	   "1 - TRUE
		0 - FALSE"
   DEFVAL  { 1 }
		::= { wirelessInterface 53 }

wirelessInterfaceRateMinMCS	 OBJECT-TYPE
		SYNTAX	   Integer32 (0..15)
		MAX-ACCESS read-write
		STATUS	   current
		DESCRIPTION
		"Minimum locked MCS rate.
		Default allocation: AP, SM."
		DEFVAL	{ 0 }
		::= { wirelessInterface 55 }

wirelessInterfaceRateMaxMCS  OBJECT-TYPE
        SYNTAX     Integer32 (0..15)
        MAX-ACCESS read-write
        STATUS     current
        DESCRIPTION
        "Maximum locked MCS rate.
        Default allocation: AP, SM."
        DEFVAL  { 15 }
        ::= { wirelessInterface 56 }

wirelessMulticastIgmpFastLeave  OBJECT-TYPE
        SYNTAX     Integer32 (0|1)
        MAX-ACCESS read-write
        STATUS     current
        DESCRIPTION
        "Multicast enhancement mode 
            0 - IGMP Fast Leave OFF
            1 - IGMP Fast Leave ON
        Device Allocation: AP"
        DEFVAL  { 0 }
        ::= { wirelessInterface 57 }

wirelessInterfaceTDDFrameSize  OBJECT-TYPE
		SYNTAX     Integer32 (2500|5000)
		MAX-ACCESS read-write
		STATUS     current
		DESCRIPTION
		"TDD Frame Duration in microseconds
			2500 - 2.5 ms
			5000 - 5 ms
		Device Allocation: AP"
		DEFVAL  { 5000 }
		::= { wirelessInterface 58 }

wirelessInterfaceColocState  OBJECT-TYPE
		SYNTAX     Integer32 (0|1)
		MAX-ACCESS read-write
		STATUS     current
		DESCRIPTION
		"Co-location state
			0 - disabled
			1 - FSK co-location
		Device Allocation: AP"
		DEFVAL  { 0 }
		::= { wirelessInterface 59 }

wirelessInterfaceColocSystemSyncSrc  OBJECT-TYPE
		SYNTAX     Integer32 (1|2|4)
		MAX-ACCESS read-write
		STATUS     current
		DESCRIPTION
		"Co-location state
			1 - GPS,
			2 - CMM4,
			4 - CMM3
		Device Allocation: AP"
		DEFVAL  { 2 }
		::= { wirelessInterface 60 }

wirelessAPWifiWLANmode  OBJECT-TYPE
                SYNTAX     Integer32 (0|1)
                MAX-ACCESS read-write
                STATUS     current
                DESCRIPTION
                "AP Wi-Fi WLAN mode (short, 1000m operational distance)
                        0 - Disabled,
                        1 - Enabled
                Device Allocation: AP"
                DEFVAL  { 0 }
                ::= { wirelessInterface 61 }

apWiFiDLCTSMode  OBJECT-TYPE
                SYNTAX     Integer32 (0|1)
                MAX-ACCESS read-write
                STATUS     current
                DESCRIPTION
                "Force AP WiFi to enable Self CTS
                        0 - Disabled,
                        1 - Enabled
                Device Allocation: AP"
                DEFVAL  { 1 }
                ::= { wirelessInterface 62 }

apWiFiULCTSRTSMode  OBJECT-TYPE
                SYNTAX     Integer32 (0|1)
                MAX-ACCESS read-write
                STATUS     current
                DESCRIPTION
                "Force AP WiFi to add ERP IE to the Beacon
                        0 - Disabled,
                        1 - Enabled
                Device Allocation: AP"
                DEFVAL  { 1 }
                ::= { wirelessInterface 63 }

apWiFiRTSThreshold  OBJECT-TYPE
                SYNTAX     Integer32 (1..2346)
                MAX-ACCESS read-write
                STATUS     current
                DESCRIPTION
                "Wi-Fi interface RTS Threshold
                Device Allocation: AP, SM"
                DEFVAL  { 2346 }
                ::= { wirelessInterface 64 }

wirelessMACFilter  OBJECT-TYPE
		SYNTAX     Integer32 (0|1)
		MAX-ACCESS read-write
		STATUS     current
		DESCRIPTION
		"Enable/Disable MAC list filter
			0 - Disabled,
			1 - Enabled
		Device Allocation: AP"
		DEFVAL  { 0 }
		::= { wirelessInterface 70 }

wirelessMACFilterPolicy  OBJECT-TYPE
		SYNTAX     Integer32 (1|2)
		MAX-ACCESS read-write
		STATUS     current
		DESCRIPTION
		"Permit/Prevent policy for MAC list
			1 - Prevent
			2 - Permit
		Device Allocation: AP"
		DEFVAL  { 1 }
		::= { wirelessInterface 71 }
		
wirelessMACFilterTable	 OBJECT-TYPE
	SYNTAX SEQUENCE OF WirelessMACFilterEntry
	MAX-ACCESS not-accessible
	STATUS	   current
	DESCRIPTION 
		"Table for MAC filter list
		Device Allocation: AP"
	::= { wirelessInterface 72 }

wirelessMACFilterEntry	 OBJECT-TYPE
	SYNTAX	WirelessMACFilterEntry
	MAX-ACCESS not-accessible
	STATUS	   current
	DESCRIPTION 
		"L2 ACL Table Entry
		Device Allocation: AP"
	INDEX	{ wirelessMACFilterIndex }
	::= { wirelessMACFilterTable 1 }
	
WirelessMACFilterEntry ::= SEQUENCE {
	wirelessMACFilterIndex
		Integer32,
	wirelessFilterMAC
		DisplayString,
	wirelessFilterInfo
		DisplayString
}

wirelessMACFilterIndex  OBJECT-TYPE
		SYNTAX	   Integer32 (0..128)
		MAX-ACCESS read-write
		STATUS	   current
		DESCRIPTION
		"MAC filter list table Index(equal max STA)
		Table Entry is cleared if Index is set to zero
		Device Allocation: AP"
		::= { wirelessMACFilterEntry 1 }

wirelessFilterMAC	 OBJECT-TYPE
		SYNTAX	   DisplayString (SIZE(0|1..128))
		MAX-ACCESS read-write
		STATUS	   current
		DESCRIPTION
		"MAC of SM for filter table
		Device Allocation: AP"
		::= { wirelessMACFilterEntry 2 }
		
wirelessFilterInfo	 OBJECT-TYPE
		SYNTAX	   DisplayString (SIZE(0|1..128))
		MAX-ACCESS read-write
		STATUS	   current
		DESCRIPTION
		"Description for MAC in the filter table
		Device Allocation: AP"
		::= { wirelessMACFilterEntry 3 }

l2FirewallEnable  OBJECT-TYPE
		SYNTAX	   Integer32 (0|1)
		MAX-ACCESS read-write
		STATUS	   current
		DESCRIPTION
		"L2 ACL Status Flag: 
			0 - Disable, 
			1 - Enable.
		Device Allocation: AP, SM"
		::= { l2Firewall 1 }

l2FirewallTable	 OBJECT-TYPE
	SYNTAX SEQUENCE OF L2FirewallEntry
	MAX-ACCESS not-accessible
	STATUS	   current
	DESCRIPTION 
		"Table for L2 ACL
		Device Allocation: AP, SM"
	::= { l2Firewall 2 }

l2FirewallEntry	 OBJECT-TYPE
	SYNTAX	L2FirewallEntry
	MAX-ACCESS not-accessible
	STATUS	   current
	DESCRIPTION 
		"L2 ACL Table Entry
		Device Allocation: AP, SM"
	INDEX	{ l2FirewallEntryIndex }
	::= { l2FirewallTable 1 }

L2FirewallEntry ::= SEQUENCE {
	l2FirewallEntryIndex
		Integer32,
	l2FirewallEntryName
		DisplayString,
	l2FirewallEntryAction
		Integer32,
	l2FirewallEntryInterface
		Integer32,
	l2FirewallEntryLog
		Integer32,
	l2FirewallEntryEtherType
		Integer32,
	l2FirewallEntryVlanID
		Integer32,
	l2FirewallEntrySrcMAC
		DisplayString,
	l2FirewallEntrySrcMask
		DisplayString,
	l2FirewallEntryDstMAC
		DisplayString,
	l2FirewallEntryDstMask
		DisplayString
}

l2FirewallEntryIndex  OBJECT-TYPE
		SYNTAX	   Integer32 (0..16)
		MAX-ACCESS read-write
		STATUS	   current
		DESCRIPTION
		"L2 Firewall Table Index
		Table Entry is cleared if Index is set to zero
		Device Allocation: AP, SM"
		::= { l2FirewallEntry 1 }

l2FirewallEntryName	 OBJECT-TYPE
		SYNTAX	   DisplayString (SIZE(0|1..128))
		MAX-ACCESS read-write
		STATUS	   current
		DESCRIPTION
		"L2 ACL Rule Name.
		Device Allocation: AP, SM"
		::= { l2FirewallEntry 2 }

l2FirewallEntryAction  OBJECT-TYPE
	SYNTAX	   Integer32 (0|1)
	MAX-ACCESS read-write
	STATUS	   current
	DESCRIPTION 
		"Action:
			0 - Reject, 
			1 - Permit.
		Device Allocation: AP, SM"
	::= { l2FirewallEntry 3 }

l2FirewallEntryInterface  OBJECT-TYPE
	SYNTAX	   Integer32 (0|1|2)
	MAX-ACCESS read-write
	STATUS	   current
	DESCRIPTION 
		"Interface:
			1 - WAN, 
			2 - LAN.
		Device Allocation: AP, SM"
	::= { l2FirewallEntry 4 }

l2FirewallEntryLog	OBJECT-TYPE
	SYNTAX	   Integer32 (0|1)
	MAX-ACCESS read-write
	STATUS	   current
	DESCRIPTION 
		"Log:
			1 - On, 
			0 - Off.
		Device Allocation: AP, SM"
	::= { l2FirewallEntry 5 }

l2FirewallEntryEtherType  OBJECT-TYPE
	SYNTAX	   Integer32 (0..65535)
	MAX-ACCESS read-write
	STATUS	   current
	DESCRIPTION 
		"L2 ACL Ethernet type: 0000-ffff
		Device Allocation: AP, SM"
	::= { l2FirewallEntry 6 }

l2FirewallEntryVlanID  OBJECT-TYPE
	SYNTAX	   Integer32 (0|1..4094)
	MAX-ACCESS read-write
	STATUS	   current
	DESCRIPTION 
		"L2 ACL Vlan ID
		Device Allocation: AP, SM"
	::= { l2FirewallEntry 7 }

l2FirewallEntrySrcMAC  OBJECT-TYPE
	SYNTAX	   DisplayString (SIZE(0|11..17))
	MAX-ACCESS read-write
	STATUS	   current
	DESCRIPTION 
		"L2 ACL Source MAC Address
		Device Allocation: AP, SM"
	::= { l2FirewallEntry 8 }

l2FirewallEntrySrcMask	OBJECT-TYPE
	SYNTAX	   DisplayString (SIZE(0|11..17))
	MAX-ACCESS read-write
	STATUS	   current
	DESCRIPTION 
		"L2 ACL Source MAC Address Mask
		Device Allocation: AP, SM"
	::= { l2FirewallEntry 9 }

l2FirewallEntryDstMAC  OBJECT-TYPE
	SYNTAX	   DisplayString (SIZE(0|11..17))
	MAX-ACCESS read-write
	STATUS	   current
	DESCRIPTION 
		"L2 ACL Destination MAC Address
		Device Allocation: AP, SM"
	::= { l2FirewallEntry 10 }

l2FirewallEntryDstMask	OBJECT-TYPE
	SYNTAX	   DisplayString (SIZE(0|11..17))
	MAX-ACCESS read-write
	STATUS	   current
	DESCRIPTION 
		"L2 ACL Destination MAC Address Mask
		Device Allocation: AP, SM"
	::= { l2FirewallEntry 11 }

l2WanRemoteAccess  OBJECT-TYPE
		SYNTAX	   Integer32 (0|1)
		MAX-ACCESS read-write
		STATUS	   current
		DESCRIPTION
		"Remote Access To AP Through Wan:
			0 - Decline, 
			1 - Allow
		Device Allocation: AP, SM"
		DEFVAL	{ 0 }
		::= { l2Firewall 3 }

l2SnmpLanRemoteAccess  OBJECT-TYPE
		SYNTAX	   Integer32 (0|1)
		MAX-ACCESS read-write
		STATUS	   current
		DESCRIPTION
		"SNMP access from LAN:
			0 - Decline, 
			1 - Allow
		Device Allocation: AP, SM"
		DEFVAL	{ 1 }
		::= { l2Firewall 4 }

l2DHCPServersBelowSTA  OBJECT-TYPE
		SYNTAX	   Integer32 (0|1)
		MAX-ACCESS read-write
		STATUS	   current
		DESCRIPTION
		"Allow DHCP Servers Below SM:
			0 - Decline, 
			1 - Allow
		Device Allocation: SM"
		DEFVAL	{ 0 }
		::= { l2Firewall 5 }

l2LanRemoteAccess  OBJECT-TYPE
        SYNTAX     Integer32 (0|1)
        MAX-ACCESS read-write
        STATUS     current
        DESCRIPTION
		"SM Management Access Through LAN:
			0 - Wireless Only,
			1 - Ethernet and Wireless
		Device Allocation: SM"
        DEFVAL  { 0 }
        ::= { l2Firewall 6 }

l3FirewallEnable  OBJECT-TYPE
		SYNTAX	   Integer32 (0|1)
		MAX-ACCESS read-write
		STATUS	   current
		DESCRIPTION
		"L3 ACL Rule Status
			1 - Enable, 
			0 - Disable
		Device Allocation: AP, SM"
		::= { l3Firewall 1 }
		
l3FirewallTable	 OBJECT-TYPE
	SYNTAX SEQUENCE OF L3FirewallEntry
	MAX-ACCESS not-accessible
	STATUS	   current
	DESCRIPTION 
		"L3 Firewall Table
		Device Allocation: AP, SM"
	::= { l3Firewall 2 }

l3FirewallEntry	 OBJECT-TYPE
	SYNTAX	L3FirewallEntry
	MAX-ACCESS not-accessible
	STATUS	   current
	DESCRIPTION 
		"L3 Firewall Table Entry
		Device Allocation: AP, SM"
	INDEX	{ l3FirewallEntryIndex }
	::= { l3FirewallTable 1 }

L3FirewallEntry ::= SEQUENCE {
	l3FirewallEntryIndex
		Integer32,
	l3FirewallEntryName
		DisplayString,
	l3FirewallEntryAction
		Integer32,
	l3FirewallEntryInterface
		Integer32,
	l3FirewallEntryLog
		Integer32,
	l3FirewallEntryProtocol
		Integer32,
	l3FirewallEntryPort
		Integer32,
	l3FirewallEntrySrcIP
		IpAddress,
	l3FirewallEntrySrcMask
		IpAddress,
	l3FirewallEntryDstIP
		IpAddress,
	l3FirewallEntryDstMask
		IpAddress,
	l3FirewallEntryDSCP
		Integer32,
	l3FirewallEntryToS
		Integer32
}

l3FirewallEntryIndex  OBJECT-TYPE
		SYNTAX	   Integer32 (0..16)
		MAX-ACCESS read-write
		STATUS	   current
		DESCRIPTION
		"L3 ACL Table Index
		Table Entry is cleared if Index is set to zero
		Device Allocation: AP, SM"
		::= { l3FirewallEntry 1 }

l3FirewallEntryName	 OBJECT-TYPE
	SYNTAX	   DisplayString(SIZE(0|1..128))
	MAX-ACCESS read-write
	STATUS	   current
	DESCRIPTION 
		"L3 ACL Rule Name
		Device Allocation: AP, SM"
	::= { l3FirewallEntry 2 }

l3FirewallEntryAction  OBJECT-TYPE
	SYNTAX	   Integer32 (0|1)
	MAX-ACCESS read-write
	STATUS	   current
	DESCRIPTION 
		"L3 ACL Rule Acrion
			0 - Reject, 
			1 - Permit
		Device Allocation: AP, SM"
	::= { l3FirewallEntry 3 }

l3FirewallEntryInterface  OBJECT-TYPE
	SYNTAX	   Integer32 (0|1|2)
	MAX-ACCESS read-write
	STATUS	   current
	DESCRIPTION 
		"L3 ACL Rule Interface
			1 - WAN, 
			2 - LAN
		Device Allocation: AP, SM"
	::= { l3FirewallEntry 4 }

l3FirewallEntryLog	OBJECT-TYPE
	SYNTAX	   Integer32 (0|1)
	MAX-ACCESS read-write
	STATUS	   current
	DESCRIPTION 
		"L3 ACL Rule Log Flag
			1 - Rule Loggin is On, 
			0 - Rule Logging is Off
		Device Allocation: AP, SM"
	::= { l3FirewallEntry 5 }

l3FirewallEntryProtocol	 OBJECT-TYPE
	SYNTAX	   Integer32 (0|1|2|3|4|5)
	MAX-ACCESS read-write
	STATUS	   current
	DESCRIPTION 
		"L3 ACL Rules IP Protocol
			1 - TCP, 
			2 - UDP, 
			3 - TCP+UDP, 
			4 - ICMP, 
			5 - IP
		Device Allocation: AP, SM"
	::= { l3FirewallEntry 6 }

l3FirewallEntryPort	 OBJECT-TYPE
	SYNTAX	   Integer32 (0..65535)
	MAX-ACCESS read-write
	STATUS	   current
	DESCRIPTION 
		"L3 ACL Rule Port
		Device Allocation: AP, SM"
	::= { l3FirewallEntry 7 }

l3FirewallEntrySrcIP  OBJECT-TYPE
	SYNTAX	   IpAddress
	MAX-ACCESS read-write
	STATUS	   current
	DESCRIPTION 
		"L3 ACL Rule Source IP Address
		Device Allocation: AP, SM"
	::= { l3FirewallEntry 8 }

l3FirewallEntrySrcMask	OBJECT-TYPE
	SYNTAX	   IpAddress
	MAX-ACCESS read-write
	STATUS	   current
	DESCRIPTION 
		"L3 ACL Rule Source Network Mask
		Device Allocation: AP, SM"
	::= { l3FirewallEntry 9 }

l3FirewallEntryDstIP  OBJECT-TYPE
	SYNTAX	   IpAddress
	MAX-ACCESS read-write
	STATUS	   current
	DESCRIPTION 
		"L3 ACL Rule Destination IP Address
		Device Allocation: AP, SM"
	::= { l3FirewallEntry 10 }

l3FirewallEntryDstMask	OBJECT-TYPE
	SYNTAX	   IpAddress
	MAX-ACCESS read-write
	STATUS	   current
	DESCRIPTION 
		"L3 ACL Rule Destination Network Mask
		Device Allocation: AP, SM"
	::= { l3FirewallEntry 11 }

l3FirewallEntryDSCP	 OBJECT-TYPE
	SYNTAX	   Integer32 (0..63)
	MAX-ACCESS read-write
	STATUS	   current
	DESCRIPTION 
		"L3 ACL Rule DSCP
		Device Allocation: AP, SM"
	::= { l3FirewallEntry 12 }

l3FirewallEntryToS	OBJECT-TYPE
	SYNTAX	   Integer32 (0..255)
	MAX-ACCESS read-write
	STATUS	   current
	DESCRIPTION 
		"L3 ACL Rule TOS
		Device Allocation: AP, SM"
	::= { l3FirewallEntry 13 }

dmzEnable  OBJECT-TYPE
	SYNTAX	   Integer32 (0|1)
	MAX-ACCESS read-write
	STATUS	   current
	DESCRIPTION 
		"Enable DMZ:
			1 - Enable, 
			0 - Disable.
		Device Allocation: SM"
	DEFVAL	{ 0 }
	::= { dmz 1 }

dmzIPAddress  OBJECT-TYPE
	SYNTAX	   IpAddress
	MAX-ACCESS read-write
	STATUS	   current
	DESCRIPTION 
		"DMZ IP Address.
		Device Allocation: SM"
	::= { dmz 2 }

voipEnable	OBJECT-TYPE
	SYNTAX	   Integer32 (0|1)
	MAX-ACCESS read-write
	STATUS	   current
	DESCRIPTION 
		"VoIP Enable:
			0 - disable, 
			1 - enable
		Device Allocation: AP, SM"
	DEFVAL	{ 0 }
	::= { confQoS 1 }

qosEnable  OBJECT-TYPE
	SYNTAX	   Integer32 (0|1)
	MAX-ACCESS read-write
	STATUS	   current
	DESCRIPTION 
		"Enable QoS:
			0 - disable, 
			1 - enable
		Device Allocation: AP, SM"
	DEFVAL	{ 0 }
	::= { confQoS 2 }

classificationListTable	 OBJECT-TYPE
	SYNTAX SEQUENCE OF ClassificationListEntry
	MAX-ACCESS not-accessible
	STATUS	   current
	DESCRIPTION 
		"Quality of Service rules Table
		Device Allocation: AP, SM"
	::= { confQoS 3 }
	
mcPriority	OBJECT-TYPE
	SYNTAX	   Integer32 (0|1)
	MAX-ACCESS read-write
	STATUS	   current
	DESCRIPTION
		"Multicast Priority:
			0 - low, 
			1 - high
		Device Allocation: AP, SM"
	DEFVAL	{ 0 }
	::= { confQoS 4 }

bcPriority	OBJECT-TYPE
	SYNTAX	   Integer32 (0|1)
	MAX-ACCESS read-write
	STATUS	   current
	DESCRIPTION
		"Broadcast Priority:
			0 - low, 
			1 - high
		Device Allocation: AP, SM"
	DEFVAL	{ 0 }
	::= { confQoS 5 }

classificationListEntry	 OBJECT-TYPE
	SYNTAX	ClassificationListEntry
	MAX-ACCESS not-accessible
	STATUS	   current
	DESCRIPTION 
		"Quality of Service Rule Entry
		Device Allocation: AP, SM"
	INDEX	{ classificationRuleIndex }
	::= { classificationListTable 1 }

ClassificationListEntry ::= SEQUENCE {
	classificationRuleIndex
		Integer32,
	classificationRuleType
		Integer32,
	classificationRuleValue
		Integer32,
	classificationRuleIP
		IpAddress,
	classificationRuleMAC
		DisplayString,
	classificationRuleMask
		DisplayString,
	classificationRuleDirection
		Integer32,
	classificationRuleQueue
		Integer32
}

classificationRuleIndex	 OBJECT-TYPE
		SYNTAX	   Integer32 (0..14)
		MAX-ACCESS read-write
		STATUS	   current
		DESCRIPTION
		"QoS Rule Table Index
		Table Entry is cleared if Index is set to zero
		Device Allocation: AP, SM"
		::= { classificationListEntry 1 }

classificationRuleType	OBJECT-TYPE
	SYNTAX	   Integer32 (0|1..9)
	MAX-ACCESS read-write
	STATUS	   current
	DESCRIPTION 
		"QoS Rule Type: 
			1 - voip, 
			2 - dscp, 
			3 - cos, 
			4 - vlanid, 
			5 - ethertype, 
			6 - ipv4, 
			7 - mac, 
			8 - broadcast, 
			9 - multicast
		Device Allocation: AP, SM"
	::= { classificationListEntry 2 }

classificationRuleValue	 OBJECT-TYPE
	SYNTAX	   Integer32 (0..65535)
	MAX-ACCESS read-write
	STATUS	   current
	DESCRIPTION 
		"QoS Rule Value. Qos rule value is valid only for dscp, cos, vlanid and ethertype Rule types
		Device Allocation: AP, SM"
	::= { classificationListEntry 3 }

classificationRuleIP  OBJECT-TYPE
	SYNTAX	   IpAddress
	MAX-ACCESS read-write
	STATUS	   current
	DESCRIPTION 
		"QoS IP Address
		Device Allocation: AP, SM"
	::= { classificationListEntry 4 }

classificationRuleMAC  OBJECT-TYPE
	SYNTAX	   DisplayString (SIZE(0|17))
	MAX-ACCESS read-write
	STATUS	   current
	DESCRIPTION 
		"QoS MAC Address
		Device Allocation: AP, SM"
	::= { classificationListEntry 5 }

classificationRuleMask	OBJECT-TYPE
	SYNTAX	   DisplayString (SIZE(0|7..17))
	MAX-ACCESS read-write
	STATUS	   current
	DESCRIPTION 
		"QoS Netmask
		Device Allocation: AP, SM"
	::= { classificationListEntry 6 }

classificationRuleDirection	 OBJECT-TYPE
	SYNTAX	   Integer32 (0|1..3)
	MAX-ACCESS read-write
	STATUS	   current
	DESCRIPTION 
		"IP or MAC Rules direction: 
			1 - Source, 
			2 - Destination, 
			3 - Either (or Both directions)
		Device Allocation: AP, SM"
	::= { classificationListEntry 7 }

classificationRuleQueue	 OBJECT-TYPE
	SYNTAX	   Integer32 (0|1..3)
	MAX-ACCESS read-write
	STATUS	   current
	DESCRIPTION 
		"Rule Queue: 
			1- Hight, 
			2 - Low, 
			3 - VoIP
		Device Allocation: AP, SM"
	::= { classificationListEntry 8 }

portForwardingEntryEnable  OBJECT-TYPE
		SYNTAX	   Integer32 (0|1)
		MAX-ACCESS read-write
		STATUS	   current
		DESCRIPTION
		"Port Forwarding feature:
			0 - Disable, 
			1 - Enable
		Device Allocation: SM"
		::= { portForwarding 1 }

portForwardingTable	 OBJECT-TYPE
		SYNTAX SEQUENCE OF PortForwardingEntry
		MAX-ACCESS not-accessible
		STATUS	   current
		DESCRIPTION
		"Port Forwarding Rules Table
		Device Allocation: SM"
		::= { portForwarding 2 }
		
portForwardingEntry	 OBJECT-TYPE
		SYNTAX	PortForwardingEntry
		MAX-ACCESS not-accessible
		STATUS	   current
		DESCRIPTION
		"Port Forwarding Table Rule Entry
		Device Allocation: SM"
		INDEX	{ portForwardingTableEntryIndex }
		::= { portForwardingTable 1 }

PortForwardingEntry ::= SEQUENCE {
		portForwardingTableEntryIndex
				Integer32,
		portForwardingTableEntryProtocol
				Integer32,
		portForwardingTableEntryWLANPortBegin
				Integer32,
		portForwardingTableEntryWLANPortEnd
				Integer32,
		portForwardingTableEntryLANIP
				IpAddress,
		portForwardingTableEntryWLANPortMappedBegin
				Integer32
}

portForwardingTableEntryIndex  OBJECT-TYPE
		SYNTAX	   Integer32 (0..16)
		MAX-ACCESS read-write
		STATUS	   current
		DESCRIPTION
		"Port Forwarding Table Entry Index
		Table Entry is cleared if Index is set to zero
		Device Allocation: SM"
		::= { portForwardingEntry 1 }

portForwardingTableEntryProtocol  OBJECT-TYPE
		SYNTAX	   Integer32 (0|1|2|3)
		MAX-ACCESS read-write
		STATUS	   current
		DESCRIPTION
		"Port Forwarding Table Entry Rule Protocol:
			0 - Clear Rule, 
			1 - UDP, 
			2 - TCP, 
			3 - UDP+TCP
		Device Allocation: SM"
		::= { portForwardingEntry 2 }

portForwardingTableEntryWLANPortBegin  OBJECT-TYPE
		SYNTAX	   Integer32 (0..65535)
		MAX-ACCESS read-write
		STATUS	   current
		DESCRIPTION
		"Port Forwarding WLAN Port Start number
		Device Allocation: SM"
		::= { portForwardingEntry 3 }

portForwardingTableEntryWLANPortEnd	 OBJECT-TYPE
		SYNTAX	   Integer32 (0..65535)
		MAX-ACCESS read-write
		STATUS	   current
		DESCRIPTION
		"Port Forwarding WLAN Port End number
		Device Allocation: SM"
		::= { portForwardingEntry 4 }

portForwardingTableEntryLANIP  OBJECT-TYPE
		SYNTAX	   IpAddress
		MAX-ACCESS read-write
		STATUS	   current
		DESCRIPTION
		"Port Forwarding LAN IP Address
		Device Allocation: SM"
		::= { portForwardingEntry 5 }

portForwardingTableEntryWLANPortMappedBegin  OBJECT-TYPE
		SYNTAX     Integer32 (0..65535)
		MAX-ACCESS read-write
		STATUS     current
		DESCRIPTION
		"Port Forwarding Mapped Port number
		Device Allocation: SM"
		::= { portForwardingEntry 6 }

portForwardingSepMangIPEntryEnable  OBJECT-TYPE
                SYNTAX     Integer32 (0|1)
                MAX-ACCESS read-write
                STATUS     current
                DESCRIPTION     
                "SM Separate Management IP Port Forwarding feature:
                        0 - Disable,
                        1 - Enable
                Device Allocation: SM"
                ::= { portForwarding 3 }

portForwardingSepMangIPTable      OBJECT-TYPE
                SYNTAX SEQUENCE OF PortForwardingSepMangIPEntry
                MAX-ACCESS not-accessible
                STATUS     current
                DESCRIPTION
                "SM Separate Management IP Port Forwarding Rules Table
                Device Allocation: SM"
                ::= { portForwarding 4 }

portForwardingSepMangIPEntry      OBJECT-TYPE
                SYNTAX  PortForwardingSepMangIPEntry
                MAX-ACCESS not-accessible
                STATUS     current
                DESCRIPTION
                "SM Separate Management IP Port Forwarding Table Rule Entry
                Device Allocation: SM"
                INDEX   { portForwardingSepMangIPTableEntryIndex }
                ::= { portForwardingSepMangIPTable 1 }

PortForwardingSepMangIPEntry ::= SEQUENCE {
                portForwardingSepMangIPTableEntryIndex
                                Integer32,
                portForwardingSepMangIPTableEntryProtocol
                                Integer32,
                portForwardingSepMangIPTableEntryWLANPortBegin
                                Integer32,
                portForwardingSepMangIPTableEntryWLANPortEnd
                                Integer32,
                portForwardingSepMangIPTableEntryLANIP
                                IpAddress,
		portForwardingSepMangIPTableEntryWLANPortMappedBegin
				Integer32
}

portForwardingSepMangIPTableEntryIndex  OBJECT-TYPE
                SYNTAX     Integer32 (0..16)
                MAX-ACCESS read-write
                STATUS     current
                DESCRIPTION
                "SM Separate Management IP Port Forwarding Table Entry Index
                Table Entry is cleared if Index is set to zero
                Device Allocation: SM"
                ::= { portForwardingSepMangIPEntry 1 }

portForwardingSepMangIPTableEntryProtocol  OBJECT-TYPE
                SYNTAX     Integer32 (0|1|2|3)
                MAX-ACCESS read-write
                STATUS     current
                DESCRIPTION
                "SM Separate Management IP Port Forwarding Table Entry Rule Protocol:
                        0 - Clear Rule,
                        1 - UDP,
                        2 - TCP,
                        3 - UDP+TCP
                Device Allocation: SM"
                ::= { portForwardingSepMangIPEntry 2 }

portForwardingSepMangIPTableEntryWLANPortBegin  OBJECT-TYPE
                SYNTAX     Integer32 (0..65535)
                MAX-ACCESS read-write
                STATUS     current
                DESCRIPTION
                "SM Separate Management IP Port Forwarding WLAN Port Start number
                Device Allocation: SM"
                ::= { portForwardingSepMangIPEntry 3 }

portForwardingSepMangIPTableEntryWLANPortEnd      OBJECT-TYPE
                SYNTAX     Integer32 (0..65535)
                MAX-ACCESS read-write
                STATUS     current
                DESCRIPTION
                "SM Separate Management IP Port Forwarding WLAN Port End number
                Device Allocation: SM"
                ::= { portForwardingSepMangIPEntry 4 }

portForwardingSepMangIPTableEntryLANIP  OBJECT-TYPE
                SYNTAX     IpAddress
                MAX-ACCESS read-write
                STATUS     current
                DESCRIPTION
                "SM Separate Management IP Port Forwarding LAN IP Address
                Device Allocation: SM"
                ::= { portForwardingSepMangIPEntry 5 }

portForwardingSepMangIPTableEntryWLANPortMappedBegin  OBJECT-TYPE
                SYNTAX     Integer32 (0..65535)
                MAX-ACCESS read-write
                STATUS     current
                DESCRIPTION
                "SM Separate Management IP Port Forwarding Mapped Port number
                Device Allocation: SM"
                ::= { portForwardingSepMangIPEntry 6 }

staticRoutesEnableMain	 OBJECT-TYPE
		SYNTAX		Integer32 (0|1)
		MAX-ACCESS	read-write
		STATUS		current
		DESCRIPTION
		"Static Routes trigger
			0 - Disable
			1 - Enable"
		DEFVAL	{ 0 }
		::= { routing 1 }

cambiumStaticRoutesCnfTable	 OBJECT-TYPE
	SYNTAX SEQUENCE OF CambiumStaticRoutesCnfEntry
	MAX-ACCESS not-accessible
	STATUS	   current
	DESCRIPTION
		"Static Routes Table"
	::= { routing 2 }

cambiumDeviceAgentEnable  OBJECT-TYPE
		SYNTAX		Integer32 (0|1)
		MAX-ACCESS	read-write
		STATUS		current
		DESCRIPTION
			"Remote Management:
				0 - Disable
				1 - Enable
			Cambium provides cloud management of Cambium devices called cnMaestro.
			This allows a user to manage all of their various Cambium devices via the web from any location in the world.
			This field enables this cnMaestro Cloud Management."
		DEFVAL	{ 1 }
		::= { cambiumDeviceAgent 1 }

cambiumDeviceAgentCNSURL  OBJECT-TYPE
		SYNTAX	   DisplayString (SIZE(0..128))
		MAX-ACCESS read-write
		STATUS	   current
		DESCRIPTION
			"cnMaestro URL:
			 This specifies the URL for accessing the cnMaestro Cloud Manager"
		::= { cambiumDeviceAgent 2 }

cambiumCNSDeviceAgentID  OBJECT-TYPE
		SYNTAX     DisplayString (SIZE(0..128))
		MAX-ACCESS read-write
		STATUS     current
		DESCRIPTION
			"Cambium ID:
			This is a user name for the cnMaestro Remote Management system.
			This is used with the 'Onboarding Key' to on-board older Cambium devices, 
			which are not provisioned with an MSN in the Cambium factory."
		::= { cambiumDeviceAgent 3 }

cambiumCNSDeviceAgentPassword  OBJECT-TYPE
		SYNTAX     DisplayString (SIZE(0..128))
		MAX-ACCESS read-write
		STATUS     current
		DESCRIPTION
			"Onboarding Key:
			This is a password for the cnMaestro Remote Management system.
			This is used with the 'Cambium ID' to on-board older Cambium devices,
			which are not provisioned with an MSN in the Cambium factory."
		::= { cambiumDeviceAgent 4 }

cambiumStaticRoutesCnfEntry OBJECT-TYPE
	SYNTAX	   CambiumStaticRoutesCnfEntry
	MAX-ACCESS not-accessible
	STATUS	   current
	DESCRIPTION
		"Static Routes Dest/Getway pair entry"
	INDEX	{ cambiumStaticRoutesCnfIndex }
	::= { cambiumStaticRoutesCnfTable 1 }

CambiumStaticRoutesCnfEntry ::= SEQUENCE {
	cambiumStaticRoutesCnfIndex
		Integer32,
	cambiumStaticRoutesCnfDestIP
		IpAddress,
	cambiumStaticRoutesCnfGW
		IpAddress,
	cambiumStaticRoutesCnfNetmask
		IpAddress,
	cambiumStaticRoutesCnfEnbl
		Integer32,
	cambiumStaticRoutesCnfInfo
		DisplayString
}

cambiumStaticRoutesCnfIndex	 OBJECT-TYPE
	SYNTAX	  Integer32 (0..16)
	MAX-ACCESS read-write
	STATUS	   current
	DESCRIPTION
		"Index"
	::= { cambiumStaticRoutesCnfEntry 1 }

cambiumStaticRoutesCnfDestIP  OBJECT-TYPE
	SYNTAX	   IpAddress
	MAX-ACCESS read-write
	STATUS	   current
	DESCRIPTION
		"Destination IP"
	::= { cambiumStaticRoutesCnfEntry 2 }

cambiumStaticRoutesCnfGW  OBJECT-TYPE
	SYNTAX	   IpAddress
	MAX-ACCESS read-write
	STATUS	   current
	DESCRIPTION
		"Getway IP"
	::= { cambiumStaticRoutesCnfEntry 3 }

cambiumStaticRoutesCnfNetmask  OBJECT-TYPE
	SYNTAX	   IpAddress
	MAX-ACCESS read-write
	STATUS	   current
	DESCRIPTION
		"Dest IP Netmask"
	::= { cambiumStaticRoutesCnfEntry 4 }

cambiumStaticRoutesCnfEnbl	OBJECT-TYPE
	SYNTAX	   Integer32 (0|1)
	MAX-ACCESS read-write
	STATUS	   current
	DESCRIPTION
		"Static Routes enable an entry"
	::= { cambiumStaticRoutesCnfEntry 5 }

cambiumStaticRoutesCnfInfo	OBJECT-TYPE
	SYNTAX	   DisplayString (SIZE(0..100))
	MAX-ACCESS read-write
	STATUS	   current
	DESCRIPTION
		"Static Routes Interface Name"
	::= { cambiumStaticRoutesCnfEntry 6 }


mgmtVLANEnable	OBJECT-TYPE
		SYNTAX	   Integer32 (0|1)
		MAX-ACCESS read-write
		STATUS	   current
		DESCRIPTION
		"Management VLANs State:
			0 - Disable, 
			1 - Enable
		Device Allocation: AP, SM"
		DEFVAL	{ 0 }
		::= { mgmtVLAN 1 }

mgmtVLANVID	 OBJECT-TYPE
		SYNTAX	   Integer32 (0..4094)
		MAX-ACCESS read-write
		STATUS	   current
		DESCRIPTION
		"Management VLAN ID
		Device Allocation: AP, SM"
		::= { mgmtVLAN 2 }

mgmtVLANVP	OBJECT-TYPE
		SYNTAX	   Integer32 (0..7)
		MAX-ACCESS read-write
		STATUS	   current
		DESCRIPTION
		"Management VLAN VP
		Device Allocation: AP, SM"
		::= { mgmtVLAN 3 }

dataVLANEnable	OBJECT-TYPE
		SYNTAX	   Integer32 (0|1)
		MAX-ACCESS read-write
		STATUS	   current
		DESCRIPTION
		"Data VLANs State:
			0 - Disable, 
			1 - Enable
		Device Allocation: SM"
		DEFVAL	{ 0 }
		::= { dataVLAN 1 }

dataVLANVID	 OBJECT-TYPE
		SYNTAX	   Integer32 (0..4094)
		MAX-ACCESS read-write
		STATUS	   current
		DESCRIPTION
		"Data VLAN ID
		Device Allocation: SM"
		::= { dataVLAN 2 }

dataVLANVP	OBJECT-TYPE
		SYNTAX	   Integer32 (0..7)
		MAX-ACCESS read-write
		STATUS	   current
		DESCRIPTION
		"Data VLAN VP
		Device Allocation: SM"
		::= { dataVLAN 3 }

mcastVLANEnable	 OBJECT-TYPE
		SYNTAX	   Integer32 (0|1)
		MAX-ACCESS read-write
		STATUS	   current
		DESCRIPTION
				"Multicast VLAN State:
						0 - Disable,
						1 - Enable
				Device Allocation: SM"
		DEFVAL	{ 0 }
		::= { mcastVLAN 1 }

mcastVLANVID  OBJECT-TYPE
		SYNTAX	   Integer32 (0..4094)
		MAX-ACCESS read-write
		STATUS	   current
		DESCRIPTION
				"Multicast VLAN ID
				Device Allocation: SM"
		::= { mcastVLAN 2 }

mcastVLANVP	 OBJECT-TYPE
		SYNTAX	   Integer32 (0..7)
		MAX-ACCESS read-write
		STATUS	   current
		DESCRIPTION
				"Multicast VLAN VP
				Device Allocation: SM"
		::= { mcastVLAN 3 }

membershipVLANTable	 OBJECT-TYPE
		SYNTAX SEQUENCE OF MembershipVLANEntry
		MAX-ACCESS not-accessible
		STATUS	   current
		DESCRIPTION
		"Membership VLAN Rules Table
		Device Allocation: SM"
		::= { vlans 3 }
		
membershipVLANEntry	 OBJECT-TYPE
		SYNTAX	MembershipVLANEntry
		MAX-ACCESS not-accessible
		STATUS	   current
		DESCRIPTION
		"Membership VLAN Table Rule Entry
		Device Allocation: SM"
		INDEX	{ membershipVLANTableEntryIndex }
		::= { membershipVLANTable 1 }

MembershipVLANEntry ::= SEQUENCE {
		membershipVLANTableEntryIndex
				Integer32,
		membershipVLANTableEntryVIDBegin
				Integer32,
		membershipVLANTableEntryVIDEnd
				Integer32
}

membershipVLANTableEntryIndex  OBJECT-TYPE
		SYNTAX	   Integer32 (0..16)
		MAX-ACCESS read-write
		STATUS	   current
		DESCRIPTION
		"Membership VLAN Table Entry Index
		Table Entry is cleared if Index is set to zero
		Device Allocation: SM"
		::= { membershipVLANEntry 1 }

membershipVLANTableEntryVIDBegin  OBJECT-TYPE
		SYNTAX	   Integer32 (0|1..4095)
		MAX-ACCESS read-write
		STATUS	   current
		DESCRIPTION
		"Membership VLAN Table Entry VLAN ID Begin
		Device Allocation: SM"
		::= { membershipVLANEntry 2 }

membershipVLANTableEntryVIDEnd	OBJECT-TYPE
		SYNTAX	   Integer32 (0|1..4095)
		MAX-ACCESS read-write
		STATUS	   current
		DESCRIPTION
		"Membership VLAN Table Entry VLAN ID End
		Device Allocation: SM"
		::= { membershipVLANEntry 3 }

mappingVLANTable  OBJECT-TYPE
		SYNTAX SEQUENCE OF MappingVLANEntry
		MAX-ACCESS not-accessible
		STATUS	   current
		DESCRIPTION
				"Mapping VLAN Rules Table
				Device Allocation: SM"
		::= { vlans 5 }

mappingVLANEntry  OBJECT-TYPE
		SYNTAX	MappingVLANEntry
		MAX-ACCESS not-accessible
		STATUS	   current
		DESCRIPTION
				"Mapping VLAN Table Rule Entry
				Device Allocation: SM"
		INDEX	{ mappingVLANTableEntryIndex }
		::= { mappingVLANTable 1 }

MappingVLANEntry ::= SEQUENCE {
		mappingVLANTableEntryIndex
				Integer32,
		mappingVLANTableEntryCVLAN
				Integer32,
		mappingVLANTableEntrySVLAN
				Integer32
}

mappingVLANTableEntryIndex	OBJECT-TYPE
		SYNTAX	   Integer32 (0..16)
		MAX-ACCESS read-write
		STATUS	   current
		DESCRIPTION
				"Mapping VLAN Table Entry Index
				Table Entry is cleared if Index is set to zero
				Device Allocation: SM"
		::= { mappingVLANEntry 1 }

mappingVLANTableEntryCVLAN	OBJECT-TYPE
		SYNTAX	   Integer32 (0|1..4095)
		MAX-ACCESS read-write
		STATUS	   current
		DESCRIPTION
				"Mapping VLAN Table C-VLAN ID,
				 Defines VLAN ID to be mapped from CPE side.
				Device Allocation: SM"
		::= { mappingVLANEntry 2 }

mappingVLANTableEntrySVLAN  OBJECT-TYPE
        SYNTAX     Integer32 (0|1..4095)
        MAX-ACCESS read-write
        STATUS     current
        DESCRIPTION
                "Mapping VLAN Table S-VLAN ID,
                 Defines VLAN ID to be mapped from Service provider.
                Device Allocation: SM"
        ::= { mappingVLANEntry 3 }

dlkmNATSIPHelpers OBJECT-TYPE
	SYNTAX     Integer32 (0|1)
	MAX-ACCESS read-write
	STATUS     current
	DESCRIPTION
		"Enables Auxiliary Netfilter NAT SIP Helper modules support:
			0 - Disable,
			1 - Enabled
		Device Allocation: AP, SM"
	::= { dlkm 1 }

prefferedAPTable OBJECT-TYPE
		SYNTAX SEQUENCE OF PrefferedAPEntry
		MAX-ACCESS not-accessible
		STATUS	   current
		DESCRIPTION
		"Preffered AP Table
		Device Allocation: SM"
		::= { wirelessPrefList 1 }

prefferedAPEntry  OBJECT-TYPE
		SYNTAX	PrefferedAPEntry
		MAX-ACCESS not-accessible
		STATUS	   current
		DESCRIPTION
		"Preffered SSID Table Entry
		Device Allocation: SM"
		INDEX	{ prefferedListTableEntryIndex }
		::= { prefferedAPTable 1 }

PrefferedAPEntry ::= SEQUENCE {
		prefferedListTableEntryIndex
				Integer32,
		prefferedListTableEntrySSID
				DisplayString,
		prefferedListTableEntryKEY
				DisplayString,
		prefferedListTableSecurityMethod
				Integer32
}

prefferedListTableEntryIndex  OBJECT-TYPE
		SYNTAX	   Integer32 (0..16)
		MAX-ACCESS read-write
		STATUS	   current
		DESCRIPTION
		"Preferred AP Table Index
		Table Entry is cleared if Index is set to zero
		Device Allocation: SM"
		::= { prefferedAPEntry 1 }

prefferedListTableEntrySSID	 OBJECT-TYPE
		SYNTAX	   DisplayString (SIZE(0|1..32))
		MAX-ACCESS read-write
		STATUS	   current
		DESCRIPTION
		"Preferred AP SSID
		Device Allocation: SM"
		::= { prefferedAPEntry 2 }

prefferedListTableEntryKEY	OBJECT-TYPE
		SYNTAX	   DisplayString (SIZE(0|8..63))
		MAX-ACCESS read-write
		STATUS	   current
		DESCRIPTION
		"Preferred AP Shared Key
		Device Allocation: SM"
		::= { prefferedAPEntry 3 }
		
prefferedListTableSecurityMethod  OBJECT-TYPE
		SYNTAX	   Integer32(0..6)
		MAX-ACCESS read-write
		STATUS	   current
		DESCRIPTION
		"Authentication modes to connect to AP
		Device Allocation: SM
		Use bitmask to enable pereferred methods, 0 - means enable method:
		set 0-th bit to 0 - Open method (110b)
		set 1-st bit to 0 - WPA2 method (101b)
		set 2-nd bit to 0 - EAP-TTLS method (011b)
		0x00 - All enabled"
		DEFVAL	{ 0 }
		::= { prefferedAPEntry 4 }


cambiumpmp80211DeviceReboot	 OBJECT-TYPE
	SYNTAX	   Integer32 (1)
	MAX-ACCESS read-write
	STATUS	   current
	DESCRIPTION 
		"OID for Device Reboot, send reboot command to device
		Device Allocation: AP, SM"
	::= { cambiumpmp80211SystemActions 1 }

cambiumpmp80211ConfigurationReset  OBJECT-TYPE
	SYNTAX	   Integer32 (1)
	MAX-ACCESS read-write
	STATUS	   current
	DESCRIPTION 
		"OID for System Configuration reset to Defaults
		Device Allocation: AP, SM"
	::= { cambiumpmp80211SystemActions 2 }

cambiumpmp80211ConfigurationSave  OBJECT-TYPE
	SYNTAX	   Integer32 (1)
	MAX-ACCESS read-write
	STATUS	   current
	DESCRIPTION 
		"OID for configuration save
		Device Allocation: AP, SM"
	::= { cambiumpmp80211SystemActions 3 }

-- OID for configuration Apply action

cambiumpmp80211ConfigurationApply  OBJECT-TYPE
	SYNTAX	   Integer32 (1)
	MAX-ACCESS read-write
	STATUS	   current
	DESCRIPTION 
		"OID for configuration Apply
		Device Allocation: AP, SM"
	::= { cambiumpmp80211SystemActions 4 }

cambiumpmp80211ConfigurationDiscard	 OBJECT-TYPE
		SYNTAX	   Integer32 (1)
		MAX-ACCESS read-write
		STATUS	   current
		DESCRIPTION
		"OID for configuration Discard
		Device Allocation: AP, SM"
		::= { cambiumpmp80211SystemActions 5 }

cambiumpmp80211ConfigurationState  OBJECT-TYPE
		SYNTAX	   Integer32 (0..127)
		MAX-ACCESS read-only
		STATUS	   current
		DESCRIPTION
		"System configuration state OID.
		Bit masks:
			0000 0001 - System is configured.
			0000 0010 - There are unsaved changesets.
			0000 0100 - There are unrestarted services.
			0000 1000 - Needed reboot of the system.
			0001 0000 - Configurations was reset.
			0010 0000 - Services restarting in process.
			0100 0000 - Software Update performed.
		Device Allocation: AP, SM"
		::= { cambiumpmp80211SystemActions 6 }

cambiumpmp80211SoftwareUpdate  OBJECT-TYPE
	SYNTAX	   DisplayString
	MAX-ACCESS read-write
	STATUS	   current
	DESCRIPTION 
		"System OID for Software Update Agent,
		SW Update link value can be either remote firmware link (http, https, ftp),
		or local file link: /tmp/firmware.tar.gz
		NOTE: Device is automatically rebooted if link type is remote
		Device Allocation: AP, SM"
	::= { cambiumpmp80211SystemActions 7 }

cambiumpmp80211SoftwareUpdateStatus	 OBJECT-TYPE
	SYNTAX	   Integer32 (0..10)
	MAX-ACCESS read-only
	STATUS	   current
	DESCRIPTION 
		"Software Update Status OID
			0 - No SW Update is pending or No SW upgrade occurs,
			1 - SW Update is in progress, Uploading image to device,
			2 - SW Update is in progress, Verifying SHA2 signature,
			3 - SW Update is in progress, Executing pre-update script,
			4 - SW Update is in progress, Uploading image to flash,
			5 - SW Update is in progress, Uploading u-boot to flash,
			6 - SW Update is in progress, Executing post-update script,
			7 - SW Update is finished, waiting for reboot,
			8 - SW Update is in progress, Executing config down-grade script
		When SW Update is successfully, return value is 7,
		GUI or NMS indicate that SW update was successful,
		Device can be rebooted.
		Device Allocation: AP, SM"
	::= { cambiumpmp80211SystemActions 8 }

cambiumpmp80211STAListUpdate  OBJECT-TYPE
		SYNTAX	   Integer32 (1)
		MAX-ACCESS read-write
		STATUS	   current
		DESCRIPTION
		"System OID for SM List update
		When this OID is received, 
		Connected SM list table is getting updated with actual SM list
		Device Allocation: AP"
		::= { cambiumpmp80211SystemActions 9 }

cambiumpmp80211STAListUpdateStatus	OBJECT-TYPE
		SYNTAX	   Integer32 (0|1|2)
		MAX-ACCESS read-write
		STATUS	   current
		DESCRIPTION
		"Sta List Update Status OID.
		This OID is used to indicate SM list table status:
			0 - No SMs are registerd to AP
			1 - SM List Table is getting updated
			2 - SM Data is ready
		Device Allocation: AP"
		::= { cambiumpmp80211SystemActions 10 }

cambiumpmp80211APListUpdate	 OBJECT-TYPE
		SYNTAX	   Integer32 (1)
		MAX-ACCESS read-write
		STATUS	   current
		DESCRIPTION
		"System OID for AP List update
		When this OID is received,
		Scanned AP list table is getting updated with actual AP scan list
		Device Allocation: SM"
		::= { cambiumpmp80211SystemActions 11 }

cambiumpmp80211APListUpdateStatus  OBJECT-TYPE
		SYNTAX	   Integer32 (0|1|2)
		MAX-ACCESS read-write
		STATUS	   current
		DESCRIPTION
		"AP List Update Status OID.
		This OID is used to indicate AP list table status:
			0 - No APs are available in the list
			1 - AP List Table is getting updated
			2 - AP Data is ready
		Device Allocation: SM"
		::= { cambiumpmp80211SystemActions 12 }

cambiumpmp80211SoftwareUpdateError  OBJECT-TYPE
        SYNTAX     Integer32 (0..22)
        MAX-ACCESS read-only
        STATUS     current
        DESCRIPTION
	  "Software Update error code:
		0 - Finished successfully, waiting for reboot
		1 - SW update file download failed
		2 - Unpack failed, damaged or wrong format package
		3 - Firmware digital signature check failed
		4 - U-Boot digital signature check failed
		5 - Firmware FLASH write failed
		6 - U-Boot FLASH write failed
		7 - Boot partition switch failed
		8 - Board SKU is not supported for this firmware
		9 - Can't read firmware version, upgrade is impossible
		10 - Down-grade not supported for 802.11 driver
		11 - Down-grade below 2.3.1 is not supported for AP Lite device
		12 - Down-grade not supported for non SM TDD mode
		13 - Down-grade below 2.4.2 not supported for Ironman/Ironland board type
		14 - Down-grade below 2.5.0 not supported for AP WiFi
		15 - Down-grade below 2.4.3 not supported for Reset Via Power Sequence
		16 - Down-grade below 2.4.3 not supported for Particular Country Locked device
		17 - Down-grade below 2.5.0 not supported for 2.5ms mode
		18 - Down-grade below 2.5.2 not supported for Use MAC Address as EAP-TTLS Username
		19 - Down-grade below 2.6.0 not supported for 5/10Mhz BW for WiFi & ePTP mode
		20 - Down-grade below 2.6.0 not supported for Separate Management IP Port Forwarding
		21 - General error. Device has no free memory
		22 - General error code
                Device Allocation: AP, SM"
        ::= { cambiumpmp80211SystemActions 13 }

cambiumpmp80211StatsPerSTAListUpdateStatus	OBJECT-TYPE
		SYNTAX	   Integer32 (0|1|2)
		MAX-ACCESS read-write
		STATUS	   current
		DESCRIPTION
				"Stats per SM List Update Status OID.
				 This OID is used to indicate Stats per SM list table status:
				 0 - No SMs are registerd to AP
				 1 - TBD
				 2 - TBD"
		::= { cambiumpmp80211SystemActions 14 }

cambiumpmp80211StatsPerSTAListUpdate  OBJECT-TYPE
		SYNTAX	   Integer32 (1)
		MAX-ACCESS read-write
		STATUS	   current
		DESCRIPTION
				"System OID for Stats per SM table update
				 When this OID is received,
				 Stats per SM table is getting updated with actual data"
		::= { cambiumpmp80211SystemActions 15 }

cambiumpmp80211STADisconnect OBJECT-TYPE
		SYNTAX	   Integer32 (1..120)
		MAX-ACCESS read-write
		STATUS	   current
		DESCRIPTION
				"System OID for particular SM disconnection
				Device Allocation: AP"
		::= { cambiumpmp80211SystemActions 16 }
		
cambiumpmp80211GPSAutopopulate OBJECT-TYPE
		SYNTAX	   Integer32 (1)
		MAX-ACCESS read-write
		STATUS	   current
		DESCRIPTION
				"System action to auto-populate GPS stats for device
				 into system configuration
				 device location for latitude, longitude and height
				Device Allocation: AP, SM"
		::= { cambiumpmp80211SystemActions 17 }
		
cambiumpmp80211SoftwareUpdateErrorStr  OBJECT-TYPE
		SYNTAX	   DisplayString (SIZE(1..128))
		MAX-ACCESS read-only
		STATUS	   current
		DESCRIPTION "Software Update error, text descriprion"
		::= { cambiumpmp80211SystemActions 18 }	 
		
cambiumpmp80211GpsFirmwareUpdate  OBJECT-TYPE
	SYNTAX	   DisplayString
	MAX-ACCESS read-write
	STATUS	   current
	DESCRIPTION 
		"System OID for GPS Firmware Update Agent,
		Gps FW Update link value can be either remote firmware link (http, https, ftp),
		or local file link: /tmp/firmware.tar.gz
		NOTE: Device is automatically rebooted if link type is remote
		Device Allocation: AP, SM"
	::= { cambiumpmp80211SystemActions 19 } 
	
cambiumpmp80211GpsFirmwareUpdateError  OBJECT-TYPE
		SYNTAX	   Integer32 (0..8)
		MAX-ACCESS read-only
		STATUS	   current
		DESCRIPTION
				"Firmware Update error code:
						0 - Finished successfully
						1 - SW update file download failed
						2 - Unpack failed, damaged or wrong format package, or file access error
						3 - GPS Firmware digital signature check failed
						4 - GPS DA digital signature check failed
						5 - GPS DA download to GPS device failed
						6 - GPS FW download to GPS device failed
						7 - Board SKU is not supported for this firmware
						8 - GPS general communication error					  
				Device Allocation: AP, SM"
		::= { cambiumpmp80211SystemActions 21 }
		
cambiumpmp80211GpsFirmwareUpdateErrorStr  OBJECT-TYPE
		SYNTAX	   DisplayString (SIZE(1..128))
		MAX-ACCESS read-only
		STATUS	   current
		DESCRIPTION "GPS Firmware Update error, text description"
		::= { cambiumpmp80211SystemActions 22 }	  

cambiumBridgeTableAPStatus	OBJECT-TYPE
		SYNTAX	   Integer32 (0|1|2)
		MAX-ACCESS read-write
		STATUS	   current
		DESCRIPTION
		"AP Bridge Table Update Status OID.
		This OID is used to indicate bridge table status:
			0 - Bridge table is empty
			1 - Bridge table is filled with data
			2 - AP Data is ready
		Device Allocation: AP"
		::= { cambiumpmp80211SystemActions 25 }

cambiumBridgeTableSTAUpdate	 OBJECT-TYPE
		SYNTAX	   Integer32 (1)
		MAX-ACCESS read-write
		STATUS	   current
		DESCRIPTION
		"System OID for AP Bridge Table update.
		 When this OID is received, bridge table is getting updated with actual
		 bridge table list
		 Device Allocation: SM"
		::= { cambiumpmp80211SystemActions 26 }

cambiumBridgeTableSTAStatus	 OBJECT-TYPE
		SYNTAX	   Integer32 (0|1|2)
		MAX-ACCESS read-write
		STATUS	   current
		DESCRIPTION
		"Bridge Table Update Status OID.
		This OID is used to indicate bridge table status:
			0 - Bridge table is empty
			1 - Bridge table is filled with data
			2 - SM Data is ready
		Device Allocation: SM"
		::= { cambiumpmp80211SystemActions 27 }
		
cambiumBridgeTableAPUpdate	OBJECT-TYPE
		SYNTAX	   Integer32 (1)
		MAX-ACCESS read-write
		STATUS	   current
		DESCRIPTION
		"System OID for Bridge Table update.
		 When this OID is received, bridge table is getting updated with actual
		 bridge table list
		 Device Allocation: AP"
		::= { cambiumpmp80211SystemActions 28 }
			
cambiumForceTabUpdDHCP	OBJECT-TYPE
	SYNTAX	   Integer32 (1)
	MAX-ACCESS read-write
	STATUS	   current
	DESCRIPTION
	"Force update DHCP Host table, 
		1 - Force action
	Device Allocation: SM"
	::= { cambiumpmp80211SystemActions 30 }

cambiumForceTabUpdTrap	OBJECT-TYPE
	SYNTAX	   Integer32 (1)
	MAX-ACCESS read-write
	STATUS	   current
	DESCRIPTION
	"Force update SNMP Trap table, 
		1 - Force action
	Device Allocation: AP, SM"
	::= { cambiumpmp80211SystemActions 31 }

cambiumForceTabUpdl2Frw	 OBJECT-TYPE
	SYNTAX	   Integer32 (1)
	MAX-ACCESS read-write
	STATUS	   current
	DESCRIPTION
	"Force update l2 Firewal table, 
		1 - Force action
	Device Allocation: AP, SM"
	::= { cambiumpmp80211SystemActions 32 }

cambiumForceTabUpdl3Frw	 OBJECT-TYPE
	SYNTAX	   Integer32 (1)
	MAX-ACCESS read-write
	STATUS	   current
	DESCRIPTION
	"Force update l3 Firewal table, 
		1 - Force action
	Device Allocation: AP, SM"
	::= { cambiumpmp80211SystemActions 33 }

cambiumForceTabUpdQos  OBJECT-TYPE
	SYNTAX	   Integer32 (1)
	MAX-ACCESS read-write
	STATUS	   current
	DESCRIPTION
	"Force update Quality of Service table, 
		1 - Force action
	Device Allocation: AP, SM"
	::= { cambiumpmp80211SystemActions 34 }

cambiumForceTabUpdPortFw  OBJECT-TYPE
	SYNTAX	   Integer32 (1)
	MAX-ACCESS read-write
	STATUS	   current
	DESCRIPTION
	"Force update Port Forwarding table, 
		1 - Force action
	Device Allocation: SM"
	::= { cambiumpmp80211SystemActions 35 }

cambiumForceTabUpdVlan	OBJECT-TYPE
	SYNTAX	   Integer32 (1)
	MAX-ACCESS read-write
	STATUS	   current
	DESCRIPTION
	"Force update Membership VLAN table, 
		1 - Force action
	Device Allocation: SM"
	::= { cambiumpmp80211SystemActions 36 }

cambiumForceTabUpdMappingVlan OBJECT-TYPE
	SYNTAX	   Integer32 (1)
		MAX-ACCESS read-write
		STATUS	   current
		DESCRIPTION
		"Force update VLAN Mapping table,
				1 - Force action
		Device Allocation: AP, SM"
		::= { cambiumpmp80211SystemActions 37 }

cambiumConfigurationApplyOnReboot  OBJECT-TYPE
		SYNTAX	   Integer32 (1)
		MAX-ACCESS read-write
		STATUS	   current
		DESCRIPTION
				"OID for configuration Apply
				on stage of device reboot.
				Device Allocation: AP, SM"
		::= { cambiumpmp80211SystemActions 38 }
		
cambiumForceSTARescan OBJECT-TYPE
	SYNTAX	   Integer32 (1)
		MAX-ACCESS read-write
		STATUS	   current
		DESCRIPTION
		"force a STA rescan,
				1 - Force action
		Device Allocation: AP, SM"
		::= { cambiumpmp80211SystemActions 39 }

cambiumForceTabUpdMcastDeny OBJECT-TYPE
	SYNTAX	   Integer32 (1)
		MAX-ACCESS read-write
		STATUS	   current
		DESCRIPTION
		"Force update Multicast deny table,
				1 - Force action
		Device Allocation: AP, SM"
		::= { cambiumpmp80211SystemActions 40 }

cambiumForceTabUpdStaticRoutesCnf OBJECT-TYPE
	SYNTAX	   Integer32 (1)
		MAX-ACCESS read-write
		STATUS	   current
		DESCRIPTION
		"Force update Static Routes Conf table,
				1 - Force action
		Device Allocation: AP, SM"
		::= { cambiumpmp80211SystemActions 41 }

cambiumForceTabUpdMIR OBJECT-TYPE
	SYNTAX	   Integer32 (1)
		MAX-ACCESS read-write
		STATUS	   current
		DESCRIPTION
		"Force update MIR table,
				1 - Force action
		Device Allocation: AP, SM"
		::= { cambiumpmp80211SystemActions 42 }

cambiumForceTabUpdRadiusServ OBJECT-TYPE
	SYNTAX	   Integer32 (1)
		MAX-ACCESS read-write
		STATUS	   current
		DESCRIPTION
		"Force update Radius Server table,
				1 - Force action
		Device Allocation: AP, SM"
		::= { cambiumpmp80211SystemActions 43 }

cambiumForceTabUpdPrefAPList OBJECT-TYPE
	SYNTAX	   Integer32 (1)
		MAX-ACCESS read-write
		STATUS	   current
		DESCRIPTION
		"Force update Preferred AP list table,
				1 - Force action
		Device Allocation: AP, SM"
		::= { cambiumpmp80211SystemActions 44 }

cambiumForceTabUpdAPAlias OBJECT-TYPE
	SYNTAX	   Integer32 (1)
		MAX-ACCESS read-write
		STATUS	   current
		DESCRIPTION
		"Force update AP Alias table,
				1 - Force action
		Device Allocation: AP, SM"
		::= { cambiumpmp80211SystemActions 45 }

cambiumForceTabUpdPortFwSepMangIP  OBJECT-TYPE
        SYNTAX     Integer32 (1)
        MAX-ACCESS read-write
        STATUS     current
        DESCRIPTION
        "Force update Separate Management IP Port Forwarding table,
                1 - Force action
        Device Allocation: SM"
        ::= { cambiumpmp80211SystemActions 46 }

cambiumpmp80211SoftwareUpdateStatusTrap NOTIFICATION-TYPE
	OBJECTS { 
		cambiumpmp80211SoftwareUpdateError, 
		cambiumpmp80211SoftwareUpdateErrorStr 
	}
	STATUS	   current
	DESCRIPTION 
		"Software Update error TRAP. Trap indicating Software Update State. 
		This state is indicated by the included value of cambiumpmp80211GpsFirmwareUpdateError
		Device Allocation: AP, SM"
	::= { cambiumpmp80211SystemTraps 1 }

cambiumpmp80211GPSSyncStatusTrap NOTIFICATION-TYPE
		OBJECTS { cambiumToolbarGPSSyncState }
		STATUS	   current
		DESCRIPTION
		"GPS Sync Status TRAP. Trap indicating GPS Sync State change.
		This state is indicated by the included value of cambiumToolbarGPSSyncState
		Device Allocation: AP, SM"
		::= { cambiumpmp80211SystemTraps 2 }

cambiumpmp80211SystemUpTrap NOTIFICATION-TYPE
		STATUS	   current
		DESCRIPTION
		"System UP TRAP. Trap indicating SNMP subSystem UP
		Device Allocation: AP, SM"
		::= { cambiumpmp80211SystemTraps 3 }

cambiumpmp80211DFSStatusTrap NOTIFICATION-TYPE
		OBJECTS { cambiumDFSStatus, cambiumDFSStatusStr }
		STATUS	   current
		DESCRIPTION
		"DFS Status TRAP. Trap indicating DFS Event.
		This event is indicated by the included value of cambiumDFSStatus
		Device Allocation: AP, SM"
		::= { cambiumpmp80211SystemTraps 4 }

cambiumpmp80211JSONCfgImportTrap NOTIFICATION-TYPE
		OBJECTS { cambiumJSONCfgImportError }
		STATUS	   current
		DESCRIPTION
		"JSON configuration import error trap. Trap catches JSON configuration
		import state. This state is indicated by the included value of
		cambiumJSONCfgImportError.
		Device Allocation: AP, SM"
		::= { cambiumpmp80211SystemTraps 5 }

cambiumpmp80211JSONCfgExportTrap NOTIFICATION-TYPE
		OBJECTS { cambiumJSONCfgExportError }
		STATUS	   current
		DESCRIPTION
		"JSON configuration export error trap. Trap catches JSON configuration
		export state. This state is indicated by the included value of
		cambiumJSONCfgExportError.
		Device Allocation: AP, SM"
		::= { cambiumpmp80211SystemTraps 6 }

cambiumpmp80211FullCfgRestoreTrap NOTIFICATION-TYPE
		OBJECTS { cambiumFullCfgRestoreError }
		STATUS	   current
		DESCRIPTION
		"Full configuration restore error trap. Trap catches full configuration
		restoring state. This state is indicated by the included value of
		cambiumFullCfgRestoreError.
		Device Allocation: AP, SM"
		::= { cambiumpmp80211SystemTraps 7 }

cambiumpmp80211FullCfgBackupTrap NOTIFICATION-TYPE
		OBJECTS { cambiumFullCfgBackUpError }
		STATUS	   current
		DESCRIPTION
		"Full configuration backup error trap. Trap catches full configuration
		backup state. This state is indicated by the included value of
		cambiumFullCfgBackUpError.
		Device Allocation: AP, SM"
		::= { cambiumpmp80211SystemTraps 8 }
		
cambiumpmp80211GpsFirmwareUpdateStatusTrap NOTIFICATION-TYPE
	OBJECTS {  
		cambiumpmp80211GpsFirmwareUpdateError, 
		cambiumpmp80211GpsFirmwareUpdateErrorStr
	}
	STATUS	   current
	DESCRIPTION 
		"GPS Update error TRAP. Trap indicating GPS Firmware Update State. 
		This state is indicated by the included value of cambiumpmp80211GpsFirmwareUpdateError
		Device Allocation: AP, SM"
	::= { cambiumpmp80211SystemTraps 9 }

cambiumpmp80211STADropTrap NOTIFICATION-TYPE
		OBJECTS { cambiumSTAMAC, cambiumSTADropReason }
		STATUS	   current
		DESCRIPTION
		"SM Drop trap. Trap catches dropped SM info. Information is
		contained in the included values of cambiumSTAMAC and
		cambiumSTADropReason.
		Device Allocation: AP"
		::= { cambiumpmp80211SystemTraps 10 }

cambiumpmp80211SMRegTrap NOTIFICATION-TYPE
		OBJECTS { cambiumSTAMAC }
		STATUS	   current
		DESCRIPTION
		"SM Registration trap. Trap catches registered SM info. Information is
		contained in the included value of cambiumSTAMAC.
		Device Allocation: AP"
		::= { cambiumpmp80211SystemTraps 11 }

cambiumpmp80211SystemRebootTrap NOTIFICATION-TYPE
		STATUS	   current
		DESCRIPTION
		"System reboot trap. Trap indicates that snmpd daemon has been shut
		down and the system is going to reboot.
		Device Allocation: AP, SM"
		::= { cambiumpmp80211SystemTraps 12 }
		
cambiumpmp80211SAModeTrap NOTIFICATION-TYPE
		STATUS	   current
		DESCRIPTION
		"Spectrum Analyzer mode trap. Trap indicates that he system is going to
		reboot in SA mode.
		Device Allocation: AP, SM"
		::= { cambiumpmp80211SystemTraps 13 }

cambiumpmpETSIframeSkipTrap NOTIFICATION-TYPE
		STATUS	   current
		DESCRIPTION
		"To much frame skipped due to CCA.
		Device Allocation: AP"
		::= { cambiumpmp80211SystemTraps 14 }

cambiumpmp80211NetworkEntryFailureTrap NOTIFICATION-TYPE
		OBJECTS { cambiumNetworkEntryFailureSTAMAC, cambiumNetworkEntryFailureReason }
		STATUS	   current
		DESCRIPTION
		"SM rejected trap. Trap obtains info about the latest rejected SM. Trap string
		is contained an information string with rejected reason and MAC of 
		rejected SM. Trap message for a host is consisted of cambiumNetworkEntryFailureSTAMAC and 
		cambiumNetworkEntryFailureReason objects.
		Device Allocation: AP"
		::= { cambiumpmp80211SystemTraps 15 }		

cambiumLinkTestDuration	 OBJECT-TYPE
	SYNTAX	   Integer32 (2|4|6|8|10|12|14|16|18|20)
	MAX-ACCESS read-write
	STATUS	   current
	DESCRIPTION
		"Link Test Duration OID.
		Device Allocation: AP, SM"
	DEFVAL	{ 10 }
	::= { cambiumLinkTest 1 }

cambiumLinkTestPckSize	OBJECT-TYPE
	SYNTAX	   Integer32 (128|800|1500)
	MAX-ACCESS read-write
	STATUS	   current
	DESCRIPTION
		"Link Test Packet Size OID.
		Device Allocation: AP, SM"
	DEFVAL	{ 1500 }
	::= { cambiumLinkTest 2 }

cambiumLinkTestStartForMAC	OBJECT-TYPE
	SYNTAX	   DisplayString (SIZE(11..17))
	MAX-ACCESS read-write
	STATUS	   current
	DESCRIPTION
		"The Link Test Destination MAC address.
		Start Link Test by write this OID.
		Device Allocation: AP, SM"
	::= { cambiumLinkTest 3 }

cambiumLinkTestStatus  OBJECT-TYPE
	SYNTAX	   Integer32 (0..6)
	MAX-ACCESS read-only
	STATUS	   current
	DESCRIPTION
		"The Link Test Status OID.
		0: WAIT
		1: START
		2: BUSY
		3: SUCCESS
		4: SUCCESS (PREF PERIOD)
		5: ERROR UNREACHABLE
		6: ERROR FAIL
		Device Allocation: AP, SM"
	::= { cambiumLinkTest 4 }

cambiumLinkTestResultDate  OBJECT-TYPE
	SYNTAX	   DisplayString (SIZE(6..24))
	MAX-ACCESS read-only
	STATUS	   current
	DESCRIPTION
		"The Link Test Result Timestamp
		Device Allocation: AP, SM"
	::= { cambiumLinkTest 5 }

cambiumLinkTestResultUL	 OBJECT-TYPE
	SYNTAX	   Integer32 (0..1000000)
	MAX-ACCESS read-only
	STATUS	   current
	DESCRIPTION
		"Link Test Result Uplink.
		Device Allocation: AP, SM"
	DEFVAL	{ 0 }
	::= { cambiumLinkTest 6 }

cambiumLinkTestResultDL	 OBJECT-TYPE
	SYNTAX	   Integer32 (0..1000000)
	MAX-ACCESS read-only
	STATUS	   current
	DESCRIPTION
		"Link Test Result Downlink.
		Device Allocation: AP, SM"
	DEFVAL	{ 0 }
	::= { cambiumLinkTest 7 }

caminfoScanFrequencyListCountry	 OBJECT-TYPE
		SYNTAX	   DisplayString (SIZE(0..128))
		MAX-ACCESS read-write
		STATUS	   current
		DESCRIPTION
		"Country for Frequency List 20/40 MHz band
		Device Allocation: AP, SM"
		::= { caminfo 1 }

caminfoScanFrequencyListTwentyBand	OBJECT-TYPE
		SYNTAX	   DisplayString (SIZE(0..1064))
		MAX-ACCESS read-only
		STATUS	   current
		DESCRIPTION
		"Scan Frequency List for 20 MHz band
		Device Allocation: SM"
		::= { caminfo 2 }

caminfoScanFrequencyListFortyBand  OBJECT-TYPE
		SYNTAX	   DisplayString (SIZE(0..1064))
		MAX-ACCESS read-only
		STATUS	   current
		DESCRIPTION
		"Scan Frequency List for 40 MHz band
		Device Allocation: SM"
		::= { caminfo 3 }

caminfoScanFrequencyListAllow59band	 OBJECT-TYPE
		SYNTAX	   Integer32 (0|1)
		MAX-ACCESS read-only
		STATUS	   current
		DESCRIPTION
		"Allow 59 band if the board is calibrated
		using new frequency values. 
			0 - Do not Allow 
			1 - Allow
		Device Allocation: AP, SM"
		::= { caminfo 4 }		 

cambiumInternetConnectionServerIP OBJECT-TYPE
		SYNTAX	   IpAddress
		MAX-ACCESS read-write
		STATUS	   current
		DESCRIPTION
		"Internet Connection Server IP Address
		This is auxiliary IP address to ping 
		in order to define Internet connection Status
		Device Allocation: AP, SM"
		::= { cambiumToolBarOpts 1 }

cambiumInternetConnectionPollPeriod OBJECT-TYPE
		SYNTAX	   Integer32 (1..3600)
		MAX-ACCESS read-write
		STATUS	   current
		DESCRIPTION
		"Internet Connection Server Ping period in seconds
		Device Allocation: AP, SM"
		::= { cambiumToolBarOpts 2 }

cambiumToolbarGlobeState OBJECT-TYPE
		SYNTAX	   Integer32 (0|1)
		MAX-ACCESS read-only
		STATUS	   current 
		DESCRIPTION 
		"Globe Internet Connectivity Status Icon State:
			0 - No Internet Connectivity,
			1 - Internet Connectivity
		Device Allocation: AP, SM"
		::= { cambiumToolBarStates 1 }

cambiumToolbarGPSSyncState OBJECT-TYPE
		SYNTAX	   Integer32 (0..5)
		MAX-ACCESS read-only
		STATUS	   current
		DESCRIPTION
		"GPS Current SYNC State:
			0 - The Initialization State
			1 - The No Synchronization State
			2 - The Synchronization State
			3 - The Hold Off State
			4 - The Regaining Sync State
			5 - The Free Run State
		Device Allocation: AP"
		::= { cambiumToolBarStates 2 }

cambiumToolbarDeviceConfigurationState	OBJECT-TYPE
		SYNTAX	   Integer32 (0..127)
		MAX-ACCESS read-only
		STATUS	   current
		DESCRIPTION
		"System configuration state OID.
		Bit masks:
			0000 0001 - System is configured.
			0000 0010 - There are unsaved changesets.
			0000 0100 - There are unrestarted services.
			0000 1000 - Needed reboot of the system.
			0001 0000 - Configurations was reset.
			0010 0000 - Services restarting in process.
			0100 0000 - Software Update performed.
		Device Allocation: AP, SM"
		::= { cambiumToolBarStates 3 }

cambiumToolbarSyncSource OBJECT-TYPE
		SYNTAX	   Integer32 (1|2|3|4)
		MAX-ACCESS read-only
		STATUS	   current
		DESCRIPTION
		"Sync Source Status:
			1 - GPS Sync Up, 
			2 - GPS Sync Down, 
			3 - CMM4 Sync,
			4 - CMM3 Sync
		Device Allocation: AP"
		::= { cambiumToolBarStates 4 }

cambiumToolbarGPSSyncStateStr OBJECT-TYPE
		SYNTAX	   DisplayString (SIZE(0..128))
		MAX-ACCESS read-only
		STATUS	   current
		DESCRIPTION
		"GPS Current SYNC State (text)
		Device Allocation: AP"
		::= { cambiumToolBarStates 5 }

cambiumJSONCfgImport OBJECT-TYPE
		SYNTAX	   DisplayString (SIZE(0..128))
		MAX-ACCESS read-write
		STATUS	   current
		DESCRIPTION
		"OID to start import process, when valid link to JSON configuration file
		is received.
		Device Allocation: AP, SM"
		::= { cambiumCfg 1 }

cambiumJSONCfgImportStatus OBJECT-TYPE
		SYNTAX	   Integer32 (-1..3)
		MAX-ACCESS read-only
		STATUS	   current
		DESCRIPTION
		"OID to get the status of the import process:
		-1	Error
		 0	Idle
		 1	Downloading file
		 2	Importing file
		 3	Rebooting
		Device Allocation: AP, SM"
		::= { cambiumCfg 2 }

cambiumJSONCfgImportError OBJECT-TYPE
		SYNTAX	   DisplayString (SIZE(1..128))
		MAX-ACCESS read-only
		STATUS	   current
		DESCRIPTION
		"Import config Error message (text) 
		Device Allocation: AP, SM"
		::= { cambiumCfg 3 }

cambiumJSONCfgExport OBJECT-TYPE
		SYNTAX	   Integer32 (0|1)
		MAX-ACCESS read-write
		STATUS	   current
		DESCRIPTION
		"OID to start export process
		0	No action
		1	Start
		Device Allocation: AP, SM"
		::= { cambiumCfg 10 }

cambiumJSONCfgExportStatus OBJECT-TYPE
		SYNTAX	   Integer32 (-1..4)
		MAX-ACCESS read-only
		STATUS	   current
		DESCRIPTION
		"OID to get the status of the export process:
		-1	Error
		 0	Idle
		 1	Exporting JSON config
		 2	Moving config into upload directory
		 3	Preparing link for uploading
		 4	Success
		Device Allocation: AP, SM"
		::= { cambiumCfg 11 }

cambiumJSONCfgExportError OBJECT-TYPE
		SYNTAX	   DisplayString (SIZE(1..128))
		MAX-ACCESS read-only
		STATUS	   current
		DESCRIPTION
		"Export config Error message (text)
		Device Allocation: AP, SM"
		::= { cambiumCfg 12 }

cambiumJSONCfgExportLink OBJECT-TYPE
		SYNTAX	   DisplayString (SIZE(0..128))
		MAX-ACCESS read-only
		STATUS	   current
		DESCRIPTION
		"Link to the configuration file on the board
		Device Allocation: AP, SM"
		::= { cambiumCfg 13 }

cambiumFullCfgRestore OBJECT-TYPE
		SYNTAX	   DisplayString (SIZE(0..128))
		MAX-ACCESS read-write
		STATUS	   current
		DESCRIPTION
		"OID to start restore process, when valid link to full configuration
		file is received.
		Device Allocation: AP, SM"
		::= { cambiumCfg 20 }

cambiumFullCfgRestoreStatus OBJECT-TYPE
		SYNTAX	   Integer32 (-1..5)
		MAX-ACCESS read-only
		STATUS	   current
		DESCRIPTION
		"OID to get the status of the restore process:
		-1	Error
		 0	Idle
		 1	Downloading file
		 2	Decrypting
		 3	Unpacking
		 4	Importing
		 5	Rebooting
		Device Allocation: AP, SM"
		::= { cambiumCfg 21 }

cambiumFullCfgRestoreError OBJECT-TYPE
		SYNTAX	   DisplayString (SIZE(1..128))
		MAX-ACCESS read-only
		STATUS	   current
		DESCRIPTION
		"Restore config Error message (text)
		Device Allocation: AP, SM"
		::= { cambiumCfg 22 }

cambiumFullCfgBackUp OBJECT-TYPE
		SYNTAX	   Integer32 (1..7)
		MAX-ACCESS read-write
		STATUS	   current
		DESCRIPTION
		"OID to start backup process
		Bitmask indicating which part of configuration to backup:
		001 - json-config files
		010 - files of security & certificates
		100 - log files 
		Device Allocation: AP, SM"
		::= { cambiumCfg 30 }

cambiumFullCfgBackUpStatus OBJECT-TYPE
		SYNTAX	   Integer32 (-1..5)
		MAX-ACCESS read-only
		STATUS	   current
		DESCRIPTION
		"OID to get the status of the backup process:
		-1	Error
		 0	Idle
		 1	Packing configuration files
		 2	Encrypting configuration files
		 3	Moving packed files into upload directory
		 4	Preparing link for uploading
		 5	Success
		Device Allocation: AP, SM"
		::= { cambiumCfg 31 }

cambiumFullCfgBackUpError OBJECT-TYPE
		SYNTAX	   DisplayString (SIZE(1..128))
		MAX-ACCESS read-only
		STATUS	   current
		DESCRIPTION
		"Backup config Error message (text)
		Device Allocation: AP, SM"
		::= { cambiumCfg 32 }

cambiumFullCfgBackUpLink OBJECT-TYPE
		SYNTAX	   DisplayString
		MAX-ACCESS read-only
		STATUS	   current
		DESCRIPTION
		"Link to the packed configuration files on the board, ready to upload
		Device Allocation: AP, SM"
		::= { cambiumCfg 33 }

acsEnable  OBJECT-TYPE
		SYNTAX	   Integer32 (0|1)
		MAX-ACCESS read-write
		STATUS	   current
		DESCRIPTION
		"Automatic Channel Selection (ACS) automatically selects best values for
		centerFrequency, dfsAlternative1CenterFrequency and dfsAlternative2CenterFrequency:
		 0 - Disable,
		 1 - Enable
		Device Allocation: AP"
		DEFVAL	{ 0 }
		::= { cambiumACSCfg 1 }

acsScanMinDwellTime	 OBJECT-TYPE
		SYNTAX	   Integer32 (50..500)
		MAX-ACCESS read-write
		STATUS	   current
		DESCRIPTION
		"Minimum dwell time during Automatic Channel Selection (ACS) scan in milliseconds.
		Device Allocation: AP"
		DEFVAL	{ 200 }
		::= { cambiumACSCfg 2 }

acsScanMaxDwellTime	 OBJECT-TYPE
		SYNTAX	   Integer32 (300..600)
		MAX-ACCESS read-write
		STATUS	   current
		DESCRIPTION
		"Maximum dwell time during Automatic Channel Selection (ACS) scan in milliseconds.
		Device Allocation: AP"
		DEFVAL	{ 300 }
		::= { cambiumACSCfg 3 }

acsControl	OBJECT-TYPE
		SYNTAX	   Integer32 (0..2)
		MAX-ACCESS read-write
		STATUS	   current
		DESCRIPTION
		"Automatic Channel Selection (ACS) control:
		 0 - No change,
		 1 - Run scan now,
		 2 - Abort current scan
		Device Allocation: AP"
		DEFVAL	{ 0 }
		::= { cambiumACSCfg 4 }

cambiumIDMMode OBJECT-TYPE
		SYNTAX	   Integer32 (0..1)
		MAX-ACCESS read-write
		STATUS	   current
		DESCRIPTION
		"OID to configure IDM Mode
		0 - System Wide
		1 - Local
		Device Allocation: AP, SM"
		::= { cambiumIDM 1 }

cambiumIDMTime OBJECT-TYPE
		SYNTAX	   Integer32 (1000..120000)
		MAX-ACCESS read-write
		STATUS	   current
		DESCRIPTION
		"OID to configure IDM Time.
		Device Allocation: AP, SM"
		::= { cambiumIDM 2 }

cambiumIDMEnable OBJECT-TYPE
		SYNTAX	   Integer32 (0|1)
		MAX-ACCESS read-write
		STATUS	   current
		DESCRIPTION
		"OID to enable/disable IDM feature
		0 - Enable IDM
		1 - Disable IDM
		Device Allocation: AP, SM"
		::= { cambiumIDM 3 }

cambiumIDMResultsTable OBJECT-TYPE
	SYNTAX	   SEQUENCE OF CambiumIDMResultsEntry
	MAX-ACCESS not-accessible
	STATUS	   current
	DESCRIPTION
	"This table contains information of IDM Results:
		  IDM Cycle,
		  Device MAC,
		  Last Comb RSSI,
		  Last Rate,
		  Max Rate,
		  Number of Packets,
		  CRC Comb RSSI,
		  CRC Ch0 RSSI,
		  CRC Ch1 RSSI,
		  CRC Number of Packets,
		  PRQ Comb RSSI,
		  PRQ Ch0 RSSI,
		  PRQ Ch1 RSSI,
		  PRQ Number of Packets,
	Device Allocation: AP, SM"
	::= { cambiumIDM 10 }

cambiumIDMResultsEntry OBJECT-TYPE
	SYNTAX	   CambiumIDMResultsEntry
	MAX-ACCESS not-accessible
	STATUS	   current
	DESCRIPTION
	"Wireless parameters mapping for particular device.
	Device Allocation: AP, SM"
	INDEX	{ cambiumAPNumberOfConnectedSTA }
	::= { cambiumIDMResultsTable 1 }

CambiumIDMResultsEntry ::= SEQUENCE {
		idmDeviceListCycle		  Integer32,
		idmDeviceListMAC		  DisplayString,
		idmDeviceListLCombRSSI	  Integer32,
		idmDeviceListLRate		  DisplayString,
		idmDeviceListMaxRate	  DisplayString,
		idmDeviceListPcktsNum	  Integer32,
		idmDeviceListCRCCombRSSI  Integer32,
		idmDeviceListCRCCh0RSSI	  Integer32,
		idmDeviceListCRCCh1RSSI	  Integer32,
		idmDeviceListCRCPcktsNum  Integer32,
		idmDeviceListPRQCombRSSI  Integer32,
		idmDeviceListPRQCh0RSSI	  Integer32,
		idmDeviceListPRQCh1RSSI	  Integer32,
		idmDeviceListPRQPcktsNum  Integer32
	}

idmDeviceListCycle OBJECT-TYPE
	SYNTAX	   Integer32(1..1024)
	MAX-ACCESS read-only
	STATUS	   current
	DESCRIPTION
	"IDM Cycle Number.
	Device Allocation: AP, SM"
	::= { cambiumIDMResultsEntry 1 }

idmDeviceListMAC OBJECT-TYPE
	SYNTAX	   DisplayString (SIZE(11..17))
	MAX-ACCESS read-only
	STATUS	   current
	DESCRIPTION
	"MAC Address of device collected IDM Statistics.
	Device Allocation: AP, SM"
	::= { cambiumIDMResultsEntry 2 }

idmDeviceListLCombRSSI OBJECT-TYPE
	SYNTAX	   Integer32(-128..127)
	MAX-ACCESS read-only
	STATUS	   current
	DESCRIPTION
	"Combined RSSI of last received MPDU.
	Device Allocation: AP, SM"
	::= { cambiumIDMResultsEntry 3 }

idmDeviceListLRate OBJECT-TYPE
	SYNTAX	   DisplayString (SIZE(1..5))
	MAX-ACCESS read-only
	STATUS	   current
	DESCRIPTION
	"Rate code of last received MPDU.
	Device Allocation: AP, SM"
	::= { cambiumIDMResultsEntry 4 }

idmDeviceListMaxRate OBJECT-TYPE
	SYNTAX	   DisplayString (SIZE(1..5))
	MAX-ACCESS read-only
	STATUS	   current
	DESCRIPTION
	"Maximum rate code.
	Device Allocation: AP, SM"
	::= { cambiumIDMResultsEntry 5 }

idmDeviceListPcktsNum OBJECT-TYPE
	SYNTAX	   Integer32
	MAX-ACCESS read-only
	STATUS	   current
	DESCRIPTION
	"Number of packets filtered by IDM.
	Device Allocation: AP, SM"
	::= { cambiumIDMResultsEntry 6 }

idmDeviceListCRCCombRSSI OBJECT-TYPE
	SYNTAX	   Integer32(-128..127)
	MAX-ACCESS read-only
	STATUS	   current
	DESCRIPTION
	"Combined RSSI of maximum received CRC error MPDU.
	Device Allocation: AP, SM"
	::= { cambiumIDMResultsEntry 7 }

idmDeviceListCRCCh0RSSI OBJECT-TYPE
	SYNTAX	   Integer32(-128..127)
	MAX-ACCESS read-only
	STATUS	   current
	DESCRIPTION
	"Channel 0 RSSI of maximum received CRC error MPDU.
	Device Allocation: AP, SM"
	::= { cambiumIDMResultsEntry 8 }

idmDeviceListCRCCh1RSSI OBJECT-TYPE
	SYNTAX	   Integer32(-128..127)
	MAX-ACCESS read-only
	STATUS	   current
	DESCRIPTION
	"Channel 1 RSSI of maximum received CRC error MPDU.
	Device Allocation: AP, SM"
	::= { cambiumIDMResultsEntry 9 }

idmDeviceListCRCPcktsNum OBJECT-TYPE
	SYNTAX	   Integer32
	MAX-ACCESS read-only
	STATUS	   current
	DESCRIPTION
	"Number of packets with CRC error filtered by IDM.
	Device Allocation: AP, SM"
	::= { cambiumIDMResultsEntry 10 }

idmDeviceListPRQCombRSSI OBJECT-TYPE
	SYNTAX	   Integer32(-128..127)
	MAX-ACCESS read-only
	STATUS	   current
	DESCRIPTION
	"Combined RSSI of maximum received Probe Requests MPDU.
	Device Allocation: AP, SM"
	::= { cambiumIDMResultsEntry 11 }

idmDeviceListPRQCh0RSSI OBJECT-TYPE
	SYNTAX	   Integer32(-128..127)
	MAX-ACCESS read-only
	STATUS	   current
	DESCRIPTION
	"Channel 0 RSSI of maximum received Probe Requests MPDU.
	Device Allocation: AP, SM"
	::= { cambiumIDMResultsEntry 12 }

idmDeviceListPRQCh1RSSI OBJECT-TYPE
	SYNTAX	   Integer32(-128..127)
	MAX-ACCESS read-only
	STATUS	   current
	DESCRIPTION
	"Channel 1 RSSI of maximum received Probe Requests MPDU.
	Device Allocation: AP, SM"
	::= { cambiumIDMResultsEntry 13 }

idmDeviceListPRQPcktsNum OBJECT-TYPE
	SYNTAX	   Integer32
	MAX-ACCESS read-only
	STATUS	   current
	DESCRIPTION
	"Number of Probe Requests filtered by IDM.
	Device Allocation: AP, SM"
	::= { cambiumIDMResultsEntry 14 }

cambiumIDMSumMAC OBJECT-TYPE
	SYNTAX	   DisplayString (SIZE(11..17))
	MAX-ACCESS read-write
	STATUS	   current
	DESCRIPTION
	"MAC Address of device collected IDM Summary Statistics.
	Device Allocation: AP, SM"
	::= { cambiumIDM 11 }

cambiumIDMSumLCombRSSI OBJECT-TYPE
	SYNTAX	   Integer32(-128..127)
	MAX-ACCESS read-only
	STATUS	   current
	DESCRIPTION
	"Summary Combined RSSI of last received MPDU.
	Device Allocation: AP, SM"
	::= { cambiumIDM 12 }

cambiumIDMSumLRate OBJECT-TYPE
	SYNTAX	   DisplayString (SIZE(1..5))
	MAX-ACCESS read-only
	STATUS	   current
	DESCRIPTION
	"Summary Rate code of last received MPDU.
	Device Allocation: AP, SM"
	::= { cambiumIDM 13 }

cambiumIDMSumMaxRate OBJECT-TYPE
	SYNTAX	   DisplayString (SIZE(1..5))
	MAX-ACCESS read-only
	STATUS	   current
	DESCRIPTION
	"Summary Maximum rate code.
	Device Allocation: AP, SM"
	::= { cambiumIDM 14 }

cambiumIDMSumPcktsNum OBJECT-TYPE
	SYNTAX	   Integer32
	MAX-ACCESS read-only
	STATUS	   current
	DESCRIPTION
	"Summary Number of packets filtered by IDM.
	Device Allocation: AP, SM"
	::= { cambiumIDM 15 }

cambiumIDMSumCRCCombRSSI OBJECT-TYPE
	SYNTAX	   Integer32(-128..127)
	MAX-ACCESS read-only
	STATUS	   current
	DESCRIPTION
	"Summary Combined RSSI of maximum received CRC error MPDU.
	Device Allocation: AP, SM"
	::= { cambiumIDM 16 }

cambiumIDMSumCRCCh0RSSI OBJECT-TYPE
	SYNTAX	   Integer32(-128..127)
	MAX-ACCESS read-only
	STATUS	   current
	DESCRIPTION
	"Summary Channel 0 RSSI of maximum received CRC error MPDU.
	Device Allocation: AP, SM"
	::= { cambiumIDM 17 }

cambiumIDMSumCRCCh1RSSI OBJECT-TYPE
	SYNTAX	   Integer32(-128..127)
	MAX-ACCESS read-only
	STATUS	   current
	DESCRIPTION
	"Summary Channel 1 RSSI of maximum received CRC error MPDU.
	Device Allocation: AP, SM"
	::= { cambiumIDM 18 }

cambiumIDMSumCRCPcktsNum OBJECT-TYPE
	SYNTAX	   Integer32
	MAX-ACCESS read-only
	STATUS	   current
	DESCRIPTION
	"Summary Number of packets with CRC error filtered by IDM.
	Device Allocation: AP, SM"
	::= { cambiumIDM 19 }

cambiumIDMSumPRQCombRSSI OBJECT-TYPE
	SYNTAX	   Integer32(-128..127)
	MAX-ACCESS read-only
	STATUS	   current
	DESCRIPTION
	"Summary Combined RSSI of maximum received Probe Requests MPDU.
	Device Allocation: AP, SM"
	::= { cambiumIDM 20 }

cambiumIDMSumPRQCh0RSSI OBJECT-TYPE
	SYNTAX	   Integer32(-128..127)
	MAX-ACCESS read-only
	STATUS	   current
	DESCRIPTION
	"Summary Channel 0 RSSI of maximum received Probe Requests MPDU.
	Device Allocation: AP, SM"
	::= { cambiumIDM 21 }

cambiumIDMSumPRQCh1RSSI OBJECT-TYPE
	SYNTAX	   Integer32(-128..127)
	MAX-ACCESS read-only
	STATUS	   current
	DESCRIPTION
	"Summary Channel 1 RSSI of maximum received Probe Requests MPDU.
	Device Allocation: AP, SM"
	::= { cambiumIDM 22 }

cambiumIDMSumPRQPcktsNum OBJECT-TYPE
	SYNTAX	   Integer32
	MAX-ACCESS read-only
	STATUS	   current
	DESCRIPTION
	"Summary Number of Probe Requests filtered by IDM.
	Device Allocation: AP, SM"
	::= { cambiumIDM 23 }

cambiumIDMSummaryTable OBJECT-TYPE
	SYNTAX	   SEQUENCE OF CambiumIDMSummaryEntry
	MAX-ACCESS not-accessible
	STATUS	   current
	DESCRIPTION
	"This table contains information of IDM Summary Top Interferers:
		  Intrf MAC,
		  Intrf RSSI,
		  Intrf Ch0 RSSI,
		  Intrf Ch1 RSSI,
		  Intrf SSID,
	Device Allocation: AP, SM"
	::= { cambiumIDM 30 }

cambiumIDMSummaryEntry OBJECT-TYPE
	SYNTAX	   CambiumIDMSummaryEntry
	MAX-ACCESS not-accessible
	STATUS	   current
	DESCRIPTION
	"Wireless parameters mapping for particular device.
	Device Allocation: AP, SM"
	INDEX	{ cambiumAPNumberOfConnectedSTA }
	::= { cambiumIDMSummaryTable 1 }

CambiumIDMSummaryEntry ::= SEQUENCE {
		idmSummaryIntMAC	  DisplayString,
		idmSummaryIntCombRSSI Integer32,
		idmSummaryIntCh0RSSI  Integer32,
		idmSummaryIntCh1RSSI  Integer32,
		idmSummaryIntSSID	   DisplayString
	}

idmSummaryIntMAC OBJECT-TYPE SYNTAX		DisplayString (SIZE(11..17))
	MAX-ACCESS read-only
	STATUS	   current
	DESCRIPTION
	"MAC Address of Interferer.
	Device Allocation: AP, SM"
	::= { cambiumIDMSummaryEntry 1 }
idmSummaryIntCombRSSI OBJECT-TYPE SYNTAX	 Integer32(-128..127)
	MAX-ACCESS read-only
	STATUS	   current
	DESCRIPTION
	"Interferer Combined RSSI.
	Device Allocation: AP, SM"
	::= { cambiumIDMSummaryEntry 2 }
idmSummaryIntCh0RSSI OBJECT-TYPE SYNTAX		Integer32(-128..127)
	MAX-ACCESS read-only
	STATUS	   current
	DESCRIPTION
	"Interferer Channel 0 RSSI.
	Device Allocation: AP, SM"
	::= { cambiumIDMSummaryEntry 3 }
idmSummaryIntCh1RSSI OBJECT-TYPE SYNTAX		Integer32(-128..127)
	MAX-ACCESS read-only
	STATUS	   current
	DESCRIPTION
	"Interferer Channel 1 RSSI.
	Device Allocation: AP, SM"
	::= { cambiumIDMSummaryEntry 4 }
idmSummaryIntSSID OBJECT-TYPE SYNTAX	 DisplayString (SIZE(0..32))
	MAX-ACCESS read-only
	STATUS	   current
	DESCRIPTION
	"SSID name of Interferer.
	Device Allocation: AP, SM"
	::= { cambiumIDMSummaryEntry 5 } 

END
