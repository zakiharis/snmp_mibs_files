-- *****************************************************************
-- CISCO-POLICY-GROUP-CAPABILITY.my:
-- Cisco CISCO-POLICY-GROUP-MIB AGENT-CAPABILITIES
--
-- June 2006, Edward Pham 
--
-- Copyright (c) 2006 by Cisco Systems, Inc.
-- All rights reserved.
-- *****************************************************************

CISCO-POLICY-GROUP-CAPABILITY DEFINITIONS ::= BEGIN

IMPORTS
        MODULE-IDENTITY
                FROM SNMPv2-SMI
        InetAddressType
               FROM INET-ADDRESS-MIB
        SnmpAdminString
                FROM SNMP-FRAMEWORK-MIB
        AGENT-CAPABILITIES
                FROM SNMPv2-CONF
        ciscoAgentCapability
                FROM CISCO-SMI;

ciscoPolicyGroupCapability MODULE-IDENTITY
        LAST-UPDATED    "200606260000Z"
        ORGANIZATION    "Cisco Systems, Inc."
        CONTACT-INFO
                "       Cisco Systems
                        Customer Service

                Postal: 170 West Tasman Drive
                        San Jose, CA  95134
                        USA

                   Tel: +1 800 553-NETS

                E-mail: cs-lan-switch-snmp@cisco.com"
        DESCRIPTION
                "The capabilities description of
                 CISCO-POLICY-GROUP-MIB."
        REVISION        "200606260000Z"
        DESCRIPTION
                "Initial version of this MIB module."
        ::= { ciscoAgentCapability 512 }

ciscoPolicyGroupCapV08R0601 AGENT-CAPABILITIES
    PRODUCT-RELEASE      "Cisco CatOS 8.6(1)"
    STATUS               current
    DESCRIPTION         "CISCO-POLICY-GROUP-MIB capabilities."
 
    SUPPORTS             CISCO-POLICY-GROUP-MIB
        INCLUDES         { ciscoCpgGroupInfoGroup,
                           ciscoCpgGroupIpInfoGroup,
                           ciscoCpgPolicyInfoGroup,
                           ciscoCpgPolicyGroupInfoGroup
                         }

        VARIATION        cpgGroupName 
            SYNTAX       SnmpAdminString (SIZE (1..31))
            DESCRIPTION  "Implementation supports a group name of
                          size 1 to 31 octets."

        VARIATION        cpgGroupSourceType 
            SYNTAX       INTEGER { accessList(2) } 
            DESCRIPTION  "Only limited set of enumerated values
                         are supported."

        VARIATION        cpgGroupRowStatus 
            SYNTAX       INTEGER { active(1) }
            ACCESS       read-only
            DESCRIPTION  "Unable to set this object in CatOS."

        VARIATION        cpgGroupIpGroupName 
            SYNTAX       SnmpAdminString (SIZE (1..31))
            DESCRIPTION  "Implementation supports a group name of
                          size 1 to 31 octets."

       VARIATION         cpgGroupIpAddrType 
            SYNTAX       InetAddressType { ipv4(1) }
            DESCRIPTION  "Only limited set of enumerated values
                         are supported."

        VARIATION        cpgGroupIpRowStatus 
            SYNTAX       INTEGER {
                             active(1),
                             createAndGo(4),
                             destroy(6)
                         }
            DESCRIPTION  "Only limited set of enumerated values
                         are supported."

        VARIATION        cpgPolicyName 
            SYNTAX       SnmpAdminString (SIZE (1..31))
            DESCRIPTION  "Implementation supports a policy name of
                          size 1 to 31 octets."

        VARIATION        cpgPolicyGroupPolicyName 
            SYNTAX       SnmpAdminString (SIZE (1..31))
            DESCRIPTION  "Implementation supports a policy name of
                          size 1 to 31 octets."

        VARIATION        cpgPolicyGroupGroupName 
            SYNTAX       SnmpAdminString (SIZE (1..31))
            DESCRIPTION  "Implementation supports a group name of
                          size 1 to 31 octets."

        VARIATION        cpgPolicyGroupRowStatus 
            SYNTAX       INTEGER {
                             active(1),
                             createAndGo(4),
                             destroy(6)
                         }
            DESCRIPTION  "Only limited set of enumerated values
                         are supported."

    ::= { ciscoPolicyGroupCapability 1 }

END
