-- *********************************************************************
-- CISCO-FCIP-MGMT-EXT-MIB.my: Cisco extension mib to
--                             CISCO-FCIP-MGMT-MIB  mib
--
-- December 2002, Srini Kode
-- Copyright (c) 2002-2003, 2004, 2005 by cisco Systems, Inc.
-- All rights reserved.
--
-- *********************************************************************

CISCO-FCIP-MGMT-EXT-MIB DEFINITIONS ::= BEGIN
 
IMPORTS
     OBJECT-TYPE,
     MODULE-IDENTITY,
     Unsigned32                 FROM SNMPv2-SMI
     SnmpAdminString            FROM SNMP-FRAMEWORK-MIB
     TruthValue                 FROM SNMPv2-TC     
     MODULE-COMPLIANCE,
     OBJECT-GROUP               FROM SNMPv2-CONF
     ciscoMgmt                  FROM CISCO-SMI
     cfmFcipEntityInstanceEntry,
     cfmFcipLinkEntry           FROM CISCO-FCIP-MGMT-MIB
     CiscoPort                  FROM CISCO-TC
     InetPortNumber             FROM INET-ADDRESS-MIB
     InterfaceIndex             FROM IF-MIB
     FcList                     FROM CISCO-ZS-MIB;

ciscoFcipMgmtExtMIB MODULE-IDENTITY
     LAST-UPDATED "200510120000Z"
     ORGANIZATION "Cisco Systems Inc."
     CONTACT-INFO
                "     Cisco Systems
                      Customer Service
                Postal: 170 W Tasman Drive
                      San Jose, CA  95134
                      USA
                Tel: +1 800 553 -NETS
                E-mail: cs-san@cisco.com"

     DESCRIPTION
         "A MIB module for extending the CISCO-FCIP-MGMT-MIB
          to add objects which provide additional information
          about FCIP interfaces not available in other MIBS. "

     REVISION    "200510120000Z"
     DESCRIPTION
         "Added the following objects in cfmFcipLinkExtTable:
             - cfmFcipLinkExtTapeReadAccOper
             - cfmFcipLinkExtFiconTAVsanL2k
             - cfmFcipLinkExtFiconTAVsanL4k
             - cfmFcipLinkExtFiconTAVsanLOper2k
             - cfmFcipLinkExtFiconTAVsanLOper4k"

     REVISION    "200506070000Z"
     DESCRIPTION
         "Added the following objects in cfmFcipLinkExtTable:
              cfmFcipLinkExtPhyIfIndex,
              cfmFcipLinkExtWriteAccOper, and
              cfmFcipLinkExtTapeAccOper.
          Also added a new table cfmFcipLinkExtStatsTable with
          objects:
              cfmFcipLinkStatsRxIPCompRatio and
              cfmFcipLinkStatsTxIPCompRatio. "

     REVISION    "200505140000Z"
     DESCRIPTION
          "Added following objects in cfmFcipLinkExtTable.
              cfmFcipLinkExtIPSec
           Added cfmFcipLinkExtGroupRev2Sup1.

           Added following object in cfmFcipEntityExtTable.
              cfmFcipEntityExtTcpLocalPort.
              cfmFcipEntityExtTcpMaxJitter.
              cfmFcipEntityExtTcpSACKEnable.

           Added cfmFcipEntityExtGroupSup1.

           Added cfmFcipExtCompliance4.
          "

     REVISION    "200409230000Z"
     DESCRIPTION 
          "Added following objects in cfmFcipLinkExtTable.
              cfmFcipLinkExtTapeAccelerator,
              cfmFcipLinkExtFlowCtrlBurstSize. 

           Added cfmFcipLinkMapTable. "      

     REVISION    "200403100000Z"
     DESCRIPTION 
          "Added following objects in cfmFcipEntityExtTable.
              cfmFcipEntityExtCWMEnable,
              cfmFcipEntityExtCWMBurstSize. "      

     REVISION    "200311050000Z"
     DESCRIPTION 
          "Removed cfmFcipLinkExtIPCompAlgorithm and renamed
          object cfmFcipLinkExtIPCompPerf to cfmFcipLinkExtIPComp
          Added compliance statement for
          cfmFcipLinkExtTimestampTolerance." 

     REVISION    "200309190000Z"
     DESCRIPTION
         "Added: cfmFcipLinkExtEthIfIndex,
          cfmFcipLinkExtWriteAccelerator,
          cfmFcipLinkExtIPCompAlgorithm,cfmFcipLinkExtIPCompPerf.
          Updated the Compliance statement. "

     REVISION    "200305060000Z"
     DESCRIPTION
         "Modified ranges and added DEFVAL clause to objects: 
          cfmFcipEntityExtTcpSendBufSize,cfmFcipEntityExtTcpMaxBW,
          cfmFcipEntityExtTcpMinAvailBW,
          cfmFcipEntityExtTcpRndTrpTimeEst. "         

     REVISION    "200303250000Z"
     DESCRIPTION
         "Modified objects: cfmFcipEntityExtTcpKeepAliveTO.
          Replaced: cfmFcipLinkExtLocalEntityMode with
          cfmFcipLinkExtLocalBPortEnable. cfmFcipEntityExtTcpInitRTO 
          with cfmFcipEntityExtTcpMinRTO.
          Added: cfmFcipEntityExtTcpSendBufSize,
          cfmFcipEntityExtTcpMaxBW,cfmFcipEntityExtTcpMinAvailBW,
          cfmFcipEntityExtTcpRndTrpTimeEst,cfmFcipLinkExtCntrlQOSField,
          cfmFcipLinkExtDataQOSField.
          Removed cfmFcipEntityExtWindowSize."

     REVISION    "200301070000Z"
     DESCRIPTION
         "Added objects cfmFcipLinkExtSpecialFrameEnable,
          cfmFcipLinkExtBPortKAEnable.
          Modified the range values for some objects. "

     REVISION    "200212060000Z"
     DESCRIPTION
         "Initial version of this MIB module."
     ::= { ciscoMgmt 329 } 
 
ciscoFcipMgmtExtMIBNotifs        OBJECT IDENTIFIER
                                    ::= { ciscoFcipMgmtExtMIB 0 }
ciscoFcipMgmtExtMIBObjects       OBJECT IDENTIFIER
                                    ::= { ciscoFcipMgmtExtMIB 1 }
ciscoFcipMgmtExtMIBConform       OBJECT IDENTIFIER
                                    ::= { ciscoFcipMgmtExtMIB 2 }

cfmFcipMgmtExtConfig          OBJECT IDENTIFIER
                                    ::= { ciscoFcipMgmtExtMIBObjects 1 }

cfmFcipMgmtExtStats           OBJECT IDENTIFIER
                                    ::= { ciscoFcipMgmtExtMIBObjects 2 }
--
-- cfmFcipEntityExtTable
--

cfmFcipEntityExtTable OBJECT-TYPE
     SYNTAX     SEQUENCE OF CfmFcipEntityExtEntry
     MAX-ACCESS not-accessible
     STATUS     current
     DESCRIPTION
         "A table contains objects which provide more information
          of FCIP entity which is not available in
          CISCO-FCIP-MGMT-MIB. "
     ::= { cfmFcipMgmtExtConfig 1 }

cfmFcipEntityExtEntry OBJECT-TYPE
     SYNTAX     CfmFcipEntityExtEntry
     MAX-ACCESS not-accessible
     STATUS     current
     DESCRIPTION
         "A entry into the cfmFcipEntityExtTable. Each entry
          contains attributes associated with an FCIP entity. "
     AUGMENTS { cfmFcipEntityInstanceEntry }
     ::= { cfmFcipEntityExtTable 1 }

CfmFcipEntityExtEntry ::=
     SEQUENCE {
        cfmFcipEntityExtTcpKeepAliveTO   Unsigned32,
        cfmFcipEntityExtTcpMaxReTx       Unsigned32,
        cfmFcipEntityExtPMTUEnable       TruthValue,
        cfmFcipEntityExtPMTUResetTO      Unsigned32,
        cfmFcipEntityExtTcpMinRTO        Unsigned32,
        cfmFcipEntityExtTcpSendBufSize   Unsigned32,
        cfmFcipEntityExtTcpMaxBW         Unsigned32,
        cfmFcipEntityExtTcpMinAvailBW    Unsigned32,
        cfmFcipEntityExtTcpRndTrpTimeEst Unsigned32,
        cfmFcipEntityExtCWMEnable        TruthValue,
        cfmFcipEntityExtCWMBurstSize     Unsigned32,
        cfmFcipEntityExtTcpSACKEnable    TruthValue,
        cfmFcipEntityExtTcpLocalPort     InetPortNumber,
        cfmFcipEntityExtTcpMaxJitter     Unsigned32
}

cfmFcipEntityExtTcpKeepAliveTO   OBJECT-TYPE
     SYNTAX     Unsigned32 (1..7200)
     UNITS      "seconds"
     MAX-ACCESS read-create
     STATUS     current
     DESCRIPTION
         "The TCP Keep alive timeout for all links within this
          entity. "
     DEFVAL {60}
     ::= { cfmFcipEntityExtEntry 1 }

cfmFcipEntityExtTcpMaxReTx   OBJECT-TYPE
     SYNTAX     Unsigned32 (1..8)
     MAX-ACCESS read-create
     STATUS     current
     DESCRIPTION
         "The Maximum number of times that the same item of data
          will be retransmitted over a TCP connection. If delivery
          is not acknowledged after this number of retransmissions
          then the TCP connection is terminated. "
     DEFVAL {4}
     ::= { cfmFcipEntityExtEntry 2 }

cfmFcipEntityExtPMTUEnable   OBJECT-TYPE
     SYNTAX     TruthValue
     MAX-ACCESS read-create
     STATUS     current
     DESCRIPTION
         "The path MTU discovery is enabled if the value of
         this object is true(1), else it is disabled, and
         has the value false(2). "
     REFERENCE
         "RFC 1191 - Path MTU Discovery"
     DEFVAL {true}
     ::= { cfmFcipEntityExtEntry 3 }

cfmFcipEntityExtPMTUResetTO   OBJECT-TYPE
     SYNTAX     Unsigned32 (60..3600)
     UNITS      "seconds"
     MAX-ACCESS read-create
     STATUS     current
     DESCRIPTION
         "The time interval for which the discovered pathMTU
         is valid, before MSS reverts back to the negotiated
         TCP value. This object is writeble only if
         cfmFcipEntityExtPMTUEnable is 'true'. "
     DEFVAL {3600}
     ::= { cfmFcipEntityExtEntry 4 }

cfmFcipEntityExtTcpMinRTO   OBJECT-TYPE
     SYNTAX     Unsigned32 (100..5000)
     UNITS      "milliseconds"
     MAX-ACCESS read-create
     STATUS     current
     DESCRIPTION
         "The TCP minimum retransmit timeout for all the links on
          this entity. "
     DEFVAL {100}
     ::= { cfmFcipEntityExtEntry 5 }

cfmFcipEntityExtTcpSendBufSize   OBJECT-TYPE
     SYNTAX     Unsigned32 (0..8192)
     UNITS      "kilobytes"
     MAX-ACCESS read-create
     STATUS     current
     DESCRIPTION
         "The aggregate TCP send window for all TCP connections on all
          Links within this entity. This value is used for Egress
          Flow Control. When the aggregate of the data queued
          on all connections within this entity reaches this value,
          the sender is flow controlled. "
     DEFVAL {0}
     ::= { cfmFcipEntityExtEntry 6 }

cfmFcipEntityExtTcpMaxBW   OBJECT-TYPE
     SYNTAX     Unsigned32 (1000..1000000)
     UNITS      "kilobits"
     MAX-ACCESS read-create
     STATUS     current
     DESCRIPTION
         "This is an estimate of the Bandwidth of the network pipe
         used for the B-D product computation, which lets us derive
         the TCP receive window to advertise.
         The cfmFcipEntityExtTcpMaxBW,cfmFcipEntityExtTcpMinAvailBW,
         cfmFcipEntityExtTcpRndTrpTimeEst must be set in the same
         SNMP set request. SET operation would fail if this object
         is set individually."
     DEFVAL {1000000}
     ::= { cfmFcipEntityExtEntry 7 }

cfmFcipEntityExtTcpMinAvailBW   OBJECT-TYPE
     SYNTAX     Unsigned32 (1000..1000000)
     UNITS      "kilobits"
     MAX-ACCESS read-create
     STATUS     current
     DESCRIPTION
         "The minimum available bandwidth for the TCP connections
         on the Links within this entity.
         The cfmFcipEntityExtTcpMaxBW,cfmFcipEntityExtTcpMinAvailBW,
         cfmFcipEntityExtTcpRndTrpTimeEst must be set in the same
         SNMP set request. SET operation would fail if this object
         is set individually. "
     DEFVAL {15000}
     ::= { cfmFcipEntityExtEntry 8 }

cfmFcipEntityExtTcpRndTrpTimeEst   OBJECT-TYPE
     SYNTAX     Unsigned32 (0..300000)
     UNITS      "microseconds"
     MAX-ACCESS read-create
     STATUS     current
     DESCRIPTION
         "This is an estimate of the round trip delay of the network
          pipe used for the B-D product computation, which lets us
          derive the TCP receive window to advertise.
          The cfmFcipEntityExtTcpMaxBW,cfmFcipEntityExtTcpMinAvailBW,
          cfmFcipEntityExtTcpRndTrpTimeEst must be set in the same
          SNMP set request. SET operation would fail if this object
          is set individually. "
     DEFVAL {1000}
     ::= { cfmFcipEntityExtEntry 9 }

cfmFcipEntityExtCWMEnable   OBJECT-TYPE
     SYNTAX     TruthValue
     MAX-ACCESS read-create
     STATUS     current
     DESCRIPTION
         "This object is used for enabling/disabling the congestion
          window monitoring. If the value of this object is true(1),
          it is enabled. It is disabled if the value is false(2). "
     REFERENCE
         "Congestion Window Monitoring (Hughes, Touch, and Heidemann)"
     DEFVAL {true}
     ::= { cfmFcipEntityExtEntry 10 }

cfmFcipEntityExtCWMBurstSize   OBJECT-TYPE
     SYNTAX     Unsigned32 (10..100)
     UNITS      "kilobytes"
     MAX-ACCESS read-create
     STATUS     current
     DESCRIPTION
         "The maximum burst sent after a tcp sender idle
          period. This object is writeble only if
          cfmFcipEntityExtCWMEnable is 'true'. "
     DEFVAL {50}
     ::= { cfmFcipEntityExtEntry 11 }

cfmFcipEntityExtTcpSACKEnable OBJECT-TYPE
     SYNTAX     TruthValue
     MAX-ACCESS read-create
     STATUS     current
     DESCRIPTION
         "Setting the value to 'True', enables the Selective
          Acknowledgement (SACK) on this link."
     ::= { cfmFcipEntityExtEntry 12 }

cfmFcipEntityExtTcpLocalPort OBJECT-TYPE
     SYNTAX     InetPortNumber
     MAX-ACCESS read-create
     STATUS     current
     DESCRIPTION
         "The local TCP port to which the local FCIP entity will
         connect if and when it initiates a TCP connection setup
         for this link."
     ::= { cfmFcipEntityExtEntry 13 }

cfmFcipEntityExtTcpMaxJitter  OBJECT-TYPE
     SYNTAX     Unsigned32 (0..65535)
     UNITS      "milliseconds"
     MAX-ACCESS read-create
     STATUS     current
     DESCRIPTION
         "The maximum delay variation that is not due to
          congestion that can be experienced by TCP
          connections for all links on this entity."
     DEFVAL {1}
     ::= { cfmFcipEntityExtEntry 14 }

--
-- cfmFcipLinkExtTable
--

cfmFcipLinkExtTable OBJECT-TYPE
     SYNTAX     SEQUENCE OF CfmFcipLinkExtEntry
     MAX-ACCESS not-accessible
     STATUS     current
     DESCRIPTION
         "A table contains objects which provide more information
         of FCIP link which is not available in CISCO-FCIP-MGMT-MIB."
     ::= { cfmFcipMgmtExtConfig 2 }

cfmFcipLinkExtEntry OBJECT-TYPE
     SYNTAX     CfmFcipLinkExtEntry
     MAX-ACCESS not-accessible
     STATUS     current
     DESCRIPTION
         "A entry into cfmFcipLinkExtTable. Each entry
          contains attributes associated with an FCIP Link. "
     AUGMENTS { cfmFcipLinkEntry }
     ::= { cfmFcipLinkExtTable 1 }

CfmFcipLinkExtEntry ::=
     SEQUENCE {
        cfmFcipLinkExtPassiveMode               TruthValue,
        cfmFcipLinkExtNumTcpConn                Unsigned32,
        cfmFcipLinkExtCheckTimestamp            TruthValue,
        cfmFcipLinkExtTimestampTolerance        Unsigned32,
        cfmFcipLinkExtTcpRemPort                CiscoPort,
        cfmFcipLinkExtLocalBPortEnable          TruthValue,
        cfmFcipLinkExtSpecialFrameEnable        TruthValue,
        cfmFcipLinkExtBPortKAEnable             TruthValue,
        cfmFcipLinkExtCntrlQOSField             Unsigned32,
        cfmFcipLinkExtDataQOSField              Unsigned32,
        cfmFcipLinkExtEthIfIndex                InterfaceIndex,
        cfmFcipLinkExtWriteAccelerator          TruthValue,
        cfmFcipLinkExtIPComp                    INTEGER,
        cfmFcipLinkExtTapeAccelerator           TruthValue,
        cfmFcipLinkExtFlowCtrlBufSize           Unsigned32,
        cfmFcipLinkExtIPSec                     TruthValue,
        cfmFcipLinkExtPhyIfIndex                InterfaceIndex,
        cfmFcipLinkExtWriteAccOper              TruthValue,
        cfmFcipLinkExtTapeAccOper               TruthValue,
        cfmFcipLinkExtTapeReadAccOper           TruthValue,
        cfmFcipLinkExtFiconTAVsanL2k            FcList,
        cfmFcipLinkExtFiconTAVsanL4k            FcList,
        cfmFcipLinkExtFiconTAVsanLOper2k        FcList,
        cfmFcipLinkExtFiconTAVsanLOper4k        FcList
}

cfmFcipLinkExtPassiveMode     OBJECT-TYPE
     SYNTAX     TruthValue
     MAX-ACCESS read-create
     STATUS     current
     DESCRIPTION
         "If the value is set to 'false' this link endpoint actively
         tries to connect to the peer. If it is set to 'true' the link
         endpoint waits for the peer to connect to it. "
     DEFVAL {false}
     ::= { cfmFcipLinkExtEntry 1 }

cfmFcipLinkExtNumTcpConn   OBJECT-TYPE
     SYNTAX     Unsigned32 (1..100)
     UNITS      "tcp connections"
     MAX-ACCESS read-create
     STATUS     current
     DESCRIPTION
         "The maximum number of TCP connections allowed on this
         link. "
     DEFVAL {2}
     ::= { cfmFcipLinkExtEntry 2 }

cfmFcipLinkExtCheckTimestamp   OBJECT-TYPE
     SYNTAX     TruthValue
     MAX-ACCESS read-create
     STATUS     current
     DESCRIPTION
         "The value is 'true', if the timestamp in FCIP header
         is to checked. If 'false' the timestamp is ignored. "
     DEFVAL {false}
     ::= { cfmFcipLinkExtEntry 3 }

cfmFcipLinkExtTimestampTolerance   OBJECT-TYPE
     SYNTAX     Unsigned32 (100..10000)
     UNITS      "milliseconds"
     MAX-ACCESS read-create
     STATUS     current
     DESCRIPTION
         "The accepted time difference between the local time
         and the timestamp value received in the FCIP header.
         By default this value will be EDTOV/2. EDTOV is the
         Error_Detect_Timeout Value used for Fibre channel Ports
         as the timeout value for detecting an error condition."
     REFERENCE
         "Section 29.2.1.2 E_D_TOV in FC-PH (Fibre Channel -
          Physical and Signaling Interface) Rev 4.3."
     ::= { cfmFcipLinkExtEntry 4 }

cfmFcipLinkExtTcpRemPort   OBJECT-TYPE
     SYNTAX     CiscoPort(1..65535)
     MAX-ACCESS read-create
     STATUS     current
     DESCRIPTION
         "The remote TCP port to which the local FCIP entity will
         connect if and when it initiates a TCP connection setup
         for this link. "
     ::= { cfmFcipLinkExtEntry 5 }

cfmFcipLinkExtLocalBPortEnable   OBJECT-TYPE
     SYNTAX     TruthValue
     MAX-ACCESS read-create
     STATUS     current
     DESCRIPTION
         "If the value is set to 'true', the B port mode is enabled
          on the local FCIP link. If set to 'false' the B port mode
          is disabled. "
     DEFVAL {false}
     ::= { cfmFcipLinkExtEntry 6 }

cfmFcipLinkExtSpecialFrameEnable   OBJECT-TYPE
     SYNTAX     TruthValue
     MAX-ACCESS read-create
     STATUS     current
     DESCRIPTION
         "If the value is set to 'true', the TCP active opener
          initiates FCIP special frames and the TCP passive
          opener responds to the FCIP special frames.
          If it is set to 'false', the FCIP special frames are
          neither generated nor responded to. "
     REFERENCE
         "Section 8 in draft-ietf-ips-fcovertcpip-12.txt."
     DEFVAL {false}
     ::= { cfmFcipLinkExtEntry 7 }

cfmFcipLinkExtBPortKAEnable  OBJECT-TYPE
     SYNTAX     TruthValue
     MAX-ACCESS read-create
     STATUS     current
     DESCRIPTION
         "If the value is set to 'true', a message is
          sent in response to a (Fibre Channel) ELS Echo
          frame received from the peer. Some B Port
          implementations use ELS Echo request/response frames
          as Link Keep Alive.
          If it is set to 'false', this response is not
          generated.
          This object is valid only if the
          cfmFcipLinkExtLocalBPortEnable is  'true'. "
     REFERENCE
         "Section 15.5.4 Echo in FC-FS (Fibre Channel -
          Framing and Signaling ) Rev 0.50."
     DEFVAL {false}
     ::= { cfmFcipLinkExtEntry 8 }

cfmFcipLinkExtCntrlQOSField   OBJECT-TYPE
     SYNTAX     Unsigned32 (0..63)
     MAX-ACCESS read-create
     STATUS     current
     DESCRIPTION
         "The value to be set for the TOS field in IP header
         for the TCP control connection.
         The cfmFcipLinkExtCntrlQOSField,cfmFcipLinkExtDataQOSField
         must be set in the same SNMP set request. SET operation would
         fail if this object is set individually. "
     DEFVAL {0}
     ::= { cfmFcipLinkExtEntry 9 }

cfmFcipLinkExtDataQOSField   OBJECT-TYPE
     SYNTAX     Unsigned32 (0..63)
     MAX-ACCESS read-create
     STATUS     current
     DESCRIPTION
         "The value to be set for the TOS field in IP header
         for the TCP Data connection.
         The cfmFcipLinkExtCntrlQOSField,cfmFcipLinkExtDataQOSField
         must be set in the same SNMP set request. SET operation would
         fail if this object is set individually. "
     DEFVAL {0}
     ::= { cfmFcipLinkExtEntry 10 }

cfmFcipLinkExtEthIfIndex   OBJECT-TYPE
    SYNTAX InterfaceIndex
    MAX-ACCESS read-only
    STATUS current
    DESCRIPTION
      "The ifIndex of the interface on which this FCIP link was
      initiated. "
    ::=  { cfmFcipLinkExtEntry 11 }

cfmFcipLinkExtWriteAccelerator   OBJECT-TYPE
     SYNTAX     TruthValue
     MAX-ACCESS read-create
     STATUS     current
     DESCRIPTION
         "The Write accelerator allows for enhancing SCSI write
         performance.
         If 'true', the FCIP Write accelerator is enabled on this link
         If 'false' it is disabled."
     DEFVAL {false}
     ::= { cfmFcipLinkExtEntry  12}

cfmFcipLinkExtIPComp OBJECT-TYPE
     SYNTAX     INTEGER {
                           none(1),
                           highCompressionRatio(2),
                           highThroughput(3),
                           auto(4),
                           mode1(5),
                           mode2(6),
                           mode3(7)
            }
     MAX-ACCESS read-create
     STATUS     current
     DESCRIPTION
         "The configuration for the IP compression.
          'none'                 - ip compression is disabled.

          'highCompressionRatio' - indicates better compression
                                   performance at the cost of lower
                                   throughput.

          'highThroughput'       - indicates better throughput at
                                   the cost of lower compression
                                   performance.

          'auto'                 - indicates that an appropriate
                                   mode wll be picked based on
                                   the bandwidth and data.

          'mode1'                - fast compression mode for high
                                   bandwidth WAN links with bandwidth
                                   greater than 30 Mbps.

          'mode2'                - high compression mode for
                                   moderately low bandwidth WAN links,
                                   i.e. bandwidth between 15 and 30
                                   Mbps.

          'mode3'                - high compression mode for
                                   low bandwidth WAN links,
                                   i.e. banwidth less than 15 Mbps.

         "
     DEFVAL { none }
     ::= { cfmFcipLinkExtEntry 13 }

 cfmFcipLinkExtTapeAccelerator   OBJECT-TYPE
     SYNTAX     TruthValue
     MAX-ACCESS read-create
     STATUS     current
     DESCRIPTION
         "The Tape accelerator allows for enhancing Tape write
         performance.
         If 'true', the FCIP Tape accelerator is enabled on this link
         If 'false' it is disabled."
     DEFVAL {false}
     ::= { cfmFcipLinkExtEntry  14}

 cfmFcipLinkExtFlowCtrlBufSize OBJECT-TYPE
     SYNTAX     Unsigned32 (0..12288)
     UNITS      "bytes"
     MAX-ACCESS read-create
     STATUS     current
     DESCRIPTION
              "The flow control buffer size."
     DEFVAL { 256 }
     ::= { cfmFcipLinkExtEntry 15 }

cfmFcipLinkExtIPSec  OBJECT-TYPE
     SYNTAX     TruthValue
     MAX-ACCESS read-only
     STATUS     current
     DESCRIPTION
         "Indicates whether the IP Security has been turned on or
          off on this link."
     DEFVAL {false}

     ::= { cfmFcipLinkExtEntry 16 }

cfmFcipLinkExtPhyIfIndex   OBJECT-TYPE
    SYNTAX     InterfaceIndex
    MAX-ACCESS read-only
    STATUS     current
    DESCRIPTION
      "The physical ifIndex of the interface on which this FCIP link
      is currently bound. "
    ::=  { cfmFcipLinkExtEntry 17 }

cfmFcipLinkExtWriteAccOper     OBJECT-TYPE
     SYNTAX     TruthValue
     MAX-ACCESS read-only
     STATUS     current
     DESCRIPTION
         "When Write Acceleration is operationally off for the FCIP
         link, the value of this object will be set to 'false'.
         When Write Acceleration is operationally on for the FCIP
         link, the value of this object will be set to 'true'. "
     DEFVAL {false}
     ::= { cfmFcipLinkExtEntry 18 }

cfmFcipLinkExtTapeAccOper     OBJECT-TYPE
     SYNTAX     TruthValue
     MAX-ACCESS read-only
     STATUS     current
     DESCRIPTION
         "When Tape Acceleration is operationally off for the FCIP
         link, the value of this object will be set to 'false'.
         When Tape Acceleration is operationally on for the FCIP
         link, the value of this object will be set to 'true'. "
     DEFVAL {false}
     ::= { cfmFcipLinkExtEntry 19 }

cfmFcipLinkExtTapeReadAccOper     OBJECT-TYPE
     SYNTAX     TruthValue
     MAX-ACCESS read-only
     STATUS     current
     DESCRIPTION
         "This object represents the state of the Tape Read
         Acceleration for an FCIP link.  Tape Read Acceleration
         is automatically operational when Tape Acceleration is
         operational (cfmFcipLinkExtTapeAccOper) and both sides 
         of the FCIP link support Tape Read Acceleration. 
         When Tape Read Acceleration is operationally off for 
         the FCIP link, the value of this object is 'false'. 
         When Tape Read Acceleration is operationally on for 
         the FCIP link, the value of this object is 'true'. "
     DEFVAL {false}
     ::= { cfmFcipLinkExtEntry 20 }

cfmFcipLinkExtFiconTAVsanL2k   OBJECT-TYPE
     SYNTAX     FcList
     MAX-ACCESS read-create
     STATUS     current
     DESCRIPTION
         "The list of VSANs (in the range 1 through 2047)
          for which Ficon Tape Acceleration is configured.
          Only VSANs with a cficonVsanEntry of CISCO-FICON-MIB
          present can be configured for Ficon Tape Acceleration."
     DEFVAL { ''H }
     ::= { cfmFcipLinkExtEntry 21 }

cfmFcipLinkExtFiconTAVsanL4k   OBJECT-TYPE
     SYNTAX     FcList
     MAX-ACCESS read-create
     STATUS     current
     DESCRIPTION
         "The list of VSANs (in the range 2048 through 4096)
          for which Ficon Tape Acceleration is configured.
          Only VSANs with a cficonVsanEntry of CISCO-FICON-MIB
          present can be configured for Ficon Tape Acceleration."
     DEFVAL { ''H }
     ::= { cfmFcipLinkExtEntry 22 }

cfmFcipLinkExtFiconTAVsanLOper2k   OBJECT-TYPE
     SYNTAX     FcList
     MAX-ACCESS read-only
     STATUS     current
     DESCRIPTION
         "The list of VSANs (in the range 1 through 2047)
          for which Ficon Tape Acceleration is operationally
          ON."
     ::= { cfmFcipLinkExtEntry 23 }

cfmFcipLinkExtFiconTAVsanLOper4k   OBJECT-TYPE
     SYNTAX     FcList
     MAX-ACCESS read-only
     STATUS     current
     DESCRIPTION
         "The list of VSANs (in the range 2048 through 4096)
          for which Ficon Tape Acceleration is operationally
          ON."
     ::= { cfmFcipLinkExtEntry 24 }

--
-- cfmFcipLinkMapTable
--
-- A mapping table to map the fcipLinkIndex to
-- fcipEntityId
--

cfmFcipLinkMapTable OBJECT-TYPE
     SYNTAX     SEQUENCE OF CfmFcipLinkMapEntry
     MAX-ACCESS not-accessible
     STATUS     current
     DESCRIPTION
         "A table containing FCIP link index to
          Entity Identifier mapping for a FCIP link."
     ::= { cfmFcipMgmtExtConfig 3 }

cfmFcipLinkMapEntry OBJECT-TYPE
     SYNTAX     CfmFcipLinkMapEntry
     MAX-ACCESS not-accessible
     STATUS     current
     DESCRIPTION
         "A conceptual row of the FCIP link map table
          mapping the fcip link index to FCIP Entity
          Identifier. "
     INDEX { cfmFcipLinkMapIndex }
     ::= { cfmFcipLinkMapTable 1 }

CfmFcipLinkMapEntry ::=
     SEQUENCE {
        cfmFcipLinkMapIndex     Unsigned32,
        cfmFcipMapEntityId      Unsigned32
}

cfmFcipLinkMapIndex  OBJECT-TYPE
     SYNTAX           Unsigned32
     MAX-ACCESS       not-accessible
     STATUS           current
     DESCRIPTION
         "An arbitrary integer which uniquely identifies one FCIP link
          within a FCIP entity. "
     ::= { cfmFcipLinkMapEntry 1 }

cfmFcipMapEntityId   OBJECT-TYPE
     SYNTAX           Unsigned32
     MAX-ACCESS       read-only
     STATUS           current
     DESCRIPTION
         "The FCIP entity Identifier corresponding to the instance
          of cfmFcipLinkMapIndex."
     ::= { cfmFcipLinkMapEntry 2 }

--
-- cfmFcipLinkExtStatsTable
--

cfmFcipLinkExtStatsTable OBJECT-TYPE
     SYNTAX     SEQUENCE OF CfmFcipLinkExtStatsEntry
     MAX-ACCESS not-accessible
     STATUS     current
     DESCRIPTION
         "A table containing objects which provide status information
         of the FCIP link for the cfmFcipLinkExtTable configured
         information. "
     ::= { cfmFcipMgmtExtStats 1 }

cfmFcipLinkExtStatsEntry OBJECT-TYPE
     SYNTAX     CfmFcipLinkExtStatsEntry
     MAX-ACCESS not-accessible
     STATUS     current
     DESCRIPTION
         "An entry into cfmFcipLinkExtStatsTable. Each entry
          contains attributes associated with an FCIP Link. "
     AUGMENTS { cfmFcipLinkEntry }
     ::= { cfmFcipLinkExtStatsTable 1 }

 CfmFcipLinkExtStatsEntry ::=
     SEQUENCE {
        cfmFcipLinkStatsRxIPCompRatio   SnmpAdminString,
        cfmFcipLinkStatsTxIPCompRatio   SnmpAdminString
      }

cfmFcipLinkStatsRxIPCompRatio       OBJECT-TYPE
     SYNTAX     SnmpAdminString
     MAX-ACCESS read-only
     STATUS     current
     DESCRIPTION
         "The IP Copmression ratio for received packets on
         the FCIP device.  The value of this object will be
         presented as a floating point number with two digits
         after the decimal point. "
     ::= { cfmFcipLinkExtStatsEntry 1 }

cfmFcipLinkStatsTxIPCompRatio       OBJECT-TYPE
     SYNTAX     SnmpAdminString
     MAX-ACCESS read-only
     STATUS     current
     DESCRIPTION
         "The IP Copmression ratio for transmitted packets on
         the FCIP device.  The value of this object will be
         presented as a floating point number with two digits
         after the decimal point. "
     ::= { cfmFcipLinkExtStatsEntry 2 }

--
-- Conformance
--
cfmFcipExtCompliances  OBJECT IDENTIFIER
                              ::= { ciscoFcipMgmtExtMIBConform 1 }
cfmFcipExtGroups       OBJECT IDENTIFIER
                              ::= { ciscoFcipMgmtExtMIBConform 2 }

cfmFcipExtCompliance MODULE-COMPLIANCE
     STATUS deprecated  -- superceeded by
                        -- cfmFcipExtCompliance1
     DESCRIPTION
         "Compliance statement for FCIP Extension MIB. "
     MODULE       -- this module
     MANDATORY-GROUPS {
         cfmFcipEntityExtGroup,
         cfmFcipLinkExtGroup
     }

     OBJECT cfmFcipLinkExtNumTcpConn
     SYNTAX Unsigned32 (1..2)
     DESCRIPTION
         "It is compliant to support a value which is
          less than the defined values."

     ::= { cfmFcipExtCompliances 1 }

cfmFcipExtCompliance1 MODULE-COMPLIANCE
     STATUS deprecated  -- superceeded by
                        -- cfmFcipExtCompliance2
     DESCRIPTION
         "Compliance statement for FCIP Extension MIB. "
     MODULE       -- this module
     MANDATORY-GROUPS {
         cfmFcipEntityExtGroup,
         cfmFcipLinkExtGroup,
         cfmFcipLinkExtGroupRev1
     }

     OBJECT cfmFcipLinkExtNumTcpConn
     SYNTAX Unsigned32 (1..2)
     DESCRIPTION
         "It is compliant to support a value which is
          less than the defined values."

     OBJECT cfmFcipLinkExtTimestampTolerance
     DESCRIPTION
         "It is compliant to support only a subset of values
          from the range defined. "
     ::= { cfmFcipExtCompliances 2 }

cfmFcipExtCompliance2 MODULE-COMPLIANCE
     STATUS deprecated -- superceeded by
                       -- cfmFcipExtCompliance3
     DESCRIPTION
         "Compliance statement for FCIP Extension MIB. "
     MODULE       -- this module
     MANDATORY-GROUPS {
         cfmFcipEntityExtGroup,
         cfmFcipLinkExtGroup,
         cfmFcipLinkExtGroupRev1,
         cfmFcipEntityExtCWMGroup
     }

     OBJECT cfmFcipLinkExtNumTcpConn
     SYNTAX Unsigned32 (1..2)
     DESCRIPTION
         "It is compliant to support a value which is
          less than the defined values."

     OBJECT cfmFcipLinkExtTimestampTolerance
     DESCRIPTION
         "It is compliant to support only a subset of values
          from the range defined. "

     OBJECT cfmFcipEntityExtCWMBurstSize
     DESCRIPTION
         "It is compliant to support a value which is
          less than the defined values."
     ::= { cfmFcipExtCompliances 3 }


cfmFcipExtCompliance3 MODULE-COMPLIANCE
     STATUS deprecated  -- superceded by
                        -- cfmFcipExtCompliance4
     DESCRIPTION
         "Compliance statement for FCIP Extension MIB. "
     MODULE       -- this module
     MANDATORY-GROUPS {
         cfmFcipEntityExtGroup,
         cfmFcipLinkExtGroup,
         cfmFcipLinkExtGroupRev1,
         cfmFcipEntityExtCWMGroup,
         cfmFcipLinkExtGroupRev2,
         cfmFcipLinkExtMapGroup

     }

     OBJECT cfmFcipLinkExtNumTcpConn
     SYNTAX Unsigned32 (1..2)
     DESCRIPTION
         "It is compliant to support a value which is
          less than the defined values."

     OBJECT cfmFcipLinkExtTimestampTolerance
     DESCRIPTION
         "It is compliant to support only a subset of values
          from the range defined. "

     OBJECT cfmFcipEntityExtCWMBurstSize
     DESCRIPTION
         "It is compliant to support a value which is
          less than the defined values."
     ::= { cfmFcipExtCompliances 4 }


cfmFcipExtCompliance4 MODULE-COMPLIANCE
     STATUS deprecated -- superceeded by
                       -- cfmFcipExtCompliance5
     DESCRIPTION
         "Compliance statement for FCIP Extension MIB. "
     MODULE       -- this module
     MANDATORY-GROUPS {
         cfmFcipEntityExtGroup,
         cfmFcipEntityExtGroupSup1,
         cfmFcipLinkExtGroup,
         cfmFcipLinkExtGroupRev1,
         cfmFcipEntityExtCWMGroup,
         cfmFcipLinkExtGroupRev2,
         cfmFcipLinkExtGroupRev2Sup1,
         cfmFcipLinkExtMapGroup

     }

     OBJECT cfmFcipLinkExtNumTcpConn
     SYNTAX Unsigned32 (1..2)
     DESCRIPTION
         "It is compliant to support a value which is
          less than the defined values."

     OBJECT cfmFcipLinkExtTimestampTolerance
     DESCRIPTION
         "It is compliant to support only a subset of values
          from the range defined. "

     OBJECT cfmFcipEntityExtCWMBurstSize
     DESCRIPTION
         "It is compliant to support a value which is
          less than the defined values."

     ::= { cfmFcipExtCompliances 5 }

cfmFcipExtCompliance5 MODULE-COMPLIANCE
     STATUS deprecated -- superceeded by
                       -- cfmFcipExtCompliance6
     DESCRIPTION
         "Compliance statement for FCIP Extension MIB. "
     MODULE       -- this module
     MANDATORY-GROUPS {
         cfmFcipEntityExtGroup,
         cfmFcipLinkExtGroup,
         cfmFcipLinkExtGroupRev1,
         cfmFcipEntityExtCWMGroup,
         cfmFcipLinkExtGroupRev2,
         cfmFcipLinkExtGroupRev2Sup1,
         cfmFcipLinkExtGroupRev2Sup2,
         cfmFcipLinkExtStatsGroup
     }

     OBJECT cfmFcipLinkExtNumTcpConn
     SYNTAX Unsigned32 (1..2)
     DESCRIPTION
         "It is compliant to support a value which is
          less than the defined values."

     OBJECT cfmFcipLinkExtTimestampTolerance
     DESCRIPTION
         "It is compliant to support only a subset of values
          from the range defined. "

     OBJECT cfmFcipEntityExtCWMBurstSize
     DESCRIPTION
         "It is compliant to support a value which is
          less than the defined values."
     ::= { cfmFcipExtCompliances 6 }

cfmFcipExtCompliance6 MODULE-COMPLIANCE
     STATUS current
     DESCRIPTION
         "Compliance statement for FCIP Extension MIB. "
     MODULE       -- this module
     MANDATORY-GROUPS {
         cfmFcipEntityExtGroup,
         cfmFcipLinkExtGroup,
         cfmFcipLinkExtGroupRev1,
         cfmFcipEntityExtCWMGroup,
         cfmFcipLinkExtGroupRev2,
         cfmFcipLinkExtGroupRev2Sup1,
         cfmFcipLinkExtGroupRev2Sup2,
         cfmFcipLinkExtStatsGroup,
         cfmFcipLinkExtGroupRev2Sup3
     }

     OBJECT cfmFcipLinkExtNumTcpConn
     SYNTAX Unsigned32 (1..2)
     DESCRIPTION
         "It is compliant to support a value which is
          less than the defined values."

     OBJECT cfmFcipLinkExtTimestampTolerance
     DESCRIPTION
         "It is compliant to support only a subset of values
          from the range defined. "

     OBJECT cfmFcipEntityExtCWMBurstSize
     DESCRIPTION
         "It is compliant to support a value which is
          less than the defined values."
     ::= { cfmFcipExtCompliances 7 }

-- Units of Conformance

cfmFcipEntityExtGroup OBJECT-GROUP
     OBJECTS {
                cfmFcipEntityExtTcpKeepAliveTO,
                cfmFcipEntityExtTcpMaxReTx,
                cfmFcipEntityExtPMTUEnable,
                cfmFcipEntityExtPMTUResetTO,
                cfmFcipEntityExtTcpMinRTO,
                cfmFcipEntityExtTcpSendBufSize,
                cfmFcipEntityExtTcpMaxBW,
                cfmFcipEntityExtTcpMinAvailBW,
                cfmFcipEntityExtTcpRndTrpTimeEst
     }
     STATUS current
     DESCRIPTION
         "A collection of objects providing information about FCIP
          Entity. "
     ::= { cfmFcipExtGroups 1 }

cfmFcipLinkExtGroup OBJECT-GROUP
     OBJECTS {
               cfmFcipLinkExtPassiveMode,
               cfmFcipLinkExtNumTcpConn,
               cfmFcipLinkExtCheckTimestamp,
               cfmFcipLinkExtTimestampTolerance,
               cfmFcipLinkExtTcpRemPort,
               cfmFcipLinkExtLocalBPortEnable,
               cfmFcipLinkExtSpecialFrameEnable,
               cfmFcipLinkExtBPortKAEnable,
               cfmFcipLinkExtCntrlQOSField,
               cfmFcipLinkExtDataQOSField
     }
     STATUS current
     DESCRIPTION
         "A collection of objects providing information about FCIP
          Links. "
     ::= { cfmFcipExtGroups 2 }

cfmFcipLinkExtGroupRev1 OBJECT-GROUP
     OBJECTS {
               cfmFcipLinkExtEthIfIndex,
               cfmFcipLinkExtWriteAccelerator,
               cfmFcipLinkExtIPComp
      }
     STATUS current
     DESCRIPTION
         "A collection of objects providing information about FCIP
          Links. "
     ::= { cfmFcipExtGroups 3 }

cfmFcipEntityExtCWMGroup OBJECT-GROUP
     OBJECTS {
                cfmFcipEntityExtCWMEnable,
                cfmFcipEntityExtCWMBurstSize,
                cfmFcipEntityExtTcpSACKEnable,
                cfmFcipEntityExtTcpLocalPort
     }
     STATUS current
     DESCRIPTION
         "A collection of objects providing information on Congestion
         Window Monitoring of a FCIP Entity. "
     ::= { cfmFcipExtGroups 4 }

cfmFcipLinkExtGroupRev2 OBJECT-GROUP
     OBJECTS {
               cfmFcipLinkExtTapeAccelerator,
               cfmFcipLinkExtFlowCtrlBufSize
      }
     STATUS current
     DESCRIPTION
         "A collection of objects providing information about FCIP
          Links, especially about the tape acceleration. "
     ::= { cfmFcipExtGroups 5 }

cfmFcipLinkExtMapGroup OBJECT-GROUP
     OBJECTS {
               cfmFcipMapEntityId
      }
     STATUS current
     DESCRIPTION
         "A collection of objects providing mapping between FCIP
          Links and their enrity Identifiers "
     ::= { cfmFcipExtGroups 6 }

cfmFcipEntityExtGroupSup1 OBJECT-GROUP
     OBJECTS {
                cfmFcipEntityExtTcpMaxJitter
     }
     STATUS current
     DESCRIPTION
         "A collection of objects providing information about FCIP
          Entity. "
     ::= { cfmFcipExtGroups 7 }

cfmFcipLinkExtGroupRev2Sup1 OBJECT-GROUP
     OBJECTS {
               cfmFcipLinkExtIPSec
      }
     STATUS current
     DESCRIPTION
         "A collection of objects providing information about FCIP
          Links, especially about the tape acceleration and IP
          Security. "
     ::= { cfmFcipExtGroups 8 }

cfmFcipLinkExtGroupRev2Sup2 OBJECT-GROUP
     OBJECTS {
              cfmFcipLinkExtPhyIfIndex,
              cfmFcipLinkExtWriteAccOper,
              cfmFcipLinkExtTapeAccOper
      }
     STATUS current
     DESCRIPTION
         "A collection of objects providing information about FCIP
          Link Operational state."
     ::= { cfmFcipExtGroups 9 }

cfmFcipLinkExtStatsGroup OBJECT-GROUP
     OBJECTS {
               cfmFcipLinkStatsRxIPCompRatio,
               cfmFcipLinkStatsTxIPCompRatio
      }
     STATUS current
     DESCRIPTION
         "A collection of objects providing information about FCIP
          statistics. "
     ::= { cfmFcipExtGroups 10 }

cfmFcipLinkExtGroupRev2Sup3 OBJECT-GROUP
     OBJECTS {
              cfmFcipLinkExtTapeReadAccOper,
              cfmFcipLinkExtFiconTAVsanL2k,
              cfmFcipLinkExtFiconTAVsanL4k,
              cfmFcipLinkExtFiconTAVsanLOper2k,
              cfmFcipLinkExtFiconTAVsanLOper4k
      }
     STATUS current
     DESCRIPTION
         "A collection of objects providing information about FCIP
          Link Tape Read and Ficon Tape Acceleration Configuration
          and Operational status. "
     ::= { cfmFcipExtGroups 11 }

END
