-- *****************************************************************
-- CISCO-UDP-STD-CAPABILITY.my: UDP-MIB AGENT-CAPABILITIES
--   
-- February 2006, Sreenivasulu Chalamcharla
--   
-- Copyright (c) 2006, 2008 by cisco Systems, Inc.
-- All rights reserved.
--   
-- *****************************************************************

CISCO-UDP-STD-CAPABILITY DEFINITIONS ::= BEGIN

IMPORTS
    MODULE-IDENTITY
        FROM SNMPv2-SMI
    AGENT-CAPABILITIES
        FROM SNMPv2-CONF
    ciscoAgentCapability
        FROM CISCO-SMI;


ciscoUdpStdCapability MODULE-IDENTITY
    LAST-UPDATED    "200806300000Z"
    ORGANIZATION    "Cisco Systems, Inc."
    CONTACT-INFO
            "Cisco Systems
            Customer Service
            Postal: 170 West Tasman Drive
            San Jose, CA  95134
            USA

            Tel: +1 800 553-NETS

            E-mail: cs-snmp@cisco.com"
    DESCRIPTION
        "Agent capabilities for UDP-MIB"
    REVISION        "200806300000Z"
    DESCRIPTION
        "Added ciscoUdpStdCapc4710aceVA1R700 agent capability
        for ACE 4710 Application Control Engine Appliance."
    REVISION        "200611080000Z"
    DESCRIPTION
        "Added agent capability for IOS XR 3.4"
    REVISION        "200605260000Z"
    DESCRIPTION
        "Added capability statement
        ciscoUdpStdCapACSWV03R000."
    REVISION        "200602070000Z"
    DESCRIPTION
        "Initial version of this MIB module."
    ::= { ciscoAgentCapability 482 }



ciscoUdpStdCapIOSXRV3R2CRS1 AGENT-CAPABILITIES
    PRODUCT-RELEASE "Cisco IOS XR 3.2.0 for CRS-1"
    STATUS          current
    DESCRIPTION
        "UDP-MIB capabilities
        for IOS XR release 3.2.0"

    SUPPORTS        UDP-MIB
    INCLUDES        {
                        udpGroup,
                        udpBaseGroup,
                        udpHCGroup
                    }
    ::= { ciscoUdpStdCapability 1 }

ciscoUdpStdCapACSWV03R000 AGENT-CAPABILITIES
    PRODUCT-RELEASE "ACSW (Application Control Software) 3.0
                     for Application Control Engine(ACE) 
                     Service Module."
    STATUS          current
    DESCRIPTION
        "UDP-MIB capabilities for ACSW 3.0"

    SUPPORTS        UDP-MIB
    INCLUDES        { udpBaseGroup }
    ::= { ciscoUdpStdCapability 2 }

ciscoUdpStdCapIOSXRV3R4CRS1 AGENT-CAPABILITIES
    PRODUCT-RELEASE "Cisco IOS XR 3.4 for CRS-1"
    STATUS          current
    DESCRIPTION
        "UDP-MIB capabilities
        for IOS XR release 3.4"

    SUPPORTS        UDP-MIB
    INCLUDES        {
                        udpGroup,
                        udpBaseGroup,
                        udpHCGroup,
                        udpEndpointGroup
                    }
    ::= { ciscoUdpStdCapability 3 }

ciscoUdpStdCapc4710aceVA1R700 AGENT-CAPABILITIES
    PRODUCT-RELEASE "ACSW (Application Control Software) A1(7)
                    for ACE 4710 Application Control Engine 
                    Appliance."
    STATUS          current
    DESCRIPTION
        "UDP-MIB capabilities for ACSW A1(7)."

    SUPPORTS        UDP-MIB
    INCLUDES        { udpBaseGroup }
    ::= { ciscoUdpStdCapability 4 }

END
