-- *****************************************************************
--
-- CYAN-MIB.my:  The MIB for Cyan products
--
-- 2014-12-06, Paul Warner
--
-- Copyright (C) 2006-2011 by Cyan, Inc.
-- All rights reserved.
-- 
-- *****************************************************************



CYAN-MIB DEFINITIONS ::= BEGIN

IMPORTS
  MODULE-IDENTITY,
  OBJECT-TYPE,
  OBJECT-IDENTITY,
  NOTIFICATION-TYPE,
  enterprises,
  Integer32
                    FROM SNMPv2-SMI
  TEXTUAL-CONVENTION,
  DisplayString
                     FROM SNMPv2-TC
  MODULE-COMPLIANCE,
  NOTIFICATION-GROUP,
  OBJECT-GROUP
                     FROM SNMPv2-CONF;


cyanAlarmMibModule MODULE-IDENTITY
  LAST-UPDATED "201412070601Z" -- Sun Dec  7 06:01:16 2014
  ORGANIZATION "Cyan, Inc."
  CONTACT-INFO
     "
      E-mail:  support@cyaninc.com

      Postal:  Cyan, Inc.
               1390 N. McDowell Blvd., # G-327
               Petaluma, CA  94954
               USA

      Tel:     +1-707-735-2300"

  DESCRIPTION    "This is the MIB module for Cyan specific MIBs."
  REVISION     "201412070601Z" -- Sun Dec  7 06:01:16 2014
  DESCRIPTION  "Release 6.0 build 1416362081"

  ::= { cyanMibModules 20 }


-- The root of the sub-tree for Cyan OID

cyan OBJECT-IDENTITY
  STATUS current
  DESCRIPTION
    "Sub-tree for Cyan enterprise OID"

  ::= { enterprises 28533 }

cyanMibModules OBJECT-IDENTITY
  STATUS current
  DESCRIPTION
    "Sub-tree to register MIB modules."

  ::= { cyan 5 }

cyanEntityModules OBJECT-IDENTITY
  STATUS current
  DESCRIPTION
    "Sub-tree to register Entity modules."

  ::= { cyanMibModules 30 }

cyanAlarmObjectTypes OBJECT-IDENTITY
     STATUS      current
     DESCRIPTION
           "Objects that get reported with alarms / traps"

     ::= { cyanAlarmMibModule 20 }

cyanAlarmObjectGroups OBJECT-IDENTITY
     STATUS      current
     DESCRIPTION
           "Groups of objects that get reported with alarms / traps"

     ::= { cyanAlarmMibModule 21 }

cyanAlarms OBJECT-IDENTITY
     STATUS      current
     DESCRIPTION
           "traps that can get reported to the manager"

     ::= { cyanAlarmMibModule 30 }



cyanProducts OBJECT-IDENTITY
    STATUS current
	DESCRIPTION
		"This module maps Cyan hardware types to OIDs"

	::= { cyan 1 }

cyanZ77 OBJECT IDENTIFIER ::= { cyanProducts 1}

cyanLAMP OBJECT IDENTIFIER ::= { cyanProducts 2}

cyanZ33 OBJECT IDENTIFIER ::= { cyanProducts 3}

cyanZ22 OBJECT IDENTIFIER ::= { cyanProducts 5}



-- **************************************************************
-- CYAN textual conventions
-- **************************************************************

CyanProbablecauseTc ::= TEXTUAL-CONVENTION
  STATUS current
  DESCRIPTION
      "probableCause"
  SYNTAX INTEGER {
      na              (0),
      unequipped      (1),
      eqptRestart     (2),
      eqptFail        (3),
      eqptDgrade      (4),
      eqptMismtch     (5),
      eqptUnexpected  (6),
      eqptWarning     (7),
      notConfig       (8),
      autoUpgrade     (11),
      batFail         (31),
      batDgrade       (32),
      tpLol           (49),
      preAmp          (50),
      tpLos           (51),
      tpLoc           (52),
      tpLof           (53),
      tpAis           (54),
      tpLom           (55),
      tpSf            (56),
      tpBdi           (57),
      tpFdi           (58),
      tpPmi           (59),
      tpSd            (60),
      tpRdi           (61),
      tpTim           (62),
      tpIae           (63),
      tpBiae          (64),
      tpOci           (65),
      tpLck           (66),
      tpLoflom        (67),
      tpSsf           (68),
      tpOorangeAlm    (69),
      tpOorangeWrn    (70),
      tpFaclpbk       (71),
      tpHighLoss      (72),
      tpLowLoss       (73),
      tpFiber         (74),
      tpPlm           (75),
      tpLtc           (76),
      tpMsim          (77),
      protFail        (78),
      ccm             (79),
      tpLfd           (80),
      tpLink          (81),
      tpGfp           (82),
      tpTpt           (83),
      gtp             (84),
      tpSqm           (85),
      tpLoa           (86),
      tpLti           (87),
      ltm             (88),
      aps             (89),
      tpLop           (90),
      tpUneq          (91),
      csf             (92),
      exmism          (93),
      upm             (94),
      protCmd         (95),
      farendCmd       (96),
      protocolErr     (97),
      loopback        (98),
      lmm             (99),
      dmm             (100),
      commFail        (101),
      commDgrade      (102),
      packetLpbk      (103),
      xcspktsloss     (104),
      xcspktserr      (105),
      srcaddrmis      (106),
      arp             (107),
      tsa             (108),
      erpPort         (109),
      tpLoomfi        (110),
      syncFail        (201),
      syncDgrade      (202),
      holdover        (203),
      xcsholdover     (204),
      syncExcmdActive (205),
      envAlm          (301),
      envWrn          (302),
      incmpld         (401),
      admin           (402)}


CyanAlarmstateTc ::= TEXTUAL-CONVENTION
  STATUS current
  DESCRIPTION
      "alarmState"
  SYNTAX INTEGER {
      asCleared (0),
      asSet     (1)}


CyanTypeTc ::= TEXTUAL-CONVENTION
  STATUS current
  DESCRIPTION
      "type"
  SYNTAX INTEGER {
      unknown                           (0),
      unequipped                        (1),
      unavailable                       (2),
      cyanMs                            (3),
      cyanNetwork                       (4),
      cyanTopologicalline               (5),
      cyanTopologicallink               (6),
      cyanZ77                           (7),
      cyanShelf16slot                   (8),
      cyanShelf16                       (9),
      cyanShelf8                        (10),
      cyanXfpslot                       (11),
      cyanSfpslot                       (12),
      cyanAmcslot                       (13),
      cyanLampcoreeqpt                  (14),
      cyanLampshelf                     (15),
      cyanLamp                          (16),
      cyanShelfslot                     (17),
      cyanZ33                           (18),
      cyanLgx3shelf                     (19),
      cyanOfx4                          (20),
      cyanPemslot                       (21),
      cyanBtmslot                       (22),
      cyanRtmslot                       (23),
      cyanOpticalfabricslot             (24),
      cyanPacketfabricslot              (25),
      cyanAwg40                         (26),
      cyanAwg40shelf                    (27),
      cyanShelf16v2                     (28),
      cyanShelf4                        (29),
      cyanCemslot                       (30),
      cyanBossslot                      (31),
      cyanFimslot                       (32),
      cyanFanslot                       (33),
      cyanOppanelslot                   (34),
      cyanZ77fanslot                    (35),
      cyanZ22                           (36),
      cyanSfppslot                      (37),
      cyanCfpslot                       (38),
      cyanSfppdslot                     (39),
      cyanAwg96shelf                    (40),
      cyanAwg96                         (41),
      cyanOfx8                          (42),
      cyanLad2g                         (96),
      cyanZ22fan                        (97),
      cyanZ77fan                        (98),
      cyanLad2p                         (99),
      cyanZ33fan                        (100),
      cyanBoss                          (101),
      cyanFan                           (106),
      cyanOperationpanel                (107),
      cyanCem                           (108),
      cyanMinifan                       (111),
      cyanLad4                          (112),
      cyanLad4a                         (113),
      cyanMse1482                       (114),
      cyanPsx280                        (115),
      cyanPsw20                         (116),
      cyanLad2pLgx                      (117),
      cyanPme412                        (118),
      cyanSmx28                         (119),
      cyanSmx416                        (120),
      cyanLme4                          (121),
      cyanLad8                          (122),
      cyanLad8a                         (123),
      cyanLad8e                         (124),
      cyanDtm8g                         (126),
      cyanLad2gLgx                      (127),
      cyanDtm8                          (128),
      cyanSft8                          (129),
      cyanLac8                          (130),
      cyanLedpanel                      (131),
      cyanWss402                        (132),
      cyanWss404                        (133),
      cyanPme216                        (135),
      cyanWmx                           (136),
      cyanCemi                          (137),
      cyanLad8i                         (138),
      cyanLad40                         (139),
      cyanLad40e                        (140),
      cyanLme10g10                      (141),
      cyanXc2800                        (143),
      cyanTsw10                         (144),
      cyanBoss2                         (146),
      cyanDtm4                          (147),
      cyanLad8x                         (148),
      cyanSft10g16                      (149),
      cyanFlx216                        (150),
      cyanDtm100g                       (151),
      cyanPsw10                         (152),
      cyanPsw618                        (153),
      cyanPsw100g                       (154),
      cyanMsw10g12                      (155),
      cyanDtm100g2                      (156),
      cyanLad96                         (157),
      cyanPsw10g20                      (159),
      cyanWssF2                         (160),
      cyanWssF4                         (161),
      cyanWssF8                         (162),
      cyanOla200                        (163),
      cyanOla201                        (164),
      cyanOla220                        (165),
      cyanOla010                        (166),
      cyanOla221                        (167),
      cyanXfpxcvr                       (201),
      cyanCfpxcvr                       (202),
      cyanSfpxcvr                       (204),
      cyanAmc                           (207),
      cyanPem2                          (299),
      cyanLampbtm                       (300),
      cyanBtm                           (301),
      cyanPxc280                        (303),
      cyanPem                           (304),
      cyanR1g8sfp                       (305),
      cyanRtm2x                         (306),
      cyanRcm                           (308),
      cyanMidstageptp                   (309),
      cyanEqptClockTtp                  (310),
      cyanStm1msTtp                     (311),
      cyanStm4msTtp                     (312),
      cyanStm16msTtp                    (313),
      cyanStm64msTtp                    (314),
      cyanSaug1Ttp                      (315),
      cyanAug1Ttp                       (316),
      cyanAug4Ttp                       (317),
      cyanAug16Ttp                      (318),
      cyanAug64Ttp                      (319),
      cyanSaug4Ttp                      (320),
      cyanStm1rsTtp                     (321),
      cyanStm4rsTtp                     (322),
      cyanStm16rsTtp                    (323),
      cyanStm64rsTtp                    (324),
      cyanMuxadddropfiberptp            (325),
      cyanOcgptp                        (326),
      cyanTxextsdTtp                    (327),
      cyanTxsdTtp                       (328),
      cyanRxsdTtp                       (329),
      cyanAdddropcwdmfiberptp           (330),
      cyanLinetimingttp                 (331),
      cyan3rfiberptp                    (332),
      cyan10gafiberptp                  (333),
      cyanLadoscTtp                     (334),
      cyanLadaomsTtp                    (335),
      cyanLadomsTtp                     (336),
      cyanAdddropfiberptp               (337),
      cyanS1fiberptp                    (338),
      cyanS4fiberptp                    (339),
      cyanS16fiberptp                   (340),
      cyanS16mrfiberptp                 (341),
      cyanS64fiberptp                   (342),
      cyanOtu2fiberptp                  (343),
      cyanLadeotmPtp                    (344),
      cyanSdhlinkftp                    (345),
      cyanExtcc2mhzrxttp                (346),
      cyanExtcc2mhzptp                  (347),
      cyanPflinkttp                     (348),
      cyanLinkftp                       (349),
      cyan10gemfiberptp                 (350),
      cyanElectricalctp                 (351),
      cyanOtmPtp                        (352),
      cyanFiberptp                      (353),
      cyanFiberttp                      (354),
      cyan10gfiberptp                   (355),
      cyan10gefiberptp                  (356),
      cyanDerivedtimingreference        (357),
      cyanTimingrefftp                  (358),
      cyanTss                           (359),
      cyanExttimingreference            (360),
      cyanTimingreference               (361),
      cyanExttimingptp                  (362),
      cyanExttimingtxttp                (363),
      cyanExttimingrxttp                (364),
      cyanOc48Ttp                       (365),
      cyanStm16Ttp                      (366),
      cyanOc192Ttp                      (367),
      cyanStm64Ttp                      (368),
      ituOtu1gcc0tp                     (369),
      ituOtu2gcc0tp                     (370),
      ituOdu1gcc12tp                    (371),
      ituOdu2gcc12tp                    (372),
      cyanOdu1nim                       (373),
      cyanOdu2nim                       (374),
      cyanOdu1ctp                       (375),
      cyanOdu2ctp                       (376),
      cyanOdu1tcmTtp                    (377),
      cyanOdu2tcmTtp                    (378),
      cyanClientftp                     (379),
      cyanOdu1ttp                       (380),
      cyanOdu2ttp                       (381),
      cyanOtukctp                       (382),
      cyanOtu1ttp                       (383),
      cyanOtu2ttp                       (384),
      cyanFiberotu2ttp                  (385),
      cyanOcgttp                        (386),
      cyanOccnimctp                     (387),
      cyanOccttp                        (388),
      cyanOchttp                        (389),
      cyanOscttp                        (390),
      cyanOmsTtp                        (391),
      cyanOtsTtp                        (392),
      cyanLag                           (393),
      cyanLampotmPtp                    (394),
      cyanLadotmPtp                     (395),
      cyanLadaotmPtp                    (396),
      cyanLadotsTtp                     (397),
      cyanTetyTtp                       (398),
      cyanMauTtp                        (399),
      cyanMautTtp                       (400),
      cyanGfpTtp                        (401),
      cyanEttyTtp                       (402),
      cyanEty31Ptp                      (403),
      cyanEty32Ptp                      (404),
      cyanGigeptp                       (405),
      cyanEthernetttp                   (406),
      cyanEtyTtp                        (407),
      cyanDcnptp                        (408),
      pbbEspTesi                        (409),
      pbbFlowpointpool                  (410),
      cyanEthflowpointpool              (411),
      cyanEthuni                        (412),
      cyanEthnni                        (413),
      cyanOccctp                        (414),
      cyanEthlagfpp                     (415),
      cyanGfecotu2ttp                   (416),
      cyanTety10gTtp                    (417),
      cyanEtty10gTtp                    (418),
      cyanLadeotsTtp                    (419),
      cyanLadeomsTtp                    (420),
      cyanEthflowpoint                  (421),
      pbbFlowpoint                      (422),
      cyanEosApi                        (423),
      cyanOtu2ettp                      (424),
      dot1agmip                         (425),
      cyanEthlagflowpoint               (426),
      cyanOdu2ettp                      (427),
      cyanUfecotu2ttp                   (428),
      cyan10geofiberptp                 (429),
      cyanWmxotmPtp                     (430),
      dot3ahmep                         (431),
      cyanEoamApi                       (432),
      cyanEthflowdomain                 (433),
      cyanEthbridge                     (434),
      dot1agmd                          (435),
      dot1agma                          (436),
      dot1agmep                         (437),
      cyanFtp                           (438),
      cyanVcg                           (439),
      pbbGtp                            (440),
      cyanEthbwprofile                  (441),
      cyanEthcosprofile                 (442),
      cyanEthqueueprofile               (443),
      cyanUserethqueueprofile           (444),
      cyanUserethbwprofile              (445),
      cyanEthlinkoamprofile             (446),
      cyanUserethlinkoamprofile         (447),
      cyanEthkbwprofile                 (448),
      cyanUserethkbwprofile             (449),
      cyanSdhsonetApi                   (450),
      cyanXgewanTtp                     (451),
      cyanAdddropwwdmfiberptp           (452),
      cyanMultifibertp                  (453),
      cyanOcgettp                       (454),
      cyanSethTtp                       (455),
      cyanLadocgptp                     (456),
      cyanmd                            (457),
      cyanEty32bPtp                     (458),
      cyanGigeptpnopmstats              (459),
      cyanEthernetttpwpmstats           (460),
      cyanGigeptpnopmstatsroute         (461),
      cyan10gaofiberptp                 (462),
      cyanOdu0ttp                       (463),
      cyanOduflexttp                    (464),
      cyanOdu2muxttp                    (465),
      cyanOdu1muxttp                    (466),
      cyanErppGtp                       (467),
      erpFlowpointpool                  (468),
      erpFlowpoint                      (469),
      cyanSethTxttp                     (470),
      cyanLad40eotmPtp                  (471),
      cyan3r10gmrfiberptp               (472),
      cyanLad8xotmPtp                   (473),
      cyan10geopfiberptp                (474),
      cyanNetty10gTtp                   (475),
      cyanErpv2Profile                  (476),
      cyanUsererpv2Profile              (477),
      cyanPathpg                        (478),
      cyanEthoamprofile                 (479),
      cyanUserethoamprofile             (480),
      eprotectiongroupT                 (481),
      cyanPg                            (482),
      cyanOpticalpg                     (483),
      cyanMsprPg                        (484),
      cyanTesiexpressApi                (485),
      cyanErp                           (486),
      cyanS0Ctp                         (487),
      cyanS1Ctp                         (488),
      cyanS4Ctp                         (489),
      cyanS16Ctp                        (490),
      cyanS0Ttp                         (491),
      cyanS1Ttp                         (492),
      cyanS4Ttp                         (493),
      cyanS16Ttp                        (494),
      cyanS64Ttp                        (495),
      cyanTimingrefprofile              (496),
      cyanTimingrefprofileline          (497),
      cyanErpProfile                    (498),
      cyanUsererpProfile                (499),
      cyanEthscheduleprofile            (500),
      cimOspfservice                    (501),
      cimIpprotocolendpoint             (502),
      cimIpinterface                    (503),
      cimOspfprotocolendpoint           (504),
      cimOspfinterface                  (505),
      cimOspfarea                       (506),
      cyanOspflsdb                      (507),
      cyanOspfneighbor                  (508),
      cimDcnipTtp                       (509),
      cimDcnospfTtp                     (510),
      cyanUserethscheduleprofile        (511),
      cyanAfecotu2ttp                   (512),
      cyanMrflxptp                      (513),
      cyan100gemfiberptp                (514),
      cyanTety100gTtp                   (515),
      cyanOtu4ttp                       (516),
      cyanGfecotu4ttp                   (517),
      cyanOdu4ttp                       (518),
      cyanOtm04Ptp                      (519),
      cyanOccrctp                       (520),
      cyanSection155mTtp                (521),
      cyanSection622mTtp                (522),
      cyanSection2488mTtp               (523),
      cyanOcgwssptp                     (524),
      cyanEtyLbTtp                      (525),
      cyan10gepfiberptp                 (526),
      cyanEtyFpgaTtp                    (527),
      cyanElectricalgtp                 (528),
      cyanElectricalFlowpointpool       (529),
      cyanElectricalFlowpoint           (530),
      cyanEthflowdomainfrmnt            (531),
      cyanIngressoffp                   (532),
      cyanEthflowdomainintfrmnt         (533),
      cyanOcgwssfptp                    (534),
      cyanSfecotu2ttp                   (535),
      cyanElectricalPbbflowpoint        (536),
      cyanElectricalErpflowpoint        (537),
      cyanElectricalLagflowpoint        (538),
      cyanElectricalUniflowpoint        (539),
      cyanOdukCtp                       (540),
      cyanSbconEsconTtp                 (541),
      cyanFc100FiconTtp                 (542),
      cyanFc200FiconxTtp                (543),
      cyanFc400Ttp                      (544),
      cyanFc800Ttp                      (545),
      cyanFc1200Ttp                     (546),
      cyan10ggfiberptp                  (547),
      cyanOtu4fiberptp                  (548),
      cyanRodu2ttp                      (549),
      cyanLogicalinterface              (550),
      cyanMplstpNode                    (551),
      cyanMplstpInterface               (552),
      cyanMplstpTunnel                  (553),
      cyanMplstpLsp                     (554),
      cyanPwFlowpoint                   (555),
      cyanPwFlowpointpool               (556),
      cyanPwFlowdomain                  (557),
      cyanMplstpMd                      (558),
      cyanMplstpMa                      (559),
      cyanMplstpMep                     (560),
      cyanMplstpMip                     (561),
      cyanMplstpLabelrange              (562),
      cyanMplstpOamApi                  (563),
      cyanElectricalOfflowpoint         (564),
      cyanEtty100gTtp                   (565),
      cyanWssfotmPtp                    (566),
      cyanMultifiber7tp                 (567),
      cyanMplsexp2cospidprofile         (568),
      cyanUsermplsexp2cospidprofile     (569),
      cyanInternalOdu2ttp               (570),
      cyanInternalOtu2ttp               (571),
      cyanOlaotmPtp                     (572),
      cyanOlaocmotmPtp                  (573),
      cyanMplstpLspFrgmnt               (574),
      cyanMplstpMepFrgmnt               (575),
      cyanMsaotu4ttp                    (576),
      cyanCfpnetworklanePtp             (577),
      cyanNetworklaneTtp                (578),
      cyanWssfxXconApi                  (580),
      cyanCrossconnect                  (601),
      cyanSubnetworkconnection          (602),
      cyanSta                           (603),
      cyanPcapfile                      (604),
      cyanSvcApi                        (605),
      cyanMiniroot                      (702),
      asapT                             (703),
      tcaparameterprofileT              (704),
      pmpT                              (705),
      cyanOpticaltcaparameterprofile    (706),
      usertcaparameterprofileT          (707),
      cyanUseropticaltcaparamprofile    (708),
      cyanLagp                          (709),
      userAsapT                         (710),
      cyanBurstydegthresholdprofile     (711),
      cyanSonetsdhmsprofile             (712),
      cyanShelfprofile                  (713),
      cyanEthpcp2cospidprofile          (714),
      cyanSonetsdhvcprofile             (715),
      cyanAugnprofile                   (716),
      cyanInternalclockgen              (717),
      cyanStationclockgen               (718),
      cyanUsersonetsdhvcprofile         (719),
      cyanUsersonetsdhmsprofile         (720),
      cyanUserethpcp2cospidprofile      (721),
      cyanUserburstydegthresholdprofile (722),
      cyanUserpgprofile                 (723),
      cyanUsermsprProfile               (724),
      cyanUserlagp                      (725),
      cyanDscp2cospidprofile            (726),
      cyanUserdscp2cospidprofile        (727),
      tcaparameterprofile               (728),
      usertcaparameterprofile           (729),
      mepTcaparameterprofile            (730),
      usermepTcaparameterprofile        (731),
      cyanOchtcaparameterprofile        (732),
      cyanUserochtcaparamprofile        (733),
      cyanMaclimitprofile               (734),
      cyanEdprofile                     (735),
      cyanPcp2colorprofile              (736),
      cyanEqptprofile                   (737),
      cyanUsereqptprofile               (738),
      cyanUser                          (800),
      cyanRole                          (801),
      cyanSshkeys                       (802)}


CyanProbablecausequalifierTc ::= TEXTUAL-CONVENTION
  STATUS current
  DESCRIPTION
      "probableCauseQualifier"
  SYNTAX INTEGER {
      na                  (0),
      comm1               (1),
      comm2               (2),
      unassigned          (3),
      hiRxpwr             (4),
      lowRxpwr            (5),
      hiTxpwr             (6),
      lowTxpwr            (7),
      hiVoltage           (8),
      lowVoltage          (9),
      hiCurrent           (10),
      lowCurrent          (11),
      hiTempRise          (12),
      memAccess           (13),
      pwrAOverVltg        (14),
      pwrAUnderVltg       (15),
      eidInvalid          (16),
      memFull             (17),
      memLow              (18),
      warmUp              (19),
      midStage            (20),
      fuse1Fail           (21),
      fuse2Fail           (22),
      fuse3Fail           (23),
      fuse4Fail           (24),
      pwrFeed1Loss        (25),
      pwrFeed2Loss        (26),
      pwrFeed3Loss        (27),
      pwrFeed4Loss        (28),
      pwrA                (29),
      pwrB                (30),
      och                 (31),
      overhead            (32),
      payload             (33),
      provMism            (34),
      noResp              (35),
      farEnd              (36),
      hiRxpwrOh           (37),
      lowRxpwrOh          (38),
      hiTxpwrOh           (39),
      lowTxpwrOh          (40),
      txFreq              (41),
      rxFreq              (42),
      allPwrFeeds         (43),
      unitA               (44),
      unitB               (45),
      tx                  (46),
      rx                  (47),
      xover               (48),
      txPayload           (49),
      tec                 (50),
      xcon                (51),
      error               (52),
      rmep                (53),
      macStat             (54),
      rdi                 (55),
      unitC               (56),
      unitD               (57),
      i2cErr              (58),
      rtDiagNotsupp       (59),
      uncertified         (60),
      dupIpaddr           (61),
      dupNodename         (62),
      sntpHost            (63),
      ssf                 (64),
      dyingGasp           (65),
      critical            (66),
      pwrFeedLoss         (67),
      maxTca              (68),
      packet              (69),
      mismerge            (70),
      unexmel             (71),
      unexmep             (72),
      unexperiod          (73),
      lacp                (74),
      cfgNotsupp          (75),
      lowPostamprxpwr     (80),
      lowRxspanloss       (81),
      hiRxspanloss        (82),
      diskLow             (83),
      cpuHi               (84),
      mfgmode             (85),
      ipc                 (86),
      lbus                (87),
      ddrPktCrc           (88),
      eccFail             (89),
      farendSfP           (90),
      protocol            (91),
      nodeIdMism          (92),
      farendSfW           (93),
      apsByteFail         (94),
      dfltKbytes          (95),
      apsModeMism         (96),
      lockout             (97),
      manual              (98),
      forced              (99),
      esmc                (100),
      oscPrtcl            (101),
      dccFail             (102),
      gcc0Fail            (103),
      gcc12Fail           (104),
      apsChMism           (105),
      apsincmpld          (106),
      ccm                 (107),
      path                (108),
      blocked             (109),
      dsbld               (110),
      fail                (111),
      csf                 (112),
      lfd                 (113),
      exmism              (114),
      ssm                 (115),
      ip                  (116),
      upm                 (117),
      maint               (118),
      swMism              (201),
      swBad               (202),
      dbMism              (203),
      dbBad               (204),
      swUpgradeFail       (205),
      swUpgradeDsbld      (206),
      swIncompatible      (207),
      hiTemp              (301),
      lowTemp             (302),
      hiTempIn            (303),
      lowTempIn           (304),
      hiTempOut           (305),
      lowTempOut          (306),
      cooling             (307),
      rxLaserHiTemp       (311),
      rxLaserLowTemp      (312),
      rxLaserHiCurrent    (313),
      rxLaserLowCurrent   (314),
      rxLaserHiTxpwr      (315),
      rxLaserLowTxpwr     (316),
      rxTec               (317),
      wlenUnlocked        (318),
      apdPwrSupply        (319),
      rxFifoErr           (320),
      hwInterLock         (321),
      fanFilterDirty      (380),
      device              (381),
      pwrBOverVltg        (382),
      pwrBUnderVltg       (383),
      deviceGpio          (384),
      pwrFeedOverVltg     (385),
      pwrFeedUnderVltg    (386),
      compressorFail      (401),
      airConditioningFail (402),
      airDryerFail        (403),
      batteryDischarge    (404),
      batteryFail         (405),
      coolFanFail         (406),
      engineFail          (407),
      engineOperating     (408),
      explosiveGas        (409),
      fireDetectorFail    (410),
      fire                (411),
      flood               (412),
      fuseFail            (413),
      generatorFail       (414),
      hiAirflow           (415),
      hiHumidity          (416),
      hiWater             (417),
      intrusion           (418),
      lowBatteryVoltage   (419),
      lowFuel             (420),
      lowHumidity         (421),
      lowCablePress       (422),
      lowWater            (423),
      userDefinedAlm1     (424),
      openDoor            (425),
      commPowerFail       (426),
      pumpFail            (427),
      powerSupplyFail     (428),
      rectifierFail       (429),
      rectifierHiVoltage  (430),
      rectifierLowVoltage (431),
      smoke               (432),
      toxicGas            (433),
      ventilationFail     (434),
      userDefinedAlm2     (435),
      userDefinedAlm3     (436),
      userDefinedAlm4     (437),
      userDefinedAlm5     (438),
      remoteAco           (439),
      heatExchangerFail   (440),
      rectifierFailMjr    (441)}


AssignedseverityTTc ::= TEXTUAL-CONVENTION
  STATUS current
  DESCRIPTION
      "AssignedSeverity"
  SYNTAX INTEGER {
      indeterminate (0),
      nonalarmed    (1),
      freeChoice    (2),
      warning       (3),
      minor         (4),
      major         (5),
      critical      (6)}


EventtypeTc ::= TEXTUAL-CONVENTION
  STATUS current
  DESCRIPTION
      "eventType"
  SYNTAX INTEGER {
      unknown                (0),
      objectcreation         (1),
      objectdeletion         (2),
      attributevaluechange   (3),
      statechange            (4),
      routechange            (5),
      alarm                  (6),
      tca                    (7),
      pmBeginunavailtime     (8),
      pmEndunavailtime       (9),
      pmContses              (10),
      pmStatechange          (11),
      pmStatechangetca       (12),
      filetransferstatusip   (21),
      filetransferstatusdone (22),
      filetransferstatusfail (23),
      backupstatusip         (24),
      backupstatusdone       (25),
      backupstatusfail       (26),
      dbRestoreip            (27),
      dbRestoredone          (28),
      dbRestorefail          (29),
      swdwnldip              (31),
      swdwnlddone            (32),
      swdwnldfail            (33),
      swupgradeip            (34),
      swupgradedone          (35),
      autoupgradeip          (36),
      autoupgradedone        (37),
      swrevertdone           (38),
      swautorevertip         (39),
      swmanrevertip          (40),
      equipped               (51),
      unequipped             (52),
      coldrestart            (53),
      warmrestart            (54),
      swmismatch             (55),
      autoprovisioning       (56),
      parityerror            (57),
      loginfail              (61),
      loginsucceed           (62),
      loginend               (63),
      pll                    (71),
      go2freerun             (72),
      locked                 (73),
      aps                    (74),
      lockout                (75),
      manual                 (76),
      forced                 (77),
      ssm                    (78),
      clear                  (79),
      revertive              (80),
      eqptprotectionswitch   (81),
      protectionswitch       (82),
      heartbeat              (83),
      physicaltopochange     (91)}


cyanAlarmProbCause OBJECT-TYPE
      SYNTAX       CyanProbablecauseTc
      MAX-ACCESS   read-only
      STATUS       current
      DESCRIPTION
      "Probable cause"

      ::= { cyanAlarmObjectTypes 1 }


cyanAlarmProbCauseQualifier OBJECT-TYPE
      SYNTAX       CyanProbablecausequalifierTc
      MAX-ACCESS   read-only
      STATUS       current
      DESCRIPTION
      "A qualifier to uniquely identify the probable cause"

      ::= { cyanAlarmObjectTypes 2 }


cyanAlarmSourceType OBJECT-TYPE
      SYNTAX       CyanTypeTc
      MAX-ACCESS   read-only
      STATUS       current
      DESCRIPTION
      "Type of the managed entity that gave rise to the alarm or event"

      ::= { cyanAlarmObjectTypes 3 }


cyanAlarmSourceAddress OBJECT-TYPE
      SYNTAX       DisplayString
      MAX-ACCESS   read-only
      STATUS       current
      DESCRIPTION
      "AID of the object that gave rise to alarm"

      ::= { cyanAlarmObjectTypes 4 }


cyanAlarmState OBJECT-TYPE
      SYNTAX       CyanAlarmstateTc
      MAX-ACCESS   read-only
      STATUS       current
      DESCRIPTION
      "Alarm state"

      ::= { cyanAlarmObjectTypes 5 }


cyanAlarmSeverity OBJECT-TYPE
      SYNTAX       AssignedseverityTTc
      MAX-ACCESS   read-only
      STATUS       current
      DESCRIPTION
      "Processed & reported alarm severity"

      ::= { cyanAlarmObjectTypes 6 }


cyanAlarmReportingTimeStamp OBJECT-TYPE
      SYNTAX       Integer32
      MAX-ACCESS   read-only
      STATUS       current
      DESCRIPTION
      "Reporting time stamp in seconds since Jan 1 1970 GMT"

      ::= { cyanAlarmObjectTypes 7 }


cyanAlarmAdditionalText OBJECT-TYPE
      SYNTAX       DisplayString
      MAX-ACCESS   read-only
      STATUS       current
      DESCRIPTION
      "User-definable text"

      ::= { cyanAlarmObjectTypes 8 }


cyanAlarmNodeName OBJECT-TYPE
      SYNTAX       DisplayString
      MAX-ACCESS   read-only
      STATUS       current
      DESCRIPTION
      "NativeEMSName of the node"

      ::= { cyanAlarmObjectTypes 16 }


cyanAlarmSourceDescription OBJECT-TYPE
      SYNTAX       DisplayString
      MAX-ACCESS   read-only
      STATUS       current
      DESCRIPTION
      "Description of the object that gave rise to alarm"

      ::= { cyanAlarmObjectTypes 17 }


cyanAlarmSourceOSSLabel OBJECT-TYPE
      SYNTAX       DisplayString
      MAX-ACCESS   read-only
      STATUS       current
      DESCRIPTION
      "OSS Lable of the object that gave rise to alarm"

      ::= { cyanAlarmObjectTypes 18 }


cyanEventType OBJECT-TYPE
      SYNTAX       EventtypeTc
      MAX-ACCESS   read-only
      STATUS       current
      DESCRIPTION
      "Event type name"

      ::= { cyanAlarmObjectTypes 9 }


cyanEventName OBJECT-TYPE
      SYNTAX       DisplayString
      MAX-ACCESS   read-only
      STATUS       current
      DESCRIPTION
      "Event name"

      ::= { cyanAlarmObjectTypes 10 }


cyanEventSourceType OBJECT-TYPE
      SYNTAX       CyanTypeTc
      MAX-ACCESS   read-only
      STATUS       current
      DESCRIPTION
      "Type of the managed entity that gave rise to the alarm or event"

      ::= { cyanAlarmObjectTypes 11 }


cyanEventSourceAddress OBJECT-TYPE
      SYNTAX       DisplayString
      MAX-ACCESS   read-only
      STATUS       current
      DESCRIPTION
      "AID of the object that gave rise to event"

      ::= { cyanAlarmObjectTypes 12 }


cyanEventReportingTimeStamp OBJECT-TYPE
      SYNTAX       Integer32
      MAX-ACCESS   read-only
      STATUS       current
      DESCRIPTION
      "Reporting time stamp in seconds since Jan 1 1970 GMT"

      ::= { cyanAlarmObjectTypes 13 }


cyanEventAdditionalText OBJECT-TYPE
      SYNTAX       DisplayString
      MAX-ACCESS   read-only
      STATUS       current
      DESCRIPTION
      "List of attribute names and new values"

      ::= { cyanAlarmObjectTypes 14 }


cyanEventNodeName OBJECT-TYPE
      SYNTAX       DisplayString
      MAX-ACCESS   read-only
      STATUS       current
      DESCRIPTION
      "NativeEMSName of the node"

      ::= { cyanAlarmObjectTypes 15 }


cyanEventSourceDescription OBJECT-TYPE
      SYNTAX       DisplayString
      MAX-ACCESS   read-only
      STATUS       current
      DESCRIPTION
      "Description of the object that gave rise to event"

      ::= { cyanAlarmObjectTypes 19 }


cyanEventSourceOSSLabel OBJECT-TYPE
      SYNTAX       DisplayString
      MAX-ACCESS   read-only
      STATUS       current
      DESCRIPTION
      "OSS Lable of the object that gave rise to event"

      ::= { cyanAlarmObjectTypes 20 }


cyanAlarmNa  NOTIFICATION-TYPE
   OBJECTS {
              cyanAlarmProbCause,
              cyanAlarmProbCauseQualifier,
              cyanAlarmSourceType,
              cyanAlarmSourceAddress,
              cyanAlarmState,
              cyanAlarmSeverity,
              cyanAlarmReportingTimeStamp,
              cyanAlarmAdditionalText,
              cyanAlarmNodeName,
              cyanAlarmSourceDescription,
              cyanAlarmSourceOSSLabel
           }
   STATUS current
   DESCRIPTION "NA"

   ::= { cyanAlarms 1 }


cyanAlarmUnequipped  NOTIFICATION-TYPE
   OBJECTS {
              cyanAlarmProbCause,
              cyanAlarmProbCauseQualifier,
              cyanAlarmSourceType,
              cyanAlarmSourceAddress,
              cyanAlarmState,
              cyanAlarmSeverity,
              cyanAlarmReportingTimeStamp,
              cyanAlarmAdditionalText,
              cyanAlarmNodeName,
              cyanAlarmSourceDescription,
              cyanAlarmSourceOSSLabel
           }
   STATUS current
   DESCRIPTION "UNEQUIPPED"

   ::= { cyanAlarms 2 }


cyanAlarmEqptRestart  NOTIFICATION-TYPE
   OBJECTS {
              cyanAlarmProbCause,
              cyanAlarmProbCauseQualifier,
              cyanAlarmSourceType,
              cyanAlarmSourceAddress,
              cyanAlarmState,
              cyanAlarmSeverity,
              cyanAlarmReportingTimeStamp,
              cyanAlarmAdditionalText,
              cyanAlarmNodeName,
              cyanAlarmSourceDescription,
              cyanAlarmSourceOSSLabel
           }
   STATUS current
   DESCRIPTION "EQPT_RESTART"

   ::= { cyanAlarms 3 }


cyanAlarmEqptFail  NOTIFICATION-TYPE
   OBJECTS {
              cyanAlarmProbCause,
              cyanAlarmProbCauseQualifier,
              cyanAlarmSourceType,
              cyanAlarmSourceAddress,
              cyanAlarmState,
              cyanAlarmSeverity,
              cyanAlarmReportingTimeStamp,
              cyanAlarmAdditionalText,
              cyanAlarmNodeName,
              cyanAlarmSourceDescription,
              cyanAlarmSourceOSSLabel
           }
   STATUS current
   DESCRIPTION "EQPT_FAIL"

   ::= { cyanAlarms 4 }


cyanAlarmEqptDgrade  NOTIFICATION-TYPE
   OBJECTS {
              cyanAlarmProbCause,
              cyanAlarmProbCauseQualifier,
              cyanAlarmSourceType,
              cyanAlarmSourceAddress,
              cyanAlarmState,
              cyanAlarmSeverity,
              cyanAlarmReportingTimeStamp,
              cyanAlarmAdditionalText,
              cyanAlarmNodeName,
              cyanAlarmSourceDescription,
              cyanAlarmSourceOSSLabel
           }
   STATUS current
   DESCRIPTION "EQPT_DGRADE"

   ::= { cyanAlarms 5 }


cyanAlarmEqptMismtch  NOTIFICATION-TYPE
   OBJECTS {
              cyanAlarmProbCause,
              cyanAlarmProbCauseQualifier,
              cyanAlarmSourceType,
              cyanAlarmSourceAddress,
              cyanAlarmState,
              cyanAlarmSeverity,
              cyanAlarmReportingTimeStamp,
              cyanAlarmAdditionalText,
              cyanAlarmNodeName,
              cyanAlarmSourceDescription,
              cyanAlarmSourceOSSLabel
           }
   STATUS current
   DESCRIPTION "EQPT_MISMTCH"

   ::= { cyanAlarms 6 }


cyanAlarmEqptUnexpected  NOTIFICATION-TYPE
   OBJECTS {
              cyanAlarmProbCause,
              cyanAlarmProbCauseQualifier,
              cyanAlarmSourceType,
              cyanAlarmSourceAddress,
              cyanAlarmState,
              cyanAlarmSeverity,
              cyanAlarmReportingTimeStamp,
              cyanAlarmAdditionalText,
              cyanAlarmNodeName,
              cyanAlarmSourceDescription,
              cyanAlarmSourceOSSLabel
           }
   STATUS current
   DESCRIPTION "EQPT_UNEXPECTED"

   ::= { cyanAlarms 7 }


cyanAlarmEqptWarning  NOTIFICATION-TYPE
   OBJECTS {
              cyanAlarmProbCause,
              cyanAlarmProbCauseQualifier,
              cyanAlarmSourceType,
              cyanAlarmSourceAddress,
              cyanAlarmState,
              cyanAlarmSeverity,
              cyanAlarmReportingTimeStamp,
              cyanAlarmAdditionalText,
              cyanAlarmNodeName,
              cyanAlarmSourceDescription,
              cyanAlarmSourceOSSLabel
           }
   STATUS current
   DESCRIPTION "EQPT_WARNING"

   ::= { cyanAlarms 8 }


cyanAlarmNotConfig  NOTIFICATION-TYPE
   OBJECTS {
              cyanAlarmProbCause,
              cyanAlarmProbCauseQualifier,
              cyanAlarmSourceType,
              cyanAlarmSourceAddress,
              cyanAlarmState,
              cyanAlarmSeverity,
              cyanAlarmReportingTimeStamp,
              cyanAlarmAdditionalText,
              cyanAlarmNodeName,
              cyanAlarmSourceDescription,
              cyanAlarmSourceOSSLabel
           }
   STATUS current
   DESCRIPTION "NOT_CONFIG"

   ::= { cyanAlarms 9 }


cyanAlarmAutoUpgrade  NOTIFICATION-TYPE
   OBJECTS {
              cyanAlarmProbCause,
              cyanAlarmProbCauseQualifier,
              cyanAlarmSourceType,
              cyanAlarmSourceAddress,
              cyanAlarmState,
              cyanAlarmSeverity,
              cyanAlarmReportingTimeStamp,
              cyanAlarmAdditionalText,
              cyanAlarmNodeName,
              cyanAlarmSourceDescription,
              cyanAlarmSourceOSSLabel
           }
   STATUS current
   DESCRIPTION "AUTO_UPGRADE"

   ::= { cyanAlarms 12 }


cyanAlarmBatFail  NOTIFICATION-TYPE
   OBJECTS {
              cyanAlarmProbCause,
              cyanAlarmProbCauseQualifier,
              cyanAlarmSourceType,
              cyanAlarmSourceAddress,
              cyanAlarmState,
              cyanAlarmSeverity,
              cyanAlarmReportingTimeStamp,
              cyanAlarmAdditionalText,
              cyanAlarmNodeName,
              cyanAlarmSourceDescription,
              cyanAlarmSourceOSSLabel
           }
   STATUS current
   DESCRIPTION "BAT_FAIL"

   ::= { cyanAlarms 32 }


cyanAlarmBatDgrade  NOTIFICATION-TYPE
   OBJECTS {
              cyanAlarmProbCause,
              cyanAlarmProbCauseQualifier,
              cyanAlarmSourceType,
              cyanAlarmSourceAddress,
              cyanAlarmState,
              cyanAlarmSeverity,
              cyanAlarmReportingTimeStamp,
              cyanAlarmAdditionalText,
              cyanAlarmNodeName,
              cyanAlarmSourceDescription,
              cyanAlarmSourceOSSLabel
           }
   STATUS current
   DESCRIPTION "BAT_DGRADE"

   ::= { cyanAlarms 33 }


cyanAlarmTpLol  NOTIFICATION-TYPE
   OBJECTS {
              cyanAlarmProbCause,
              cyanAlarmProbCauseQualifier,
              cyanAlarmSourceType,
              cyanAlarmSourceAddress,
              cyanAlarmState,
              cyanAlarmSeverity,
              cyanAlarmReportingTimeStamp,
              cyanAlarmAdditionalText,
              cyanAlarmNodeName,
              cyanAlarmSourceDescription,
              cyanAlarmSourceOSSLabel
           }
   STATUS current
   DESCRIPTION "TP_LOL"

   ::= { cyanAlarms 50 }


cyanAlarmPreAmp  NOTIFICATION-TYPE
   OBJECTS {
              cyanAlarmProbCause,
              cyanAlarmProbCauseQualifier,
              cyanAlarmSourceType,
              cyanAlarmSourceAddress,
              cyanAlarmState,
              cyanAlarmSeverity,
              cyanAlarmReportingTimeStamp,
              cyanAlarmAdditionalText,
              cyanAlarmNodeName,
              cyanAlarmSourceDescription,
              cyanAlarmSourceOSSLabel
           }
   STATUS current
   DESCRIPTION "PRE_AMP"

   ::= { cyanAlarms 51 }


cyanAlarmTpLos  NOTIFICATION-TYPE
   OBJECTS {
              cyanAlarmProbCause,
              cyanAlarmProbCauseQualifier,
              cyanAlarmSourceType,
              cyanAlarmSourceAddress,
              cyanAlarmState,
              cyanAlarmSeverity,
              cyanAlarmReportingTimeStamp,
              cyanAlarmAdditionalText,
              cyanAlarmNodeName,
              cyanAlarmSourceDescription,
              cyanAlarmSourceOSSLabel
           }
   STATUS current
   DESCRIPTION "TP_LOS"

   ::= { cyanAlarms 52 }


cyanAlarmTpLoc  NOTIFICATION-TYPE
   OBJECTS {
              cyanAlarmProbCause,
              cyanAlarmProbCauseQualifier,
              cyanAlarmSourceType,
              cyanAlarmSourceAddress,
              cyanAlarmState,
              cyanAlarmSeverity,
              cyanAlarmReportingTimeStamp,
              cyanAlarmAdditionalText,
              cyanAlarmNodeName,
              cyanAlarmSourceDescription,
              cyanAlarmSourceOSSLabel
           }
   STATUS current
   DESCRIPTION "TP_LOC"

   ::= { cyanAlarms 53 }


cyanAlarmTpLof  NOTIFICATION-TYPE
   OBJECTS {
              cyanAlarmProbCause,
              cyanAlarmProbCauseQualifier,
              cyanAlarmSourceType,
              cyanAlarmSourceAddress,
              cyanAlarmState,
              cyanAlarmSeverity,
              cyanAlarmReportingTimeStamp,
              cyanAlarmAdditionalText,
              cyanAlarmNodeName,
              cyanAlarmSourceDescription,
              cyanAlarmSourceOSSLabel
           }
   STATUS current
   DESCRIPTION "TP_LOF"

   ::= { cyanAlarms 54 }


cyanAlarmTpAis  NOTIFICATION-TYPE
   OBJECTS {
              cyanAlarmProbCause,
              cyanAlarmProbCauseQualifier,
              cyanAlarmSourceType,
              cyanAlarmSourceAddress,
              cyanAlarmState,
              cyanAlarmSeverity,
              cyanAlarmReportingTimeStamp,
              cyanAlarmAdditionalText,
              cyanAlarmNodeName,
              cyanAlarmSourceDescription,
              cyanAlarmSourceOSSLabel
           }
   STATUS current
   DESCRIPTION "TP_AIS"

   ::= { cyanAlarms 55 }


cyanAlarmTpLom  NOTIFICATION-TYPE
   OBJECTS {
              cyanAlarmProbCause,
              cyanAlarmProbCauseQualifier,
              cyanAlarmSourceType,
              cyanAlarmSourceAddress,
              cyanAlarmState,
              cyanAlarmSeverity,
              cyanAlarmReportingTimeStamp,
              cyanAlarmAdditionalText,
              cyanAlarmNodeName,
              cyanAlarmSourceDescription,
              cyanAlarmSourceOSSLabel
           }
   STATUS current
   DESCRIPTION "TP_LOM"

   ::= { cyanAlarms 56 }


cyanAlarmTpSf  NOTIFICATION-TYPE
   OBJECTS {
              cyanAlarmProbCause,
              cyanAlarmProbCauseQualifier,
              cyanAlarmSourceType,
              cyanAlarmSourceAddress,
              cyanAlarmState,
              cyanAlarmSeverity,
              cyanAlarmReportingTimeStamp,
              cyanAlarmAdditionalText,
              cyanAlarmNodeName,
              cyanAlarmSourceDescription,
              cyanAlarmSourceOSSLabel
           }
   STATUS current
   DESCRIPTION "TP_SF"

   ::= { cyanAlarms 57 }


cyanAlarmTpBdi  NOTIFICATION-TYPE
   OBJECTS {
              cyanAlarmProbCause,
              cyanAlarmProbCauseQualifier,
              cyanAlarmSourceType,
              cyanAlarmSourceAddress,
              cyanAlarmState,
              cyanAlarmSeverity,
              cyanAlarmReportingTimeStamp,
              cyanAlarmAdditionalText,
              cyanAlarmNodeName,
              cyanAlarmSourceDescription,
              cyanAlarmSourceOSSLabel
           }
   STATUS current
   DESCRIPTION "TP_BDI"

   ::= { cyanAlarms 58 }


cyanAlarmTpFdi  NOTIFICATION-TYPE
   OBJECTS {
              cyanAlarmProbCause,
              cyanAlarmProbCauseQualifier,
              cyanAlarmSourceType,
              cyanAlarmSourceAddress,
              cyanAlarmState,
              cyanAlarmSeverity,
              cyanAlarmReportingTimeStamp,
              cyanAlarmAdditionalText,
              cyanAlarmNodeName,
              cyanAlarmSourceDescription,
              cyanAlarmSourceOSSLabel
           }
   STATUS current
   DESCRIPTION "TP_FDI"

   ::= { cyanAlarms 59 }


cyanAlarmTpPmi  NOTIFICATION-TYPE
   OBJECTS {
              cyanAlarmProbCause,
              cyanAlarmProbCauseQualifier,
              cyanAlarmSourceType,
              cyanAlarmSourceAddress,
              cyanAlarmState,
              cyanAlarmSeverity,
              cyanAlarmReportingTimeStamp,
              cyanAlarmAdditionalText,
              cyanAlarmNodeName,
              cyanAlarmSourceDescription,
              cyanAlarmSourceOSSLabel
           }
   STATUS current
   DESCRIPTION "TP_PMI"

   ::= { cyanAlarms 60 }


cyanAlarmTpSd  NOTIFICATION-TYPE
   OBJECTS {
              cyanAlarmProbCause,
              cyanAlarmProbCauseQualifier,
              cyanAlarmSourceType,
              cyanAlarmSourceAddress,
              cyanAlarmState,
              cyanAlarmSeverity,
              cyanAlarmReportingTimeStamp,
              cyanAlarmAdditionalText,
              cyanAlarmNodeName,
              cyanAlarmSourceDescription,
              cyanAlarmSourceOSSLabel
           }
   STATUS current
   DESCRIPTION "TP_SD"

   ::= { cyanAlarms 61 }


cyanAlarmTpRdi  NOTIFICATION-TYPE
   OBJECTS {
              cyanAlarmProbCause,
              cyanAlarmProbCauseQualifier,
              cyanAlarmSourceType,
              cyanAlarmSourceAddress,
              cyanAlarmState,
              cyanAlarmSeverity,
              cyanAlarmReportingTimeStamp,
              cyanAlarmAdditionalText,
              cyanAlarmNodeName,
              cyanAlarmSourceDescription,
              cyanAlarmSourceOSSLabel
           }
   STATUS current
   DESCRIPTION "TP_RDI"

   ::= { cyanAlarms 62 }


cyanAlarmTpTim  NOTIFICATION-TYPE
   OBJECTS {
              cyanAlarmProbCause,
              cyanAlarmProbCauseQualifier,
              cyanAlarmSourceType,
              cyanAlarmSourceAddress,
              cyanAlarmState,
              cyanAlarmSeverity,
              cyanAlarmReportingTimeStamp,
              cyanAlarmAdditionalText,
              cyanAlarmNodeName,
              cyanAlarmSourceDescription,
              cyanAlarmSourceOSSLabel
           }
   STATUS current
   DESCRIPTION "TP_TIM"

   ::= { cyanAlarms 63 }


cyanAlarmTpIae  NOTIFICATION-TYPE
   OBJECTS {
              cyanAlarmProbCause,
              cyanAlarmProbCauseQualifier,
              cyanAlarmSourceType,
              cyanAlarmSourceAddress,
              cyanAlarmState,
              cyanAlarmSeverity,
              cyanAlarmReportingTimeStamp,
              cyanAlarmAdditionalText,
              cyanAlarmNodeName,
              cyanAlarmSourceDescription,
              cyanAlarmSourceOSSLabel
           }
   STATUS current
   DESCRIPTION "TP_IAE"

   ::= { cyanAlarms 64 }


cyanAlarmTpBiae  NOTIFICATION-TYPE
   OBJECTS {
              cyanAlarmProbCause,
              cyanAlarmProbCauseQualifier,
              cyanAlarmSourceType,
              cyanAlarmSourceAddress,
              cyanAlarmState,
              cyanAlarmSeverity,
              cyanAlarmReportingTimeStamp,
              cyanAlarmAdditionalText,
              cyanAlarmNodeName,
              cyanAlarmSourceDescription,
              cyanAlarmSourceOSSLabel
           }
   STATUS current
   DESCRIPTION "TP_BIAE"

   ::= { cyanAlarms 65 }


cyanAlarmTpOci  NOTIFICATION-TYPE
   OBJECTS {
              cyanAlarmProbCause,
              cyanAlarmProbCauseQualifier,
              cyanAlarmSourceType,
              cyanAlarmSourceAddress,
              cyanAlarmState,
              cyanAlarmSeverity,
              cyanAlarmReportingTimeStamp,
              cyanAlarmAdditionalText,
              cyanAlarmNodeName,
              cyanAlarmSourceDescription,
              cyanAlarmSourceOSSLabel
           }
   STATUS current
   DESCRIPTION "TP_OCI"

   ::= { cyanAlarms 66 }


cyanAlarmTpLck  NOTIFICATION-TYPE
   OBJECTS {
              cyanAlarmProbCause,
              cyanAlarmProbCauseQualifier,
              cyanAlarmSourceType,
              cyanAlarmSourceAddress,
              cyanAlarmState,
              cyanAlarmSeverity,
              cyanAlarmReportingTimeStamp,
              cyanAlarmAdditionalText,
              cyanAlarmNodeName,
              cyanAlarmSourceDescription,
              cyanAlarmSourceOSSLabel
           }
   STATUS current
   DESCRIPTION "TP_LCK"

   ::= { cyanAlarms 67 }


cyanAlarmTpLoflom  NOTIFICATION-TYPE
   OBJECTS {
              cyanAlarmProbCause,
              cyanAlarmProbCauseQualifier,
              cyanAlarmSourceType,
              cyanAlarmSourceAddress,
              cyanAlarmState,
              cyanAlarmSeverity,
              cyanAlarmReportingTimeStamp,
              cyanAlarmAdditionalText,
              cyanAlarmNodeName,
              cyanAlarmSourceDescription,
              cyanAlarmSourceOSSLabel
           }
   STATUS current
   DESCRIPTION "TP_LOFLOM"

   ::= { cyanAlarms 68 }


cyanAlarmTpSsf  NOTIFICATION-TYPE
   OBJECTS {
              cyanAlarmProbCause,
              cyanAlarmProbCauseQualifier,
              cyanAlarmSourceType,
              cyanAlarmSourceAddress,
              cyanAlarmState,
              cyanAlarmSeverity,
              cyanAlarmReportingTimeStamp,
              cyanAlarmAdditionalText,
              cyanAlarmNodeName,
              cyanAlarmSourceDescription,
              cyanAlarmSourceOSSLabel
           }
   STATUS current
   DESCRIPTION "TP_SSF"

   ::= { cyanAlarms 69 }


cyanAlarmTpOorangeAlm  NOTIFICATION-TYPE
   OBJECTS {
              cyanAlarmProbCause,
              cyanAlarmProbCauseQualifier,
              cyanAlarmSourceType,
              cyanAlarmSourceAddress,
              cyanAlarmState,
              cyanAlarmSeverity,
              cyanAlarmReportingTimeStamp,
              cyanAlarmAdditionalText,
              cyanAlarmNodeName,
              cyanAlarmSourceDescription,
              cyanAlarmSourceOSSLabel
           }
   STATUS current
   DESCRIPTION "TP_OORANGE_ALM"

   ::= { cyanAlarms 70 }


cyanAlarmTpOorangeWrn  NOTIFICATION-TYPE
   OBJECTS {
              cyanAlarmProbCause,
              cyanAlarmProbCauseQualifier,
              cyanAlarmSourceType,
              cyanAlarmSourceAddress,
              cyanAlarmState,
              cyanAlarmSeverity,
              cyanAlarmReportingTimeStamp,
              cyanAlarmAdditionalText,
              cyanAlarmNodeName,
              cyanAlarmSourceDescription,
              cyanAlarmSourceOSSLabel
           }
   STATUS current
   DESCRIPTION "TP_OORANGE_WRN"

   ::= { cyanAlarms 71 }


cyanAlarmTpFaclpbk  NOTIFICATION-TYPE
   OBJECTS {
              cyanAlarmProbCause,
              cyanAlarmProbCauseQualifier,
              cyanAlarmSourceType,
              cyanAlarmSourceAddress,
              cyanAlarmState,
              cyanAlarmSeverity,
              cyanAlarmReportingTimeStamp,
              cyanAlarmAdditionalText,
              cyanAlarmNodeName,
              cyanAlarmSourceDescription,
              cyanAlarmSourceOSSLabel
           }
   STATUS current
   DESCRIPTION "TP_FACLPBK"

   ::= { cyanAlarms 72 }


cyanAlarmTpHighLoss  NOTIFICATION-TYPE
   OBJECTS {
              cyanAlarmProbCause,
              cyanAlarmProbCauseQualifier,
              cyanAlarmSourceType,
              cyanAlarmSourceAddress,
              cyanAlarmState,
              cyanAlarmSeverity,
              cyanAlarmReportingTimeStamp,
              cyanAlarmAdditionalText,
              cyanAlarmNodeName,
              cyanAlarmSourceDescription,
              cyanAlarmSourceOSSLabel
           }
   STATUS current
   DESCRIPTION "TP_HIGH_LOSS"

   ::= { cyanAlarms 73 }


cyanAlarmTpLowLoss  NOTIFICATION-TYPE
   OBJECTS {
              cyanAlarmProbCause,
              cyanAlarmProbCauseQualifier,
              cyanAlarmSourceType,
              cyanAlarmSourceAddress,
              cyanAlarmState,
              cyanAlarmSeverity,
              cyanAlarmReportingTimeStamp,
              cyanAlarmAdditionalText,
              cyanAlarmNodeName,
              cyanAlarmSourceDescription,
              cyanAlarmSourceOSSLabel
           }
   STATUS current
   DESCRIPTION "TP_LOW_LOSS"

   ::= { cyanAlarms 74 }


cyanAlarmTpFiber  NOTIFICATION-TYPE
   OBJECTS {
              cyanAlarmProbCause,
              cyanAlarmProbCauseQualifier,
              cyanAlarmSourceType,
              cyanAlarmSourceAddress,
              cyanAlarmState,
              cyanAlarmSeverity,
              cyanAlarmReportingTimeStamp,
              cyanAlarmAdditionalText,
              cyanAlarmNodeName,
              cyanAlarmSourceDescription,
              cyanAlarmSourceOSSLabel
           }
   STATUS current
   DESCRIPTION "TP_FIBER"

   ::= { cyanAlarms 75 }


cyanAlarmTpPlm  NOTIFICATION-TYPE
   OBJECTS {
              cyanAlarmProbCause,
              cyanAlarmProbCauseQualifier,
              cyanAlarmSourceType,
              cyanAlarmSourceAddress,
              cyanAlarmState,
              cyanAlarmSeverity,
              cyanAlarmReportingTimeStamp,
              cyanAlarmAdditionalText,
              cyanAlarmNodeName,
              cyanAlarmSourceDescription,
              cyanAlarmSourceOSSLabel
           }
   STATUS current
   DESCRIPTION "TP_PLM"

   ::= { cyanAlarms 76 }


cyanAlarmTpLtc  NOTIFICATION-TYPE
   OBJECTS {
              cyanAlarmProbCause,
              cyanAlarmProbCauseQualifier,
              cyanAlarmSourceType,
              cyanAlarmSourceAddress,
              cyanAlarmState,
              cyanAlarmSeverity,
              cyanAlarmReportingTimeStamp,
              cyanAlarmAdditionalText,
              cyanAlarmNodeName,
              cyanAlarmSourceDescription,
              cyanAlarmSourceOSSLabel
           }
   STATUS current
   DESCRIPTION "TP_LTC"

   ::= { cyanAlarms 77 }


cyanAlarmTpMsim  NOTIFICATION-TYPE
   OBJECTS {
              cyanAlarmProbCause,
              cyanAlarmProbCauseQualifier,
              cyanAlarmSourceType,
              cyanAlarmSourceAddress,
              cyanAlarmState,
              cyanAlarmSeverity,
              cyanAlarmReportingTimeStamp,
              cyanAlarmAdditionalText,
              cyanAlarmNodeName,
              cyanAlarmSourceDescription,
              cyanAlarmSourceOSSLabel
           }
   STATUS current
   DESCRIPTION "TP_MSIM"

   ::= { cyanAlarms 78 }


cyanAlarmProtFail  NOTIFICATION-TYPE
   OBJECTS {
              cyanAlarmProbCause,
              cyanAlarmProbCauseQualifier,
              cyanAlarmSourceType,
              cyanAlarmSourceAddress,
              cyanAlarmState,
              cyanAlarmSeverity,
              cyanAlarmReportingTimeStamp,
              cyanAlarmAdditionalText,
              cyanAlarmNodeName,
              cyanAlarmSourceDescription,
              cyanAlarmSourceOSSLabel
           }
   STATUS current
   DESCRIPTION "PROT_FAIL"

   ::= { cyanAlarms 79 }


cyanAlarmCcm  NOTIFICATION-TYPE
   OBJECTS {
              cyanAlarmProbCause,
              cyanAlarmProbCauseQualifier,
              cyanAlarmSourceType,
              cyanAlarmSourceAddress,
              cyanAlarmState,
              cyanAlarmSeverity,
              cyanAlarmReportingTimeStamp,
              cyanAlarmAdditionalText,
              cyanAlarmNodeName,
              cyanAlarmSourceDescription,
              cyanAlarmSourceOSSLabel
           }
   STATUS current
   DESCRIPTION "CCM"

   ::= { cyanAlarms 80 }


cyanAlarmTpLfd  NOTIFICATION-TYPE
   OBJECTS {
              cyanAlarmProbCause,
              cyanAlarmProbCauseQualifier,
              cyanAlarmSourceType,
              cyanAlarmSourceAddress,
              cyanAlarmState,
              cyanAlarmSeverity,
              cyanAlarmReportingTimeStamp,
              cyanAlarmAdditionalText,
              cyanAlarmNodeName,
              cyanAlarmSourceDescription,
              cyanAlarmSourceOSSLabel
           }
   STATUS current
   DESCRIPTION "TP_LFD"

   ::= { cyanAlarms 81 }


cyanAlarmTpLink  NOTIFICATION-TYPE
   OBJECTS {
              cyanAlarmProbCause,
              cyanAlarmProbCauseQualifier,
              cyanAlarmSourceType,
              cyanAlarmSourceAddress,
              cyanAlarmState,
              cyanAlarmSeverity,
              cyanAlarmReportingTimeStamp,
              cyanAlarmAdditionalText,
              cyanAlarmNodeName,
              cyanAlarmSourceDescription,
              cyanAlarmSourceOSSLabel
           }
   STATUS current
   DESCRIPTION "TP_LINK"

   ::= { cyanAlarms 82 }


cyanAlarmTpGfp  NOTIFICATION-TYPE
   OBJECTS {
              cyanAlarmProbCause,
              cyanAlarmProbCauseQualifier,
              cyanAlarmSourceType,
              cyanAlarmSourceAddress,
              cyanAlarmState,
              cyanAlarmSeverity,
              cyanAlarmReportingTimeStamp,
              cyanAlarmAdditionalText,
              cyanAlarmNodeName,
              cyanAlarmSourceDescription,
              cyanAlarmSourceOSSLabel
           }
   STATUS current
   DESCRIPTION "TP_GFP"

   ::= { cyanAlarms 83 }


cyanAlarmTpTpt  NOTIFICATION-TYPE
   OBJECTS {
              cyanAlarmProbCause,
              cyanAlarmProbCauseQualifier,
              cyanAlarmSourceType,
              cyanAlarmSourceAddress,
              cyanAlarmState,
              cyanAlarmSeverity,
              cyanAlarmReportingTimeStamp,
              cyanAlarmAdditionalText,
              cyanAlarmNodeName,
              cyanAlarmSourceDescription,
              cyanAlarmSourceOSSLabel
           }
   STATUS current
   DESCRIPTION "TP_TPT"

   ::= { cyanAlarms 84 }


cyanAlarmGtp  NOTIFICATION-TYPE
   OBJECTS {
              cyanAlarmProbCause,
              cyanAlarmProbCauseQualifier,
              cyanAlarmSourceType,
              cyanAlarmSourceAddress,
              cyanAlarmState,
              cyanAlarmSeverity,
              cyanAlarmReportingTimeStamp,
              cyanAlarmAdditionalText,
              cyanAlarmNodeName,
              cyanAlarmSourceDescription,
              cyanAlarmSourceOSSLabel
           }
   STATUS current
   DESCRIPTION "GTP"

   ::= { cyanAlarms 85 }


cyanAlarmTpSqm  NOTIFICATION-TYPE
   OBJECTS {
              cyanAlarmProbCause,
              cyanAlarmProbCauseQualifier,
              cyanAlarmSourceType,
              cyanAlarmSourceAddress,
              cyanAlarmState,
              cyanAlarmSeverity,
              cyanAlarmReportingTimeStamp,
              cyanAlarmAdditionalText,
              cyanAlarmNodeName,
              cyanAlarmSourceDescription,
              cyanAlarmSourceOSSLabel
           }
   STATUS current
   DESCRIPTION "TP_SQM"

   ::= { cyanAlarms 86 }


cyanAlarmTpLoa  NOTIFICATION-TYPE
   OBJECTS {
              cyanAlarmProbCause,
              cyanAlarmProbCauseQualifier,
              cyanAlarmSourceType,
              cyanAlarmSourceAddress,
              cyanAlarmState,
              cyanAlarmSeverity,
              cyanAlarmReportingTimeStamp,
              cyanAlarmAdditionalText,
              cyanAlarmNodeName,
              cyanAlarmSourceDescription,
              cyanAlarmSourceOSSLabel
           }
   STATUS current
   DESCRIPTION "TP_LOA"

   ::= { cyanAlarms 87 }


cyanAlarmTpLti  NOTIFICATION-TYPE
   OBJECTS {
              cyanAlarmProbCause,
              cyanAlarmProbCauseQualifier,
              cyanAlarmSourceType,
              cyanAlarmSourceAddress,
              cyanAlarmState,
              cyanAlarmSeverity,
              cyanAlarmReportingTimeStamp,
              cyanAlarmAdditionalText,
              cyanAlarmNodeName,
              cyanAlarmSourceDescription,
              cyanAlarmSourceOSSLabel
           }
   STATUS current
   DESCRIPTION "TP_LTI"

   ::= { cyanAlarms 88 }


cyanAlarmLtm  NOTIFICATION-TYPE
   OBJECTS {
              cyanAlarmProbCause,
              cyanAlarmProbCauseQualifier,
              cyanAlarmSourceType,
              cyanAlarmSourceAddress,
              cyanAlarmState,
              cyanAlarmSeverity,
              cyanAlarmReportingTimeStamp,
              cyanAlarmAdditionalText,
              cyanAlarmNodeName,
              cyanAlarmSourceDescription,
              cyanAlarmSourceOSSLabel
           }
   STATUS current
   DESCRIPTION "LTM"

   ::= { cyanAlarms 89 }


cyanAlarmAps  NOTIFICATION-TYPE
   OBJECTS {
              cyanAlarmProbCause,
              cyanAlarmProbCauseQualifier,
              cyanAlarmSourceType,
              cyanAlarmSourceAddress,
              cyanAlarmState,
              cyanAlarmSeverity,
              cyanAlarmReportingTimeStamp,
              cyanAlarmAdditionalText,
              cyanAlarmNodeName,
              cyanAlarmSourceDescription,
              cyanAlarmSourceOSSLabel
           }
   STATUS current
   DESCRIPTION "APS"

   ::= { cyanAlarms 90 }


cyanAlarmTpLop  NOTIFICATION-TYPE
   OBJECTS {
              cyanAlarmProbCause,
              cyanAlarmProbCauseQualifier,
              cyanAlarmSourceType,
              cyanAlarmSourceAddress,
              cyanAlarmState,
              cyanAlarmSeverity,
              cyanAlarmReportingTimeStamp,
              cyanAlarmAdditionalText,
              cyanAlarmNodeName,
              cyanAlarmSourceDescription,
              cyanAlarmSourceOSSLabel
           }
   STATUS current
   DESCRIPTION "TP_LOP"

   ::= { cyanAlarms 91 }


cyanAlarmTpUneq  NOTIFICATION-TYPE
   OBJECTS {
              cyanAlarmProbCause,
              cyanAlarmProbCauseQualifier,
              cyanAlarmSourceType,
              cyanAlarmSourceAddress,
              cyanAlarmState,
              cyanAlarmSeverity,
              cyanAlarmReportingTimeStamp,
              cyanAlarmAdditionalText,
              cyanAlarmNodeName,
              cyanAlarmSourceDescription,
              cyanAlarmSourceOSSLabel
           }
   STATUS current
   DESCRIPTION "TP_UNEQ"

   ::= { cyanAlarms 92 }


cyanAlarmCsf  NOTIFICATION-TYPE
   OBJECTS {
              cyanAlarmProbCause,
              cyanAlarmProbCauseQualifier,
              cyanAlarmSourceType,
              cyanAlarmSourceAddress,
              cyanAlarmState,
              cyanAlarmSeverity,
              cyanAlarmReportingTimeStamp,
              cyanAlarmAdditionalText,
              cyanAlarmNodeName,
              cyanAlarmSourceDescription,
              cyanAlarmSourceOSSLabel
           }
   STATUS current
   DESCRIPTION "CSF"

   ::= { cyanAlarms 93 }


cyanAlarmExmism  NOTIFICATION-TYPE
   OBJECTS {
              cyanAlarmProbCause,
              cyanAlarmProbCauseQualifier,
              cyanAlarmSourceType,
              cyanAlarmSourceAddress,
              cyanAlarmState,
              cyanAlarmSeverity,
              cyanAlarmReportingTimeStamp,
              cyanAlarmAdditionalText,
              cyanAlarmNodeName,
              cyanAlarmSourceDescription,
              cyanAlarmSourceOSSLabel
           }
   STATUS current
   DESCRIPTION "EXMISM"

   ::= { cyanAlarms 94 }


cyanAlarmUpm  NOTIFICATION-TYPE
   OBJECTS {
              cyanAlarmProbCause,
              cyanAlarmProbCauseQualifier,
              cyanAlarmSourceType,
              cyanAlarmSourceAddress,
              cyanAlarmState,
              cyanAlarmSeverity,
              cyanAlarmReportingTimeStamp,
              cyanAlarmAdditionalText,
              cyanAlarmNodeName,
              cyanAlarmSourceDescription,
              cyanAlarmSourceOSSLabel
           }
   STATUS current
   DESCRIPTION "UPM"

   ::= { cyanAlarms 95 }


cyanAlarmProtCmd  NOTIFICATION-TYPE
   OBJECTS {
              cyanAlarmProbCause,
              cyanAlarmProbCauseQualifier,
              cyanAlarmSourceType,
              cyanAlarmSourceAddress,
              cyanAlarmState,
              cyanAlarmSeverity,
              cyanAlarmReportingTimeStamp,
              cyanAlarmAdditionalText,
              cyanAlarmNodeName,
              cyanAlarmSourceDescription,
              cyanAlarmSourceOSSLabel
           }
   STATUS current
   DESCRIPTION "PROT_CMD"

   ::= { cyanAlarms 96 }


cyanAlarmFarendCmd  NOTIFICATION-TYPE
   OBJECTS {
              cyanAlarmProbCause,
              cyanAlarmProbCauseQualifier,
              cyanAlarmSourceType,
              cyanAlarmSourceAddress,
              cyanAlarmState,
              cyanAlarmSeverity,
              cyanAlarmReportingTimeStamp,
              cyanAlarmAdditionalText,
              cyanAlarmNodeName,
              cyanAlarmSourceDescription,
              cyanAlarmSourceOSSLabel
           }
   STATUS current
   DESCRIPTION "FAREND_CMD"

   ::= { cyanAlarms 97 }


cyanAlarmProtocolErr  NOTIFICATION-TYPE
   OBJECTS {
              cyanAlarmProbCause,
              cyanAlarmProbCauseQualifier,
              cyanAlarmSourceType,
              cyanAlarmSourceAddress,
              cyanAlarmState,
              cyanAlarmSeverity,
              cyanAlarmReportingTimeStamp,
              cyanAlarmAdditionalText,
              cyanAlarmNodeName,
              cyanAlarmSourceDescription,
              cyanAlarmSourceOSSLabel
           }
   STATUS current
   DESCRIPTION "PROTOCOL_ERR"

   ::= { cyanAlarms 98 }


cyanAlarmLoopback  NOTIFICATION-TYPE
   OBJECTS {
              cyanAlarmProbCause,
              cyanAlarmProbCauseQualifier,
              cyanAlarmSourceType,
              cyanAlarmSourceAddress,
              cyanAlarmState,
              cyanAlarmSeverity,
              cyanAlarmReportingTimeStamp,
              cyanAlarmAdditionalText,
              cyanAlarmNodeName,
              cyanAlarmSourceDescription,
              cyanAlarmSourceOSSLabel
           }
   STATUS current
   DESCRIPTION "LOOPBACK"

   ::= { cyanAlarms 99 }


cyanAlarmLmm  NOTIFICATION-TYPE
   OBJECTS {
              cyanAlarmProbCause,
              cyanAlarmProbCauseQualifier,
              cyanAlarmSourceType,
              cyanAlarmSourceAddress,
              cyanAlarmState,
              cyanAlarmSeverity,
              cyanAlarmReportingTimeStamp,
              cyanAlarmAdditionalText,
              cyanAlarmNodeName,
              cyanAlarmSourceDescription,
              cyanAlarmSourceOSSLabel
           }
   STATUS current
   DESCRIPTION "LMM"

   ::= { cyanAlarms 100 }


cyanAlarmDmm  NOTIFICATION-TYPE
   OBJECTS {
              cyanAlarmProbCause,
              cyanAlarmProbCauseQualifier,
              cyanAlarmSourceType,
              cyanAlarmSourceAddress,
              cyanAlarmState,
              cyanAlarmSeverity,
              cyanAlarmReportingTimeStamp,
              cyanAlarmAdditionalText,
              cyanAlarmNodeName,
              cyanAlarmSourceDescription,
              cyanAlarmSourceOSSLabel
           }
   STATUS current
   DESCRIPTION "DMM"

   ::= { cyanAlarms 101 }


cyanAlarmCommFail  NOTIFICATION-TYPE
   OBJECTS {
              cyanAlarmProbCause,
              cyanAlarmProbCauseQualifier,
              cyanAlarmSourceType,
              cyanAlarmSourceAddress,
              cyanAlarmState,
              cyanAlarmSeverity,
              cyanAlarmReportingTimeStamp,
              cyanAlarmAdditionalText,
              cyanAlarmNodeName,
              cyanAlarmSourceDescription,
              cyanAlarmSourceOSSLabel
           }
   STATUS current
   DESCRIPTION "COMM_FAIL"

   ::= { cyanAlarms 102 }


cyanAlarmCommDgrade  NOTIFICATION-TYPE
   OBJECTS {
              cyanAlarmProbCause,
              cyanAlarmProbCauseQualifier,
              cyanAlarmSourceType,
              cyanAlarmSourceAddress,
              cyanAlarmState,
              cyanAlarmSeverity,
              cyanAlarmReportingTimeStamp,
              cyanAlarmAdditionalText,
              cyanAlarmNodeName,
              cyanAlarmSourceDescription,
              cyanAlarmSourceOSSLabel
           }
   STATUS current
   DESCRIPTION "COMM_DGRADE"

   ::= { cyanAlarms 103 }


cyanAlarmPacketLpbk  NOTIFICATION-TYPE
   OBJECTS {
              cyanAlarmProbCause,
              cyanAlarmProbCauseQualifier,
              cyanAlarmSourceType,
              cyanAlarmSourceAddress,
              cyanAlarmState,
              cyanAlarmSeverity,
              cyanAlarmReportingTimeStamp,
              cyanAlarmAdditionalText,
              cyanAlarmNodeName,
              cyanAlarmSourceDescription,
              cyanAlarmSourceOSSLabel
           }
   STATUS current
   DESCRIPTION "PACKET_LPBK"

   ::= { cyanAlarms 104 }


cyanAlarmXcspktsloss  NOTIFICATION-TYPE
   OBJECTS {
              cyanAlarmProbCause,
              cyanAlarmProbCauseQualifier,
              cyanAlarmSourceType,
              cyanAlarmSourceAddress,
              cyanAlarmState,
              cyanAlarmSeverity,
              cyanAlarmReportingTimeStamp,
              cyanAlarmAdditionalText,
              cyanAlarmNodeName,
              cyanAlarmSourceDescription,
              cyanAlarmSourceOSSLabel
           }
   STATUS current
   DESCRIPTION "XCSPKTSLOSS"

   ::= { cyanAlarms 105 }


cyanAlarmXcspktserr  NOTIFICATION-TYPE
   OBJECTS {
              cyanAlarmProbCause,
              cyanAlarmProbCauseQualifier,
              cyanAlarmSourceType,
              cyanAlarmSourceAddress,
              cyanAlarmState,
              cyanAlarmSeverity,
              cyanAlarmReportingTimeStamp,
              cyanAlarmAdditionalText,
              cyanAlarmNodeName,
              cyanAlarmSourceDescription,
              cyanAlarmSourceOSSLabel
           }
   STATUS current
   DESCRIPTION "XCSPKTSERR"

   ::= { cyanAlarms 106 }


cyanAlarmSrcaddrmis  NOTIFICATION-TYPE
   OBJECTS {
              cyanAlarmProbCause,
              cyanAlarmProbCauseQualifier,
              cyanAlarmSourceType,
              cyanAlarmSourceAddress,
              cyanAlarmState,
              cyanAlarmSeverity,
              cyanAlarmReportingTimeStamp,
              cyanAlarmAdditionalText,
              cyanAlarmNodeName,
              cyanAlarmSourceDescription,
              cyanAlarmSourceOSSLabel
           }
   STATUS current
   DESCRIPTION "SRCADDRMIS"

   ::= { cyanAlarms 107 }


cyanAlarmArp  NOTIFICATION-TYPE
   OBJECTS {
              cyanAlarmProbCause,
              cyanAlarmProbCauseQualifier,
              cyanAlarmSourceType,
              cyanAlarmSourceAddress,
              cyanAlarmState,
              cyanAlarmSeverity,
              cyanAlarmReportingTimeStamp,
              cyanAlarmAdditionalText,
              cyanAlarmNodeName,
              cyanAlarmSourceDescription,
              cyanAlarmSourceOSSLabel
           }
   STATUS current
   DESCRIPTION "ARP"

   ::= { cyanAlarms 108 }


cyanAlarmTsa  NOTIFICATION-TYPE
   OBJECTS {
              cyanAlarmProbCause,
              cyanAlarmProbCauseQualifier,
              cyanAlarmSourceType,
              cyanAlarmSourceAddress,
              cyanAlarmState,
              cyanAlarmSeverity,
              cyanAlarmReportingTimeStamp,
              cyanAlarmAdditionalText,
              cyanAlarmNodeName,
              cyanAlarmSourceDescription,
              cyanAlarmSourceOSSLabel
           }
   STATUS current
   DESCRIPTION "TSA"

   ::= { cyanAlarms 109 }


cyanAlarmErpPort  NOTIFICATION-TYPE
   OBJECTS {
              cyanAlarmProbCause,
              cyanAlarmProbCauseQualifier,
              cyanAlarmSourceType,
              cyanAlarmSourceAddress,
              cyanAlarmState,
              cyanAlarmSeverity,
              cyanAlarmReportingTimeStamp,
              cyanAlarmAdditionalText,
              cyanAlarmNodeName,
              cyanAlarmSourceDescription,
              cyanAlarmSourceOSSLabel
           }
   STATUS current
   DESCRIPTION "ERP_PORT"

   ::= { cyanAlarms 110 }


cyanAlarmTpLoomfi  NOTIFICATION-TYPE
   OBJECTS {
              cyanAlarmProbCause,
              cyanAlarmProbCauseQualifier,
              cyanAlarmSourceType,
              cyanAlarmSourceAddress,
              cyanAlarmState,
              cyanAlarmSeverity,
              cyanAlarmReportingTimeStamp,
              cyanAlarmAdditionalText,
              cyanAlarmNodeName,
              cyanAlarmSourceDescription,
              cyanAlarmSourceOSSLabel
           }
   STATUS current
   DESCRIPTION "TP_LOOMFI"

   ::= { cyanAlarms 111 }


cyanAlarmSyncFail  NOTIFICATION-TYPE
   OBJECTS {
              cyanAlarmProbCause,
              cyanAlarmProbCauseQualifier,
              cyanAlarmSourceType,
              cyanAlarmSourceAddress,
              cyanAlarmState,
              cyanAlarmSeverity,
              cyanAlarmReportingTimeStamp,
              cyanAlarmAdditionalText,
              cyanAlarmNodeName,
              cyanAlarmSourceDescription,
              cyanAlarmSourceOSSLabel
           }
   STATUS current
   DESCRIPTION "SYNC_FAIL"

   ::= { cyanAlarms 202 }


cyanAlarmSyncDgrade  NOTIFICATION-TYPE
   OBJECTS {
              cyanAlarmProbCause,
              cyanAlarmProbCauseQualifier,
              cyanAlarmSourceType,
              cyanAlarmSourceAddress,
              cyanAlarmState,
              cyanAlarmSeverity,
              cyanAlarmReportingTimeStamp,
              cyanAlarmAdditionalText,
              cyanAlarmNodeName,
              cyanAlarmSourceDescription,
              cyanAlarmSourceOSSLabel
           }
   STATUS current
   DESCRIPTION "SYNC_DGRADE"

   ::= { cyanAlarms 203 }


cyanAlarmHoldover  NOTIFICATION-TYPE
   OBJECTS {
              cyanAlarmProbCause,
              cyanAlarmProbCauseQualifier,
              cyanAlarmSourceType,
              cyanAlarmSourceAddress,
              cyanAlarmState,
              cyanAlarmSeverity,
              cyanAlarmReportingTimeStamp,
              cyanAlarmAdditionalText,
              cyanAlarmNodeName,
              cyanAlarmSourceDescription,
              cyanAlarmSourceOSSLabel
           }
   STATUS current
   DESCRIPTION "HOLDOVER"

   ::= { cyanAlarms 204 }


cyanAlarmXcsholdover  NOTIFICATION-TYPE
   OBJECTS {
              cyanAlarmProbCause,
              cyanAlarmProbCauseQualifier,
              cyanAlarmSourceType,
              cyanAlarmSourceAddress,
              cyanAlarmState,
              cyanAlarmSeverity,
              cyanAlarmReportingTimeStamp,
              cyanAlarmAdditionalText,
              cyanAlarmNodeName,
              cyanAlarmSourceDescription,
              cyanAlarmSourceOSSLabel
           }
   STATUS current
   DESCRIPTION "XCSHOLDOVER"

   ::= { cyanAlarms 205 }


cyanAlarmSyncExcmdActive  NOTIFICATION-TYPE
   OBJECTS {
              cyanAlarmProbCause,
              cyanAlarmProbCauseQualifier,
              cyanAlarmSourceType,
              cyanAlarmSourceAddress,
              cyanAlarmState,
              cyanAlarmSeverity,
              cyanAlarmReportingTimeStamp,
              cyanAlarmAdditionalText,
              cyanAlarmNodeName,
              cyanAlarmSourceDescription,
              cyanAlarmSourceOSSLabel
           }
   STATUS current
   DESCRIPTION "SYNC_EXCMD_ACTIVE"

   ::= { cyanAlarms 206 }


cyanAlarmEnvAlm  NOTIFICATION-TYPE
   OBJECTS {
              cyanAlarmProbCause,
              cyanAlarmProbCauseQualifier,
              cyanAlarmSourceType,
              cyanAlarmSourceAddress,
              cyanAlarmState,
              cyanAlarmSeverity,
              cyanAlarmReportingTimeStamp,
              cyanAlarmAdditionalText,
              cyanAlarmNodeName,
              cyanAlarmSourceDescription,
              cyanAlarmSourceOSSLabel
           }
   STATUS current
   DESCRIPTION "ENV_ALM"

   ::= { cyanAlarms 302 }


cyanAlarmEnvWrn  NOTIFICATION-TYPE
   OBJECTS {
              cyanAlarmProbCause,
              cyanAlarmProbCauseQualifier,
              cyanAlarmSourceType,
              cyanAlarmSourceAddress,
              cyanAlarmState,
              cyanAlarmSeverity,
              cyanAlarmReportingTimeStamp,
              cyanAlarmAdditionalText,
              cyanAlarmNodeName,
              cyanAlarmSourceDescription,
              cyanAlarmSourceOSSLabel
           }
   STATUS current
   DESCRIPTION "ENV_WRN"

   ::= { cyanAlarms 303 }


cyanAlarmIncmpld  NOTIFICATION-TYPE
   OBJECTS {
              cyanAlarmProbCause,
              cyanAlarmProbCauseQualifier,
              cyanAlarmSourceType,
              cyanAlarmSourceAddress,
              cyanAlarmState,
              cyanAlarmSeverity,
              cyanAlarmReportingTimeStamp,
              cyanAlarmAdditionalText,
              cyanAlarmNodeName,
              cyanAlarmSourceDescription,
              cyanAlarmSourceOSSLabel
           }
   STATUS current
   DESCRIPTION "INCMPLD"

   ::= { cyanAlarms 402 }


cyanAlarmAdmin  NOTIFICATION-TYPE
   OBJECTS {
              cyanAlarmProbCause,
              cyanAlarmProbCauseQualifier,
              cyanAlarmSourceType,
              cyanAlarmSourceAddress,
              cyanAlarmState,
              cyanAlarmSeverity,
              cyanAlarmReportingTimeStamp,
              cyanAlarmAdditionalText,
              cyanAlarmNodeName,
              cyanAlarmSourceDescription,
              cyanAlarmSourceOSSLabel
           }
   STATUS current
   DESCRIPTION "ADMIN"

   ::= { cyanAlarms 403 }


cyanEventTca  NOTIFICATION-TYPE
   OBJECTS {
              cyanEventType,
              cyanEventName,
              cyanEventSourceType,
              cyanEventSourceAddress,
              cyanEventReportingTimeStamp,
              cyanEventAdditionalText,
              cyanEventNodeName,
              cyanEventSourceDescription,
              cyanEventSourceOSSLabel
           }
   STATUS current
   DESCRIPTION "TCA"

   ::= { cyanAlarms 10008 }


  cyanAlarmGroup NOTIFICATION-GROUP
    NOTIFICATIONS {
      cyanAlarmNa,
      cyanAlarmUnequipped,
      cyanAlarmEqptRestart,
      cyanAlarmEqptFail,
      cyanAlarmEqptDgrade,
      cyanAlarmEqptMismtch,
      cyanAlarmEqptUnexpected,
      cyanAlarmEqptWarning,
      cyanAlarmNotConfig,
      cyanAlarmAutoUpgrade,
      cyanAlarmBatFail,
      cyanAlarmBatDgrade,
      cyanAlarmTpLol,
      cyanAlarmPreAmp,
      cyanAlarmTpLos,
      cyanAlarmTpLoc,
      cyanAlarmTpLof,
      cyanAlarmTpAis,
      cyanAlarmTpLom,
      cyanAlarmTpSf,
      cyanAlarmTpBdi,
      cyanAlarmTpFdi,
      cyanAlarmTpPmi,
      cyanAlarmTpSd,
      cyanAlarmTpRdi,
      cyanAlarmTpTim,
      cyanAlarmTpIae,
      cyanAlarmTpBiae,
      cyanAlarmTpOci,
      cyanAlarmTpLck,
      cyanAlarmTpLoflom,
      cyanAlarmTpSsf,
      cyanAlarmTpOorangeAlm,
      cyanAlarmTpOorangeWrn,
      cyanAlarmTpFaclpbk,
      cyanAlarmTpHighLoss,
      cyanAlarmTpLowLoss,
      cyanAlarmTpFiber,
      cyanAlarmTpPlm,
      cyanAlarmTpLtc,
      cyanAlarmTpMsim,
      cyanAlarmProtFail,
      cyanAlarmCcm,
      cyanAlarmTpLfd,
      cyanAlarmTpLink,
      cyanAlarmTpGfp,
      cyanAlarmTpTpt,
      cyanAlarmGtp,
      cyanAlarmTpSqm,
      cyanAlarmTpLoa,
      cyanAlarmTpLti,
      cyanAlarmLtm,
      cyanAlarmAps,
      cyanAlarmTpLop,
      cyanAlarmTpUneq,
      cyanAlarmCsf,
      cyanAlarmExmism,
      cyanAlarmUpm,
      cyanAlarmProtCmd,
      cyanAlarmFarendCmd,
      cyanAlarmProtocolErr,
      cyanAlarmLoopback,
      cyanAlarmLmm,
      cyanAlarmDmm,
      cyanAlarmCommFail,
      cyanAlarmCommDgrade,
      cyanAlarmPacketLpbk,
      cyanAlarmXcspktsloss,
      cyanAlarmXcspktserr,
      cyanAlarmSrcaddrmis,
      cyanAlarmArp,
      cyanAlarmTsa,
      cyanAlarmErpPort,
      cyanAlarmTpLoomfi,
      cyanAlarmSyncFail,
      cyanAlarmSyncDgrade,
      cyanAlarmHoldover,
      cyanAlarmXcsholdover,
      cyanAlarmSyncExcmdActive,
      cyanAlarmEnvAlm,
      cyanAlarmEnvWrn,
      cyanAlarmIncmpld,
      cyanAlarmAdmin,
      cyanEventTca
    }
       STATUS current
       DESCRIPTION
         "Group of all the alarms that Cyan nodes can send as taps"
       ::= { cyanAlarmMibModule 50 }



    cyanAlarmObjectGroup OBJECT-GROUP
      OBJECTS {
              cyanAlarmProbCause,
              cyanAlarmProbCauseQualifier,
              cyanAlarmSourceType,
              cyanAlarmSourceAddress,
              cyanAlarmState,
              cyanAlarmSeverity,
              cyanAlarmReportingTimeStamp,
              cyanAlarmAdditionalText,
              cyanAlarmNodeName,
              cyanAlarmSourceDescription,
              cyanAlarmSourceOSSLabel
           }
      STATUS current
      DESCRIPTION        "Group of objects that come with alarms"
      ::= {cyanAlarmObjectGroups 1}

cyanEventObjectGroup OBJECT-GROUP
      OBJECTS {
	      cyanEventType,
              cyanEventName,
              cyanEventSourceType,
              cyanEventSourceAddress,
              cyanEventReportingTimeStamp,
              cyanEventAdditionalText,
              cyanEventNodeName,
              cyanEventSourceDescription,
              cyanEventSourceOSSLabel
           }
      STATUS current
      DESCRIPTION        "Group of objects that come with events"
      ::= {cyanAlarmObjectGroups 2}


    cyanAlarmCompliance MODULE-COMPLIANCE
      STATUS current
      DESCRIPTION
        "The basic info needed to be a cyan node wrt traps"
      MODULE
        MANDATORY-GROUPS {
          cyanAlarmGroup,
          cyanAlarmObjectGroup,
	  cyanEventObjectGroup
       }
      ::= { cyanAlarmMibModule 60 }
      
END
