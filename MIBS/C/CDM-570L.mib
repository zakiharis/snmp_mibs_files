--
-- CDM-570L.my
-- MIB generated by MG-SOFT Visual MIB Builder Version 2.1 Build 199
-- Monday, May 09, 2005 at 11:37:48
--

	CDM-570L DEFINITIONS ::= BEGIN

		IMPORTS
    		comtechEFData	
    			FROM ComtechEFData		
			cdm570, cdm570SystemEquipmentID, cdm570AlarmMask, cdm570ODU, cdm570Alarms, 
			cdm570ODUParams, cdm570Conformance			
				FROM CDM-570			
			OBJECT-GROUP, MODULE-COMPLIANCE, NOTIFICATION-GROUP			
				FROM SNMPv2-CONF			
			OBJECT-TYPE, NOTIFICATION-TYPE, MODULE-IDENTITY		
				FROM SNMPv2-SMI;


		cdm570 MODULE-IDENTITY
			LAST-UPDATED "200602220000Z"
			ORGANIZATION
				"Comtech EF Data Corp."
			CONTACT-INFO
				"Comtech EF Data Crop.
				2114 W. 7th Street
				Tempe, AZ  85281 USA

				Tel: 480-333-2200
				Fax: 480-333-2540
				Web: http://www.comtechefdata.com
				"
			DESCRIPTION
				"Module Identity for both CDM-570 L-Band and 
				IF-Band Satellite Modems."
			REVISION "200602220000Z"
			DESCRIPTION
				"Updated for 1.5.3 Maint. Release"
			::= { comtechEFData 24 }
	
	
--
-- Node definitions
--
	
		cdm570LBUCOption OBJECT-TYPE
			SYNTAX INTEGER
				{
				none(0),
				buc100watt(1),
				buc150watt(2)
				}
			MAX-ACCESS read-only
			STATUS current
			DESCRIPTION
				"BUC option, where:
				0 = None
				1 = 100 watt
				2 = 150 watt"
			::= { cdm570SystemEquipmentID 7 }
		
		cdm570LAlarmMaskBUC OBJECT-TYPE
			SYNTAX INTEGER
				{
				unmasked(0),
				masked(1)
				}
			MAX-ACCESS read-write
			STATUS current
			DESCRIPTION
				"BUC alarm mask, where:
				0 = Unmasked
				1 = Masked"
			::= { cdm570AlarmMask 9 }
		
		cdm570LAlarmMaskLNB OBJECT-TYPE
			SYNTAX INTEGER
				{
				unmasked(0),
				masked(1)
				}
			MAX-ACCESS read-write
			STATUS current
			DESCRIPTION
				"LNB alarm mask, where:
				0 = Unmasked
				1 = Masked"
			::= { cdm570AlarmMask 10 }
		
		cdm570LBUC OBJECT IDENTIFIER ::= { cdm570ODU 1 }
		
		cdm570LBUCDCPower OBJECT-TYPE
			SYNTAX INTEGER
				{
				disable(0),
				enable(1)
				}
			MAX-ACCESS read-write
			STATUS current
			DESCRIPTION
				"BUC power control, where:
				0 = Disable BUC DC Power
				1 = Enable BUC DC Power"
			::= { cdm570LBUC 1 }
		
		cdm570LBUCFSK OBJECT IDENTIFIER ::= { cdm570LBUC 2 }
		
		cdm570LBUCComms OBJECT-TYPE
			SYNTAX INTEGER
				{
				disabled(0),
				enabled(1)
				}
			MAX-ACCESS read-write
			STATUS current
			DESCRIPTION
				"Enables or disables communication, via the 
				FSK link, with an  externally connected 
				Block Up Converted (BUC), where:
				0 = Disabled
				1 = Enabled"
			::= { cdm570LBUCFSK 1 }
		
		cdm570LBUCAddress OBJECT-TYPE
			SYNTAX INTEGER (1..15)
			MAX-ACCESS read-write
			STATUS current
			DESCRIPTION
				"Indicates the BUC address, between 1 and 15."
			::= { cdm570LBUCFSK 2 }
		
		cdm570LBUCRFOutput OBJECT-TYPE
			SYNTAX INTEGER
				{
				off(0),
				on(1)
				}
			MAX-ACCESS read-write
			STATUS current
			DESCRIPTION
				"Indicates BUC output enable, where:
				0 = Off (output disabled)
				1 = On (output enabled)"
			::= { cdm570LBUCFSK 3 }
		
		cdm570LBUC10MHzReference OBJECT-TYPE
			SYNTAX INTEGER
				{
				disabled(0),
				enabled(1)
				}
			MAX-ACCESS read-write
			STATUS current
			DESCRIPTION
				"Enables or disables the 10 MHz frequency 
				reference to the BUC, where:
				0 = Disabled
				1 = Enabled"
			::= { cdm570LBUC 3 }
		
		cdm570LBUCAlarm OBJECT IDENTIFIER ::= { cdm570LBUC 4 }
		
		cdm570LBUCHighCurrentLimit OBJECT-TYPE
			SYNTAX INTEGER (500..4000)
			UNITS "mA"
			MAX-ACCESS read-write
			STATUS current
			DESCRIPTION
				"BUC high current limit, between 500 and 4000 mA."
			::= { cdm570LBUCAlarm 1 }
		
		cdm570LBUCLowCurrentLimit OBJECT-TYPE
			SYNTAX INTEGER (0..3000)
			UNITS "mA"
			MAX-ACCESS read-write
			STATUS current
			DESCRIPTION
				"BUC low current limit, between 0 and 3000 mA.
				BUC low current limit must not exceed BUC high current limit."
			::= { cdm570LBUCAlarm 2 }
		
		cdm570LBUCLO OBJECT IDENTIFIER ::= { cdm570LBUC 5 }
		
		cdm570LBUCLOFrequency OBJECT-TYPE
			SYNTAX INTEGER (0 | 3000..65000)
			UNITS "MHz"
			MAX-ACCESS read-write
			STATUS current
			DESCRIPTION
				"BUC transmit LO frequency in the range of 3000 
				to 65000 MHz.
				Setting 0 disables this feature.
				
				Terminal Frequency = BUC_LO +/- Tx_Frequency 
				(depending on LO mix)."
			::= { cdm570LBUCLO 1 }
		
		cdm570LBUCLOMix OBJECT-TYPE
			SYNTAX INTEGER
				{
				lowSideMix(0),
				highSideMix(1)
				}
			MAX-ACCESS read-write
			STATUS current
			DESCRIPTION
				"BUC LO frequency mix, where:
				0 = Low-side mix
				1 = High-side mix"
			::= { cdm570LBUCLO 2 }
		
		cdm570LLNB OBJECT IDENTIFIER ::= { cdm570ODU 2 }
		
		cdm570LLNBDCPower OBJECT-TYPE
			SYNTAX INTEGER
				{
				off(0),
				on13volts(1),
				on18volts(2),
				on24volts(3)
				}
			MAX-ACCESS read-write
			STATUS current
			DESCRIPTION
				"LNB power control, where:
				0 = Off
				1 = On, 13V LNB voltage
				2 = On, 18V LNB voltage
				3 = On, 24V LNB voltage"
			::= { cdm570LLNB 1 }
		
		cdm570LLNB10MHzReference OBJECT-TYPE
			SYNTAX INTEGER
				{
				disable(0),
				enable(1)
				}
			MAX-ACCESS read-write
			STATUS current
			DESCRIPTION
				"LNB 10MHz frequency reference, where:
				0 = Disable LNB 10MHz reference
				1 = Enable LNB 10MHz reference"
			::= { cdm570LLNB 2 }
		
		cdm570LLNBAlarm OBJECT IDENTIFIER ::= { cdm570LLNB 3 }
		
		cdm570LLNBHighCurrentLimit OBJECT-TYPE
			SYNTAX INTEGER (50..600)
			UNITS "mA"
			MAX-ACCESS read-write
			STATUS current
			DESCRIPTION
				"LNB upper alarm limit for current, between 
				50 and 600 mA."
			::= { cdm570LLNBAlarm 1 }
		
		cdm570LLNBLowCurrentLimit OBJECT-TYPE
			SYNTAX INTEGER (10..400)
			UNITS "mA"
			MAX-ACCESS read-write
			STATUS current
			DESCRIPTION
				"LNB lower alarm limit for current, between 
				10 and 400 mA."
			::= { cdm570LLNBAlarm 2 }
		
		cdm570LLNBLO OBJECT IDENTIFIER ::= { cdm570LLNB 4 }
		
		cdm570LLNBLOFrequency OBJECT-TYPE
			SYNTAX INTEGER (0 | 3000..65000)
			UNITS "MHz"
			MAX-ACCESS read-write
			STATUS current
			DESCRIPTION
				"LNB receieve LO frequency, in the range of 
				3000 to 65000 MHz.
				Setting a 0 disables the feature.
				
				Terminal Frequency = LNB_LO +/- Rx_Frequency 
				(depending on High/Low Mix)"
			::= { cdm570LLNBLO 1 }
		
		cdm570LLNBLOMix OBJECT-TYPE
			SYNTAX INTEGER
				{
				lowSideMix(0),
				highSideMix(1)
				}
			MAX-ACCESS read-write
			STATUS current
			DESCRIPTION
				"LO frequency mix, where:
				0 = Low-side mix
				1 = High-side mix"
			::= { cdm570LLNBLO 2 }
		
		cdm570LODUAlarms OBJECT-TYPE
			SYNTAX INTEGER
				{
				noODUfaults(0),
				bucPLL(1),
				bucCurrent(3),
				bucVoltage(5),
				lnbCurrent(7),
				lnbVoltage(9),
				bucTemperature(11),
				bucChecksum(13)
				}
			MAX-ACCESS read-only
			STATUS current
			DESCRIPTION
				"ODU Faults
				
				   Value   Description of status parameter
				
				     0     No ODU faults
				     1     BUC PLL
				     3     BUC current
				     5     BUC voltage
				     7     LNB current
				     9     LNB voltage
				     11    BUC temperature
				     13    BUC checksum"
			::= { cdm570Alarms 4 }
		
		cdm570LBUCParams OBJECT IDENTIFIER ::= { cdm570ODUParams 1 }
		
		cdm570LBUCCurrent OBJECT-TYPE
			SYNTAX INTEGER (0..9999)
			UNITS "mA"
			MAX-ACCESS read-only
			STATUS current
			DESCRIPTION
				"Indicates the value of the BUC current, 
				between 0 and 9999 mA.
				Units = mA."
			::= { cdm570LBUCParams 1 }
		
		cdm570LBUCVoltage OBJECT-TYPE
			SYNTAX INTEGER (0..640)
			UNITS "0.1 volts"
			MAX-ACCESS read-only
			STATUS current
			DESCRIPTION
				"Indicates the value ofthe BUC voltage, 
				between 0 and 64 volts in 0.1 volts.
				Units = 0.1 volts."
			::= { cdm570LBUCParams 2 }
		
		cdm570LBUCTemperature OBJECT-TYPE
			SYNTAX INTEGER (-99..99)
			UNITS "degrees Celsius"
			MAX-ACCESS read-only
			STATUS current
			DESCRIPTION
				"Indicates the BUC temperature in degrees Celsius.
				If not available, response is -99.
				
				Note: This query is only valid when FSK 
				and BUC power are turned On."
			::= { cdm570LBUCParams 3 }
		
		cdm570LBUCSoftwareVersion OBJECT-TYPE
			SYNTAX INTEGER (0 | 1..15)
			MAX-ACCESS read-only
			STATUS current
			DESCRIPTION
				"Indicates the BUC software version, 
				between 1 and 15.
				If not available, response is 0."
			::= { cdm570LBUCParams 4 }
		
		cdm570LBUCPLLAlarm OBJECT-TYPE
			SYNTAX INTEGER
				{
				locked(0),
				unlocked(1),
				unavailable(9)
				}
			MAX-ACCESS read-only
			STATUS current
			DESCRIPTION
				"BUC PLL lock state, where:
				0 = Locked
				1 = Unlocked
				9 = Unavailable"
			::= { cdm570LBUCParams 5 }
		
		cdm570LBUCPowerLevel OBJECT-TYPE
			SYNTAX INTEGER (0..999)
			UNITS "0.1 watts"
			MAX-ACCESS read-only
			STATUS current
			DESCRIPTION
				"BUC output power level in 0.1 watts.
				Units = 0.1 watts.
				
				Returns 0 when FSK and BUC power are not enabled."
			::= { cdm570LBUCParams 6 }
		
		cdm570LBUCTerminalTxFrequency OBJECT-TYPE
			SYNTAX INTEGER (0..999999999)
			UNITS "100 Hz"
			MAX-ACCESS read-only
			STATUS current
			DESCRIPTION
				"Terminal Tx Frequency = BUC_LO +/- Tx_Frequency
				(depending on LO mix)
				Units = 100 Hz
				Resolution = 100 Hz
				
				Returns 0 if BUC LO is zero."
			::= { cdm570LBUCParams 7 }
		
		cdm570LLNBParams OBJECT IDENTIFIER ::= { cdm570ODUParams 2 }
		
		cdm570LLNBCurrent OBJECT-TYPE
			SYNTAX INTEGER (0..999)
			MAX-ACCESS read-only
			STATUS current
			DESCRIPTION
				"Indicates the value of the LNB current, 
				between 0 and 999 mA."
			::= { cdm570LLNBParams 1 }
		
		cdm570LLNBVoltage OBJECT-TYPE
			SYNTAX INTEGER (0..300)
			MAX-ACCESS read-only
			STATUS current
			DESCRIPTION
				"Indicates the value of the LNB voltage, 
				between 0 and 30 volts.
				Units = 0.1 volts
				
				If not available, response is 0."
			::= { cdm570LLNBParams 2 }
		
		cdm570LLNBTerminalRxFrequency OBJECT-TYPE
			SYNTAX INTEGER (0..999999999)
			UNITS "100 Hz"
			MAX-ACCESS read-only
			STATUS current
			DESCRIPTION
				"Terminal Rx frequency = LNB LO +/- Rx_Frequency
				(depending on LO mix)
				Units = 100 Hz
				Resolution = 100 Hz
				
				Returns 0 if LNB_LO is zero."
			::= { cdm570LLNBParams 3 }
		
		cdm570Notifications OBJECT IDENTIFIER ::= { cdm570 2 }
		
		cdm570NotificationsPrefix OBJECT IDENTIFIER ::= { cdm570Notifications 0 }
		
		cdm570LODUAlarm NOTIFICATION-TYPE
			OBJECTS { cdm570LODUAlarms }
			STATUS current
			DESCRIPTION
				"CDM-570L BUC and LNB ODU Alarm Trap"
			::= { cdm570NotificationsPrefix 4 }
		
		cdm570LGroups OBJECT IDENTIFIER ::= { cdm570Conformance 3 }
		
		cdm570LObjectsGroup OBJECT-GROUP
			OBJECTS { cdm570LBUCOption, cdm570LAlarmMaskBUC, cdm570LAlarmMaskLNB, cdm570LBUCDCPower, cdm570LBUCComms, 
				cdm570LBUCAddress, cdm570LBUCRFOutput, cdm570LBUC10MHzReference, cdm570LBUCHighCurrentLimit, cdm570LBUCLowCurrentLimit, 
				cdm570LBUCLOFrequency, cdm570LBUCLOMix, cdm570LLNBDCPower, cdm570LLNB10MHzReference, cdm570LLNBHighCurrentLimit, 
				cdm570LLNBLowCurrentLimit, cdm570LLNBLOFrequency, cdm570LLNBLOMix, cdm570LODUAlarms, cdm570LBUCCurrent, 
				cdm570LBUCVoltage, cdm570LBUCTemperature, cdm570LBUCSoftwareVersion, cdm570LBUCPLLAlarm, cdm570LBUCPowerLevel, 
				cdm570LBUCTerminalTxFrequency, cdm570LLNBCurrent, cdm570LLNBVoltage, cdm570LLNBTerminalRxFrequency }
			STATUS current
			DESCRIPTION
				"CDM-570L Objects Group."
			::= { cdm570LGroups 1 }
		
		cdm570LNotificationsGroup NOTIFICATION-GROUP
			NOTIFICATIONS { cdm570LODUAlarm }
			STATUS current
			DESCRIPTION
				"CDM-570L Notifications Group."
			::= { cdm570LGroups 2 }
		
		cdm570LCompliances OBJECT IDENTIFIER ::= { cdm570Conformance 4 }
		
		cdm570LCompliance MODULE-COMPLIANCE
			STATUS current
			DESCRIPTION
				"CDM-570L Compliance."
			MODULE -- this module
				MANDATORY-GROUPS { cdm570LObjectsGroup, cdm570LNotificationsGroup }
			::= { cdm570LCompliances 1 }
		
	
	END

--
-- CDM-570L.my
--
