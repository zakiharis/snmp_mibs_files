CYAN-NODE-MIB DEFINITIONS ::= BEGIN
IMPORTS
    MODULE-IDENTITY,
    OBJECT-TYPE,
    Integer32,
    Unsigned32
                    FROM SNMPv2-SMI

    DisplayString
                    FROM SNMPv2-TC

    CyanSecServiceStateTc,
    CyanNationalizationTc,
    CyanOpStateTc,
    CyanTimezoneTc,
    CyanOpStateQualTc,
    CyanAdminStateTc,
    CyanEnDisabledTc
                    FROM CYAN-TC-MIB

    CyanTypeTc,
    cyanEntityModules
		    FROM CYAN-MIB

    MODULE-COMPLIANCE, 
    OBJECT-GROUP
	            FROM SNMPv2-CONF;


cyanNodeModule MODULE-IDENTITY
    LAST-UPDATED "201412070545Z" -- Sun Dec  7 05:45:22 2014
    ORGANIZATION "Cyan, Inc."
    CONTACT-INFO
        "
        E-mail:  support@cyaninc.com

        Postal:  Cyan, Inc.
               1390 N. McDowell Blvd., # G-327
               Petaluma, CA  94954
               USA

        Tel:     +1-707-735-2300"

    DESCRIPTION    "MIB module for Cyan Node"

    REVISION     "201412070545Z" -- Sun Dec  7 05:45:22 2014
    DESCRIPTION  "Release 6.0 build 1416362081"

    ::= { cyanEntityModules 10 } 

cyanNodeMibObjects           OBJECT IDENTIFIER ::={ cyanNodeModule 1 }


cyanNodeAdminState OBJECT-TYPE
    SYNTAX       CyanAdminStateTc
    MAX-ACCESS   read-only
    STATUS       current
    DESCRIPTION
        "Administrative state"

    ::= { cyanNodeMibObjects 1 }

cyanNodeAssetTag OBJECT-TYPE
    SYNTAX       DisplayString (SIZE(0..124))
    MAX-ACCESS   read-only
    STATUS       current
    DESCRIPTION
        "Asset Tag"

    ::= { cyanNodeMibObjects 2 }

cyanNodeBaseMacAddress OBJECT-TYPE
    SYNTAX       DisplayString
    MAX-ACCESS   read-only
    STATUS       current
    DESCRIPTION
        "Base MAC address of a range of addresses"

    ::= { cyanNodeMibObjects 3 }

cyanNodeBay OBJECT-TYPE
    SYNTAX       DisplayString (SIZE(0..16))
    MAX-ACCESS   read-only
    STATUS       current
    DESCRIPTION
        "Bay Number"

    ::= { cyanNodeMibObjects 4 }

cyanNodeCity OBJECT-TYPE
    SYNTAX       DisplayString (SIZE(0..32))
    MAX-ACCESS   read-only
    STATUS       current
    DESCRIPTION
        "City"

    ::= { cyanNodeMibObjects 5 }

cyanNodeCountry OBJECT-TYPE
    SYNTAX       DisplayString (SIZE(0..32))
    MAX-ACCESS   read-only
    STATUS       current
    DESCRIPTION
        "Country"

    ::= { cyanNodeMibObjects 6 }

cyanNodeCurrentTimeZone OBJECT-TYPE
    SYNTAX       CyanTimezoneTc
    MAX-ACCESS   read-only
    STATUS       current
    DESCRIPTION
        "Time zone identifier"

    ::= { cyanNodeMibObjects 7 }

cyanNodeDescription OBJECT-TYPE
    SYNTAX       DisplayString (SIZE(0..255))
    MAX-ACCESS   read-only
    STATUS       current
    DESCRIPTION
        "Description"

    ::= { cyanNodeMibObjects 8 }

cyanNodeDhcpOnConsolePort OBJECT-TYPE
    SYNTAX       CyanEnDisabledTc
    MAX-ACCESS   read-only
    STATUS       current
    DESCRIPTION
        "Enable/disable DHCP service on craft port"

    ::= { cyanNodeMibObjects 9 }

cyanNodeIdentifier OBJECT-TYPE
    SYNTAX       DisplayString
    MAX-ACCESS   read-only
    STATUS       current
    DESCRIPTION
        "string OID"

    ::= { cyanNodeMibObjects 10 }

cyanNodeLatitude OBJECT-TYPE
    SYNTAX       Integer32 -- real32 * 1000
    MAX-ACCESS   read-only
    STATUS       current
    DESCRIPTION
        "Latitude"

    ::= { cyanNodeMibObjects 11 }

cyanNodeLongitude OBJECT-TYPE
    SYNTAX       Integer32 -- real32 * 1000
    MAX-ACCESS   read-only
    STATUS       current
    DESCRIPTION
        "Longitude"

    ::= { cyanNodeMibObjects 12 }

cyanNodeMacBlockSize OBJECT-TYPE
    SYNTAX       Unsigned32 (0..255)
    MAX-ACCESS   read-only
    STATUS       current
    DESCRIPTION
        "Number of MAC addresses allocated from the base MAC address"

    ::= { cyanNodeMibObjects 13 }

cyanNodeMfgCleiCode OBJECT-TYPE
    SYNTAX       DisplayString (SIZE(0..10))
    MAX-ACCESS   read-only
    STATUS       current
    DESCRIPTION
        "Common Language Equipment Identifier"

    ::= { cyanNodeMibObjects 14 }

cyanNodeMfgEciCode OBJECT-TYPE
    SYNTAX       DisplayString (SIZE(0..6))
    MAX-ACCESS   read-only
    STATUS       current
    DESCRIPTION
        "Equipment Catalog Item"

    ::= { cyanNodeMibObjects 15 }

cyanNodeMfgModuleId OBJECT-TYPE
    SYNTAX       Unsigned32
    MAX-ACCESS   read-only
    STATUS       current
    DESCRIPTION
        "Module ID"

    ::= { cyanNodeMibObjects 16 }

cyanNodeMfgPartNumber OBJECT-TYPE
    SYNTAX       DisplayString (SIZE(0..16))
    MAX-ACCESS   read-only
    STATUS       current
    DESCRIPTION
        "Manufacturing part number"

    ::= { cyanNodeMibObjects 17 }

cyanNodeMfgRevision OBJECT-TYPE
    SYNTAX       DisplayString (SIZE(0..4))
    MAX-ACCESS   read-only
    STATUS       current
    DESCRIPTION
        "Mfg revision number"

    ::= { cyanNodeMibObjects 18 }

cyanNodeMfgSerialNumber OBJECT-TYPE
    SYNTAX       DisplayString (SIZE(0..16))
    MAX-ACCESS   read-only
    STATUS       current
    DESCRIPTION
        "Mfg serial number"

    ::= { cyanNodeMibObjects 19 }

cyanNodeName OBJECT-TYPE
    SYNTAX       DisplayString
    MAX-ACCESS   read-only
    STATUS       current
    DESCRIPTION
        "Cyan name"

    ::= { cyanNodeMibObjects 20 }

cyanNodeNationalization OBJECT-TYPE
    SYNTAX       CyanNationalizationTc
    MAX-ACCESS   read-only
    STATUS       current
    DESCRIPTION
        "Nationalization"

    ::= { cyanNodeMibObjects 21 }

cyanNodeNodeId OBJECT-TYPE
    SYNTAX       Unsigned32
    MAX-ACCESS   read-only
    STATUS       current
    DESCRIPTION
        "Node id"

    ::= { cyanNodeMibObjects 22 }

cyanNodeOidClass OBJECT-TYPE
    SYNTAX       DisplayString
    MAX-ACCESS   read-only
    STATUS       current
    DESCRIPTION
        "OID Class"

    ::= { cyanNodeMibObjects 23 }

cyanNodeOperState OBJECT-TYPE
    SYNTAX       CyanOpStateTc
    MAX-ACCESS   read-only
    STATUS       current
    DESCRIPTION
        "Primary Operation State"

    ::= { cyanNodeMibObjects 24 }

cyanNodeOperStateQual OBJECT-TYPE
    SYNTAX       CyanOpStateQualTc
    MAX-ACCESS   read-only
    STATUS       current
    DESCRIPTION
        "Operation state qualifier"

    ::= { cyanNodeMibObjects 25 }

cyanNodeOssLabel OBJECT-TYPE
    SYNTAX       DisplayString (SIZE(0..80))
    MAX-ACCESS   read-only
    STATUS       current
    DESCRIPTION
        "Node name"

    ::= { cyanNodeMibObjects 26 }

cyanNodeOwner OBJECT-TYPE
    SYNTAX       DisplayString (SIZE(0..80))
    MAX-ACCESS   read-only
    STATUS       current
    DESCRIPTION
        "Owner"

    ::= { cyanNodeMibObjects 27 }

cyanNodePartNumber OBJECT-TYPE
    SYNTAX       DisplayString (SIZE(0..11))
    MAX-ACCESS   read-only
    STATUS       current
    DESCRIPTION
        "Cyan part number"

    ::= { cyanNodeMibObjects 28 }

cyanNodePostalCode OBJECT-TYPE
    SYNTAX       DisplayString (SIZE(0..32))
    MAX-ACCESS   read-only
    STATUS       current
    DESCRIPTION
        "Postal code"

    ::= { cyanNodeMibObjects 29 }

cyanNodeRackUnits OBJECT-TYPE
    SYNTAX       DisplayString (SIZE(0..16))
    MAX-ACCESS   read-only
    STATUS       current
    DESCRIPTION
        "Rack Units"

    ::= { cyanNodeMibObjects 30 }

cyanNodeRegion OBJECT-TYPE
    SYNTAX       DisplayString (SIZE(0..32))
    MAX-ACCESS   read-only
    STATUS       current
    DESCRIPTION
        "Region or State"

    ::= { cyanNodeMibObjects 31 }

cyanNodeRelayRack OBJECT-TYPE
    SYNTAX       DisplayString (SIZE(0..16))
    MAX-ACCESS   read-only
    STATUS       current
    DESCRIPTION
        "Relay Rack Number"

    ::= { cyanNodeMibObjects 32 }

cyanNodeSecServState OBJECT-TYPE
    SYNTAX       CyanSecServiceStateTc
    MAX-ACCESS   read-only
    STATUS       current
    DESCRIPTION
        "Secondary service state"

    ::= { cyanNodeMibObjects 33 }

cyanNodeStreet OBJECT-TYPE
    SYNTAX       DisplayString (SIZE(0..32))
    MAX-ACCESS   read-only
    STATUS       current
    DESCRIPTION
        "Street"

    ::= { cyanNodeMibObjects 34 }

cyanNodeType OBJECT-TYPE
    SYNTAX       CyanTypeTc
    MAX-ACCESS   read-only
    STATUS       current
    DESCRIPTION
        "Equipment type"

    ::= { cyanNodeMibObjects 35 }

cyanNodeObjectGroup OBJECT-GROUP
    OBJECTS {
        cyanNodeAdminState,
        cyanNodeAssetTag,
        cyanNodeBaseMacAddress,
        cyanNodeBay,
        cyanNodeCity,
        cyanNodeCountry,
        cyanNodeCurrentTimeZone,
        cyanNodeDescription,
        cyanNodeDhcpOnConsolePort,
        cyanNodeIdentifier,
        cyanNodeLatitude,
        cyanNodeLongitude,
        cyanNodeMacBlockSize,
        cyanNodeMfgCleiCode,
        cyanNodeMfgEciCode,
        cyanNodeMfgModuleId,
        cyanNodeMfgPartNumber,
        cyanNodeMfgRevision,
        cyanNodeMfgSerialNumber,
        cyanNodeName,
        cyanNodeNationalization,
        cyanNodeNodeId,
        cyanNodeOidClass,
        cyanNodeOperState,
        cyanNodeOperStateQual,
        cyanNodeOssLabel,
        cyanNodeOwner,
        cyanNodePartNumber,
        cyanNodePostalCode,
        cyanNodeRackUnits,
        cyanNodeRegion,
        cyanNodeRelayRack,
        cyanNodeSecServState,
        cyanNodeStreet,
        cyanNodeType
    }

    STATUS current
    DESCRIPTION        "Group of objects that comes with Node module"
    ::= {cyanNodeModule 20}

cyanNodeCompliance MODULE-COMPLIANCE
    STATUS current
    DESCRIPTION
        "The basic info needed to be a cyan Node"
    MODULE
    MANDATORY-GROUPS {
        cyanNodeObjectGroup
    }
    ::= { cyanNodeModule 30 }


END
